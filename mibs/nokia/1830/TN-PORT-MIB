TN-PORT-MIB DEFINITIONS ::= BEGIN

-- (c) Copyright 2023 Nokia Networks.  All rights reserved.
-- This software is the confidential and proprietary property of
-- Nokia and may only be used in accordance with the terms of the
-- license agreement provided with this software.

IMPORTS
        MODULE-IDENTITY, OBJECT-TYPE,
        Unsigned32,
        Counter32, Counter64,
        Integer32
                                                FROM SNMPv2-SMI

        TEXTUAL-CONVENTION, DateAndTime,
        RowStatus, TimeStamp,
        TruthValue, MacAddress, RowPointer

                                                FROM SNMPv2-TC
        TmnxActionType, TmnxPortID,
        TNamedItemOrEmpty,
        TNamedItem,
        TItemLongDescription,
        TmnxEnabledDisabled
                                                FROM TN-TC-MIB

        tnSRMIBModules,
        tnSRNotifyPrefix,
        tnSRObjs                                FROM TROPIC-GLOBAL-REG
        tnSysSwitchId                           FROM TROPIC-SYSTEM-MIB
        ;

tnPortMIBModule MODULE-IDENTITY
        LAST-UPDATED    "202005010000Z"
        ORGANIZATION    "Nokia"
        CONTACT-INFO
            "Nokia 7x50 Support
             Web: http://www.nokia.com/comps/pages/carrier_support.jhtml"
        DESCRIPTION
        "This document is the SNMP MIB module to manage and provision the
        hardware components of the Nokia 7x50 device.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."

--
--  Revision History

        REVISION        "202005010000Z"
        DESCRIPTION     "1) Added the following to TmnxPortClass:
                            cpri4(24)       -- cpri4
                         2) Updated the comments of tnPortEtherSpeed:
                            speed3072 (14),  -- CPRI4/OBSAI4."

        REVISION        "202001100000Z"
        DESCRIPTION     "Added the following to tnPortTable:
                         tnPortOtnSignalDegrade."

        REVISION        "201911150000Z"
        DESCRIPTION     "Added the following to tnPortEtherSpeed:
                         speed25000 (15)  -- 25G."

        REVISION        "201910250000Z"
        DESCRIPTION     "Updated DESCRIPTION of TmnxPortClass:
                         tfgige (15)     -- xxvgig."

        REVISION        "201906070000Z"
        DESCRIPTION     "Added the following tables:
                         tnEMACTable
                         tnPMACTable
                         tnMMACTable."

        REVISION        "201903080000Z"
        DESCRIPTION     "1) Added the following to TmnxPortClass:
                            tfgige (15),     -- Twenty-five Giga Ethernet
                            to
                            obsai4(23)       -- obsai4
                         2) Added the following in tnPortEtherSpeed:
                            speed2457 (8)  -- CPRI3
                            to
                            speed3072 (14) -- OBSAI4."

        REVISION        "201903010000Z"
        DESCRIPTION     "Changed range of tnPortLagId from
                         INTEGER (1..200)
                         to
                         INTEGER (1..240)."

        REVISION        "201902150000Z"
        DESCRIPTION     "1) Changed the SYNTAX of tnPortEtherEgressRate from
                            Integer32 (-1 | 1..10000000) to Integer32 (-1 | 1..100000000).
                         2) Changed the SYNTAX of tnPortEtherOperEgressRate  from
                            Integer32 (-1 | 1..10000000) to Integer32 (-1 | 1..100000000)."

        REVISION        "201901250000Z"
        DESCRIPTION     "1) Added the following to tnPortTransceiverType:
                            dwdmSfpTransceiver(11),
                            to
                            sfpDd2xTransceiver(26),
                            tsopSmartSfpTransceiver(130).
                         2) Added the following to tnPortSFPConnectorCode:
                            mpo1x12(12),
                            mpo2x16(13),
                            rj45(34),
                            to
                            miniCsOptical(38)."

        REVISION        "201812280000Z"
        DESCRIPTION     "Added the following to tnPortEtherTable:
                         tnPortEtherOperEgressRate."

        REVISION        "201812140000Z"
        DESCRIPTION     "Added the following to TmnxPortClass:
                         vsme(14)        -- VSM Ethernet."

        REVISION        "201801050000Z"
        DESCRIPTION     "1) Added the following to TmnxPortClass:
                            oduflex(13)     -- oduflex.
                         2) Added the following to tnPortEtherSpeed:
                            oduflex (7)."

        REVISION        "201708020000Z"
        DESCRIPTION     "1) Changed the SYNTAX of tnPortEtherEgressRate from
                            Integer32 (-1 | 1..10000000) to Integer32 (-1 | 1..100000000).
                         2) Changed the SYNTAX of tnPortEtherIngressRate  from
                            Integer32 (-1 | 1..10000) to Integer32 (-1 | 1..100000).
                         3) Commented out the following textual conventions:
                            TmnxPortEtherReportValue
                            TmnxDs0ChannelList
                            TmnxBundleID
                            TmnxDSXBertPattern
                            TmnxDSXBertOperStatus
                            TmnxDSXIdleCycleFlags
                            TmnxDSXIdleFillType
                            TmnxDSXReportAlarm
                            TmnxDSXClockSource
                            TmnxDSXClockSyncState
                            TmnxDS1Loopback
                            TmnxDS3Loopback
                            TmnxImaGrpState
                            TmnxImaGrpFailState
                            TmnxImaLnkState
                            TmnxImaLnkFailState
                            TmnxImaTestState
                            TmnxImaGrpClockModes
                            TmnxImaGrpVersion
                            TmnxMcMlpppClassIndex
                            TmnxMlpppEndpointIdClass
                            TmnxMlfrLinkDownReason.
                         4) Fixed MIB compile issues."

        REVISION        "201705310000Z"
        DESCRIPTION     "1) Added the following to tnPortEtherSpeed:
                            speed100000 (6).
                         2) Added the following to tnPortEtherTable:
                            tnPortEtherQinqEtypelink."

        REVISION        "201703100000Z"
        DESCRIPTION     "Added the following to TmnxPortClass:
                         cgige(11), -- 100G Ethernet
                         xcmbar(12)  -- 10/100/1000/10000 Ethernet."

        REVISION        "201610190000Z"
        DESCRIPTION     "1) Added the following to tnPortTable:
                            tnPortPacketSwitchId
                         2) Added a new table tnPacketSwitchPortTable."

        REVISION        "201509020000Z"
        DESCRIPTION     "Changed the range of tnPortEtherMTU:
                          From (0|512..9212) to (0|512..9612)."

        REVISION        "201501220000Z"
        DESCRIPTION     "Updated range of the following in tnPortTable:
                         tnPortHoldTimeUp
                         tnPortHoldTimeDown."

        REVISION        "201308220000Z"
        DESCRIPTION     "1) Added the following to tnPortTable:
                            tnPortHoldTimeUnits
                            tnPortLinkLengthInfo
                            tnPortSFPNumLanes
                            tnPortPhysStateChangeCount.
                         2) Added to DESCRITPIONs of tnPortHoldTimeUp
                            and tnPortHoldTimeDown with reference to
                            tnPortHoldTimeUnits."

        REVISION        "201212050000Z"
        DESCRIPTION     "Commented out unsupported MIB tables and
                         attributes for 1830."

        REVISION        "201211060000Z"
        DESCRIPTION     "1) Added the following to TmnxPortEtherReportValue
                            and TmnxPortEtherReportStatus:
                            noBlockLock  (6),
                            noAmLock     (7),
                            duplicateLane(8).
                         2) Deleted the following from tnPortReasonDownFlags:
                            reserved1 (2),
                            reserved2 (3),
                            reserved3 (4),
                            noServicePort (5).
                         3) Added the following to tnPortReasonDownFlags and
                            updated its DESCRIPTION:
                            lagMemberPortStandby (2),
                            ethCfmFault          (3),
                            opticalTuning        (4),
                            channelOutOfRange    (5),
                            channelNotConfigured (6),
                            crcError             (7),
                            internalMacTxError   (8),
                            noServicePort        (9)."

        REVISION        "201210120000Z"
        DESCRIPTION     "Added the following to IMPORTS for TROPIC-GLOBAL-REG:
                         tnSRNotifyPrefix
                         tnSRObjs."

        REVISION        "200902280000Z"
        DESCRIPTION     "Rev 7.0                28 Feb 2009 00:00
                         7.0 release of the TIMETRA-PORT-MIB."

        REVISION        "200807010000Z"
        DESCRIPTION     "Rev 6.1                01 Jul 2008 00:00
                         6.1 release of the TIMETRA-PORT-MIB."

        REVISION        "200801010000Z"
        DESCRIPTION     "Rev 6.0                01 Jan 2008 00:00
                         6.0 release of the TIMETRA-PORT-MIB."

        REVISION        "200701010000Z"
        DESCRIPTION     "Rev 5.0                01 Jan 2007 00:00
                         5.0 release of the TIMETRA-PORT-MIB."

        REVISION        "200603160000Z"
        DESCRIPTION     "Rev 4.0                16 Mar 2006 00:00
                         4.0 release of the TIMETRA-PORT-MIB."

        REVISION        "200508310000Z"
        DESCRIPTION     "Rev 3.0                31 Aug 2005 00:00
                         3.0 release of the TIMETRA-PORT-MIB."

        REVISION        "200501240000Z"
        DESCRIPTION     "Rev 2.1                24 Jan 2005 00:00
                         2.1 release of the TIMETRA-PORT-MIB."

        REVISION        "200403010000Z"
        DESCRIPTION     "Rev 2.0                01 Mar 2004 00:00
                         2.0 release of the TIMETRA-PORT-MIB."

        ::= { tnSRMIBModules 25 }

-- The following two definitions were added from TN-CHASSIS-MIB to avoid
-- pulling that MIB into PSS.
tnHwObjs                      OBJECT IDENTIFIER ::= { tnSRObjs 2 }
tnHwNotification              OBJECT IDENTIFIER ::= { tnSRNotifyPrefix 2 }

tnPortObjs                    OBJECT IDENTIFIER ::= { tnHwObjs 4 }
-- tnPortNotificationObjects     OBJECT IDENTIFIER ::= { tnHwObjs 7 }
-- tnFRObjs                      OBJECT IDENTIFIER ::= { tnHwObjs 9 }
tnQosAppObjs                  OBJECT IDENTIFIER ::= { tnHwObjs 10 }
-- tnATMObjs                     OBJECT IDENTIFIER ::= { tnHwObjs 11 }
-- tnPortStatsObjs               OBJECT IDENTIFIER ::= { tnHwObjs 12 }

tnPortNotifyPrefix OBJECT IDENTIFIER ::= { tnHwNotification 2 }
  tnPortNotification OBJECT IDENTIFIER ::= { tnPortNotifyPrefix 0 }

-- tnPortConformance     OBJECT IDENTIFIER ::= { tnHwConformance 2 }


--%%%%%%%%%%%%%%%%%%%%%%%%%%%%%%%%%%%%%%%%%%%%%%%%%%%%%%%%%%%%%%%%%%%%%
--
--      TIMETRA-PORT-MIB textual conventions
--

--
--      TmnxPortOperStatus
--
TmnxPortOperStatus ::= TEXTUAL-CONVENTION
    STATUS  current
    DESCRIPTION
        "The current operational status of this port."
    SYNTAX  INTEGER {
                unknown (1),
                inService (2),
                outOfService (3),
                diagnosing (4),
                failed (5)
            }

--
--      TmnxPortEtherReportValue
--
-- TmnxPortEtherReportValue ::= TEXTUAL-CONVENTION
--     STATUS  current
--     DESCRIPTION
--         "The TmnxPortEtherReportValue is an enumerated integer that describes
--         the values used to identify the reason an alarm has been raised on an
--         Ethernet Port."
--     SYNTAX  INTEGER {
--                 notUsed      (0),  - not applicable
--                 signalFailure(1),  - Ethernet signal lost alarm
--                 remoteFault  (2),  - Remote Fault
--                 localFault   (3),  - Local Fault
--                 noFrameLock  (4),  - Not locked on the Ethernet framing sequence
--                 highBer      (5),  - High Bit Error Rate
--                 noBlockLock  (6),  - 40G/100G PCS Lanes Not Block Locked
--                 noAmLock     (7),  - 40G/100G PCS Alignment Marker Loss of Lock
--                 duplicateLane(8)   - 40G/100G PCS Duplicate Lane Marker
--             }

--
--      TmnxPortEtherReportStatus
--
TmnxPortEtherReportStatus ::= TEXTUAL-CONVENTION
    STATUS  current
    DESCRIPTION
        "The TmnxPortEtherReportStatus is a bitmask that describes alarms that
        can be raised/cleared on an Ethernet Port."
    SYNTAX  BITS {
                notUsed      (0),  -- not applicable
                signalFailure(1),  -- Ethernet signal lost alarm
                remoteFault  (2),  -- Remote Fault
                localFault   (3),  -- Local Fault
                noFrameLock  (4),  -- Not locked on the Ethernet framing sequence
                highBer      (5),  -- High Bit Error Rate
                noBlockLock  (6),  -- 40G/100G PCS Lanes Not Block Locked
                noAmLock     (7),  -- 40G/100G PCS Alignment Marker Loss of Lock
                duplicateLane(8)   -- 40G/100G PCS Duplicate Lane Marker
            }

--
--      TmnxPortClass
--
TmnxPortClass ::= TEXTUAL-CONVENTION
    STATUS  current
    DESCRIPTION
        "The TmnxPortClass data type is an enumerated integer that
         describes the values used to identify the class of interface
         provided by this port."
    SYNTAX  INTEGER {
                none  (1),      -- no port installed
                faste (2),      -- Fast Ethernet (10/100MBS)
                gige  (3),      -- Gigabit Ethernet
                xgige (4),      -- Ten-Gigabit Ethernet
                sonet (5),      -- SONET
                vport (6),      -- Virtual port
                unused(7),      -- Unused
                xcme  (8),      -- 10/100/1000 Ethernet
                tdm   (9),      -- TDM
                xlgige(10),     -- Forty-Gigabit Ethernet
                cgige(11),      -- 100G Ethernet
                xcmbar(12),     -- 10/100/1000/10000 Ethernet
                oduflex(13),    -- oduflex
                vsme(14),       -- VSM Ethernet
                tfgige (15),    -- xxvgig
                cpri3(16),      -- cpri3
                cpri5(17),      -- cpri5
                cpri6(18),      -- cpri6
                cpri7(19),      -- cpri7
                cpri8(20),      -- cpri8
                cpri10(21),     -- cpri10
                obsai8(22),     -- obsai8
                obsai4(23),     -- obsai4
                cpri4(24)       -- cpri4
            }

--
--      TmnxPortConnectorType
--
TmnxPortConnectorType ::= TEXTUAL-CONVENTION
    STATUS  current
    DESCRIPTION
        "The TmnxPortConnectorType data type is an enumerated integer that
         describes the values used to identify the connector type used on
         a port.  A TmnxPortConnectorType value specifies the index value
         for the entry in the tnPortConnectTypeTable used to identify a
         specific type of port connector.  Some example port connector types
         are: 'unknown', 'rj45', 'bncCoax', 'mtrj', 'scDuplex', 'sffp',
         'lcDuplex'."
    SYNTAX  Unsigned32

--
--      TmnxPortState
--
TmnxPortState ::= TEXTUAL-CONVENTION
    STATUS  current
    DESCRIPTION
        "The state level of this port.  A value of 'none' indicates the
         port is either in its initial creation state or is just about to
         be deleted.  A value of 'ghost' represents a port that is not
         physically present.  This state may represent a pre-provisioned
         port.  A value of 'linkDown' represents a port that is physically
         present but does not have a link.  The 'linkUp' state represents a
         port that is physically present and has physical link present.
         A port in 'up' state is ready to pass some kinds of traffic.
         The tnPortUpProtocols variable indicates the actual type(s) of
         traffic that can be passed on this 'up' link. The 'diagnose' state
         represents the port undergoing diagnostic test."
    SYNTAX  INTEGER {
                none (1),
                ghost (2),
                linkDown (3),
                linkUp (4),
                up (5),
                diagnose (6)
            }

--
--      TmnxPortType
--
TmnxPortType ::= TEXTUAL-CONVENTION
    STATUS      current
    DESCRIPTION
        "The TmnxPortType data type is an enumerated integer that describes
         the values used to identify the specific type of hardware port.
         A TmnxPortType value specifies the index value for the entry in the
         tnPortTypeTable used to identify a specific type of port.
         Some example port types are:
            -- unknown            - no port installed or unidentified
            -- portType100Tx      - 10/100 base copper
            -- portType100F       - 10/100 base fiber
            -- portType1000Tx     - 1000 base copper
            -- portType1000F      - 1000 base fiber
            -- portType1000dF     - 1000 base dual fiber
            -- portTypeOC3sonet   - OC-3
            -- portTypeOC12sonet  - OC-12
            -- portTypeOC48sonet  - OC-48
            -- portTypeOC192sonet - OC-192
            -- portType10000F     - 10 Gig Ethernet LAN
            -- portTypeXgigWan    - 10 Gig Ethernet WAN
            -- portTypeVport      - Virtual port
            -- portTypeDS3E3      - DS3/E3 port
            -- portTypeDS1E1      - DS1/E1 port
         "
    SYNTAX  Unsigned32

--
--      TmnxDs0ChannelList
--
-- TmnxDs0ChannelList ::= TEXTUAL-CONVENTION
--     STATUS       current
--     DESCRIPTION
--             "A list of ds0 timeslots on a DS1 line.
--
--             The list is specified as an OCTET STRING in which each ds0
--             timeslot is represented by a single bit, where  timeslots 1
--             through 8 are represented by the bits in the first octet,
--             timeslots 9 through 16 by the bits in the second octet,
--             etc.  In each octet, the lowest numbered timeslot is
--             represented by the most significant bit, and the highest
--             numbered timeslot by the least significant bit.  A timeslot
--             is present in the list when its bit is 1, and absent
--             when its bit is 0.
--
--             If the OCTET STRING value has more bits than required to
--             represent the timeslots on a DS1, then the extra bits
--             are ignored."
--     SYNTAX       OCTET STRING (SIZE(0..4))

--
--      TmnxBundleID
--
-- TmnxBundleID ::= TEXTUAL-CONVENTION
--     STATUS  current
--     DESCRIPTION
--         "A TmnxBundleID is an unique 32 bit number encoded as shown below.
--
--             |32 30| 29 26 | 25 22 | 21 16 | 15     13 | 12   1|
--             +=====+=======+=======+=======+===========+=======+
--             |001  |  slot |  mda  |   0   | bndl type | bndlid|
--             +=====+=======+=======+=======+===========+=======+
--
--          The bundle id is unique for a MDA.  The bndlid must fall in one of
--          the following ranges depending on MDA type:
--
--            mda-type             range
--            m4-choc3-as-sfp      1-256
--            m1-choc12-as-sfp     1-256
--            m12-chds3-as         1-256
--            m4-chds3-as          1-112
--            m4-chds3             1-56
--            m12-chds3            1-56
--            m1-choc12-sfp        1-56
--            m4-choc3-sfp         1-56
--            c8-chds1             1-56
--            c8-atmds1            1-8
--
--          A slot value of 15 (Invalid slot) and mda value of 0 (invalid mda)
--          represents a bundle protection group.
--          Otherwise, the bundle is considered associated with a valid slot
--          and mda.
--
--          The following bundle types are supported:
--
--          bndl type     value
--            MLPPP        000
--            IMA          001
--            MLFR         010"
--     SYNTAX  Unsigned32

--
--      TmnxDSXBertPattern
--
-- TmnxDSXBertPattern ::= TEXTUAL-CONVENTION
--     STATUS  current
--     DESCRIPTION
--         "The TmnxDSXBertPattern data type is an enumerated integer that
--          indicates the pattern used for the Bit Error Rate Test (BERT)."
--     SYNTAX  INTEGER {
--                 none        (0),
--                 ones        (1),
--                 zeros       (2),
--                 alternating (3),
--                 twoexp3     (4),
--                 twoexp9     (5),
--                 twoexp15    (6),
--                 twoexp20    (7),
--                 twoexp11    (8),
--                 twoexp20q   (9),
--                 twoexp23   (10)
--             }

--
--      TmnxDSXBertOperStatus
--
-- TmnxDSXBertOperStatus ::= TEXTUAL-CONVENTION
--     STATUS  current
--     DESCRIPTION
--         "The TmnxDSXBertOperStatus data type is an enumerated integer that
--          indicates the status of Bit Error Rate Test (BERT).
--          When BERT is activated, the status will be 'active'. Otherwise
--          the status will be 'idle' or 'noMdaResources' if the last BERT test
--          could not be executed because of an MDA concurrent BERT test limit."
--     SYNTAX  INTEGER {
--                 none (0),
--                 active (1),
--                 idle (2),
--                 noMdaResources (3)
--             }

--
--      TmnxDSXIdleCycleFlags
--
-- TmnxDSXIdleCycleFlags ::= TEXTUAL-CONVENTION
--     STATUS  current
--     DESCRIPTION
--         "The TmnxDSXIdleCycleFlags data type is an enumerated integer that
--          indicates the value that the DS3/DS1 port/channel or a DS0 channel
--          group transmits during idle cycle.
--
--          The value of 'none' is applicable to ATM and CEM ports/channels only,
--          which transmits idle cells and not octets defined by the below values.
--
--          If the value is set to 'flags', a value of 0x7E is used.
--          If the value is set to 'ones', a value of 0xFF is used."
--     SYNTAX  INTEGER {
--                 none  (0),
--                 flags (1),
--                 ones (2)
--             }

--
--      TmnxDSXIdleFillType
--
-- TmnxDSXIdleFillType ::= TEXTUAL-CONVENTION
--     STATUS  current
--     DESCRIPTION
--         "The TmnxDSXIdleFillType data type is an enumerated integer that
--          indicates the type of data fill that a CEM DS3/DS1 channel or a DS0
--          channel group plays out when the channel experiences underun.
--
--          - The value of 'notApplicable' indicates that this object is not
--            applicable to the channel.
--          - The value of 'allOnes' indicates that all 1's will be played out.
--          - The value of 'userDefinedPattern' indicates that a user defined
--            pattern will be played out."
--     SYNTAX  INTEGER {
--                 notApplicable (0),
--                 allOnes (1),
--                 userDefinedPattern (2)
--             }

--
--      TmnxDSXLoopback
--
-- TmnxDSXLoopback ::= TEXTUAL-CONVENTION
--     STATUS  obsolete
--     DESCRIPTION
--         "The TmnxDSXLoopback data type is an enumerated integer that
--          indicates the type of loopback the DS3/DS1 port/channel
--          currently is in."
--     SYNTAX  INTEGER {
--                 none (0),
--                 line (1),
--                 internal (2),
--                 remote (3)
--             }

--
--      TmnxDSXReportAlarm
--
-- TmnxDSXReportAlarm ::= TEXTUAL-CONVENTION
--     STATUS      current
--     DESCRIPTION
--         "The TmnxDSXReportAlarm data type indicates the type of TDM alarm:
--          ais - alarm indication signal errors.
--          los - loss of signal errors.
--          oof - out-of-frame errors.
--          rai - resource availability indicator events.
--          looped - far end wants the read end to loopback
--          berSd - DSX bit error signal degradation
--          berSf - DSX bit error signal failure"
--     SYNTAX      BITS {
--                     notUsed (0),
--                     ais (1),
--                     los (2),
--                     oof (3),
--                     rai (4),
--                     looped (5),
--                     berSd (6),
--                     berSf (7)
--                 }

--
--      TmnxDSXClockSource
--
-- TmnxDSXClockSource ::= TEXTUAL-CONVENTION
--     STATUS      current
--     DESCRIPTION
--         "The TmnxDSXClockSource data type is an enumerated type
--          that indicates the clock for transmitted data on a DS3 or DS1 channel.
--          loopTimed(1)     - The clock is recovered from the line's receive
--                             data stream
--          nodeTimed(2)     - The clock is internal
--          adaptive(3)      - The clock is adaptively recovered from the rate at
--                             which data is received and not from the physical
--                             layer.
--          differential(4)  - The clock is recovered from differential RTP
--                             timestamp header."
--     SYNTAX      INTEGER {
--                     loopTimed    (1),
--                     nodeTimed    (2),
--                     adaptive     (3),
--                     differential (4)
--                 }

--
--      TmnxDSXClockSyncState
--
-- TmnxDSXClockSyncState ::= TEXTUAL-CONVENTION
--     STATUS      current
--     DESCRIPTION
--         "The TmnxDSXClockSyncState data type is an enumeration type that
--          indicates the clock synchronization state on a DS3 or DS1 channel.
--          unknown(0)       - Unsupported or unknown state
--          normal(1)        - Normal (locked) state
--          holdOver(2)      - Synchronization with reference has been lost
--          freeRun(3)       - Synchronized with internal reference"
--     SYNTAX      INTEGER {
--                     unknown  (0),
--                     normal   (1),
--                     holdOver (2),
--                     freeRun  (3),
--                     phaseTracking (4),
--                     freqTracking  (5)
--                 }

--
--      TmnxDS1Loopback
--
-- TmnxDS1Loopback ::= TEXTUAL-CONVENTION
--     STATUS  current
--     DESCRIPTION
--         "The TmnxDS1Loopback data type is an enumerated integer that
--          indicates the type of loopback the DS1 port/channel
--          currently is in.
--          A 'line' loopback loops frames received on this port back to the
--          remote system.
--          A 'internal' loopback loops frames from the local system back at
--          the framer.
--          A 'fdlAnsi' requests a line loopback of type FDL ANSI T1.403.
--          A 'fdlBellcore' requests a line loopback of type FDL Bellcore
--          TR-TSY-000312.
--          A 'payloadAnsi' requests a payload loopback of type FDL ANSI T1.403.
--          A 'inbandAnsi' requests a line loopback of type inband ANSI T1.403.
--          A 'inbandBellcore' requests a line loopback of type inband Bellcore
--          TR-TSY-000312."
--     SYNTAX  INTEGER {
--                 none (0),
--                 line (1),
--                 internal (2),
--                 fdlAnsi (3),
--                 fdlBellcore (4),
--                 payloadAnsi (5),
--                 inbandAnsi  (6),
--                 inbandBellcore (7)
--             }

--
--      TmnxDS3Loopback
--
-- TmnxDS3Loopback ::= TEXTUAL-CONVENTION
--     STATUS  current
--     DESCRIPTION
--         "The TmnxDS3Loopback data type is an enumerated integer that
--          indicates the type of loopback the DS3 port/channel
--          currently is in.
--          A 'line' loopback loops frames received on this port back to the
--          remote system.
--          A 'internal' loopback loops the frames from the local system back at
--          the framer.
--          When the value is set to 'remote', a signal is sent to the remote
--          system to provide a line loopback."
--     SYNTAX  INTEGER {
--                 none (0),
--                 line (1),
--                 internal (2),
--                 remote (3)
--             }

--
--      TmnxImaGrpState
--
-- TmnxImaGrpState ::= TEXTUAL-CONVENTION
--     STATUS      current
--     DESCRIPTION
--         "The TmnxImaGrpState indicates the current state
--          of the IMA Group State Machine."
--     SYNTAX      INTEGER {
--                     invalid                          (0),
--                     notConfigured                    (1),
--                     startUp                          (2),
--                     startUpAck                       (3),
--                     configAbortUnsupportedM          (4),
--                     configAbortIncompatibleSymmetry  (5),
--                     configAbortOther                 (6),
--                     insufficientLinks                (7),
--                     blocked                          (8),
--                     operational                      (9),
--                     configAbortUnsupportedImaVersion (10)
--                 }

-- TmnxImaGrpFailState ::= TEXTUAL-CONVENTION
--     STATUS      current
--     DESCRIPTION
--         "The TmnxImaGrpFailState indcates the failure
--          reason of an IMA group."
--     SYNTAX      INTEGER {
--                     noFailure(1), - unit is up
--                     startUpNe(2),
--                     startUpFe(3),
--                     invalidMValueNe(4),
--                     invalidMValueFe(5),
--                     failedAssymetricNe(6),
--                     failedAssymetricFe(7),
--                     insufficientLinksNe(8),
--                     insufficientLinksFe(9),
--                     blockedNe(10),
--                     blockedFe(11),
--                     otherFailure(12),
--                     invalidImaVersionNe(13),
--                     invalidImaVersionFe(14)
--                 }

-- TmnxImaLnkState ::= TEXTUAL-CONVENTION
--     STATUS      current
--     DESCRIPTION
--         "The TmnxImaLnkState indicates the current
--          state of an IMA link."
--     SYNTAX      INTEGER {
--                     notInGroup(1),
--                     unusableNoGivenReason(2),
--                     unusableFault(3),
--                     unusableMisconnected(4),
--                     unusableInhibited(5),
--                     unusableFailed(6),
--                     usable(7),
--                     active(8)
--                 }

-- TmnxImaLnkFailState ::= TEXTUAL-CONVENTION
--     STATUS      current
--     DESCRIPTION
--         "The TmnxImaLnkFailState indicates the local failure
--          status of a link belonging to an IMA group."
--     SYNTAX      INTEGER {
--                     noFailure(1),
--                     imaLinkFailure(2),
--                     lifFailure(3),
--                     lodsFailure(4),
--                     misConnected(5),
--                     blocked(6),
--                     fault(7),
--                     farEndTxLinkUnusable(8),
--                     farEndRxLinkUnusable(9)
--                 }

-- TmnxImaTestState ::= TEXTUAL-CONVENTION
--     STATUS      current
--     DESCRIPTION
--         "The TmnxImaTestState indicates the current state
--          of the test pattern procedure."
--     SYNTAX      INTEGER {
--                     disabled(1),
--                     operating(2),
--                     failed(3)
--                 }

-- TmnxImaGrpClockModes ::= TEXTUAL-CONVENTION
--     STATUS      current
--     DESCRIPTION
--         "The TmnxImaGrpClockModes lists the types of
--          clock modes available to IMA Groups."
--     SYNTAX      INTEGER {
--                     ctc(1),
--                     itc(2)
--                 }

-- TmnxImaGrpVersion ::= TEXTUAL-CONVENTION
--     STATUS      current
--     DESCRIPTION
--         "The TmnxImaGrpVersion lists the types of
--          Ima versions available per IMA Groups."
--     SYNTAX      INTEGER {
--                     oneDotZero(1),
--                     oneDotOne(2)
--                 }

-- TmnxMcMlpppClassIndex ::= TEXTUAL-CONVENTION
--     STATUS      current
--     DESCRIPTION
--         "The TmnxMcMlpppClassIndex indicates the class
--          of a Multiclass MLPPP bundle.
--
--          For Multiclass MLPPP bundles with a non-zero
--          tnBundleMlpppClassCount of classes, class index takes
--          valid values from 0 to (tnBundleMlpppClassCount - 1)
--          inclusive. For example a 4-class MLPPP bundle has 4 classes
--          with indices 0, 1, 2, and 3."
--     SYNTAX      Integer32 (0..15)

-- TmnxMlpppEndpointIdClass ::= TEXTUAL-CONVENTION
--     STATUS  current
--     DESCRIPTION
--         "TmnxMlpppEndpointIdClass indicates the MLPPP Endpoint
--          Discriminator Class Field Type."
--     SYNTAX      INTEGER {
--                     nullClass (0),
--                     localAddress (1),
--                     ipAddress (2),
--                     ieee802dot1GlobalMacAddress (3),
--                     pppMagicNumberBlock (4),
--                     publicSwitchedNetworkDirNumber (5)
--                 }

-- TmnxMlfrLinkDownReason ::= TEXTUAL-CONVENTION
--     STATUS  current
--     DESCRIPTION
--         "TmnxMlfrLinkDownReason indicates the reason code for marking
--          a MLFR member link of a bundle to down.
--              A 'none' down reason indicates that the link is active.
--              An 'outOfService' down reason indicates that the link
--              operational status is down.
--              A 'redDiffDelayExceeded' down reason indicates that the
--              differential delay of the link exceeded the configured
--              value of red differential delay and the delay action was
--              configured as 'down'.
--              A 'loopback' down reason indicates that the link has been
--              detected to be in a loopback condition.
--              A 'negotiating' down reason indicates that the link has
--              not successfully negotiated the link into a bundle.
--              A 'noRxHelloAck' down reason indicates that the link has
--              not received a hello ack response.
--              A 'rxCause' down reason indicates that a peer failure has
--              been detected on this link.
--              A 'txCause' down reason indicates that a local failure has
--              been detected on this link.
--              A linkReset' down reason indicates that the link is being reset."
--     SYNTAX      INTEGER {
--                     none (0),
--                     outOfService (1),
--                     redDiffDelayExceeded (2),
--                     loopback (3),
--                     negotiating (4),
--                     noRxHelloAck (5),
--                     rxCause (7),
--                     txCause (8),
--                     linkReset (9)
--                 }

-- The following two definitions were added from TN-CHASSIS-MIB
--
--      TmnxAlarmState
--
TmnxAlarmState ::= TEXTUAL-CONVENTION
    STATUS      current
    DESCRIPTION
        "The TmnxAlarmState is an enumerated integer whose value indicates
         the current alarm state of a physical or logical component in the
         Nokia 7x50 SR series system."
    SYNTAX  INTEGER {
                unknown (0),
                alarmActive (1),
                alarmCleared (2)
            }

--
--      TmnxPortAdminStatus
--
TmnxPortAdminStatus ::= TEXTUAL-CONVENTION
    STATUS      current
    DESCRIPTION
        "The desired administrative status of this port."
    SYNTAX      INTEGER {
                    noop (1),
                    inService (2),
                    outOfService (3),
                    diagnose (4)
                }


--%%%%%%%%%%%%%%%%%%%%%%%%%%%%%%%%%%%%%%%%%%%%%%%%%%%%%%%%%%%%%%%%%%%%%
--
--      TIMETRA-PORT-MIB at a glance
--
--  timetra (enterprises 6527)
--    timetraProducts (3)
--      tmnxSRMIB (1)
--                tmnxSRConfs (1)
--                tmnxSRObjs (2)
--                      tmnxHwObjs (tmnxSRObjs 2)
--                tmnxSRNotifyPrefix (3)
--
--  tnPortObjs (tmnxHwObjs 4)
--        tnPortTableLastChange (1)
--        tnPortTable (2)
--        tnPortTestTable (3)
--        tnPortEtherTable (4)
--        tnSonetTable (5)
--        tnSonetPathTable (6)
--        tnPortTypeTable (7)
--        tnPortConnectTypeTable (8)
--        tnPortFCStatsTable (9)
--        tnDS3Table (10)
--        tnDS3ChannelTable (11)
--        tnDS1Table (12)
--        tnDS0ChanGroupTable (13)
--        tnBundleTable (14)
--        tnBundleMemberTable (15)
--        tnPortToChannelTable (16)
--        tnPortIngrMdaQosStatTable (17)
--        tnSonetGroupTable (18)
--        tnPortScalarObjs (19)
--        tnCiscoHDLCTable (20)
--        tnBundleImaGrpTable (21)
--        tnBundleMemberImaTable (22)
--        tnDS1PortTable (23)
--        tnPortSchedOverrideTable (24)
--        tnBPGrpAssocTable (25)
--        tnBundleMlpppTable (26)
--        tnHsmdaPortSchOvrTblLastChngd (27)
--        tnHsmdaPortSchOvrTable (28)
--        tnDigitalDiagMonitorTable (29)
--
--  tnPortNotificationObjects (7)
--        tnPortNotifyPortId (1)
--        tnPortNotifySonetAlarmReason (2)
--        tnPortNotifySonetPathAlarmReason (3)
--        tnPortNotifyError (4)
--        tnPortNotifyDS3AlarmReason (5)
--        tnPortNotifyDS1AlarmReason (6)
--        tnPortNotifyBundleId (7)
--        tnPortNotifyEtherAlarmReason (8)
--        tnDDMFailedObject (9)
--        tmnxDSXClockSyncStateObject (10)
--        tnPortNotifyDescription (11)
--
--  tnFRObjs (9)
--        tmnxFRDlcmiTable (1)
--
--  tnQosAppObjs (10)
--        tnQosPoolAppTable (2)
--
--  tnATMObjs (11)
--        tmnxATMIntfTable (1)
--
--  tnPortStatsObjs (12)
--        tnPortNetIngressStatsTable    (1)
--        tnPortNetEgressStatsTable     (2)
--        tnCiscoHDLCStatsTable         (3)
--        tnMcMlpppStatsTable           (4)
--

--%%%%%%%%%%%%%%%%%%%%%%%%%%%%%%%%%%%%%%%%%%%%%%%%%%%%%%%%%%%%%%%%%%%%%
--
--      IOM Port tables
--
tnPortTableLastChange   OBJECT-TYPE
    SYNTAX      TimeStamp
    MAX-ACCESS  read-only
    STATUS      current
    DESCRIPTION
        "The value of sysUpTime when the tnPortTable was last changed."
    ::= { tnPortObjs 1 }

tnPortTable OBJECT-TYPE
    SYNTAX      SEQUENCE OF TmnxPortEntry
    MAX-ACCESS  not-accessible
    STATUS      current
    DESCRIPTION
        "The port table has an entry for each port on each IOM card in each
         chassis in the TMNX system."
    ::= { tnPortObjs 2 }

tnPortEntry       OBJECT-TYPE
    SYNTAX      TmnxPortEntry
    MAX-ACCESS  not-accessible
    STATUS      current
    DESCRIPTION
        "Each row entry represents a port on a IOM card in a chassis in the
         system.  Entries cannot be created and deleted via SNMP SET
         operations.  Before an IOM tmnxMDAEntry can be deleted from the
         tmnxMDATable, its supported tnPortEntry rows must be in the proper
         state for removal."
    INDEX   { tnPortPortID }
    ::= { tnPortTable 1 }

TmnxPortEntry ::=
    SEQUENCE {
        tnPortPortID                    TmnxPortID,
        tnPortLastChangeTime            TimeStamp,
        tnPortType                      TmnxPortType,
        tnPortClass                     TmnxPortClass,
        tnPortDescription               TItemLongDescription,
        tnPortName                      TNamedItemOrEmpty,
        tnPortAlias                     TNamedItemOrEmpty,
        tnPortUserAssignedMac           TruthValue,
        tnPortMacAddress                MacAddress,
        tnPortHwMacAddress              MacAddress,
        tnPortMode                      INTEGER,
        tnPortEncapType                 INTEGER,
        tnPortLagId                     Unsigned32,
        tnPortHoldTimeUp                Unsigned32,
        tnPortHoldTimeDown              Unsigned32,
        tnPortUpProtocols               BITS,
        tnPortConnectorType             TmnxPortConnectorType,
        tnPortTransceiverType           INTEGER,
--        tnPortTransceiverCode           BITS,
        tnPortTransceiverLaserWaveLen   Unsigned32,
        tnPortTransceiverDiagCapable    INTEGER,
        tnPortTransceiverModelNumber    TNamedItemOrEmpty,
        tnPortSFPConnectorCode          INTEGER,
        tnPortSFPVendorOUI              Unsigned32,
        tnPortSFPVendorManufactureDate  DateAndTime,
        tnPortSFPMedia                  INTEGER,
        tnPortSFPEquipped               TruthValue,
        tnPortEquipped                  TruthValue,
        tnPortLinkStatus                TruthValue,
        tnPortAdminStatus               TmnxPortAdminStatus,
        tnPortOperStatus                TmnxPortOperStatus,
        tnPortState                     TmnxPortState,
        tnPortPrevState                 TmnxPortState,
        tnPortNumAlarms                 Unsigned32,
        tnPortAlarmState                TmnxAlarmState,
        tnPortLastAlarmEvent            RowPointer,
        tnPortClearAlarms               TmnxActionType,
        tnPortSFPVendorSerialNum        TNamedItemOrEmpty,
        tnPortSFPVendorPartNum          TNamedItemOrEmpty,
        tnPortLastStateChanged          TimeStamp,
        tnPortNumChannels               Unsigned32,
        tnPortNetworkEgrQueues          TNamedItemOrEmpty,
        tnPortBundleNumber              Integer32,
        tnPortIsLeaf                    TruthValue,
--        tnPortChanType                  TmnxMDAChanType,
        tnPortParentPortID              TmnxPortID,
        tnPortOpticalCompliance         OCTET STRING,
        tnPortLoadBalanceAlgorithm      INTEGER,
        tnPortEgrPortSchedPlcy          TNamedItemOrEmpty,
        tnPortLastClearedTime           TimeStamp,
        tnPortEgrHsmdaSchedPlcy         TNamedItemOrEmpty,
        tnPortIngNamedPoolPlcy          TNamedItemOrEmpty,
        tnPortEgrNamedPoolPlcy          TNamedItemOrEmpty,
        tnPortIngPoolPercentRate        Unsigned32,
        tnPortEgrPoolPercentRate        Unsigned32,
        tnPortDDMEventSuppression       TruthValue,
        tnPortSFPStatus                 INTEGER,
        tnPortReasonDownFlags           BITS,
        tnPortSSMRxQualityLevel         INTEGER,
        tnPortDwdmLaserChannel          Unsigned32,
        tnPortOtuCapable                TruthValue,
        tnPortHoldTimeUnits             INTEGER,
        tnPortLinkLengthInfo            OCTET STRING,
        tnPortSFPNumLanes               Unsigned32,
        tnPortPhysStateChangeCount      Counter32,
        tnPortPacketSwitchId            Unsigned32,
        tnPortOtnSignalDegrade          TmnxEnabledDisabled
    }

tnPortPortID          OBJECT-TYPE
    SYNTAX      TmnxPortID
    MAX-ACCESS  not-accessible
    STATUS      current
    DESCRIPTION
        "tnPortPortID is an index into this table. It maps this port to its
         entry in the mib-2 interfaces table."
    ::= { tnPortEntry 1 }

tnPortLastChangeTime    OBJECT-TYPE
    SYNTAX      TimeStamp
    MAX-ACCESS  read-only
    STATUS      current
    DESCRIPTION
        "The tnPortLastChangeTime variable contains the sysUpTime
         value of the most recently modified writable variable in the
         tnPortEntry row for this port."
    ::= { tnPortEntry 2 }

tnPortType        OBJECT-TYPE
    SYNTAX      TmnxPortType
    MAX-ACCESS  read-only
    STATUS      current
    DESCRIPTION
        "The type of port or optical pack installed."
    ::= { tnPortEntry 3 }

tnPortClass        OBJECT-TYPE
    SYNTAX      TmnxPortClass
    MAX-ACCESS  read-only
    STATUS      current
    DESCRIPTION
        "The class of port or optical pack installed.  This can be
         derived from tnPortType."
    ::= { tnPortEntry 4 }

tnPortDescription     OBJECT-TYPE
    SYNTAX      TItemLongDescription
    MAX-ACCESS  read-write
    STATUS      current
    DESCRIPTION
        "A textual string containing user supplied information about the
         interface."
    DEFVAL { ''H }
    ::= { tnPortEntry 5 }

tnPortName        OBJECT-TYPE
    SYNTAX      TNamedItemOrEmpty
    MAX-ACCESS  read-only
    STATUS      current
    DESCRIPTION
        "The textual name of the interface.  The value of this
         object should be the name of the interface as assigned by
         the local device and should be suitable for use in commands
         entered at the device's `console'.  This might be a text
         name, such as `le0' or 'sys171-2/1."
    ::= { tnPortEntry 6 }

tnPortAlias        OBJECT-TYPE
    SYNTAX      TNamedItemOrEmpty
    MAX-ACCESS  read-write
    STATUS      current
    DESCRIPTION
        "This object is an 'alias' name for the interface as
         specified by a network manager, and provides a non-volatile
         'handle' for the interface.

         On the first instantiation of an interface, the value of
         tnPortAlias associated with that interface is the zero-length
         string.  As and when a value is written into an instance of
         tnPortAlias through a network management set operation, then the
         agent must retain the supplied value in the tnPortAlias instance
         associated with the same interface for as long as that
         interface remains instantiated, including across all re-
         initializations/reboots of the network management system."
    DEFVAL { ''H }
    ::= { tnPortEntry 7 }

tnPortUserAssignedMac OBJECT-TYPE
    SYNTAX      TruthValue
    MAX-ACCESS  read-only
    STATUS      current
    DESCRIPTION
        "When tnPortUserAssignedMac has a value of 'true', the value of
         tnPortMacAddress has been explicitly assigned by a SNMP SET
         request.  When tnPortUserAssignedMac is set to 'false',
         tnPortMacAddress returns the system assigned MAC address."
    DEFVAL { false }
    ::= { tnPortEntry 8 }

tnPortMacAddress  OBJECT-TYPE
    SYNTAX      MacAddress
    MAX-ACCESS  read-write
    STATUS      current
    DESCRIPTION
        "When tnPortUserAssignedMac has a value of 'true',
         tnPortMacAddress has the value that has been explicitly
         assigned by a SNMP SET request.  When tnPortUserAssignedMac
         has a value of 'false', tnPortMacAddress returns the same
         value as tnPortMacAddress, the hardware or system assigned
         MAC address.  When tnPortMacAddress is modified by a SET
         request, the agent sets tnPortUserAssignedMac to 'true'.

         Setting tnPortMacAddress to all zeros causes the agent to
         revert to using the default tnPortHwMacAddress and also to
         return tnPortUserAssignedMac as 'false'."
    DEFVAL { '000000000000'h }
    ::= { tnPortEntry 9 }

tnPortHwMacAddress  OBJECT-TYPE
    SYNTAX      MacAddress
    MAX-ACCESS  read-only
    STATUS      current
    DESCRIPTION
        "The interface's hardware or system assigned MAC address at its
         protocol sub-layer.  When tnPortUserAssignedMac has a value of
         'true', the value of tnPortMacAddress is used instead of
         tnPortHwMacAddress.

         In the case of a pre-provisioned port that is not yet physically
         in the system, the MAC address may not be known.  In this case
         a MAC address of all zeros is returned."
    ::= { tnPortEntry 10 }

tnPortMode        OBJECT-TYPE
    SYNTAX      INTEGER {
                    undefined (0),
                    access (1),
                    network (2)
                }
    MAX-ACCESS  read-write
    STATUS      current
    DESCRIPTION
        "The tnPortMode variable indicates if the interface on this port
         is configured as a service access port or a network access
         port.

         If the port mode equals 'access', and the tmnxMDAAssignedType
         is of ATM MDA family, then tnPortEncapType is automatically
         set to 'atmEncap'.

         If port mode equals 'access', tnPortEncapType must also
         be configured to 'qEncap' (For Ethernet MDAs) or to
         'bcpNullEncap' for Sonet/SDH MDAs.

         Once the port's operation mode has been configured
         for 'access' mode, multiple services may be configured
         on the port.

         If the port mode equals 'network', tnPortEncapType must also
         be configured to 'nullEncap' (Ethernet MDAs), or 'pppAutoEncap'
         (Sonet/SDH MDAs) and tnPortEncapType is defaulted to those
         values on the mode change."
    ::= { tnPortEntry 11 }

tnPortEncapType   OBJECT-TYPE
    SYNTAX      INTEGER {
                    unknown (0),
                    nullEncap (1),
                    qEncap (2),
                    mplsEncap (3),
                    bcpNullEncap (4),
                    bcpDot1qEncap (5),
                    ipcpEncap (6),
                    frEncap (7),
                    pppAutoEncap (8),
                    atmEncap (9),
                    qinqEncap (10),
                    wanMirrorEncap (11),
                    ciscoHDLCEncap (12),
                    cemEncap (13)
                }
    MAX-ACCESS  read-write
    STATUS      current
    DESCRIPTION
        "The type of encapsulation protocol configured on this
         port's network interface.  If tnPortEncapType has a value
         of 'nullEncap', frames received will not carry any tags
         or labels and as a result only one service can be
         configured on this port.  Sometimes this is referred to
         as raw Ethernet packets.

         If tnPortEncapType has a value of 'qEncap', ingress frames
         carry 802.1q tags where each different tag can signify a
         different service. This is not a valid value if
         tnPortClass has a value of 'sonetPath'.

         If tnPortEncapType has a value of 'bcpNullEncap',
         Bcp is used on the sonet path as the NCP control protocol.
         The BCP IEEE 802 Tagged Frame Configuration Option (type 8)
         is negotiated to 'enabled'.  VLAN tagged frames are
         allowed into the sonet path.  Only a single SAP can
         be associated with the sonet path.  'bcpNullEncap' is
         valid only if tnPortClass has a value of 'sonetPath'.

         If tnPortEncapType has a value of 'bcpDot1qEncap',
         BCP is used as the NCP control protocol.  The BCP IEEE 802
         Tagged Frame Configuration Option (type 8) is negotiated to
         'enabled'.  VLAN tagged frames are allowed on the sonet path.
         This encapsulation type is required when multiple SAPs are
         defined on the sonet path where each one is service
         delimited by a provisioned Dot1q tag.  When 'bcpDot1qEncap'
         is specified, BCP does not enter the 'open' state unless
         the far end peer also supports 'bcpDot1qEncap'.  This allows
         a LCP negotiation to transmit configuration request and
         confirmation messages to enable this feature.  'bcpDot1qEncap'
         is a valid value only if tnPortClass has a value of 'sonetPath'.

         If tnPortEncapType has a value of 'ipcpEncap',
         BCP will not be used on this sonet path.  IPCP NCP is used
         instead.  'ipcpEncap' is a valid only if tnPortClass has
         a value of 'sonetPath'.

         If tnPortEncapType has a value of 'frEncap', Frame Relay is
         the expected encapsulation.

         If tnPortEncapType has a value of 'pppAutoEncap', IPCP is
         automatically enabled. This encap type is only valid on
         ports/paths in network mode.

         If tnPortEncapType has a value of 'atmEncap', the encapsulation
         on the port is ATM. The 'atmEncap' is also used when mirroring
         ATM ports.

         If tnPortEncapType has a value of 'wanMirrorEncap', the
         port is used for mirroring of frame-relay and POS ports. On such
         ports no link management protocol would run.

         If tnPortEncapType has a value of 'ciscoHDLCEncap', the Cisco HDLC
         encapsulation is applied. This encap type is only valid if
         TmnxPortClass has a value of 'tdm' or 'sonet'.

         If tnPortEncapType has a value of 'cemEncap', encapsulation of
         frames will be circuit emulation.  This is used to support transparent
         transmission of frames.  This encap type is only valid
         if TmnxPortClass has a value of 'tdm' or 'sonet' in access mode.

         tnPortEncapType is set to 'unknown' for physical SONET/SDH and
         TDM ports.
         "
    ::= { tnPortEntry 12 }

tnPortLagId OBJECT-TYPE
    SYNTAX      Unsigned32 (0..240)
    MAX-ACCESS  read-write
    STATUS      current
    DESCRIPTION
        "The value of tnPortLagId indicates which LAG or multi-link trunk
         (MLT) this port is assigned to. If this port is not associated
         with any LAG, this value will be set to zero(0).

         The maximum value of this object is '64', when the value of
         TIMETRA-CHASSIS-MIB::tnChassisType is '5' (ESS-1/SR-1)."
    DEFVAL { 0 }
    ::= { tnPortEntry 13 }

tnPortHoldTimeUp  OBJECT-TYPE
    SYNTAX      Unsigned32 (0..90000)
    MAX-ACCESS  read-write
    STATUS      current
    DESCRIPTION
        "The value of tnPortHoldTimeUp is used to configure the
         hold-timer for link up event dampening. This guards against
         reporting excessive interface transitions. This is implemented
         by not advertising subsequent transitions of the interface to
         upper layer protocols until the configured timer has expired.
         A value of zero (0) indicates that an up transition is reported
         immediately.  The value of tnPortHoldTimeUp is not applicable
         when tnPortClass has a value of 'sonet (5)'. In that case,
         tnSonetHoldTimeUp is used instead.

         tnPortHoldTimeUp is measured in units as specified by
         tnPortHoldTimeUnits. The maximum hold-time for this object is
         15 minutes, regardless of the units specified. Attempts to change
         the maximum value to a hold-time longer than 15 minutes will result
         in an INCONSISTENT error."
    DEFVAL { 0 }
    ::= { tnPortEntry 14 }

tnPortHoldTimeDown    OBJECT-TYPE
    SYNTAX      Unsigned32 (0..90000)
    MAX-ACCESS  read-write
    STATUS      current
    DESCRIPTION
        "The value of tnPortHoldTimeDown is used to configure the
         hold-timer for link down event dampening. This guards against
         reporting excessive interface transitions. This is implemented
         by not advertising subsequent transitions of the interface to
         upper layer protocols until the configured timer has expired.
         A value of zero (0) indicates that a down transition is reported
         immediately. The value of tnPortHoldTimeDown is not applicable
         when tnPortClass has a value of 'sonet (5)'. In that case,
         tnSonetHoldTimeDown is used instead.

         tnPortHoldTimeDown is measured in units as specified by
         tnPortHoldTimeUnits. The maximum hold-time for this object is
         15 minutes, regardless of the units specified. Attempts to change
         the maximum value to a hold-time longer than 15 minutes will result
         in an INCONSISTENT error."
    DEFVAL { 0 }
    ::= { tnPortEntry 15 }

tnPortUpProtocols     OBJECT-TYPE
    SYNTAX      BITS {
                    portUpIpv4  (0),
                    portUpMpls  (1),
                    portUpBcp   (2),
                    portUpIso   (3),
                    portUpFr    (4),
                    portUpAtm   (5),
                    portUpChdlc (6),
                    portUpIma   (7),
                    portUpIpv6  (8)
                }
    MAX-ACCESS  read-only
    STATUS      current
    DESCRIPTION
        "The tnPortUpProtocols variable is a bitmap that indicates what
         protocols can be used on this port type."
    ::= { tnPortEntry 16 }

tnPortConnectorType       OBJECT-TYPE
    SYNTAX      TmnxPortConnectorType
    MAX-ACCESS  read-only
    STATUS      current
    DESCRIPTION
        "The type of connector installed on this port."
    ::= { tnPortEntry 17 }

tnPortTransceiverType       OBJECT-TYPE
    SYNTAX      INTEGER {
                    unknown(0),
                    gbic(1),
                    moduleConnectorSolderedToMotherboard(2),
                    sfpTransceiver(3),
                    xbiTransceiver(4),
                    xenpakTransceiver(5),
                    xfpTransceiver(6),
                    xffTransceiver(7),
                    xfpeTransceiver(8),
                    xpakTransceiver(9),
                    x2Transceiver(10),
                    dwdmSfpTransceiver(11),
                    qsfpTransceiver(12),
                    qsfpPlusTransceiver(13),
                    cfpTransceiver(14),
                    shieldedMiniMultilaneHd4x(15),
                    shieldedMiniMultilaneHd8x(16),
                    qsfp28Transceiver(17),
                    cfp4Transceiver(18),
                    cdfpStyle1or2Transceiver(19),
                    shieldedMiniMultilaneHd4xFc(20),
                    shieldedMiniMultilaneHd8xFc(21),
                    cdfpStyle3Transceiver(22),
                    microQsfpTransceiver(23),
                    qsfpDd8xTransceiver(24),
                    osfp8xTransceiver(25),
                    sfpDd2xTransceiver(26),
                    tsopSmartSfpTransceiver(130)
                }
    MAX-ACCESS  read-only
    STATUS      current
    DESCRIPTION
        "Type of the transceiver."
    ::= { tnPortEntry 25 }

-- tnPortTransceiverCode       OBJECT-TYPE
--     SYNTAX      BITS{
--                     unknown(0),
--                     oc48-longreach(1),
--                     oc48-intermediatereach(2),
--                     oc48-shortreach(3),
--                     oc12-singlemodelongreach(4),
--                     oc12-singlemodeinterreach(5),
--                     oc12-multimodeshortreach(6),
--                     oc3-singlemodelongreach(7),
--                     oc3-singlemodeinterreach(8),
--                     oc3-multi-modeshortreach(9),
--                     gige-1000base-t(10),
--                     gige-1000base-cx(11),
--                     gige-1000base-lx(12),
--                     gige-1000base-sx(13),
--                     faste-100base-mm-fx(14),
--                     faste-100base-sm-fx(15),
--                     xgige-10gbase-sr(16),
--                     xgige-10gbase-lr(17),
--                     xgige-10gbase-er(18),
--                     xgige-10gbase-sw(19),
--                     xgige-10gbase-lw(20),
--                     xgige-10gbase-ew(21)
--                 }
--     MAX-ACCESS  read-only
--     STATUS      obsolete
--     DESCRIPTION
--         "The code for the transmission media.
--
--          tnPortOpticalCompliance is used instead of
--          tnPortTransceiverCode.tnPortOpticalCompliance  contains the
--          same information and is defined by an industry standard."
--     ::= { tnPortEntry 26 }

tnPortTransceiverLaserWaveLen       OBJECT-TYPE
    SYNTAX      Unsigned32
    MAX-ACCESS  read-only
    STATUS      current
    DESCRIPTION
        "The light wavelength transmitted by the transceiver's laser.
         A value of zero indicates that the port is not equipped with
         the transceiver."
    ::= { tnPortEntry 27 }

tnPortTransceiverDiagCapable    OBJECT-TYPE
    SYNTAX      INTEGER {
                    notApplicable(0),
                    true(1),
                    false(2)
                }
    MAX-ACCESS  read-only
    STATUS      current
    DESCRIPTION
        "Indicates if the transceiver is capable of doing diagnostics."
    ::= { tnPortEntry 28 }

tnPortTransceiverModelNumber OBJECT-TYPE
    SYNTAX       TNamedItemOrEmpty
    MAX-ACCESS   read-only
    STATUS       current
    DESCRIPTION
        "The value of tnPortTransceiverModelNumber indicates the model
         information for the transceiver, as read from the transceiver
         EEPROM.  For example, the string may contain the Nokia
         part number and CLEI for the transceiver.

         The string is expected to contain printable ASCII characters, but
         unprintable ASCII characters read from the EEPROM are not
         filtered out."
    ::= { tnPortEntry 29 }

tnPortSFPConnectorCode       OBJECT-TYPE
    SYNTAX      INTEGER {
                    unknown(0),
                    sc(1),
                    fiberChannel-Style1-CopperConnector(2),
                    fiberChannel-Style2-CopperConnector(3),
                    bncortnc(4),
                    fiberChannelCoaxialHeaders(5),
                    fiberJack(6),
                    lc(7),
                    mt-rj(8),
                    mu(9),
                    sg(10),
                    opticalPigtail(11),
                    mpo1x12(12),
                    mpo2x16(13),
                    hssdcII(32),
                    copperPigtail(33),
                    rj45(34),
                    noSeparableConnector(35),
                    mxc2x16(36),
                    csOptical(37),
                    miniCsOptical(38),
                    copperGigE(128)
                }
    MAX-ACCESS  read-only
    STATUS      current
    DESCRIPTION
        "The external connector provided on the interface."
    ::= { tnPortEntry 30 }

tnPortSFPVendorOUI       OBJECT-TYPE
    SYNTAX      Unsigned32
    MAX-ACCESS  read-only
    STATUS      current
    DESCRIPTION
        "The vendor organizationally unique identifier field (OUI)
         contains the IEEE company identifier for the vendor.
         A value of all zero indicates that the vendor OUI
         is unspecified."
    ::= { tnPortEntry 31 }

tnPortSFPVendorManufactureDate       OBJECT-TYPE
    SYNTAX      DateAndTime
    MAX-ACCESS  read-only
    STATUS      current
    DESCRIPTION
        "The vendor's date code."
    ::= { tnPortEntry 32 }

tnPortSFPMedia       OBJECT-TYPE
    SYNTAX      INTEGER {
                    notApplicable(0),
                    ethernet(1),
                    sonetsdh(2)
                }
    MAX-ACCESS  read-only
    STATUS      current
    DESCRIPTION
        "The media supported for the SFP."
    ::= { tnPortEntry 33 }

tnPortSFPEquipped    OBJECT-TYPE
    SYNTAX      TruthValue
    MAX-ACCESS  read-only
    STATUS      current
    DESCRIPTION
        "Indicates if the SFP is equipped."
    ::= { tnPortEntry 34 }

tnPortEquipped    OBJECT-TYPE
    SYNTAX      TruthValue
    MAX-ACCESS  read-only
    STATUS      current
    DESCRIPTION
        "Indicates if there is an optics pack installed in this
         port or not."
    ::= { tnPortEntry 35 }

tnPortLinkStatus  OBJECT-TYPE
    SYNTAX      TruthValue
    MAX-ACCESS  read-only
    STATUS      current
    DESCRIPTION
        "Indicates whether or not the port has a physical link."
    ::= { tnPortEntry 36 }

tnPortAdminStatus  OBJECT-TYPE
    SYNTAX      TmnxPortAdminStatus
    MAX-ACCESS  read-write
    STATUS      current
    DESCRIPTION
        "The desired administrative status of this port."
    DEFVAL { inService }
    ::= { tnPortEntry 37 }

tnPortOperStatus   OBJECT-TYPE
    SYNTAX      TmnxPortOperStatus
    MAX-ACCESS  read-only
    STATUS      current
    DESCRIPTION
        "The current operational status of this port."
    ::= { tnPortEntry 38 }

tnPortState   OBJECT-TYPE
    SYNTAX  TmnxPortState
    MAX-ACCESS  read-only
    STATUS  current
    DESCRIPTION
        "The state level of this port.  A value of 'none' indicates
         the port is either in its initial creation state or is
         just about to be deleted.  A value of 'ghost' represents
         a port that is not physically present.  This state may
         represent a pre-provisioned port.  A value of 'linkDown'
         represents a port that is physically present but does
         not have a link.  The 'linkUp' state represents a port
         that is physically present and has physical link present.
         A port in 'up' state is ready to pass some kinds of traffic.
         The tnPortUpProtocols variable indicates the actual type(s)
         of traffic can be passed on this 'up' link."
    ::= { tnPortEntry 39 }

tnPortPrevState   OBJECT-TYPE
    SYNTAX      TmnxPortState
    MAX-ACCESS  read-only
    STATUS      current
    DESCRIPTION
        "The tnPortPrevState indicates the state level that the port
         transitioned from into the current tnPortState level."
    ::= { tnPortEntry 40 }

tnPortNumAlarms   OBJECT-TYPE
    SYNTAX      Unsigned32
    MAX-ACCESS  read-only
    STATUS      current
    DESCRIPTION
        "The number of alarms currently outstanding on this port."
    ::= { tnPortEntry 41 }

tnPortAlarmState    OBJECT-TYPE
    SYNTAX  TmnxAlarmState
    MAX-ACCESS  read-only
    STATUS  current
    DESCRIPTION
        "The value of tnPortAlarmState indicates the current alarm
         state for this port."
    ::= { tnPortEntry 42 }

tnPortLastAlarmEvent    OBJECT-TYPE
    SYNTAX  RowPointer
    MAX-ACCESS  read-only
    STATUS  current
    DESCRIPTION
        "The value of tnPortLastAlarmEvent indicates the object name
         and instance value that points to the row entry in the ALARM-MIB
         containing the most recent alarm associated with this port.  If
         tnPortAlarmState has a value of 'alarmCleared(2)', the
         most recent alarm event will be in the cleared alarm table.  If it has
         a value of 'alarmActive(1)', the most recent alarm event will be in
         the active alarm table.  If the value of tnPortLastAlarmEvent is
         '0.0', either no port alarm events have occurred since the system was
         last booted, or the last port alarm event has aged out and its entry
         is no longer available in the ALARM-MIB tables."
    ::= { tnPortEntry 43 }

tnPortClearAlarms OBJECT-TYPE
    SYNTAX      TmnxActionType
    MAX-ACCESS  read-write
    STATUS      current
    DESCRIPTION
        "Setting this action variable causes all the alarms
         associated with this port to be moved from the current
         alarm log to the history alarm log. Primarily meant
         for use in development.  This object will most likely
         be removed from the MIB before product release."
    DEFVAL { notApplicable }
    ::= { tnPortEntry 44 }

tnPortSFPVendorSerialNum       OBJECT-TYPE
    SYNTAX      TNamedItemOrEmpty
    MAX-ACCESS  read-only
    STATUS      current
    DESCRIPTION
        "The value of tnPortSFPVendorSerialNum indicates the
         transceiver's vendor serial number in ASCII characters,
         as read from the transceiver EEPROM.

         An empty string indicates the vendor serial number is
         unspecified.

         The string is expected to contain printable ASCII characters,
         but unprintable ASCII characters read from the EEPROM are not
         filtered out."
    ::= { tnPortEntry 45 }

tnPortSFPVendorPartNum       OBJECT-TYPE
    SYNTAX      TNamedItemOrEmpty
    MAX-ACCESS  read-only
    STATUS      current
    DESCRIPTION
        "The value of tnPortSFPVendorPartNum indicates the
         transceiver's vendor part number (or product name) in ASCII
         characters, as read from the transceiver EEPROM.

         An empty string indicates the vendor part number is
         unspecified.

         The string is expected to contain printable ASCII characters, but
         unprintable ASCII characters read from the EEPROM are not
         filtered out."
    ::= { tnPortEntry 46 }

tnPortLastStateChanged       OBJECT-TYPE
    SYNTAX      TimeStamp
    MAX-ACCESS  read-only
    STATUS      current
    DESCRIPTION
        "The tnPortLastStateChanged variable contains the
         value of the sysUpTime the last time the operational status
         of the port changed state."
    ::= { tnPortEntry 48 }

tnPortNumChannels       OBJECT-TYPE
    SYNTAX      Unsigned32
    MAX-ACCESS  read-only
    STATUS      current
    DESCRIPTION
        "For SONET/SDH paths or TDM channels, tnPortNumChannels
         contains the number of possible immediate children. For
         leaf paths or channels, the value of this object will be zero.
         For SONET/SDH or TDM physical ports, tnPortNumChannels
         contains the total number of channels on the physical port.
         For all other entries in the tnPortTable, the value of
         this object will be zero."
    ::= { tnPortEntry 49 }

tnPortNetworkEgrQueues       OBJECT-TYPE
    SYNTAX      TNamedItemOrEmpty
    MAX-ACCESS  read-write
    STATUS      current
    DESCRIPTION
        "tnPortNetworkEgrQueues contains the network egress queue policy
        if the tnPortMode is network. Otherwise this object has no
        significance."
    ::= { tnPortEntry 50 }

tnPortBundleNumber OBJECT-TYPE
    SYNTAX      Integer32 (0..2000)
    MAX-ACCESS  read-only
    STATUS      current
    DESCRIPTION
        "tnPortBundleNumber identifies the bundle for which this port is
         a member. If this port is not a member of any bundle, the value of
         tnPortBundleNumber will be zero."
    ::= { tnPortEntry 51 }

tnPortIsLeaf OBJECT-TYPE
    SYNTAX      TruthValue
    MAX-ACCESS  read-only
    STATUS      current
    DESCRIPTION
        "tnPortIsLeaf is applicable only when the 'isSonet' and/or 'isTDM'
         bits in TIMETRA-CHASSIS-MIB:tmnxMDACapabilities are set.
         When the value of this object is 'true', it indicates that the channel
         is capable of passing traffic.

         The value of this object is 'false' for:
         1. Physical ports on SONET/TDM MDA's
         2. Intermediate channels on a channelized MDA
         3. Leaf channels which belong to a bundle

         For ports on Ethernet MDA's or for LAG ports, the value of this object
         will be 'false'."
    ::= { tnPortEntry 52 }

-- tnPortChanType      OBJECT-TYPE
--     SYNTAX      TmnxMDAChanType
--     MAX-ACCESS  read-only
--     STATUS      current
--     DESCRIPTION
--         "tnPortChanType is applicable only when the 'isSonet' and/or 'isTDM'
--          bits in TIMETRA-CHASSIS-MIB:tmnxMDACapabilities are set. It indicates
--          the type of the channel.
--          For ports on Ethernet MDA's, the value of this object will
--          be 'unknown'."
--     ::= { tnPortEntry 53 }

tnPortParentPortID      OBJECT-TYPE
    SYNTAX      TmnxPortID
    MAX-ACCESS  read-only
    STATUS      current
    DESCRIPTION
        "tnPortParentPortID  is applicable only when the 'isSonet'
         and/or 'isTDM' bits in TIMETRA-CHASSIS-MIB:tmnxMDACapabilities are set.
         For SONET or TDM channel, it indicates the port ID of its parent
         channel or port."
    ::= { tnPortEntry 54 }

tnPortOpticalCompliance   OBJECT-TYPE
    SYNTAX      OCTET STRING (SIZE (8))
    MAX-ACCESS  read-only
    STATUS      current
    DESCRIPTION
        "tnPortOpticalCompliance is applicable only when the
         tnPortSFPEquipped is set to 'true'. The value of
         tnPortOpticalCompliance indicates the 8 bytes of optical compliance
         bits stored in SFP and XFP eeproms."
    ::= { tnPortEntry 55 }


tnPortLoadBalanceAlgorithm  OBJECT-TYPE
    SYNTAX      INTEGER {
                    notApplicable (0),
                    default (1),
                    includeL4 (2),
                    excludeL4 (3)
                }
    MAX-ACCESS  read-write
    STATUS      current
    DESCRIPTION
        "The value of tnPortLoadBalanceAlgorithm specifies the load
         balancing algorithm to be used on this port. When the
         value is 'includeL4', the src and dst port are used in the
         hashing algorithm. When it's 'excludeL4', they are not included.
         When the value is 'default', the port inherits the global settings
         in tnL4LoadBalancing. The value is 'notApplicable' for ports that
         do not pass any traffic. An attempt to modify this object when it is
         set to 'notApplicable' will return an inconsistentValue error."
    DEFVAL { default }
    ::= { tnPortEntry 56 }

tnPortEgrPortSchedPlcy  OBJECT-TYPE
    SYNTAX      TNamedItemOrEmpty
    MAX-ACCESS  read-write
    STATUS      current
    DESCRIPTION
        "The value of tnPortEgrPortSchedPlcy specifies the egress QoS
         port-scheduler policy for this port. This object must correspond
         to the index of a row in TIMETRA-QOS-MIB::tPortSchedulerPlcyTable.

         A non-empty value for tnPortEgrPortSchedPlcy is only valid when the
         tmnxMDAAssignedType is a non-HSMDA MDA Type. Attempting to set
         tnPortEgrPortSchedPlcy to a non-empty string when the
         tmnxMDAAssignedType is a HSMDA MDA Type will return
         an 'inconsistentValue' error."
    DEFVAL { "" }
    ::= { tnPortEntry 57 }

tnPortLastClearedTime  OBJECT-TYPE
    SYNTAX      TimeStamp
    MAX-ACCESS  read-only
    STATUS      current
    DESCRIPTION
        "The value of tnPortLastClearedTime indicates the sysUpTime
         when the counters in the IF-MIB:ifTable were last cleared."
    ::= { tnPortEntry 58 }

 tnPortEgrHsmdaSchedPlcy  OBJECT-TYPE
   SYNTAX      TNamedItemOrEmpty
   MAX-ACCESS  read-write
   STATUS      current
   DESCRIPTION
       "The value of tnPortEgrHsmdaSchedPlcy specifies the egress QoS
        Hsmda-scheduler policy for this port. This object must correspond
        to the index of a row in TIMETRA-QOS-MIB::tHsmdaSchedulerPlcyTable,
        otherwise an 'inconsistentValue' error will be returned.

        When the tmnxMDAAssignedType is a non-HSMDA MDA Type, the value
        for tnPortEgrHsmdaSchedPlcy will be ignored. If the
        tmnxMDAAssignedType is a HSMDA MDA Type, the default for this
        object will be the string 'default'."
   DEFVAL { "" }
   ::= { tnPortEntry 59 }

tnPortIngNamedPoolPlcy OBJECT-TYPE
    SYNTAX      TNamedItemOrEmpty
    MAX-ACCESS  read-write
    STATUS      current
    DESCRIPTION
        "The value of tnPortIngNamedPoolPlcy specifies a named pool
         policy associated with an port ingress context. The policy
         governs the way named pools are created at the port level."
    DEFVAL { ''H }
    ::= { tnPortEntry 60 }

tnPortEgrNamedPoolPlcy OBJECT-TYPE
    SYNTAX      TNamedItemOrEmpty
    MAX-ACCESS  read-write
    STATUS      current
    DESCRIPTION
        "The value of tnPortEgrNamedPoolPlcy specifies a named pool
         policy associated with an port egress context. The policy
         governs the way named pools are created at the port level."
    DEFVAL { ''H }
    ::= { tnPortEntry 61 }

tnPortIngPoolPercentRate OBJECT-TYPE
    SYNTAX      Unsigned32 (1..1000)
    MAX-ACCESS  read-write
    STATUS      current
    DESCRIPTION
        "The value of tnPortIngPoolPercentRate specifies increment or
         decrement of the active bandwidth associated with the ingress port.
         This active bandwidth affects the amount of ingress buffer space
         managed by the port."
    DEFVAL { 100 }
    ::= { tnPortEntry 62 }

tnPortEgrPoolPercentRate OBJECT-TYPE
    SYNTAX      Unsigned32 (1..1000)
    MAX-ACCESS  read-write
    STATUS      current
    DESCRIPTION
        "The value of tnPortEgrPoolPercentRate specifies increment or
         decrement of the active bandwidth associated with the egress port.
         This active bandwidth affects the amount of egress buffer space
         managed by the port."
    DEFVAL { 100 }
    ::= { tnPortEntry 63 }

tnPortDDMEventSuppression OBJECT-TYPE
    SYNTAX      TruthValue
    MAX-ACCESS  read-write
    STATUS      current
    DESCRIPTION
        "The value of tnPortDDMEventSuppression specifies whether or not an
         inserted SFP/XFP that supports Digital Diagnostic Monitoring
         raises traps and events (false) or suppresses all notifications
         (true)."
    DEFVAL { false }
    ::= { tnPortEntry 64 }

tnPortSFPStatus           OBJECT-TYPE
    SYNTAX      INTEGER {
                     not-equipped (0),
                     operational  (1),
                     read-error   (2),
                     data-corrupt (3),
                     ddm-corrupt  (4),
                     unsupported  (5)
                }
    MAX-ACCESS  read-only
    STATUS      current
    DESCRIPTION
        "The value of tnPortSFPStatus indicates the operational status of
         the inserted SFP/XFP. If tnPortSFPEquipped is false, the
         tnPortSFPStatus will be 'not-equipped (0)', otherwise
         'operational (1)' if no failure is detected.

         A failure to read the SFP data will result in a 'read-error (2)',
         while corrupted information on the SFP will result in either
         'data-corrupt (3)', or 'ddm-corrupt (4)' if an SFP read results in
         invalid data or DDM information respectively.  An insertion of an
         unsupported SFP will result in 'unsupported (5)'.

         A trap will be raised if the value of tnPortSFPStatus indicates a
         failure; that is the tnPortSFPStatus is neither 'not-equipped (0)',
         nor 'operational (1)'."
    DEFVAL { not-equipped }
    ::= { tnPortEntry 65 }

tnPortReasonDownFlags          OBJECT-TYPE
    SYNTAX      BITS {
                   unknown              (0),
                   linklossFwd          (1),
                   lagMemberPortStandby (2),
                   ethCfmFault          (3),
                   opticalTuning        (4),
                   channelOutOfRange    (5),
                   channelNotConfigured (6),
                   crcError             (7),
                   internalMacTxError   (8),
                   noServicePort        (9)
                }
    MAX-ACCESS  read-only
    STATUS      current
    DESCRIPTION
        "The tnPortReasonDownFlags indicates why a port may
        be in the operationally 'down' state. The following reasons are
        detected through this object:
                unknown(0)              - Unspecified (or unknown)
                linklossFwd(1)          - A sap using this port has an LLF
                                          operational status set to 'fault'
                lagMemberPortStandby(2) - A lag using this port as a member
                                          port has set the member port to
                                          'standby' while configured to keep
                                          standby member ports down.
                ethCfmFault(3)          - A facility MEP bound to this port
                                          has its dot1agCfmMepHighestPrDefect
                                          set to a value other than 'none (0)'.
                opticalTuning(4)        - The DWDM optical receive signal is
                                          undergoing tuning and analysis by
                                          control algorithms to find the
                                          optimal settings.
                channelOutOfRange(5)    - The configured DWDM optical channel
                                          is out of range for the equipped
                                          tunable optical interface.
                channelNotConfigured(6) - The DWDM optical channel is not
                                          configured for the equipped
                                          tunable optical interface.
                crcError(7)             - CRC errors on the port exceeded the
                                          configured threshold.
                internalMacTxError(8)   - An internal MAC tx error was detected
                                          on the port.
                noServicePort(9)        - port configured as no-service port."
    ::= { tnPortEntry 66 }

tnPortSSMRxQualityLevel   OBJECT-TYPE
    SYNTAX      INTEGER {
                    unknown (0),
                    prs     (1),
                    stu     (2),
                    st2     (3),
                    tnc     (4),
                    st3e    (5),
                    st3     (6),
                    smc     (7),
                    st4     (8),
                    dus     (9),
                    prc     (10),
                    ssua    (11),
                    ssub    (12),
                    sec     (13),
                    dnu     (14),
                    inv     (15),
                    pno     (16),
                    eec1    (17),
                    eec2    (18),
                    failed  (19)
                }
    MAX-ACCESS  read-only
    STATUS      current
    DESCRIPTION
        "tnPortSSMRxQualityLevel indicates the SSM quality level
         of received SSM messages. On ports not supporting SSM, or not
         receiving SSM messages, the quality level will be 'unknown (0)'.

         The values 'prs (1)' through 'dus (9)' and 'pno (16)' correspond to
         quality levels defined in GR-253-CORE.  The values 'prc (10)' through
         'inv (15)' correspond to quality levels defined in G.781.
         The values 'eec1 (17)' and 'eec2 (18)' correspond to quality levels
         defines in G.8264.
         The value 'failed (19)' is used when there is a failure in the SSM
         channel."
    REFERENCE
        "Bellcore (Telcordia Technologies) GR-253-CORE, Issue 3, September 2000,
         5.4.2.
         ITU-T Recommendation G.781, June 1999.
         ITU-T Recommendation G.8264, October 2008."
    DEFVAL { unknown }
    ::= { tnPortEntry 67 }

tnPortDwdmLaserChannel    OBJECT-TYPE
    SYNTAX      Unsigned32 (0|17..61|170..610)
    MAX-ACCESS  read-write
    STATUS      current
    DESCRIPTION
        "tnPortDwdmLaserChannel specifies the DWDM ITU channel at which a
         tunable MDA optical interface will be configured to operate. It is
         expressed in a form that is derived from the laser's operational
         frequency. For example 193.40 THz corresponds to DWDM ITU channel 34
         in the 100 GHz grid and 193.45 THz corresponds to DWDM ITU channel 345
         in the 50 GHz grid.

         A value of zero(0) can be specified only on an administratively
         disabled port; to enable the port, the tnPortDwdmLaserChannel must be
         changed to a valid DWDM ITU channel number in either the 50GHz, or
         100GHz grid.
             Range    ITU Grid
             -------- ----------------------
             17-61    100 GHz Grid
             170-610  50 GHz Grid"
    DEFVAL { 0 }
    ::= { tnPortEntry 68 }

tnPortOtuCapable               OBJECT-TYPE
    SYNTAX      TruthValue
    MAX-ACCESS  read-only
    STATUS      current
    DESCRIPTION
        "The value of tnPortOtuCapable indicates whether or not the physical
         port supports the Optical Transport Unit (OTU) encapsulation."
    ::= { tnPortEntry 69 }

tnPortHoldTimeUnits             OBJECT-TYPE
    SYNTAX      INTEGER {
                    seconds (0),
                    centiseconds (1)
                }
    MAX-ACCESS  read-write
    STATUS      current
    DESCRIPTION
        "The value of tnPortHoldTimeUnits specifies the measurable units of
         tnPortHoldTimeDown and tnPortHoldTimeUp."
    DEFVAL { seconds }
    ::= { tnPortEntry 70 }

tnPortLinkLengthInfo           OBJECT-TYPE
    SYNTAX      OCTET STRING (SIZE (6))
    MAX-ACCESS  read-only
    STATUS      current
    DESCRIPTION
        "The value of tnPortLinkLengthInfo indicates the link length info
         stored in SFP and XFP EEPROMs.

         tnPortLinkLengthInfo is applicable only when tnPortSFPEquipped is
         'true'; otherwise, all 6 bytes will have a value of '0'.

         See SFF Committee documents for details on the representation of
         the values in each byte. For SFP EEPROMs, the 6 bytes are bytes 14 to
         19 of the A0 bank inclusive, described in SFF Committee document
         SFF-8472. For XFP EEPROMs, the first 5 bytes are bytes 142 to 146 of
         the 01 bank inclusive, described in SFF Committee document INF-8077i.
         For XFP EEPROMs, byte 6 will have a value of '0'."
    REFERENCE
        "SFF Committee, SFF-8472 Specification for Diagnostic Monitoring
         Interface for Optical Transceivers, Rev 11.0, September 14, 2010

         SFF Committee, INF-8077i 10 Gigabit Small Form Factor Pluggable
         Module, Rev 4.5, August 31, 2005"
    ::= { tnPortEntry 71 }

tnPortSFPNumLanes              OBJECT-TYPE
    SYNTAX      Unsigned32
    MAX-ACCESS  read-only
    STATUS      current
    DESCRIPTION
        "The value of tnPortSFPNumLanes indicates the total number of lanes
         supported by the CSFP/QSFP.  If tnPortSFPEquipped is false, this
         object will have a value of '0'."
    ::= { tnPortEntry 72 }

tnPortPhysStateChangeCount     OBJECT-TYPE
    SYNTAX      Counter32
    MAX-ACCESS  read-only
    STATUS      current
    DESCRIPTION
        "The value of tnPortPhysStateChangeCount indicates the number of times
         a physical port state has changed from 'linkDown (3)' to either
         'linkUp (4)' or 'up (5)' and from either 'linkUp (4)' or 'up (5)' to
         'linkDown (3)'.  The count does not include transitions between
         'linkUp (4)' and 'up (5)'.

         This counter is applicable to physical Ethernet ports only. All other
         ports maintain a count of 0.

         This object is automatically reset to zero, once the port enters the
         'ghost (2)' state.  To reset this object manually, one may use the
         tnClearTable entry whose tnClearName value is
         'clearPortPhysStateChangeCount' by specifying the tnClearParams value
         with 'port-id=<ifIndex>'."
    ::= { tnPortEntry 73 }

tnPortPacketSwitchId           OBJECT-TYPE
    SYNTAX      Unsigned32
    MAX-ACCESS  read-only
    STATUS      current
    DESCRIPTION
        "The value of tnPortPacketSwitchId indicates the packetswitch id that
         this port belongs to.  For PSS cards 11OPE8, 11QCE12X, 11QPE24,
         which are not supported by packetswitch, the value returned will be
         zero.  If a packetswitch supported card (eg 12CE120) has not been
         provisioned in a packetswitch, the id will also be zero."
    ::= { tnPortEntry 74 }

tnPortOtnSignalDegrade        OBJECT-TYPE
    SYNTAX      TmnxEnabledDisabled
    MAX-ACCESS  read-write
    STATUS      current
    DESCRIPTION
        "The value of tnPortOtnSd specifies whether to enable or disable the
         ODUk/OTUk (G.709) Signal Degrade defect to cause the port to be
         operationally down. All consequent actions of a port operational down
         status are applicable to the higher layers configured on the port.
         These include but not limited to ERP switching, MPLS-TP LSP switching,
         OAM, LAG, services etc."
    DEFVAL { disabled }
    ::= { tnPortEntry 75 }

--
--  Port Diagnostic Table
--
tnPortTestTable OBJECT-TYPE
    SYNTAX  SEQUENCE OF TmnxPortTestEntry
    MAX-ACCESS  not-accessible
    STATUS      current
    DESCRIPTION
         "The tnPortTestTable has an entry for each port on each IOM
         card in each chassis in the TMNX system."
    ::= { tnPortObjs 3 }

tnPortTestEntry       OBJECT-TYPE
    SYNTAX      TmnxPortTestEntry
    MAX-ACCESS  not-accessible
    STATUS      current
    DESCRIPTION
        "Each row entry represents a port on a IOM card in a
         chassis in the system.  Entries cannot be created and
         deleted via SNMP SET operations."
    AUGMENTS { tnPortEntry }
    ::= { tnPortTestTable 1 }

TmnxPortTestEntry ::=
    SEQUENCE {
        tnPortTestState           INTEGER,
        tnPortTestMode            INTEGER,
        tnPortTestParameter       Unsigned32,
        tnPortTestLastResult      INTEGER,
        tnPortTestStartTime       DateAndTime,
        tnPortTestEndTime         DateAndTime,
        tnPortTestDuration        Integer32,
        tnPortTestAction          INTEGER
    }

tnPortTestState   OBJECT-TYPE
    SYNTAX      INTEGER {
                    notInTest (1),
                    inTest (2)
                }
    MAX-ACCESS  read-only
    STATUS      current
    DESCRIPTION
        "The current testing status of this port."
    ::= { tnPortTestEntry 1 }

tnPortTestMode    OBJECT-TYPE
    SYNTAX      INTEGER {
                    notApplicable(0),
                    loopback1 (1),
                    loopback2 (2),
                    loopback3 (3),
                    singalInsertion (4)
                }
    MAX-ACCESS  read-write
    STATUS      current
    DESCRIPTION
        "The type of test to be executed on this port."
    ::= { tnPortTestEntry 2 }

tnPortTestParameter       OBJECT-TYPE
    SYNTAX      Unsigned32
    MAX-ACCESS  read-write
    STATUS      current
    DESCRIPTION
        "A parameter to be passed to the test program."
    ::= { tnPortTestEntry 3 }

tnPortTestLastResult      OBJECT-TYPE
    SYNTAX      INTEGER {
                    notApplicable(0),
                    success (1),
                    failure (2),
                    timeout (3)
                }
    MAX-ACCESS  read-only
    STATUS      current
    DESCRIPTION
        "The status of the last test executed on this port."
    ::= { tnPortTestEntry 4 }

tnPortTestStartTime       OBJECT-TYPE
    SYNTAX      DateAndTime
    MAX-ACCESS  read-only
    STATUS      current
    DESCRIPTION
        "The date and time the test started on this port.
         Returns 0 if tnPortTestState is notInTest."
    ::= { tnPortTestEntry 5 }

tnPortTestEndTime OBJECT-TYPE
    SYNTAX      DateAndTime
    MAX-ACCESS  read-only
    STATUS      current
    DESCRIPTION
        "The date and time the last test completed.  Returns 0
         if a test is in progress or no tests have yet to be run on
         this port."
    ::= { tnPortTestEntry 6 }

tnPortTestDuration        OBJECT-TYPE
    SYNTAX      Integer32 (0..256)
    MAX-ACCESS  read-write
    STATUS      current
    DESCRIPTION
        "The number of seconds the port test is anticipated to last."
    ::= { tnPortTestEntry 7 }

tnPortTestAction  OBJECT-TYPE
    SYNTAX      INTEGER {
                    none (1),
                    startTest (2),
                    stopTest (3)
                }
    MAX-ACCESS  read-write
    STATUS      current
    DESCRIPTION
        "The operator sets this variable to perform the appropriate
         type of testing."
    ::= { tnPortTestEntry 8 }

--
--  Ethernet Ports Table
--
tnPortEtherTable OBJECT-TYPE
    SYNTAX  SEQUENCE OF TmnxPortEtherEntry
    MAX-ACCESS  not-accessible
    STATUS      current
    DESCRIPTION
        "The tnPortEtherTable has an entry for each Ethernet
         (faste, gige, xcme or xgige) port on each IOM card in each chassis
         in the TMNX system."
    ::= { tnPortObjs 4 }

tnPortEtherEntry       OBJECT-TYPE
    SYNTAX  TmnxPortEtherEntry
    MAX-ACCESS      not-accessible
    STATUS  current
    DESCRIPTION
        "Each row entry represents an Ethernet port on a IOM card in a
         chassis in the system.  Entries cannot be created and
         deleted via SNMP SET operations.  Before an IOM card entry
         can be deleted from the tmnxMDATable, its supported
         tnPortEntry and tnPortEtherEntry rows must be in the proper
         state for removal.  The tnPortEtherEntry contains attributes
         that are unique to the Ethernet TmnxPortType."
    INDEX   { tnPortPortID }
    ::= { tnPortEtherTable 1 }

TmnxPortEtherEntry ::=
    SEQUENCE {
        tnPortEtherMTU                            Unsigned32,
        tnPortEtherDuplex                         INTEGER,
        tnPortEtherSpeed                          INTEGER,
        tnPortEtherAutoNegotiate                  INTEGER,
        tnPortEtherOperDuplex                     INTEGER,
        tnPortEtherOperSpeed                      Unsigned32,
        tnPortEtherAcctPolicyId                   Unsigned32,
        tnPortEtherCollectStats                   TruthValue,
        tnPortEtherMDIMDIX                        INTEGER,
        tnPortEtherXGigMode                       INTEGER,
        tnPortEtherEgressRate                     Integer32,
        tnPortEtherDot1qEtype                     Unsigned32,
        tnPortEtherQinqEtype                      Unsigned32,
        tnPortEtherIngressRate                    Integer32,
        tnPortEtherReportAlarm                    TmnxPortEtherReportStatus,
        tnPortEtherReportAlarmStatus              TmnxPortEtherReportStatus,
        tnPortEtherPkts1519toMax                  Counter32,
        tnPortEtherHCOverPkts1519toMax            Counter32,
        tnPortEtherHCPkts1519toMax                Counter64,
        tnPortEtherLacpTunnel                     TruthValue,
        tnPortEtherDownWhenLoopedEnabled          TruthValue,
        tnPortEtherDownWhenLoopedKeepAlive        Unsigned32,
        tnPortEtherDownWhenLoopedRetry            Unsigned32,
        tnPortEtherDownWhenLoopedState            INTEGER,
        tnPortEtherPBBEtype                       Unsigned32,
--        tnPortEtherReasonDownFlags                BITS,
        tnPortEtherSingleFiber                    TruthValue,
        tnPortEtherSSM                            TruthValue,
        tnPortEtherDWLUseBroadcastAddr            TruthValue,
        tnPortEtherSSMCodeType                    INTEGER,
        tnPortEtherSSMTxDus                       TruthValue,
        tnPortEtherSSMRxEsmc                      Unsigned32,
        tnPortEtherSSMTxQualityLevel              INTEGER,
        tnPortEtherQinqEtypelink                  Unsigned32,
        tnPortEtherOperEgressRate                 Integer32
    }

tnPortEtherMTU  OBJECT-TYPE
    SYNTAX      Unsigned32 (0|512..9612)
    UNITS       "bytes"
    MAX-ACCESS  read-write
    STATUS      current
    DESCRIPTION
        "The size of the largest packet which can be sent/received
         on the Ethernet physical interface, specified in octets.  For
         interfaces that are used for transmitting network datagrams,
         this is the size of the largest network datagram that can be
         sent on the interface.

         Setting tnPortEtherMTU to a value of zero (0), causes the agent
         to recalculate the default MTU size which can vary based on the
         current setting of tnPortMode and tnPortEncapType variables.
         Some typical default values are:
                1514 with mode access and encap-type null
                1518 with mode access and encap-type dot1q
                1518 with mode access and encap-type mpls
                9198 with mode network
        "
    ::= { tnPortEtherEntry 1 }

tnPortEtherDuplex OBJECT-TYPE
    SYNTAX      INTEGER {
                    notApplicable (0),
                    fullDuplex (1),
                    halfDuplex (2)
                }
    MAX-ACCESS  read-write
    STATUS      current
    DESCRIPTION
        "The tnPortEtherDuplex variable specifies the duplex mode used by
         the Ethernet interface if tnPortEtherAutoNegotiate has a value of
         'false' or 'limited'. If tnPortEtherAutoNegotiate has a value of
         'true', the link parameters are negotiated with the far end and
         the tnPortEtherDuplex variable is ignored. A value of 'fullDuplex'
         sets the link to full duplex mode.  A value of 'halfDuplex' sets
         the link to half duplex mode. tnPortEtherDuplex is only valid on
         Ethernet interfaces that support multiple duplex modes."
    DEFVAL { fullDuplex }
    ::= { tnPortEtherEntry 2 }

tnPortEtherSpeed  OBJECT-TYPE
    SYNTAX      INTEGER {
                    notApplicable (0),
                    speed10 (1),
                    speed100 (2),
                    speed1000 (3),
                    speed10000 (4),
                    speed40000 (5),
                    speed100000 (6),
                    oduflex (7),
                    speed2457 (8),   -- CPRI3
                    speed4915 (9),   -- CPRI5
                    spped6114 (10),  -- CPRI6/OBSAI8
                    speed9830 (11),  -- CPRI7
                    speed10137 (12), -- CPRI8
                    speed24330 (13), -- CPRI10
                    speed3072 (14),  -- CPRI4/OBSAI4
                    speed25000 (15)  -- 25G
                }
    MAX-ACCESS  read-write
    STATUS      current
    DESCRIPTION
        "The tnPortEtherSpeed variable specifies the link speed of the
         Ethernet interface if tnPortEtherAutoNegotiate has a value of
         'false' or 'limited'.  If tnPortEtherAutoNegotiate has a value of
         'true', the link parameters are negotiated with the far end and
         the tnPortEtherSpeed variable is ignored. A value of 'speed10'
         sets the link to 10 mbps.  A value of 'speed100' sets the link to
         100 mbps.  A value of 'speed1000' sets the link to 1000 mbps (1 gbps).
         tnPortEtherSpeed is only valid on Ethernet interfaces that support
         multiple link speeds."
    ::= { tnPortEtherEntry 3 }

tnPortEtherAutoNegotiate   OBJECT-TYPE
    SYNTAX      INTEGER {
                    notApplicable (0),
                    true (1),
                    false (2),
                    limited (3)
                }
    MAX-ACCESS  read-write
    STATUS      current
    DESCRIPTION
        "When the value of tnPortEtherAutoNegotiate is 'true', the Ethernet
         interface will automatically negotiate link parameters with the far
         end (including speed and duplex), and will advertise all speeds and
         duplex modes supported by the interface. When the value of
         tnPortEtherAutoNegotiate is 'limited', the Ethernet interface will
         automatically negotiate link parameters with the far end, but will
         only advertise the speed and duplex mode specified by tnPortEtherSpeed
         and tnPortEtherDuplex. If tnPortEtherAutoNegotiate is 'false',
         the Ethernet interface won't negotiate link parameters with the far
         end and will instead force the speed and duplex mode to the values specified
         by tnPortEtherSpeed and tnPortEtherDuplex respectively."
    DEFVAL { true }
    ::= { tnPortEtherEntry 4 }

tnPortEtherOperDuplex OBJECT-TYPE
    SYNTAX      INTEGER {
                    notApplicable (0),
                    fullDuplex (1),
                    halfDuplex (2)
                }
    MAX-ACCESS  read-only
    STATUS      current
    DESCRIPTION
        "The tnPortEtherOperDuplex variable indicates the operational duplex
         mode of the Ethernet interface. A value of 'fullDuplex' indicates that
         the link is in full duplex mode.  A value of 'halfDuplex' indicates
         that the link is in half duplex mode. tnPortEtherOperDuplex is only
         valid if tnPortClass is 'faste' or 'xcme'."
    ::= { tnPortEtherEntry 5 }

tnPortEtherOperSpeed  OBJECT-TYPE
    SYNTAX      Unsigned32
    UNITS       "mega-bits per second"
    MAX-ACCESS  read-only
    STATUS      current
    DESCRIPTION
        "The tnPortEtherOperSpeed variable indicates the operational speed
         of the Ethernet interface in mega-bits per second (mbps).  If the value of
         tnPortEtherAutoNegotiate is 'true', the link autonegotiates the link
         parameters with the far end side.  The value of tnPortEtherOperSpeed is
         only valid if tnPortClass is one of the Ethernet classes."
    ::= { tnPortEtherEntry 6 }

tnPortEtherAcctPolicyId  OBJECT-TYPE
    SYNTAX      Unsigned32 (0..99)
    MAX-ACCESS  read-write
    STATUS      current
    DESCRIPTION
        "The value of the accounting policy must be defined prior to associating
         the policy with the ethernet port. Accounting policies can only be
         associated with network ports.
         A non-zero value indicates the tmnxLogApPolicyId index identifying the
         policy entry in the tmnxLogApTable from the TIMETRA-LOG-MIB which is
         associated with this port.  A zero value indicates that there is no
         accounting policy associated with this port"
    DEFVAL { 0 }
    ::= { tnPortEtherEntry 7 }

tnPortEtherCollectStats        OBJECT-TYPE
    SYNTAX      TruthValue
    MAX-ACCESS  read-write
    STATUS      current
    DESCRIPTION
        "Enable/disable the collection of accounting and statistical data
         for the network ethernet port. When applying accounting policies the
         data by default will be collected in the appropriate records and
         written to the designated billing file.
         When the value is set to false, the statistics are still accumulated
         by the IOM cards, however, the CPU will not obtain the results and
         write them to the billing file."
    DEFVAL { true }
    ::= { tnPortEtherEntry 8 }

tnPortEtherMDIMDIX        OBJECT-TYPE
    SYNTAX      INTEGER {
                    unknown (0),
                    mdi (1),
                    mdix (2)
                }
    MAX-ACCESS  read-only
    STATUS      current
    DESCRIPTION
        "The tnPortEtherMDIMDIX variable indicates whether the Ethernet
         interface is of type 'mdi' (Media Dependent Interface) or
         'mdix' (Media Dependent Interface with crossover). If the agent
         cannot identify the type of Ethernet interface the value
         'unknown (0)' is indicated. tnPortEtherMDIMDIX is only valid if
         tnPortClass is 'faste' or 'xcme'."
    ::= { tnPortEtherEntry 9 }

tnPortEtherXGigMode        OBJECT-TYPE
    SYNTAX      INTEGER {
                    notApplicable (0),
                    lan (1),
                    wan (2)
                }
    MAX-ACCESS  read-write
    STATUS      current
    DESCRIPTION
        "The tnPortEtherXGigMode variable specifies whether the Ethernet
         interface is in LAN or WAN mode. tnPortEtherXGigMode must be
         'notApplicable' if tnPortClass is not 'xgige'."
    DEFVAL { lan }
    ::= { tnPortEtherEntry 10 }

tnPortEtherEgressRate        OBJECT-TYPE
    SYNTAX      Integer32 (-1 | 1..100000000)
    MAX-ACCESS  read-write
    STATUS      current
    DESCRIPTION
        "The tnPortEtherEgressRate variable specifies the maximum egress
         bandwidth (in kilobits per second) that the Ethernet interface
         can generate. A value of -1 means that the limit is the actual
         physical limit. If the provisioned sub-rate bandwidth is larger than
         the actual physical bandwidth of the interface, the latter applies."
    DEFVAL { -1 }
    ::= { tnPortEtherEntry 11 }

tnPortEtherDot1qEtype        OBJECT-TYPE
    SYNTAX      Unsigned32 ('0600'H..'ffff'H)
    MAX-ACCESS  read-write
    STATUS      current
    DESCRIPTION
        "The tnPortEtherDot1qEtype variable indicates the ethertype expected
         when the port's encapsulation type is dot1qEncap."
    DEFVAL { '8100'H }
    ::= { tnPortEtherEntry 12 }

tnPortEtherQinqEtype         OBJECT-TYPE
    SYNTAX      Unsigned32 ('0600'H..'ffff'H)
    MAX-ACCESS  read-write
    STATUS      current
    DESCRIPTION
        "The tnPortEtherQinqEtype variable indicates the ethertype expected
         when the port's encapsulation type is qinqEncap."
    DEFVAL { '8100'H }
    ::= { tnPortEtherEntry 13 }

tnPortEtherIngressRate        OBJECT-TYPE
    SYNTAX      Integer32 (-1 | 1..10000)
    UNITS       "mega-bits per second"
    MAX-ACCESS  read-write
    STATUS      current
    DESCRIPTION
        "The tnPortEtherIngressRate variable specifies the maximum ingress
         bandwidth (in mega-bits per second) that the Ethernet interface
         can receive. A value of -1 means that the limit is the actual
         physical limit. If the provisioned sub-rate bandwidth is larger than
         the actual physical bandwidth of the interface, the latter applies."
    DEFVAL { -1 }
    ::= { tnPortEtherEntry 14 }

tnPortEtherReportAlarm  OBJECT-TYPE
    SYNTAX          TmnxPortEtherReportStatus
    MAX-ACCESS      read-write
    STATUS          current
    DESCRIPTION
        "The value of tnPortEtherReportAlarm determines when and if to
         generate tnEqPortEtherAlarm and tnEqPortEtherAlarmClear."
    DEFVAL { { remoteFault, localFault } }
    ::= { tnPortEtherEntry 15 }

tnPortEtherReportAlarmStatus  OBJECT-TYPE
    SYNTAX          TmnxPortEtherReportStatus
    MAX-ACCESS      read-only
    STATUS          current
    DESCRIPTION
        "The value of tnPortEtherReportAlarmStatus indicates the alarms on
         this port."
    ::= { tnPortEtherEntry 16 }

tnPortEtherPkts1519toMax   OBJECT-TYPE
    SYNTAX     Counter32
    UNITS      "Packets"
    MAX-ACCESS read-only
    STATUS     current
    DESCRIPTION
        "The total number of packets received that were longer than 1518 octets
         but less than the maximum frame size for the particular medium, usually
         12287 octets (excluding framing bits, but including FCS octets) and were
         otherwise well formed."
    ::= { tnPortEtherEntry 17 }

tnPortEtherHCOverPkts1519toMax OBJECT-TYPE
    SYNTAX     Counter32
    UNITS      "Packets"
    MAX-ACCESS read-only
    STATUS     current
    DESCRIPTION
        "The number of times the associated tnPortEtherPkts1519toMax
        counter has overflowed."
    ::= { tnPortEtherEntry 18 }

tnPortEtherHCPkts1519toMax OBJECT-TYPE
    SYNTAX     Counter64
    UNITS      "Packets"
    MAX-ACCESS read-only
    STATUS     current
    DESCRIPTION
        "The total number of packets (including bad packets) received that were
         between 1519 octets in length and the maximum frame size, usually 12287
         octets inclusive (excluding framing bits but including FCS octets).

         The lower 32-bits of this 64-bit counter will equal the value of
         tnPortEtherHCPkts1519toMax.  The high 32-bits of this counter will
         equal the value of tnPortEtherHCOverPkts1519toMax."
    ::= { tnPortEtherEntry 19 }

tnPortEtherLacpTunnel          OBJECT-TYPE
    SYNTAX      TruthValue
    MAX-ACCESS  read-write
    STATUS      current
    DESCRIPTION
        "The value of tnPortEtherLacpTunnel specifies whether the LACP
         packet tunneling for the ethernet port is enabled or disabled.
         When tunneling is enabled, the port will not process any LACP
         packets but will tunnel them through instead. Also, the port
         cannot be added as a member to a LAG group, and vice versa."
    DEFVAL { false }
    ::= { tnPortEtherEntry 20 }

tnPortEtherDownWhenLoopedEnabled          OBJECT-TYPE
    SYNTAX      TruthValue
    MAX-ACCESS  read-write
    STATUS      current
    DESCRIPTION
        "The value of tnPortEtherDownWhenLoopedEnabled specifies whether
         physical loop detection for the Ethernet port is enabled or
         disabled.  When enabled, the port will periodically send out
         keep-alive PDUs with an EtherType of 0x9000.  If the port
         receives a keep-alive that it transmitted, tnPortState will be
         set to 'linkUp' if it was previously 'up'. The port will not move
         back to tnPortState 'up' for a period of time defined by
         tnPortEtherDownWhenLoopedRetry, but will continue to periodically
         send out keep-alive PDUs.  Every time the port receives a keep alive
         it sent while a loop has been detected, it will reset the time
         period that it will remain down as defined by
         tnPortEtherDownWhenLoopedRetry."
    DEFVAL { false }
    ::= { tnPortEtherEntry 21 }

tnPortEtherDownWhenLoopedKeepAlive         OBJECT-TYPE
    SYNTAX      Unsigned32 (1..120)
    UNITS       "seconds"
    MAX-ACCESS  read-write
    STATUS      current
    DESCRIPTION
        "The tnPortEtherDownWhenLoopedKeepAlive variable specifies the
         number of seconds between each keep alive PDU transmission."
    DEFVAL { 10 }
    ::= { tnPortEtherEntry 22 }

tnPortEtherDownWhenLoopedRetry         OBJECT-TYPE
    SYNTAX      Unsigned32 (0|10..160)
    UNITS       "seconds"
    MAX-ACCESS  read-write
    STATUS      current
    DESCRIPTION
        "The tnPortEtherDownWhenLoopedRetry variable specifies the minimum
         number of seconds the port should wait after detecting a loop before
         tnPortState can be set to 'up'.  A value of 0 specifies the the
         port should not set tnPortState to 'up' until the user
         administratively disables and re-enables the port by setting
         tnPortAdminStatus to 'outOfService' and then to 'inService'."
    DEFVAL { 120 }
    ::= { tnPortEtherEntry 23 }

tnPortEtherDownWhenLoopedState          OBJECT-TYPE
    SYNTAX      INTEGER {
                    noLoopDetected (1),
                    loopDetected (2)
                }
    MAX-ACCESS  read-only
    STATUS      current
    DESCRIPTION
        "The value of tnPortEtherDownWhenLoopedState indicates whether
         a physical loop has been detected on the port or not.  If
         tnPortEtherDownWhenLoopedEnabled is set to 'false', this value
         will be 'noLoopDetected'."
    ::= { tnPortEtherEntry 24 }

tnPortEtherPBBEtype        OBJECT-TYPE
    SYNTAX      Unsigned32 ('0600'H..'ffff'H)
    MAX-ACCESS  read-write
    STATUS      current
    DESCRIPTION
        "The tnPortEtherPBBEtype variable indicates the Ethertype expected
        for Provider Backbone Bridging Frames."
    DEFVAL { '88E7'H }
    ::= { tnPortEtherEntry 25 }

-- tnPortEtherReasonDownFlags OBJECT-TYPE
--     SYNTAX      BITS {
--                    unknown     (0),
--                    linklossFwd (1),
--                    lagMemberPortStandby (2)
--                 }
--     MAX-ACCESS  read-only
--     STATUS      obsolete
--     DESCRIPTION
--         "The tnPortEtherReasonDownFlags indicates why an ethernet port may
--         be in the operationally 'down' state. The following reasons are
--         detected through this object:
--                unknown(0)              - Unspecified (or unknown)
--                linklossFwd(1)          - A sap using this port has the object
--                                          'sapEthernetLLFOperStatus' set to
--                                          'fault'
--                lagMemberPortStandby(2) - A lag using this port as a member
--                                          port has set the member port to
--                                          'standby' while configured to keep
--                                          standby member ports down."
--     ::= { tnPortEtherEntry 26 }

tnPortEtherSingleFiber     OBJECT-TYPE
    SYNTAX      TruthValue
    MAX-ACCESS  read-write
    STATUS      current
    DESCRIPTION
        "tnPortEtherSingleFiber is used to enable/disable packet gathering and
         redirection of IP packets from a single fiber on RX port of the
         Ethernet interface and redistribute packets to other interfaces
         through either state routes or policy-based forwarding."
    DEFVAL { false }
    ::= { tnPortEtherEntry 27 }

tnPortEtherSSM                 OBJECT-TYPE
    SYNTAX      TruthValue
    MAX-ACCESS  read-write
    STATUS      current
    DESCRIPTION
        "tnPortEtherSSM specifies whether or not synchronous
         status messages (SSM) are enabled on the ethernet port."
    DEFVAL { false }
    ::= { tnPortEtherEntry 28 }

tnPortEtherDWLUseBroadcastAddr OBJECT-TYPE
    SYNTAX      TruthValue
    MAX-ACCESS  read-write
    STATUS      current
    DESCRIPTION
        "tnPortEtherDWLUseBroadcastAddr specifies whether or not the
         Down When Looped destination MAC address is the broadcast address,
         'true (1)', or the local port mac address, as specified in
         tnPortMacAddress, 'false (2)'."
    DEFVAL { false }
    ::= { tnPortEtherEntry 29 }

tnPortEtherSSMCodeType          OBJECT-TYPE
    SYNTAX      INTEGER {
                    unknown (1),
                    sonet   (2),
                    sdh     (3)
                }
    MAX-ACCESS  read-write
    STATUS      current
    DESCRIPTION
        "The value of tnPortEtherSSMCodeType specifies the code-type
         used by the Synchronous Status Message (SSM) channel."
    DEFVAL      { sdh }
    ::= { tnPortEtherEntry 30 }

tnPortEtherSSMTxDus            OBJECT-TYPE
    SYNTAX      TruthValue
    MAX-ACCESS  read-write
    STATUS      current
    DESCRIPTION
        "The value of tnPortEtherSSMTxDus specifies whether or not the
         value 0xF (dus/dnu) is forced in the Synchronous Status Message (SSM)
         channel."
    DEFVAL      { false }
    ::= { tnPortEtherEntry 31 }

tnPortEtherSSMRxEsmc           OBJECT-TYPE
    SYNTAX      Unsigned32 (0..255)
    MAX-ACCESS  read-only
    STATUS      current
    DESCRIPTION
        "The value of tnPortEtherSSMRxEsmc indicates the SSM code received on
         the Ethernet Synchronization Messaging Channel of the Ethernet port.

         The value returned for this object is only meaningful if
         tnPortEtherSSM is 'true', and tnPortSSMRxQualityLevel is not
         'failed'."
    REFERENCE
        "ITU-T Recommendation G.8264, October 2008."
    ::= { tnPortEtherEntry 32 }

tnPortEtherSSMTxQualityLevel   OBJECT-TYPE
    SYNTAX      INTEGER {
                    reserved0  (0),
                    prs        (1),
                    stu        (2),
                    st2        (3),
                    tnc        (4),
                    st3e       (5),
                    reserved6  (6),
                    smc        (7),
                    reserved8  (8),
                    dus        (9),
                    prc        (10),
                    ssua       (11),
                    ssub       (12),
                    reserved13 (13),
                    dnu        (14),
                    reserved15 (15),
                    pno        (16),
                    eec1       (17),
                    eec2       (18),
                    reserved19 (19)
                }
    MAX-ACCESS  read-only
    STATUS      current
    DESCRIPTION
        "The value of tnPortEtherSSMTxQualityLevel indicates the quality
         level transmitted in the Ethernet Synchronization Messaging Channel."
    REFERENCE
        "ITU-T Recommendation G.8264, October 2008."
    ::= { tnPortEtherEntry 33 }

tnPortEtherQinqEtypelink       OBJECT-TYPE
    SYNTAX      Unsigned32
    MAX-ACCESS  read-write
    STATUS      current
    DESCRIPTION
        "Ethertype profile ID which is referenced to tnCardEtherTypeProfileTable.
         If tnPortEtherQinqEtypelink is zero, it indicates no associations.
         If there is an association, tnPortEtherQinqEtype shall equal to tnCardEthertypeQinQEtype,
         it means that the configuration per card will override the configuration per port.
         The profile ID 1 is associated all qinq port if no other profile is explicitly specified
        "
    ::= { tnPortEtherEntry 34 }

tnPortEtherOperEgressRate        OBJECT-TYPE
    SYNTAX      Integer32 (-1 | 1..100000000)
    MAX-ACCESS  read-only
    STATUS      current
    DESCRIPTION
        "The tnPortEtherOperEgressRate variable specifies the operational egress
         bandwidth (in kilobits per second) that the Ethernet interface
         generates. A value of -1 means that the limit is the actual
         physical limit."
    DEFVAL { -1 }
    ::= { tnPortEtherEntry 35 }

--
--  Sonet Ports Table
--
-- tnSonetTable OBJECT-TYPE
--     SYNTAX  SEQUENCE OF TmnxSonetEntry
--     MAX-ACCESS  not-accessible
--     STATUS      current
--     DESCRIPTION
--         "The tnSonetTable has an entry for each packet over Sonet
--          port on each IOM card in each chassis in the TMNX system."
--     ::= { tnPortObjs 5 }
--
-- tnSonetEntry       OBJECT-TYPE
--     SYNTAX      TmnxSonetEntry
--     MAX-ACCESS  not-accessible
--     STATUS      current
--     DESCRIPTION
--         "Each row entry represents a packet over Sonet port on a
--          IOM card in a chassis in the system.  Entries cannot be
--          created and deleted via SNMP SET operations.  Before an IOM
--          tmnxMDAEntry can be deleted from the tmnxMDATable, its
--          supported tnPortEntry rows must be in the proper state for
--          removal.  The tnSonetEntry contains attributes that are
--          unique to the 'sonet' TmnxPortType.  It also contains attributes
--          that are common to all sonet paths configured on a sonet port.
--          The tnPortPortID for a sonet port includes a sonet path number
--          in the lower bits.   If the sonet path number is zero, '0', it
--          represents a single (clear) sonet path on the port that uses
--          the full bandwidth of the sonet port.  All entries in this table
--          have the sonet path number part of their tnPortPortID index
--          value set to zero."
--     INDEX   { tnPortPortID }
--     ::= { tnSonetTable 1 }
--
-- TmnxSonetEntry ::=
--     SEQUENCE {
--         tnSonetSpeed                INTEGER,
--         tnSonetClockSource          INTEGER,
--         tnSonetFraming              INTEGER,
--         tnSonetReportAlarm          BITS,
--         tnSonetBerSdThreshold       Unsigned32,
--         tnSonetBerSfThreshold       Unsigned32,
-- ==        tnSonetAps                  TruthValue,
-- ==        tnSonetApsAdminStatus       TmnxPortAdminStatus,
-- ==        tnSonetApsOperStatus        TmnxPortOperStatus,
-- ==        tnSonetApsAuthKey           OCTET STRING,
-- ==        tnSonetApsNeighborAddr      IpAddress,
-- ==        tnSonetApsAdvertiseInterval TimeInterval,
-- ==        tnSonetApsAdvertiseTimeLeft TimeInterval,
-- ==        tnSonetApsHoldTime          TimeInterval,
-- ==        tnSonetApsHoldTimeLeft      TimeInterval,
--         tnSonetLoopback             INTEGER,
--         tnSonetReportAlarmStatus    BITS,
--         tnSonetSectionTraceMode     INTEGER,
--         tnSonetJ0String             OCTET STRING,
--         tnSonetMonS1Byte            Unsigned32,
--         tnSonetMonJ0String          OCTET STRING,
--         tnSonetMonK1Byte            Unsigned32,
--         tnSonetMonK2Byte            Unsigned32,
--         tnSonetSingleFiber          TruthValue,
--         tnSonetHoldTimeUp           Unsigned32,
--         tnSonetHoldTimeDown         Unsigned32,
--         tnSonetSuppressLoOrderAlarm TruthValue
--
--     }
--
-- tnSonetSpeed    OBJECT-TYPE
--     SYNTAX      INTEGER {
--                     oc3 (1),
--                     oc12 (2),
--                     oc48 (3),
--                     oc192 (4),
--                     oc768 (5),
--                     oc1 (6)
--                 }
--     MAX-ACCESS  read-write
--     STATUS      current
--     DESCRIPTION
--         "The rate of this optical facility."
--     ::= { tnSonetEntry 1 }
--
-- tnSonetClockSource  OBJECT-TYPE
--     SYNTAX      INTEGER {
--                     loopTimed (1),
--                     nodeTimed (2)
--                 }
--     MAX-ACCESS  read-write
--     STATUS      current
--     DESCRIPTION
--         "tnSonetClockSource configures the clock for transmitted data from
--          either the internal clock ('nodeTimed') or from a clock recovered
--          from the line's receive data stream ('loopTimed')."
--     DEFVAL { loopTimed }
--     ::= { tnSonetEntry 2 }
--
-- tnSonetFraming      OBJECT-TYPE
--     SYNTAX      INTEGER {
--                     unknown (1),
--                     sonet (2),
--                     sdh (3)
--                 }
--     MAX-ACCESS  read-write
--     STATUS      current
--     DESCRIPTION
--         "The value of tnSonetFraming indicates the type of framing used
--          on this interface."
--     DEFVAL { sonet }
--     ::= { tnSonetEntry 3 }
--
-- tnSonetReportAlarm  OBJECT-TYPE
--     SYNTAX      BITS {
--                     notUsed (0),
--                     loc(1),
--                     lais(2),
--                     lrdi(3),
--                     ss1f(4),
--                     sb1err(5),
--                     lb2erSd(6),
--                     lb2erSf(7),
--                     slof(8),
--                     slos(9),
--                     stxptr(10),
--                     srxptr(11),
--                     lrei(12)
--                 }
--     MAX-ACCESS      read-write
--     STATUS          current
--     DESCRIPTION
--         "The value of tnSonetReportAlarm determines when and if to
--          generate tnEqPortSonetAlarm and tnEqPortSonetAlarmClear
--          notifications for this port:
--             loc(1)      Reports a loss of clock which causes the operational
--                         state of the port to be downed.  Set by default.
--             lais(2)     Reports line alarm indication signal errors. Not set
--                         by default.
--             lrdi(3)     Reports line remote defect initiation errors.  LRDIs
--                         are caused by remote LOF, LOC, and LOS.  Set by default.
--             ss1f(4)     Reports section synchronization failure as reported by
--                         the S1 byte.  Not set by default.
--             sb1err(5)   Reports section B1 errors.  Not set by default.
--             lb2erSd(6)  Reports line signal degradation BER errors.  Not set
--                         by default.
--             lb2erSf(7)  Reports line signal failure BER errors.  Set by default.
--             slof(8)     Reports section loss of frame errors.  Set by default
--             slos(9)     Reports section loss of signal errors. Set by default.
--             stxptr(10)  Reports a section synchronization error on the transmit
--                         side.  Indicates if there is a positive or negative
--                         justification count per channel.  Not set by default.
--             srxptr(11)  Reports a section synchronization error on the receive
--                         side.  Indicates if there is a positive or negative
--                         justification count per path.  Not set by default.
--             lrei(12)    Reports a line error condition raised by the remote
--                         as a result of B1 errors received from this node.
--                         Not set by default.
--         "
--     DEFVAL { {loc, lrdi, lb2erSf, slof, slos} }
--     ::= { tnSonetEntry 4 }
--
-- tnSonetBerSdThreshold       OBJECT-TYPE
--     SYNTAX      Unsigned32 (3..9)
--     MAX-ACCESS  read-write
--     STATUS      current
--     DESCRIPTION
--         "The value of tnSonetBerSdThreshold specifies a bit error rate (BER)
--          threshold used to determine when to send a tnEqPortSonetAlarm
--          notification for a BER SD failure and tnEqPortSonetAlarmClear
--          notification for a BER SD failure clear.  tnSonetBerSdThreshold is
--          the absolute value of the exponent of the rate expressed as 10e-n."
--     DEFVAL { 6 }
--     ::= { tnSonetEntry 5 }
--
-- tnSonetBerSfThreshold       OBJECT-TYPE
--     SYNTAX      Unsigned32 (3..6)
--     MAX-ACCESS  read-write
--     STATUS      current
--     DESCRIPTION
--         "The value of tnSonetBerSfThreshold specifies a bit error rate (BER)
--          threshold used to determine when to send a tnEqPortSonetAlarm
--          notification for a BER SF failure and tnEqPortSonetAlarmClear
--          notification for a BER SF failure clear.  tnSonetBerSdThreshold is
--          the absolute value of the exponent of the rate expressed as 10e-n."
--     DEFVAL { 3 }
--     ::= { tnSonetEntry 6 }
--
-- == tnSonetAps      OBJECT-TYPE
-- ==     SYNTAX      TruthValue
-- ==     MAX-ACCESS  read-write
-- ==     STATUS      obsolete
-- ==     DESCRIPTION
-- ==         "Automatic Protection Switching (APS) is supported on 7x50 systems
-- ==          by the APS-MIB and TIMETRA-APS-MIB."
-- ==     DEFVAL { false }
-- ==     ::= { tnSonetEntry 7 }
-- ==
-- == tnSonetApsAdminStatus   OBJECT-TYPE
-- ==     SYNTAX      TmnxPortAdminStatus
-- ==     MAX-ACCESS  read-write
-- ==     STATUS      obsolete
-- ==     DESCRIPTION
-- ==         "Automatic Protection Switching (APS) is supported on 7x50 systems
-- ==          by the APS-MIB and TIMETRA-APS-MIB."
-- ==     DEFVAL { inService }
-- ==     ::= { tnSonetEntry 8 }
-- ==
-- == tnSonetApsOperStatus    OBJECT-TYPE
-- ==     SYNTAX      TmnxPortOperStatus
-- ==     MAX-ACCESS  read-only
-- ==     STATUS      obsolete
-- ==     DESCRIPTION
-- ==         "Automatic Protection Switching (APS) is supported on 7x50 systems
-- ==          by the APS-MIB and TIMETRA-APS-MIB."
-- ==     ::= { tnSonetEntry 9 }
-- ==
-- == tnSonetApsAuthKey OBJECT-TYPE
-- ==     SYNTAX       OCTET STRING (SIZE (0..256))
-- ==     MAX-ACCESS   read-write
-- ==     STATUS       obsolete
-- ==     DESCRIPTION
-- ==         "Automatic Protection Switching (APS) is supported on 7x50 systems
-- ==          by the APS-MIB and TIMETRA-APS-MIB."
-- ==     DEFVAL { '0000000000000000'H }
-- ==     ::= { tnSonetEntry 10 }
-- ==
-- == tnSonetApsNeighborAddr      OBJECT-TYPE
-- ==     SYNTAX      IpAddress
-- ==     MAX-ACCESS  read-write
-- ==     STATUS      obsolete
-- ==     DESCRIPTION
-- ==         "Automatic Protection Switching (APS) is supported on 7x50 systems
-- ==          by the APS-MIB and TIMETRA-APS-MIB."
-- ==     DEFVAL { '00000000'H }
-- ==     ::= { tnSonetEntry 11 }
-- ==
-- == tnSonetApsAdvertiseInterval     OBJECT-TYPE
-- ==     SYNTAX      TimeInterval
-- ==     UNITS       "milliseconds"
-- ==     MAX-ACCESS  read-write
-- ==     STATUS      obsolete
-- ==      DESCRIPTION
-- ==         "Automatic Protection Switching (APS) is supported on 7x50 systems
-- ==          by the APS-MIB and TIMETRA-APS-MIB."
-- ==     DEFVAL { 1000 }
-- ==     ::= { tnSonetEntry 12 }
-- ==
-- == tnSonetApsAdvertiseTimeLeft  OBJECT-TYPE
-- ==     SYNTAX      TimeInterval
-- ==     UNITS       "milliseconds"
-- ==     MAX-ACCESS  read-only
-- ==     STATUS      obsolete
-- ==     DESCRIPTION
-- ==         "Automatic Protection Switching (APS) is supported on 7x50 systems
-- ==          by the APS-MIB and TIMETRA-APS-MIB."
-- ==     ::= { tnSonetEntry 13 }
-- ==
-- == tnSonetApsHoldTime      OBJECT-TYPE
-- ==     SYNTAX      TimeInterval
-- ==     UNITS       "milliseconds"
-- ==     MAX-ACCESS  read-write
-- ==     STATUS      obsolete
-- ==     DESCRIPTION
-- ==         "Automatic Protection Switching (APS) is supported on 7x50 systems
-- ==          by the APS-MIB and TIMETRA-APS-MIB."
-- ==     DEFVAL { 3000 }
-- ==     ::= { tnSonetEntry 14 }
-- ==
-- == tnSonetApsHoldTimeLeft   OBJECT-TYPE
-- ==     SYNTAX      TimeInterval
-- ==     UNITS       "milliseconds"
-- ==     MAX-ACCESS  read-only
-- ==     STATUS      obsolete
-- ==     DESCRIPTION
-- ==         "Automatic Protection Switching (APS) is supported on 7x50 systems
-- ==          by the APS-MIB and TIMETRA-APS-MIB."
-- ==    ::= { tnSonetEntry 15 }
--
-- tnSonetLoopback   OBJECT-TYPE
--     SYNTAX      INTEGER {
--                     none(0),
--                     line(1),
--                     internal(2)
--                 }
--     MAX-ACCESS  read-write
--     STATUS      current
--     DESCRIPTION
--         "Activate a loopback on the SONET port. The SONET port must be in a
--         shutdown state to activate any type of loopback."
--    ::= { tnSonetEntry 16 }
--
-- tnSonetReportAlarmStatus  OBJECT-TYPE
--     SYNTAX      BITS {
--                     notUsed (0),
--                     loc(1),
--                     lais(2),
--                     lrdi(3),
--                     ss1f(4),
--                     sb1err(5),
--                     lb2erSd(6),
--                     lb2erSf(7),
--                     slof(8),
--                     slos(9),
--                     stxptr(10),
--                     srxptr(11),
--                     lrei(12)
--                 }
--     MAX-ACCESS      read-only
--     STATUS          current
--     DESCRIPTION
--         "The bits in this object are used for indicating the alarms. The bits
--          are explained as follows:
--             loc(1)      Indicates a loss of clock which causes the operational
--                         state of the port to be downed.
--             lais(2)     Indicates line alarm indication signal errors.
--             lrdi(3)     Indicates line remote defect indication errors.  LRDIs
--                         are caused by remote LOF, LOC, and LOS.
--             ss1f(4)     Indicates section synchronization failure as reported by
--                         the S1 byte.
--             sb1err(5)   Indicates section B1 errors.
--             lb2erSd(6)  Indicates line signal degradation BER errors.
--             lb2erSf(7)  Indicates line signal failure BER errors.
--             slof(8)     Indicates section loss of frame errors.
--             slos(9)     Indicates section loss of signal errors.
--             stxptr(10)  Indicates a section synchronization error on the
--                         transmit side. Indicates if there is a positive or
--                         negative justification count per channel.
--             srxptr(11)  Indicates a section synchronization error on the receive
--                         side.  Indicates if there is a positive or negative
--                         justification count per sonet path.
--             lrei(12)    Indicates a line error condition raised by the remote
--                         as a result of B1 errors received from this node.
--         "
--     ::= { tnSonetEntry 17 }
--
-- tnSonetSectionTraceMode  OBJECT-TYPE
--     SYNTAX      INTEGER {
--                     increment-z0(1),
--                     byte(2),
--                     string(3)
--                 }
--     MAX-ACCESS  read-write
--     STATUS      current
--     DESCRIPTION
--         "The tnSonetSectionTraceMode variable along with the
--         tnSonetJ0String object determines the contents of
--         the section trace bytes (j0/z0) in the SONET Section Header. If the
--         mode is set to 'increment-z0', then the j0 byte is 0x01, and the
--         z0 byte increments. If the mode is set to 'byte', then the j0 byte is
--         the first octet of the tnSonetJ0String object and the z0 byte
--         is 0xcc. If the mode is set to 'string', then the J0 byte is set to
--         the 16 values in the tnSonetJ0String object and the z0 byte is
--         0xcc."
--     DEFVAL { byte }
--     ::= { tnSonetEntry 18 }
--
-- tnSonetJ0String   OBJECT-TYPE
--     SYNTAX      OCTET STRING (SIZE(0..16))
--     MAX-ACCESS  read-write
--     STATUS      current
--     DESCRIPTION
--         "The tnSonetJ0String is used with the tnSonetSectionTraceMode
--         variable to determine the contents of the j0 byte in the SONET Section
--         Header. If the tnSonetSectionTraceMode is increment-z0, this object
--         is ignored. If the mode is byte, then the first octet of this object is
--         used for the J0 byte. If the mode is string, then the 16 bytes in this
--         object are used for the J0 byte. If set to less than 16 bytes it, will
--         be padded out to 16 with zeros. The default value is 0x01 and 15 NULLs"
--     DEFVAL { '01'H }
--     ::= { tnSonetEntry 19 }
--
-- tnSonetMonS1Byte     OBJECT-TYPE
--     SYNTAX      Unsigned32 (0..255)
--     MAX-ACCESS  read-only
--     STATUS      current
--     DESCRIPTION
--         "The tnSonetMonS1Byte variable reports the Synchronization Status
--         Message from the S1 byte in the Line Overhead Header. A value of 0x00
--         indicates unknown quality. A value of 0xF0 indicates
--         `Do not use for synchronization`. Other values are documented in
--         Telcordia GR253 and ITU G.707"
--     DEFVAL { 'cc'H }
--     ::= { tnSonetEntry 20 }
--
-- tnSonetMonJ0String   OBJECT-TYPE
--     SYNTAX      OCTET STRING (SIZE(0..16))
--     MAX-ACCESS  read-only
--     STATUS      current
--     DESCRIPTION
--         "The tnSonetMonJ0String variable reports the contents of the j0 byte
--          in the SONET Section Header."
--     ::= { tnSonetEntry 21 }
--
-- tnSonetMonK1Byte     OBJECT-TYPE
--     SYNTAX      Unsigned32 (0..255)
--     MAX-ACCESS  read-only
--     STATUS      current
--     DESCRIPTION
--         "The tnSonetMonK1Byte variable reports the Automatic Protection
--          Switching(APS) signalling status from the K1 byte in the SONET
--          Line Overhead Header."
--     ::= { tnSonetEntry 22 }
--
-- tnSonetMonK2Byte     OBJECT-TYPE
--     SYNTAX      Unsigned32 (0..255)
--     MAX-ACCESS  read-only
--     STATUS      current
--     DESCRIPTION
--         "The tnSonetMonK1Byte variable reports the Automatic Protection
--          Switching(APS) signalling status from the K2 byte in the SONET
--          Line Overhead Header."
--     ::= { tnSonetEntry 23 }
--
-- tnSonetSingleFiber     OBJECT-TYPE
--     SYNTAX      TruthValue
--     MAX-ACCESS  read-write
--     STATUS      current
--     DESCRIPTION
--         "tnSonetSingleFiber is used to enable/disable packet gathering and
--          redirection of IP packets from a single fiber on RX port of the
--          SONET interface and redistribute packets to other interfaces
--          through either state routes or policy-based forwarding."
--     DEFVAL { false }
--     ::= { tnSonetEntry 24 }
--
-- tnSonetHoldTimeUp  OBJECT-TYPE
--     SYNTAX      Unsigned32 (0..100)
--     UNITS       "100s of milliseconds"
--     MAX-ACCESS  read-write
--     STATUS      current
--     DESCRIPTION
--         "The value of tnSonetHoldTimeUp is used to configure the
--          hold-timer for link up event dampening. This guards against
--          reporting excessive interface transitions. This is implemented
--          by not advertising subsequent transitions of the interface to
--          upper layer protocols until the configured timer has expired.
--          A value of zero (0) indicates that an up transition is reported
--          immediately."
--     DEFVAL { 5 }
--     ::= { tnSonetEntry 25 }
--
-- tnSonetHoldTimeDown    OBJECT-TYPE
--     SYNTAX      Unsigned32 (0..100)
--     UNITS       "100s of milliseconds"
--     MAX-ACCESS  read-write
--     STATUS      current
--     DESCRIPTION
--         "The value of tnSonetHoldTimeDown is used to configure the
--          hold-timer for link down event dampening. This guards against
--          reporting excessive interface transitions. This is implemented
--          by not advertising subsequent transitions of the interface to
--          upper layer protocols until the configured timer has expired.
--          A value of zero (0) indicates that a down transition is reported
--          immediately."
--     DEFVAL { 0 }
--     ::= { tnSonetEntry 26 }
--
-- tnSonetSuppressLoOrderAlarm  OBJECT-TYPE
--     SYNTAX      TruthValue
--     MAX-ACCESS  read-write
--     STATUS      current
--     DESCRIPTION
--         "The value of tnSonetSuppressLoOrderAlarm specifies whether
--          or not the lower order alarms on Sonet ports are suppressed."
--     DEFVAL { false }
--     ::= { tnSonetEntry 27 }

--
--  Sonet Path Table
--
-- tnSonetPathTable OBJECT-TYPE
--     SYNTAX      SEQUENCE OF TmnxSonetPathEntry
--     MAX-ACCESS  not-accessible
--     STATUS      current
--     DESCRIPTION
--         "The tnSonetPathTable has an entry for each sonet path
--          configured in each packet over Sonet port on each IOM card
--          in each chassis in the TMNX system."
--     ::= { tnPortObjs 6 }
--
-- tnSonetPathEntry       OBJECT-TYPE
--     SYNTAX      TmnxSonetPathEntry
--     MAX-ACCESS  not-accessible
--     STATUS      current
--     DESCRIPTION
--         "Each row entry represents a configured sonet path in a packet
--          over Sonet port on a IOM card in a chassis in the system.
--          The tnSonetPathEntry contains attributes that are
--          unique to a sonet path of a 'sonet' TmnxPortType. The
--          tnPortPortID for a sonet port includes a sonet path number
--          in the lower bits.  If the sonet path number is zero, '0', it
--          represents a single (clear) sonet path on the port that uses
--          the full bandwidth of the sonet port.  Entries in this table
--          that have the sonet path number part of their tnPortPortID
--          index value set to zero cannot be created and deleted via
--          SNMP SET operations.  They are created by the SNMP agent
--          when the corresponding entry in the tnSonetTable is
--          created.
--
--          Entries with non-zero sonet path numbers can be created and
--          deleted via SNMP SET operations using tnSonetPathRowStatus.
--          When a row is created in the tnSonetPathTable, the
--          agent also creates a row with the same index values in the
--          tnPortTable.  In order to delete an entry,
--          tnPortAdminStatus must first be set to 'outOfService'.  When
--          the tnSonetPathEntry is deleted, the agent also deletes
--          the corresponding row in the tnPortTable."
--     INDEX   {  tnPortPortID }
--     ::= { tnSonetPathTable 1 }
--
-- TmnxSonetPathEntry ::=
--     SEQUENCE {
--         tnSonetPathRowStatus          RowStatus,
--         tnSonetPathLastChangeTime     TimeStamp,
--         tnSonetPathMTU                Unsigned32,
--         tnSonetPathScramble           TruthValue,
--         tnSonetPathC2Byte             Unsigned32,
--         tnSonetPathJ1String           OCTET STRING,
--         tnSonetPathCRC                INTEGER,
--         tnSonetPathOperMTU            Unsigned32,
--         tnSonetPathOperMRU            Unsigned32,
--         tnSonetPathReportAlarm        BITS,
--         tnSonetPathAcctPolicyId       Unsigned32,
--         tnSonetPathCollectStats       TruthValue,
--         tnSonetPathReportAlarmStatus  BITS,
--         tnSonetPathMonC2Byte          Unsigned32,
--         tnSonetPathMonJ1String        OCTET STRING
-- ==        tnSonetPathType                INTEGER
-- ==        tnSonetPathChildType          TmnxMDAChanType
--     }
--
-- tnSonetPathRowStatus        OBJECT-TYPE
--     SYNTAX      RowStatus
--     MAX-ACCESS  read-create
--     STATUS      current
--     DESCRIPTION
--         "tnSonetPathRowStatus controls the creation and deletion of
--          row entries in the tnSonetPathTable. The tnPortPortID
--          for a sonet port includes a sonet path number in the lower bits.
--          If the sonet path number is zero, '0', it represents a single
--          (clear) sonet path on the port that uses the full bandwidth of
--          the sonet port.  Entries in this table that have the sonet path
--          number part of their tnPortPortID index value set to zero
--          cannot be created and deleted via SNMP SET operations. They
--          are created by the SNMP agent when the corresponding entry in
--          the tnSonetTable is created.
--
--          Entries with non-zero sonet path numbers can be created and deleted
--          via SNMP SET operations.  When a row is created in the
--          tnSonetPathTable, the agent also creates a row with the
--          same index values in the tnPortTable.  In order to delete an
--          entry, tnPortAdminStatus must first be set to 'outOfService'.
--          When the tnSonetPathEntry is deleted, the agent also
--          deletes the corresponding row in the tnPortTable for this
--          sonet path port."
--     ::= { tnSonetPathEntry 1 }
--
-- tnSonetPathLastChangeTime    OBJECT-TYPE
--     SYNTAX      TimeStamp
--     MAX-ACCESS  read-only
--     STATUS      current
--     DESCRIPTION
--         "The tnSonetPathLastChangeTime variable contains the sysUpTime
--          value of the most recently modified writable variable in the
--          tnSonetPathEntry row for this sonet path."
--     ::= { tnSonetPathEntry 2 }
--
-- tnSonetPathMTU  OBJECT-TYPE
--     SYNTAX      Unsigned32 (0|512..9208)
--     UNITS       "bytes"
--     MAX-ACCESS  read-create
--     STATUS      current
--     DESCRIPTION
--         "The size of the largest packet which can be sent/received
--          on the sonet path, specified in octets.  For paths that
--          are used for transmitting network datagrams, this is the
--          size of the largest network datagram that can be sent on the
--          sonet path.
--
--          Setting tnSonetPathMTU to a value of zero (0), causes the agent
--          to recalculate the default MTU size which can vary based on the
--          current setting of tnPortMode and tnPortEncapType variables.
--          Some typical default values are:
--                 1522 with mode access and encap-type bcp-null
--                 1526 with mode access and encap-type bcp-dot1q
--                 1502 with mode access and encap-type ipcp
--                 1506 with mode access and encap-type mplscp
--                 1524 with mode access and encap-type atm
--                 9208 with mode network
--         "
--     ::= { tnSonetPathEntry 3 }
--
-- tnSonetPathScramble     OBJECT-TYPE
--     SYNTAX      TruthValue
--     MAX-ACCESS  read-create
--     STATUS      current
--     DESCRIPTION
--         "If the tnSonetPathScramble variable is set to 'true',
--          SONET (SDH) payload scrambling is enabled on this sonet path.
--          Both ends of the connection must use the same scrambling
--          algorithm.  If tnSonetPathScramble is set to 'false',
--          scrambling is disabled.
--          The default value for non-ATM paths is 'false'.
--          The default value for ATM paths is 'true'
--
--          If the value of tnSonetPathC2Byte is set to the default for
--          the currently configured tnSonetPathScramble, then changing
--          the value of tnSonetPathScramble  for non-ATM paths causes a change
--          to tnSonetPathC2Byte to a default value for a new scrambling
--          option. The default values are as follows:
--          scrambled non-ATM sonet/sdh path - C2 Byte value is 0x16
--          unscrambled non-ATM sonet/sdh path - C2 Byte value is 0xCF"
--     ::= { tnSonetPathEntry 4 }
--
-- tnSonetPathC2Byte     OBJECT-TYPE
--     SYNTAX      Unsigned32 (0..254)
--     MAX-ACCESS  read-create
--     STATUS      current
--     DESCRIPTION
--         "The tnSonetPathC2Byte variable is used configure the value
--          used in the SONET/SDH C2 header byte.
--
--          For paths on an MDA that does not support channelization:
--          Setting C2 equal to 0x16 indicates scrambled sonet.
--
--          Setting C2 equal to 0xCF indicates unscrambled sonet.
--
--          Setting C2 equal to 0x13 indicates ATM.
--
--          For paths on an MDA that supports channelization, the default
--          value is based on the value of tmnxMDAMaxChannelization.
--          For 'pdhDs3' or 'pdhE3' channelization, the default value is 0x04.
--
--          Setting tnSonetPathC2Byte to a value of zero(0) causes the agent
--          to assign the default value to this object."
--     ::= { tnSonetPathEntry 5 }
--
-- tnSonetPathJ1String   OBJECT-TYPE
--     SYNTAX      OCTET STRING (SIZE(0..62))
--     MAX-ACCESS  read-create
--     STATUS      current
--     DESCRIPTION
--         "The tnSonetPathJ1String variable is used to configure the sonet path
--         trace string to be sent in the J1 Path Overhead bytes. The bytes
--         must be printable ASCII. If the string is less than 62 bytes, it
--         will be padded with NULLs. For SONET framing, an additional CR (0x0D)
--         / LF (0x0A) pair will be added by the driver. For SDH framing only
--         16 bytes are sent in the J1 bytes. The driver will set the MSB of
--         the first byte, and put the first 15 bytes of the user configured string
--         as the following bytes. The driver will set the CRC-7 of the 16 bytes
--         into the other 7 bits of the first byte.
--
--         The default value is `Nokia 7x50 SR`.
--         Setting a 1-byte long string containing 0xFF will restore the default.
--         Setting the string 'zeros' will send all-zeros (ASCII NULL characters
--         without CR/LF or CRC-7)in the J1 bytes."
--     ::= { tnSonetPathEntry 6 }
--
-- tnSonetPathCRC  OBJECT-TYPE
--     SYNTAX      INTEGER {
--                     crc16 (1),
--                     crc32 (2)
--                 }
--     MAX-ACCESS  read-create
--     STATUS      current
--     DESCRIPTION
--         "The value of tnSonetPathCRC variable indicates the precision of
--          the cyclic redundancy check.  A value of 'crc16' is a 16-bit
--          CRC calculation.  A value of 'crc32' is a 32-bit CRC
--          calculation.  32-bit CRC increases the error detection ability,
--          but it also adds some performance overhead.
--
--          For paths with encapsulation set to ATM the default and only
--          supported value is crc32 and applies to AAL5 CRC calculations
--          on that path."
--     DEFVAL { crc32 }
--     ::= { tnSonetPathEntry 7 }
--
-- tnSonetPathOperMTU        OBJECT-TYPE
--     SYNTAX      Unsigned32
--     UNITS       "bytes"
--     MAX-ACCESS  read-only
--     STATUS      current
--     DESCRIPTION
--         "The negotiated size of the largest packet which can be sent on
--          the sonet path, specified in octets.  For sonet paths that are used
--          for transmitting network datagrams, this is the size of the largest
--          network datagram that can be sent on the sonet path."
--     ::= { tnSonetPathEntry 8 }
--
-- tnSonetPathOperMRU        OBJECT-TYPE
--     SYNTAX      Unsigned32
--     UNITS       "bytes"
--     MAX-ACCESS  read-only
--     STATUS      current
--     DESCRIPTION
--         "The negotiated size of the largest packet that can be received
--          on the sonet path, specified in octets."
--     ::= { tnSonetPathEntry 9 }
--
-- tnSonetPathReportAlarm        OBJECT-TYPE
--     SYNTAX      BITS {
--                     notUsed (0),
--                     pais(1),
--                     plop(2),
--                     prdi(3),
--                     pb3err(4),
--                     pplm(5),
--                     prei(6),
--                     puneq(7),
--                     plcd(8)
--                 }
--     MAX-ACCESS  read-create
--     STATUS      current
--     DESCRIPTION
--         "The value of tnSonetPathReportAlarm determines when and if to
--          generate tnEqPortSonetPathAlarm and tnEqPortSonetPathAlarmClear
--          notifications for this port:
--             pais(1)     Reports path alarm indication signal errors. Not set by
--                         default.
--             plop(2)     Reports path loss of pointer (per tributary) errors.
--                         Set by default.
--             prdi(3)     Reports path remote defect indication errors.  Not set
--                         by default.
--             pb3err(4)   Reports path B3 errors.  Not set by default.
--             pplm(5)     Reports a path payload mismatch.  As a result the
--                         path will be operationally downed.  Set by default.
--             prei(6)     Reports a path error condition raised by the remote as
--                         a result of B3 errors received from this node.  Not
--                         set by default.
--             puneq(7)    Reports unequipped path errors. Set by default.
--             plcd(8)     Reports path loss of codegroup delineation error.
--                         It is applicable only when the value of
--                         tnPortEtherXGigMode is set to 'wan'.
--                         Not set by default.
--         "
--     DEFVAL { {plop, pplm, puneq} }
--     ::= { tnSonetPathEntry 10 }
--
-- tnSonetPathAcctPolicyId  OBJECT-TYPE
--     SYNTAX      Unsigned32 (0..99)
--     MAX-ACCESS  read-create
--     STATUS      current
--     DESCRIPTION
--         "The value of the accounting policy must be defined prior to associating
--          the policy with the sonet path. Accounting policies can only be
--          associated with network sonet path.
--          A non-zero value indicates the tmnxLogApPolicyId index identifying the
--          policy entry in the tmnxLogApTable from the TIMETRA-LOG-MIB which is
--          associated with this port.  A zero value indicates that there is no
--          accounting policy associated with this port"
--     DEFVAL { 0 }
--     ::= { tnSonetPathEntry 11 }
--
-- tnSonetPathCollectStats        OBJECT-TYPE
--     SYNTAX      TruthValue
--     MAX-ACCESS  read-create
--     STATUS      current
--     DESCRIPTION
--         "Enable/disable the collection of accounting and statistical data
--          for the network sonet path. When applying accounting policies the
--          data by default will be collected in the appropriate records and
--          written to the designated billing file.
--          When the value is set to false, the statistics are still accumulated
--          by the IOM cards, however, the CPU will not obtain the results and
--          write them to the billing file."
--     DEFVAL { true }
--     ::= { tnSonetPathEntry 12 }
--
-- tnSonetPathReportAlarmStatus        OBJECT-TYPE
--     SYNTAX      BITS {
--                     notUsed (0),
--                     pais(1),
--                     plop(2),
--                     prdi(3),
--                     pb3err(4),
--                     pplm(5),
--                     prei(6),
--                     puneq(7),
--                     plcd(8)
--                 }
--     MAX-ACCESS  read-only
--     STATUS      current
--     DESCRIPTION
--         "The bits in this object are used for indicating the alarms. The bits
--          are explained as follows:
--             pais(1)     Indicates path alarm indication signal errors.
--             plop(2)     Indicates path loss of pointer (per tributary) errors.
--             prdi(3)     Indicates path remote defect indication errors.
--             pb3err(4)   Indicates path B3 errors.
--             pplm(5)     Indicates a path payload mismatch.
--             prei(6)     Indicates a path error condition raised by the remote as
--                         a result of B3 errors received from this node.
--             puneq(7)    Indicates a far-end unequipped error.
--             plcd(8)     Indicates a path loss of codegroup delineation error.
--                         It is applicable only when the value of
--                         tnPortEtherXGigMode is set to 'wan'.
--                         Not set by default.
--         "
--     ::= { tnSonetPathEntry 13 }
--
-- tnSonetPathMonC2Byte     OBJECT-TYPE
--     SYNTAX      Unsigned32 (0..255)
--     MAX-ACCESS  read-only
--     STATUS      current
--     DESCRIPTION
--         "The tnSonetPathC2Byte variable reports the value in the SONET/SDH
--          C2 header byte."
--     ::= { tnSonetPathEntry 14 }
--
-- tnSonetPathMonJ1String   OBJECT-TYPE
--     SYNTAX      OCTET STRING (SIZE(0..64))
--     MAX-ACCESS  read-only
--     STATUS      current
--     DESCRIPTION
--         "The tnSonetPathJ1String variable reports the sonet path
--          trace string received in the J1 Path Overhead bytes."
--     ::= { tnSonetPathEntry 15 }
--
-- == tnSonetPathType       OBJECT-TYPE
-- ==     SYNTAX      INTEGER {
-- ==                     ds3 (1),
-- ==                     e3  (2),
-- ==                     vtg (3),
-- ==                     tug-2 (4),
-- ==                     tug-3 (5)
-- ==                 }
-- ==     MAX-ACCESS  read-create
-- ==     STATUS      obsolete
-- ==     DESCRIPTION
-- ==         "tnSonetPathType specifies if the associated SONET/SDH Path
-- ==          is an asynchronous circuit, a virtual tributary group or
-- ==          a tributary unit group.
-- ==             ds3   - Configures the port or channel as service access(ds3)
-- ==             e3    - Configures the port or channel as service access(e3)
-- ==             vtg   - Configures the path as a virtual tributary group.
-- ==             tug-2 - Configures the path as a tributary unit group.
-- ==             tug-3 - Configures the port or channel for transport network use."
-- ==     DEFVAL       { ds3 }
-- ==     ::= { tnSonetPathEntry 16 }
--
-- ==tnSonetPathChildType      OBJECT-TYPE
-- ==    SYNTAX      TmnxMDAChanType
-- ==    MAX-ACCESS  read-create
-- ==    STATUS      current
-- ==    DESCRIPTION
-- ==        "tnSonetPathChildType is used to configure the type of this path.
-- ==         Some typical default values are:
-- ==           pdhDs3 for STS-1 paths
-- ==           pdhE3 for TU3 paths
-- ==           pdhE1 for VT2 paths
-- ==           pdhDs1 for VT15 paths
-- ==        Examples of valid child path types are sonetSts3, sdhTug3,
-- ==         pdhDs3, pdhE3, sonetVt15, sonetVt2, pdhDs1 and pdhE1."
-- ==    ::= { tnSonetPathEntry 17 }
--
--  Nokia 7x50 SR series Port Type Definition Table
--
-- tnPortTypeTable OBJECT-TYPE
--     SYNTAX      SEQUENCE OF TmnxPortTypeEntry
--     MAX-ACCESS  not-accessible
--     STATUS      current
--     DESCRIPTION
--         "The Port type table has an entry for each Nokia 7x50 SR series
--          port model."
--     ::= { tnPortObjs 7 }
--
-- tnPortTypeEntry    OBJECT-TYPE
--     SYNTAX      TmnxPortTypeEntry
--     MAX-ACCESS  not-accessible
--     STATUS      current
--     DESCRIPTION
--         "Each row entry represents an Nokia 7x50 SR series port model.
--          Rows in this table are created by the agent at initialization and
--          cannot be created or destroyed by SNMP Get or Set requests."
--     INDEX   { tnSysSwitchId, tnPortTypeIndex }
--     ::= { tnPortTypeTable 1 }
--
-- TmnxPortTypeEntry ::=
--     SEQUENCE {
--         tnPortTypeIndex        TmnxPortType,
--         tnPortTypeName         TNamedItemOrEmpty,
--         tnPortTypeDescription  TItemDescription,
--         tnPortTypeStatus       TruthValue
--     }
--
-- tnPortTypeIndex    OBJECT-TYPE
--     SYNTAX      TmnxPortType
--     MAX-ACCESS  not-accessible
--     STATUS      current
--     DESCRIPTION
--         "The unique index value which identifies this type of Nokia 7x50
--          SR series port model."
--     ::= { tnPortTypeEntry 1 }
--
-- tnPortTypeName     OBJECT-TYPE
--     SYNTAX      TNamedItemOrEmpty
--     MAX-ACCESS  read-only
--     STATUS      current
--     DESCRIPTION
--         "The administrative name that identifies this type of Nokia
--          7x50 SR series port model.  This name string may be used in CLI
--          commands to specify a particular Port model type."
--     ::= { tnPortTypeEntry 2 }
--
-- tnPortTypeDescription  OBJECT-TYPE
--     SYNTAX      TItemDescription
--     MAX-ACCESS  read-only
--     STATUS      current
--     DESCRIPTION
--         "A detailed description of this Nokia 7x50 SR series port model."
--     ::= { tnPortTypeEntry 3 }
--
-- tnPortTypeStatus       OBJECT-TYPE
--     SYNTAX      TruthValue
--     MAX-ACCESS  read-only
--     STATUS      current
--     DESCRIPTION
--         "When tnPortTypeStatus has a value of 'true' it indicates that
--          this port model is supported in this revision of the management
--          software.  When it has a value of 'false' there is no support."
--     ::= { tnPortTypeEntry 4 }

--
--  Nokia 7x50 SR series Port Connector Type Definition Table
--
-- tnPortConnectTypeTable OBJECT-TYPE
--     SYNTAX      SEQUENCE OF TmnxPortConnectTypeEntry
--     MAX-ACCESS  not-accessible
--     STATUS      current
--     DESCRIPTION
--         "The Port Connector type table has an entry for each Nokia
--          7x50 SR series port connector model."
--     ::= { tnPortObjs 8 }
--
-- tnPortConnectTypeEntry    OBJECT-TYPE
--     SYNTAX      TmnxPortConnectTypeEntry
--     MAX-ACCESS  not-accessible
--     STATUS      current
--     DESCRIPTION
--         "Each row entry represents an Nokia 7x50 SR series port
--          Connector model.  Rows in this table are created by the agent
--          at initialization and cannot be created or destroyed by SNMP
--          Get or Set requests."
--     INDEX   { tnSysSwitchId, tnPortConnectTypeIndex }
--     ::= { tnPortConnectTypeTable 1 }
--
-- TmnxPortConnectTypeEntry ::=
--     SEQUENCE {
--         tnPortConnectTypeIndex        TmnxPortConnectorType,
--         tnPortConnectTypeName         TNamedItemOrEmpty,
--         tnPortConnectTypeDescription  TItemDescription,
--         tnPortConnectTypeStatus       TruthValue
--     }
--
-- tnPortConnectTypeIndex    OBJECT-TYPE
--     SYNTAX      TmnxPortConnectorType
--     MAX-ACCESS  not-accessible
--     STATUS      current
--     DESCRIPTION
--         "The unique index value which identifies this type of Nokia
--          7x50 SR series port connector model."
--     ::= { tnPortConnectTypeEntry 1 }
--
-- tnPortConnectTypeName     OBJECT-TYPE
--     SYNTAX      TNamedItemOrEmpty
--     MAX-ACCESS  read-only
--     STATUS      current
--     DESCRIPTION
--         "The administrative name that identifies this type of Nokia
--          7x50 SR series port connector model.  This name string may be
--          used in CLI commands to specify a particular port connector
--          model type."
--     ::= { tnPortConnectTypeEntry 2 }
--
-- tnPortConnectTypeDescription  OBJECT-TYPE
--     SYNTAX      TItemDescription
--     MAX-ACCESS  read-only
--     STATUS      current
--     DESCRIPTION
--         "A detailed description of this Nokia 7x50 SR series port
--          connector model."
--     ::= { tnPortConnectTypeEntry 3 }
--
-- tnPortConnectTypeStatus       OBJECT-TYPE
--     SYNTAX      TruthValue
--     MAX-ACCESS  read-only
--     STATUS      current
--     DESCRIPTION
--         "When tnPortConnectTypeStatus has a value of 'true' it indicates that
--          this port connector model is supported in this revision of the
--          chassis management software.  When it has a value of 'false' there
--          is no support."
--     ::= { tnPortConnectTypeEntry 4 }

--
--  Network Port FC Stats Table
--
-- tnPortFCStatsTable OBJECT-TYPE
--     SYNTAX      SEQUENCE OF TmnxPortNetworkFCStatsEntry
--     MAX-ACCESS  not-accessible
--     STATUS      obsolete
--     DESCRIPTION
--         "The Network Port FC Stats table has an entry for each forwarding
--          class defined on each network port."
--     ::= { tnPortObjs 9 }
--
-- tnPortFCStatsEntry    OBJECT-TYPE
--     SYNTAX      TmnxPortNetworkFCStatsEntry
--     MAX-ACCESS  not-accessible
--     STATUS      obsolete
--     DESCRIPTION
--         "Each row entry represents a set of ingress and egress packet and
--          octet statistics for the given network port and forwarding class.
--          Rows in this table are created by the agent when the network port
--          is provisioned and cannot be created or destroyed by SNMP Get or
--          Set requests."
--     INDEX   {  tnPortPortID, tnPortFCStatsIndex }
--     ::= { tnPortFCStatsTable 1 }
--
-- TmnxPortNetworkFCStatsEntry ::=
--     SEQUENCE {
--         tnPortFCStatsIndex             TFCName,
--         tnPortFCStatsIngFwdInProfPkts  Counter64,
--         tnPortFCStatsIngFwdOutProfPkts Counter64,
--         tnPortFCStatsIngFwdInProfOcts  Counter64,
--         tnPortFCStatsIngFwdOutProfOcts Counter64,
--         tnPortFCStatsIngDroInProfPkts  Counter64,
--         tnPortFCStatsIngDroOutProfPkts Counter64,
--         tnPortFCStatsIngDroInProfOcts  Counter64,
--         tnPortFCStatsIngDroOutProfOcts Counter64,
--         tnPortFCStatsEgrFwdInProfPkts  Counter64,
--         tnPortFCStatsEgrFwdOutProfPkts Counter64,
--         tnPortFCStatsEgrFwdInProfOcts  Counter64,
--         tnPortFCStatsEgrFwdOutProfOcts Counter64,
--         tnPortFCStatsEgrDroInProfPkts  Counter64,
--         tnPortFCStatsEgrDroOutProfPkts Counter64,
--         tnPortFCStatsEgrDroInProfOcts  Counter64,
--         tnPortFCStatsEgrDroOutProfOcts Counter64
--     }
--
-- tnPortFCStatsIndex OBJECT-TYPE
--     SYNTAX      TFCName
--     MAX-ACCESS  not-accessible
--     STATUS      obsolete
--     DESCRIPTION
--         "The forwarding class associated with these stats
--          on this network port."
--     ::= { tnPortFCStatsEntry 1 }
--
-- tnPortFCStatsIngFwdInProfPkts OBJECT-TYPE
--     SYNTAX      Counter64
--     MAX-ACCESS  read-only
--     STATUS      obsolete
--     DESCRIPTION
--         "The number of in-profile packets (rate below CIR)
--          forwarded by the ingress Qchip."
--     ::= { tnPortFCStatsEntry 2 }
--
-- tnPortFCStatsIngFwdOutProfPkts OBJECT-TYPE
--     SYNTAX      Counter64
--     MAX-ACCESS  read-only
--     STATUS      obsolete
--     DESCRIPTION
--         "The number of out-of-profile packets (rate above CIR)
--          forwarded by the ingress Qchip."
--     ::= { tnPortFCStatsEntry 3 }
--
-- tnPortFCStatsIngFwdInProfOcts OBJECT-TYPE
--     SYNTAX      Counter64
--     MAX-ACCESS  read-only
--     STATUS      obsolete
--     DESCRIPTION
--         "The number of in-profile octets (rate below CIR)
--          forwarded by the ingress Qchip."
--     ::= { tnPortFCStatsEntry 4 }
--
-- tnPortFCStatsIngFwdOutProfOcts OBJECT-TYPE
--     SYNTAX      Counter64
--     MAX-ACCESS  read-only
--     STATUS      obsolete
--     DESCRIPTION
--         "The number of out-of-profile octets (rate above CIR)
--          forwarded by the ingress Qchip."
--     ::= { tnPortFCStatsEntry 5 }
--
-- tnPortFCStatsIngDroInProfPkts OBJECT-TYPE
--     SYNTAX      Counter64
--     MAX-ACCESS  read-only
--     STATUS      obsolete
--     DESCRIPTION
--         "The number of in-profile packets (rate below CIR)
--          dropped by the ingress Qchip due to: MBS exceeded,
--          buffer pool limit exceeded, etc."
--     ::= { tnPortFCStatsEntry 6 }
--
-- tnPortFCStatsIngDroOutProfPkts OBJECT-TYPE
--     SYNTAX      Counter64
--     MAX-ACCESS  read-only
--     STATUS      obsolete
--     DESCRIPTION
--         "The number of out-of-profile packets (rate above CIR)
--          dropped by the ingress Qchip due to: MBS exceeded,
--          buffer pool limit exceeded, etc."
--     ::= { tnPortFCStatsEntry 7 }
--
-- tnPortFCStatsIngDroInProfOcts OBJECT-TYPE
--     SYNTAX      Counter64
--     MAX-ACCESS  read-only
--     STATUS      obsolete
--     DESCRIPTION
--         "The number of in-profile octets (rate below CIR)
--          dropped by the ingress Qchip due to: MBS exceeded,
--          buffer pool limit exceeded, etc."
--     ::= { tnPortFCStatsEntry 8 }
--
-- tnPortFCStatsIngDroOutProfOcts OBJECT-TYPE
--     SYNTAX      Counter64
--     MAX-ACCESS  read-only
--     STATUS      obsolete
--     DESCRIPTION
--         "The number of out-of-profile octets (rate above CIR)
--          dropped by the ingress Qchip due to: MBS exceeded,
--          buffer pool limit exceeded, etc."
--     ::= { tnPortFCStatsEntry 9 }
--
-- tnPortFCStatsEgrFwdInProfPkts OBJECT-TYPE
--     SYNTAX      Counter64
--     MAX-ACCESS  read-only
--     STATUS      obsolete
--     DESCRIPTION
--         "The number of in-profile packets (rate below CIR)
--          forwarded by the egress Qchip."
--     ::= { tnPortFCStatsEntry 10 }
--
-- tnPortFCStatsEgrFwdOutProfPkts OBJECT-TYPE
--     SYNTAX      Counter64
--     MAX-ACCESS  read-only
--     STATUS      obsolete
--     DESCRIPTION
--         "The number of out-of-profile packets (rate above CIR)
--          forwarded by the egress Qchip."
--     ::= { tnPortFCStatsEntry 11 }
--
-- tnPortFCStatsEgrFwdInProfOcts OBJECT-TYPE
--     SYNTAX      Counter64
--     MAX-ACCESS  read-only
--     STATUS      obsolete
--     DESCRIPTION
--         "The number of in-profile octets (rate below CIR)
--          forwarded by the egress Qchip."
--     ::= { tnPortFCStatsEntry 12 }
--
-- tnPortFCStatsEgrFwdOutProfOcts OBJECT-TYPE
--     SYNTAX      Counter64
--     MAX-ACCESS  read-only
--     STATUS      obsolete
--     DESCRIPTION
--         "The number of out-of-profile octets (rate above CIR)
--          forwarded by the egress Qchip."
--     ::= { tnPortFCStatsEntry 13 }
--
-- tnPortFCStatsEgrDroInProfPkts OBJECT-TYPE
--     SYNTAX      Counter64
--     MAX-ACCESS  read-only
--     STATUS      obsolete
--     DESCRIPTION
--         "The number of in-profile packets (rate below CIR)
--          dropped by the egress Qchip due to: MBS exceeded,
--          buffer pool limit exceeded, etc."
--     ::= { tnPortFCStatsEntry 14 }
--
-- tnPortFCStatsEgrDroOutProfPkts OBJECT-TYPE
--     SYNTAX      Counter64
--     MAX-ACCESS  read-only
--     STATUS      obsolete
--     DESCRIPTION
--         "The number of out-of-profile packets (rate above CIR)
--          dropped by the egress Qchip due to: MBS exceeded,
--          buffer pool limit exceeded, etc."
--     ::= { tnPortFCStatsEntry 15 }
--
-- tnPortFCStatsEgrDroInProfOcts OBJECT-TYPE
--     SYNTAX      Counter64
--     MAX-ACCESS  read-only
--     STATUS      obsolete
--     DESCRIPTION
--         "The number of in-profile octets (rate below CIR)
--          dropped by the egress Qchip due to: MBS exceeded,
--          buffer pool limit exceeded, etc."
--     ::= { tnPortFCStatsEntry 16 }
--
-- tnPortFCStatsEgrDroOutProfOcts OBJECT-TYPE
--     SYNTAX      Counter64
--     MAX-ACCESS  read-only
--     STATUS      obsolete
--     DESCRIPTION
--         "The number of out-of-profile octets (rate above CIR)
--          dropped by the egress Qchip due to: MBS exceeded,
--          buffer pool limit exceeded, etc."
--     ::= { tnPortFCStatsEntry 17 }

--
-- DS3 table
--
-- tnDS3Table OBJECT-TYPE
--     SYNTAX      SEQUENCE OF TmnxDS3Entry
--     MAX-ACCESS  not-accessible
--     STATUS      current
--     DESCRIPTION
--         "The tnDS3Table has an entry for a DS3 physical port."
--     ::= { tnPortObjs 10 }
--
-- tnDS3Entry       OBJECT-TYPE
--     SYNTAX      TmnxDS3Entry
--     MAX-ACCESS  not-accessible
--     STATUS      current
--     DESCRIPTION
--         "Each row entry represents a physical DS3 port on a
--          IOM card in a chassis in the system.  Entries cannot be created
--          and deleted via SNMP SET operations.  Entries in this table will
--          be created automatically when the tmnxMDAAssignedType object is
--          set to the DS3 MDA type The tnDS3Entry contains attributes that are
--          unique to the 'ds3e3' TmnxPortType. The tnPortPortID contains
--          the slot, mda and port numbers encoded into it.
--
--          For each tnDS3Entry, there will be a corresponding entry
--          in the tnPortTable and the ifTable."
--     INDEX       {  tnPortPortID }
--     ::= { tnDS3Table 1 }
--
-- TmnxDS3Entry ::=
--     SEQUENCE {
--         tnDS3Buildout                 INTEGER,
--         tnDS3LastChangeTime           TimeStamp,
--         tnDS3Type                     INTEGER
--     }
--
-- tnDS3Buildout    OBJECT-TYPE
--     SYNTAX      INTEGER {
--                     short (1),
--                     long  (2)
--                 }
--     MAX-ACCESS  read-create
--     STATUS      current
--     DESCRIPTION
--         "tnDS3Buildout configures the T3 line buildout. A T3 port has two
--          settings for the T3 line buildout: a short setting, which is less
--          than 225 feet, and a long setting, which is greater than 225 feet.
--          This object applies to copper-cable-based T3 ports only."
--     DEFVAL      { short }
--     ::= { tnDS3Entry 1 }
--
-- tnDS3LastChangeTime    OBJECT-TYPE
--     SYNTAX      TimeStamp
--     MAX-ACCESS  read-only
--     STATUS      current
--     DESCRIPTION
--         "The tnDS3LastChangeTime variable contains the sysUpTime
--          value of the most recently modified writable variable in the
--          tnDS3Entry row for this port."
--     ::= { tnDS3Entry 2 }
--
-- tnDS3Type     OBJECT-TYPE
--     SYNTAX      INTEGER {
--                     ds3(1),
--                     e3(2)
--                 }
--     MAX-ACCESS  read-create
--     STATUS      current
--     DESCRIPTION
--         "tnDS3Type configures the type of the physical port to 'ds3' or 'e3'."
--     DEFVAL      { ds3 }
--     ::= { tnDS3Entry 3 }

--
-- DS3 Channel table
--
-- tnDS3ChannelTable OBJECT-TYPE
--     SYNTAX      SEQUENCE OF TmnxDS3ChannelEntry
--     MAX-ACCESS  not-accessible
--     STATUS      current
--     DESCRIPTION
--         "The tnDS3ChannelTable has an entry for a DS3 channel."
--     ::= { tnPortObjs 11 }
--
-- tnDS3ChannelEntry       OBJECT-TYPE
--     SYNTAX      TmnxDS3ChannelEntry
--     MAX-ACCESS  not-accessible
--     STATUS      current
--     DESCRIPTION
--         "Each row entry represents a DS3 channel. Entries can be created
--          and deleted via SNMP SET operations.  The tnDS3ChannelEntry
--          contains attributes that are applicable to a DS3 channel which
--          can belong to the DS3 physical port or belong to a container
--          on a sonet path. The tnPortPortID contains the slot, mda and
--          port numbers encoded into it.
--
--          For each tnDS3ChannelEntry, there will be a corresponding entry
--          in the tnPortTable and the ifTable."
--     INDEX       {  tnPortPortID }
--     ::= { tnDS3ChannelTable 1 }
--
-- TmnxDS3ChannelEntry ::=
--     SEQUENCE {
--         tnDS3ChannelRowStatus                RowStatus,
--         tnDS3ChannelType                     INTEGER,
--         tnDS3ChannelFraming                  INTEGER,
--         tnDS3ChannelClockSource              TmnxDSXClockSource,
--         tnDS3ChannelChannelized              INTEGER,
--         tnDS3ChannelSubrateCSUMode           INTEGER,
--         tnDS3ChannelSubrate                  Unsigned32,
--         tnDS3ChannelIdleCycleFlags           TmnxDSXIdleCycleFlags,
--         tnDS3ChannelLoopback                 TmnxDS3Loopback,
--         tnDS3ChannelBitErrorInsertionRate    Integer32,
--         tnDS3ChannelBERTPattern              TmnxDSXBertPattern,
--         tnDS3ChannelBERTDuration             Unsigned32,
--         tnDS3ChannelMDLEicString             DisplayString,
--         tnDS3ChannelMDLLicString             DisplayString,
--         tnDS3ChannelMDLFicString             DisplayString,
--         tnDS3ChannelMDLUnitString            DisplayString,
--         tnDS3ChannelMDLPfiString             DisplayString,
--         tnDS3ChannelMDLPortString            DisplayString,
--         tnDS3ChannelMDLGenString             DisplayString,
--         tnDS3ChannelMDLMessageType           BITS,
--         tnDS3ChannelFEACLoopRespond          TruthValue,
--         tnDS3ChannelCRC                      INTEGER,
--         tnDS3ChannelMTU                      Unsigned32,
--         tnDS3ChannelOperMTU                  Unsigned32,
--         tnDS3ChannelReportAlarm              TmnxDSXReportAlarm,
--         tnDS3ChannelReportAlarmStatus        TmnxDSXReportAlarm,
--         tnDS3ChannelLastChangeTime           TimeStamp,
--         tnDS3ChannelInFEACLoop               TruthValue,
--         tnDS3ChannelMDLMonPortString         DisplayString,
--         tnDS3ChannelMDLMonGenString          DisplayString,
--         tnDS3ChannelBERTOperStatus           TmnxDSXBertOperStatus,
--         tnDS3ChannelBERTSynched              Unsigned32,
--         tnDS3ChannelBERTErrors               Counter64,
--         tnDS3ChannelBERTTotalBits            Counter64,
--         tnDS3ChannelScramble                 TruthValue,
--         tnDS3ChannelAcctPolicyId             Unsigned32,
--         tnDS3ChannelCollectStats             TruthValue,
--         tnDS3ChannelClockSyncState           TmnxDSXClockSyncState,
--         tnDS3ChannelClockMasterPortId        TmnxPortID
--     }
--
-- tnDS3ChannelRowStatus    OBJECT-TYPE
--     SYNTAX      RowStatus
--     MAX-ACCESS  read-create
--     STATUS      current
--     DESCRIPTION
--         "tnDS3ChannelRowStatus controls the creation and deletion of
--          row entries in the tnDS3ChannelTable.
--          For row creation, the manager has to first calculate the
--          tnPortPortID based on the TiMOS encoding scheme."
--     ::= { tnDS3ChannelEntry 1 }
--
-- tnDS3ChannelType    OBJECT-TYPE
--     SYNTAX      INTEGER {
--                     ds3 (1),
--                     e3  (2)
--                 }
--     MAX-ACCESS  read-only
--     STATUS      current
--     DESCRIPTION
--         "The value of tnDS3ChannelType indicates whether the channel is
--          in DS3 or E3 mode."
--     ::= { tnDS3ChannelEntry 2 }
--
-- tnDS3ChannelFraming    OBJECT-TYPE
--     SYNTAX      INTEGER {
--                     cbit (1),
--                     m23  (2),
--                     g751 (3),
--                     g832 (4),
--                     e3-unframed (5),
--                     ds3-unframed (6)
--                 }
--     MAX-ACCESS  read-create
--     STATUS      current
--     DESCRIPTION
--         "The value of tnDS3ChannelFraming indicates the type of framing
--          associated with the DS3 channel.
--          If tnDS3ChannelType is set to 'ds3', the default framing is 'cbit'.
--          If tnDS3ChannelType is set to 'e3', the default framing is 'g751'."
--     DEFVAL      { cbit }
--     ::= { tnDS3ChannelEntry 3 }
--
-- tnDS3ChannelClockSource    OBJECT-TYPE
--     SYNTAX      TmnxDSXClockSource
--     MAX-ACCESS  read-create
--     STATUS      current
--     DESCRIPTION
--         "tnDS3ChannelClockSource configures the clock for transmitted data
--          from either the internal clock ('nodeTimed'), or from a clock
--          recovered from the line's receive data stream ('loopTimed')."
--     DEFVAL      { loopTimed }
--     ::= { tnDS3ChannelEntry 4 }
--
-- tnDS3ChannelChannelized    OBJECT-TYPE
--     SYNTAX      INTEGER {
--                     none(1),
--                     ds1 (2),
--                     e1  (3),
--                     j1  (4)
--                 }
--     MAX-ACCESS  read-create
--     STATUS      current
--     DESCRIPTION
--         "tnDS3ChannelChannelized is used to create sub-channels of type
--          'ds1' or 'e1' or 'j1' on the interface. Setting the value to 'none'
--          removes the sub-channels on the interface."
--     DEFVAL      { none }
--     ::= { tnDS3ChannelEntry 5 }
--
-- tnDS3ChannelSubrateCSUMode    OBJECT-TYPE
--     SYNTAX      INTEGER {
--                     notUsed (0),
--                     digital-link (1)
--                 }
--     MAX-ACCESS  read-create
--     STATUS      current
--     DESCRIPTION
--         "tnDS3ChannelSubrateCSUMode configures the channel service unit (CSU)
--          compatibility mode to interoperate with existing DS3 subrate
--          standards.
--          This configuration applies only for a non-channelized DS3.
--
--          Changing the value of tnDS3ChannelSubrateCSUMode to notUsed resets
--          the value of tnDS3ChannelScramble to 'false'.
--
--          Changing the value of tnDS3ChannelSubrateCSUMode
--          resets the value of tnDS3ChannelSubrate to default for the mode if
--          tnDS3ChannelSubrate is not provided."
--     DEFVAL      { notUsed }
--     ::= { tnDS3ChannelEntry 6 }
--
-- tnDS3ChannelSubrate    OBJECT-TYPE
--     SYNTAX      Unsigned32
--     MAX-ACCESS  read-create
--     STATUS      current
--     DESCRIPTION
--         "tnDS3ChannelSubrate configures the subrate step.
--
--          tnDS3ChannelSubrate multiplied by the granularity for a
--          particular mode as defined by tnDS3ChannelSubrateCSUMode gives
--          the absoulte subrate in kbps.
--
--          =======================================================================
--           Subrate CSU Mode|Granularity|Default |Range     |Subrate speed range
--          =======================================================================
--           notUsed         | N/A       | 0      | 0        |N/A
--           digital-link    | 301 kbps  | 1      | 1 to 147 |301 kbps to 44.2 mbps
--          ======================================================================="
--     ::= { tnDS3ChannelEntry 7 }
--
-- tnDS3ChannelIdleCycleFlags    OBJECT-TYPE
--     SYNTAX      TmnxDSXIdleCycleFlags
--     MAX-ACCESS  read-create
--     STATUS      current
--     DESCRIPTION
--         "tnDS3ChannelIdleCycleFlags configures the value that the
--          DS3 port transmits during idle cycle.
--
--          The default value applies to HDLC channels only. For ATM
--          channels the object does not really apply so a default value
--          of 'none' is used and cannot be changed."
--     DEFVAL      { flags }
--     ::= { tnDS3ChannelEntry 8 }
--
-- tnDS3ChannelLoopback    OBJECT-TYPE
--     SYNTAX      TmnxDS3Loopback
--     MAX-ACCESS  read-create
--     STATUS      current
--     DESCRIPTION
--         "tnDS3ChannelLoopback is used to put the channel into a loopback mode.
--          The value of tnPortAdminStatus should be set to 'outOfService'
--          in order for the loopback to be enabled.
--          A 'line' loopback loops frames received on this port back to the
--          remote system.
--          A 'internal' loopback loops the frames from the local system back at
--          the framer.
--          When the value is set to 'remote', a signal is sent to the remote
--          system to provide a line loopback."
--     DEFVAL      { none }
--     ::= { tnDS3ChannelEntry 9 }
--
-- tnDS3ChannelBitErrorInsertionRate    OBJECT-TYPE
--     SYNTAX      Integer32 (0 | 2..7)
--     MAX-ACCESS  read-create
--     STATUS      current
--     DESCRIPTION
--         "tnDS3ChannelBitErrorInsertionRate is used to insert bit errors for a
--          BERT test. The number of error corresponds to 10^(-rate). A rate of 7
--          will cause an error rate of 10^(-7), or 1 error in every 10
--          million bits transmitted.
--          If the value is set to 0, it disables the insertion of bit errors
--          into the BERT.
--          Change in this value while the test is running is accepted but
--          does not take effect until the test gets restarted."
--     DEFVAL      { 0 }
--     ::= { tnDS3ChannelEntry 10 }
--
-- tnDS3ChannelBERTPattern    OBJECT-TYPE
--     SYNTAX      TmnxDSXBertPattern
--     MAX-ACCESS  read-create
--     STATUS      current
--     DESCRIPTION
--         "tnDS3ChannelBERTPattern indicates the pattern used for the
--          Bit Error Rate Test (BERT). The value of tnDS3ChannelBERTDuration
--          indicates the duration of the test.
--          Setting the value of this object to 'none' terminates the test."
--     DEFVAL      { none }
--     ::= { tnDS3ChannelEntry 11 }
--
-- tnDS3ChannelBERTDuration    OBJECT-TYPE
--     SYNTAX      Unsigned32 (0..86400)
--     UNITS       "seconds"
--     MAX-ACCESS  read-create
--     STATUS      current
--     DESCRIPTION
--         "tnDS3ChannelBERTDuration is used to set the duration of the
--          BERT test."
--     ::= { tnDS3ChannelEntry 12 }
--
-- tnDS3ChannelMDLEicString    OBJECT-TYPE
--     SYNTAX      DisplayString (SIZE (0..10))
--     MAX-ACCESS  read-create
--     STATUS      current
--     DESCRIPTION
--         "tnDS3ChannelMDLEicString configures the Equipment ID Code(EIC) of the
--          Message Data Link (MDL)."
--     ::= { tnDS3ChannelEntry 13 }
--
-- tnDS3ChannelMDLLicString    OBJECT-TYPE
--     SYNTAX      DisplayString (SIZE (0..11))
--     MAX-ACCESS  read-create
--     STATUS      current
--     DESCRIPTION
--         "tnDS3ChannelMDLLicString configures the Location ID Code(LIC) of the
--          Message Data Link (MDL)."
--     ::= { tnDS3ChannelEntry 14 }
--
-- tnDS3ChannelMDLFicString    OBJECT-TYPE
--     SYNTAX      DisplayString (SIZE (0..10))
--     MAX-ACCESS  read-create
--     STATUS      current
--     DESCRIPTION
--         "tnDS3ChannelMDLFicString configures the Frame ID Code(FIC) of the
--          Message Data Link (MDL)."
--     ::= { tnDS3ChannelEntry 15 }
--
-- tnDS3ChannelMDLUnitString    OBJECT-TYPE
--     SYNTAX      DisplayString (SIZE (0..6))
--     MAX-ACCESS  read-create
--     STATUS      current
--     DESCRIPTION
--         "tnDS3ChannelMDLUnitString configures the Unit ID Code(UIC) of the
--          Message Data Link (MDL)."
--     ::= { tnDS3ChannelEntry 16 }
--
-- tnDS3ChannelMDLPfiString    OBJECT-TYPE
--     SYNTAX      DisplayString (SIZE (0..38))
--     MAX-ACCESS  read-create
--     STATUS      current
--     DESCRIPTION
--         "tnDS3ChannelMDLPfiString configures the Facility ID Code sent in
--          the Message Data Link (MDL) Path message."
--     ::= { tnDS3ChannelEntry 17 }
--
-- tnDS3ChannelMDLPortString    OBJECT-TYPE
--     SYNTAX      DisplayString (SIZE (0..38))
--     MAX-ACCESS  read-create
--     STATUS      current
--     DESCRIPTION
--         "tnDS3ChannelMDLPortString configures the port number string sent in
--          the Message Data Link (MDL) idle signal message."
--     ::= { tnDS3ChannelEntry 18 }
--
-- tnDS3ChannelMDLGenString    OBJECT-TYPE
--     SYNTAX      DisplayString (SIZE (0..38))
--     MAX-ACCESS  read-create
--     STATUS      current
--     DESCRIPTION
--         "tnDS3ChannelMDLGenString configures the generator number string
--          sent in the Message Data Link (MDL) test signal message."
--     ::= { tnDS3ChannelEntry 19 }
--
-- tnDS3ChannelMDLMessageType    OBJECT-TYPE
--     SYNTAX      BITS {
--                     none (0),
--                     ds3Path (1),
--                     idleSignal (2),
--                     testSignal (3)
--                 }
--     MAX-ACCESS  read-create
--     STATUS      current
--     DESCRIPTION
--         "tnDS3ChannelMDLMessageType configures the type of MDL message that
--          is transmitted over the DS3 interface. If the value of this object is
--          set to 'none', MDL messages are not transmitted.
--          ds3Path(0)   - Enables transmission of the MDL path message.
--                         An MDL path message, as defined by ANSI T1.107, is
--                         distinguished from idle and test signal messages in
--                         that it contains a facility identification code as its
--                         final data element.
--         idleSignal(1) - Enables transmission of the MDL idle signal message.
--                         An MDL idle signal message, as defined by ANSI T1.107,
--                         is distinguished from path and test signal messages in
--                         that it contains a port number as its final data
--                         element.
--         testSignal(2) - Enables transmission of the MDL test signal message.
--                         An MDL test signal message, as defined by ANSI T1.107,
--                         is distinguished from path and idle signal messages in
--                         that it contains a generator number as its final data
--                         element."
--     DEFVAL      { { none } }
--     ::= { tnDS3ChannelEntry 20 }
--
-- tnDS3ChannelFEACLoopRespond    OBJECT-TYPE
--     SYNTAX      TruthValue
--     MAX-ACCESS  read-create
--     STATUS      current
--     DESCRIPTION
--         "When tnDS3ChannelFEACLoopRespond has a value of 'true', the channel
--         is enabled to respond to remote loop signals.  When it has
--         a value of 'false' the port will not respond."
--     DEFVAL      { false }
--     ::= { tnDS3ChannelEntry 21 }
--
-- tnDS3ChannelCRC    OBJECT-TYPE
--     SYNTAX      INTEGER {
--                     crc16 (1),
--                     crc32 (2)
--                 }
--     MAX-ACCESS  read-create
--     STATUS      current
--     DESCRIPTION
--         "The value of tnDS3ChannelCRC variable indicates the precision of
--          the cyclic redundancy check.  A value of 'crc16' is a 16-bit
--          CRC calculation.  A value of 'crc32' is a 32-bit CRC
--          calculation.  32-bit CRC increases the error detection ability,
--          but it also adds some performance overhead.
--
--          For ATM channels, crc32 is the default and the only value supported
--          and applies to AAL5 CRC calculation on that channel."
--     DEFVAL      { crc16 }
--     ::= { tnDS3ChannelEntry 22 }
--
-- tnDS3ChannelMTU  OBJECT-TYPE
--     SYNTAX      Unsigned32 (0|512..9208)
--     UNITS       "bytes"
--     MAX-ACCESS  read-create
--     STATUS      current
--     DESCRIPTION
--         "The size of the largest packet which can be sent/received
--          on the port, specified in octets.  For ports that
--          are used for transmitting network datagrams, this is the
--          size of the largest network datagram that can be sent on the
--          sonet path.
--
--          Setting tnDS3ChannelMTU to a value of zero (0), causes the agent
--          to recalculate the default MTU size which can vary based on the
--          current setting of tnPortMode and tnPortEncapType variables.
--          Some typical default values are:
--                 1522 with mode access and encap-type bcp-null
--                 1526 with mode access and encap-type bcp-dot1q
--                 1502 with mode access and encap-type ipcp
--                 4474 with mode access and encap-type frame-relay
--                 1524 with mode access and encap-type atm
--                 2092 with mode access and encap-type cem
--         "
--     ::= { tnDS3ChannelEntry 23 }
--
-- tnDS3ChannelOperMTU    OBJECT-TYPE
--     SYNTAX      Unsigned32
--     UNITS       "bytes"
--     MAX-ACCESS  read-only
--     STATUS      current
--     DESCRIPTION
--         "The negotiated size of the largest packet which can be sent on
--          the channel, specified in octets.  For channels that are used
--          for transmitting network datagrams, this is the size of the largest
--          network datagram that can be sent."
--     ::= { tnDS3ChannelEntry 24 }
--
-- tnDS3ChannelReportAlarm    OBJECT-TYPE
--     SYNTAX      TmnxDSXReportAlarm
--     MAX-ACCESS  read-create
--     STATUS      current
--     DESCRIPTION
--         "The value of tnDS3ChannelReportAlarm determines when and if to
--          generate notifications for this channel:
--          ais - Reports alarm indication signal errors.
--                ais alarms are issued by default.
--          los - Reports loss of signal errors.
--                los alarms are issued by default.
--          oof - Reports out-of-frame errors.
--                oof alarms are not issued by default.
--          rai - Reports resource availability indicator events.
--                rai alarms are not issued by default.
--          looped - Reports if the far end has forced the near end to loopback.
--                looped alarms are not issued by default.
--          berSd - Reports DS3/E3 signal degradation bit errors.
--                  berSd alarms are not issued by default.
--          berSf - Reports DS3/E3 signal failure bit errors.
--                  berSf alarms are not issued by default"
--     DEFVAL      { {ais, los} }
--     ::= { tnDS3ChannelEntry 25 }
--
-- tnDS3ChannelReportAlarmStatus    OBJECT-TYPE
--     SYNTAX      TmnxDSXReportAlarm
--     MAX-ACCESS  read-only
--     STATUS      current
--     DESCRIPTION
--         "The value of tnDS3ChannelReportAlarmStatus indicates the current
--          alarms on this port."
--     ::= { tnDS3ChannelEntry 26 }
--
-- tnDS3ChannelLastChangeTime    OBJECT-TYPE
--     SYNTAX      TimeStamp
--     MAX-ACCESS  read-only
--     STATUS      current
--     DESCRIPTION
--         "The tnDS3ChannelLastChangeTime variable contains the sysUpTime
--          value of the most recently modified writable variable in the
--          tnDS3ChannelEntry row for this port."
--     ::= { tnDS3ChannelEntry 27 }
--
-- tnDS3ChannelInFEACLoop    OBJECT-TYPE
--     SYNTAX      TruthValue
--     MAX-ACCESS  read-only
--     STATUS      current
--     DESCRIPTION
--         "tnDS3ChannelInFEACLoop indicates whether the remote end has put
--          this channel in FEAC(Far End Alarm Control) loopback."
--     ::= { tnDS3ChannelEntry 28 }
--
-- tnDS3ChannelMDLMonPortString    OBJECT-TYPE
--     SYNTAX      DisplayString (SIZE (0..38))
--     MAX-ACCESS  read-only
--     STATUS      current
--     DESCRIPTION
--         "tnDS3ChannelMDLMonPortString indicates the port number string
--          received in the Message Data Link (MDL) idle signal message."
--     ::= { tnDS3ChannelEntry 29 }
--
-- tnDS3ChannelMDLMonGenString    OBJECT-TYPE
--     SYNTAX      DisplayString (SIZE (0..38))
--     MAX-ACCESS  read-only
--     STATUS      current
--     DESCRIPTION
--         "tnDS3ChannelMDLMonGenString indicates the generator number string
--          received in the Message Data Link (MDL) test signal message."
--     ::= { tnDS3ChannelEntry 30 }
--
-- tnDS3ChannelBERTOperStatus    OBJECT-TYPE
--     SYNTAX      TmnxDSXBertOperStatus
--     MAX-ACCESS  read-only
--     STATUS      current
--     DESCRIPTION
--         "tnDS3ChannelBERTOperStatus indicates the status of the BERT test
--          as specified by TmnxDSXBertOperStatus."
--     ::= { tnDS3ChannelEntry 31 }
--
-- tnDS3ChannelBERTSynched    OBJECT-TYPE
--     SYNTAX      Unsigned32
--     UNITS       "seconds"
--     MAX-ACCESS  read-only
--     STATUS      current
--     DESCRIPTION
--         "tnDS3ChannelBERTSynched is the number of seconds for which the
--          BERT hardware was synchronized. This will be less than or equal to
--          the duration of the last BERT test. It is valid only after
--          tnDS3ChannelBERTOperStatus transitioned from 'active' to 'idle'
--          the last time BERT was activated."
--     ::= { tnDS3ChannelEntry 32 }
--
-- tnDS3ChannelBERTErrors    OBJECT-TYPE
--     SYNTAX      Counter64
--     MAX-ACCESS  read-only
--     STATUS      current
--     DESCRIPTION
--         "tnDS3ChannelBERTErrors is the number of bit errors detected during
--          the last BERT test. It is valid only after tnDS3ChannelBERTOperStatus
--          transitioned from 'active' to 'idle' the last time BERT
--          was activated."
--     ::= { tnDS3ChannelEntry 33 }
--
-- tnDS3ChannelBERTTotalBits    OBJECT-TYPE
--     SYNTAX      Counter64
--     MAX-ACCESS  read-only
--     STATUS      current
--     DESCRIPTION
--         "tnDS3ChannelBERTTotalBits is the total number of bits received
--          during the last BERT test. Bits are only counted when the BERT
--          hardware is synchronized. It is valid only after
--          tnDS3ChannelBERTOperStatus transitioned from 'active' to 'idle'
--          the last time BERT was activated."
--     ::= { tnDS3ChannelEntry 34 }
--
-- tnDS3ChannelScramble     OBJECT-TYPE
--     SYNTAX      TruthValue
--     MAX-ACCESS  read-create
--     STATUS      current
--     DESCRIPTION
--         "When tnDS3ChannelScramble indicates whether scrambling
--          is enabled on this channel.  Both ends of the connection
--          must use the same scrambling algorithm.  The default value
--          is 'true' if the tnPortEncapType is atmEncap for this
--          channel and indicates ATM payload scrambling; otherwise
--          (tnPortEncapType is not atmEncap) the default is 'false'
--          and can only be changed to true if the value of
--          tnDS3ChannelSubrateCSUMode is digital-link (1)"
--     ::= { tnDS3ChannelEntry 35 }
--
-- tnDS3ChannelAcctPolicyId     OBJECT-TYPE
--     SYNTAX      Unsigned32 (0..99)
--     MAX-ACCESS  read-create
--     STATUS      current
--     DESCRIPTION
--         "The value of tnDS3ChannelAcctPolicyId specifies an existing accounting
--          policy to use for the ds3 channel. Accounting policies can only be
--          associated with network ports or channels.
--
--          A non-zero value indicates the tmnxLogApPolicyId index identifying the
--          policy entry in the tmnxLogApTable from the TIMETRA-LOG-MIB which is
--          associated with this channel.  A zero value indicates that there is no
--          accounting policy associated with this channel"
--     DEFVAL { 0 }
--     ::= { tnDS3ChannelEntry 36 }
--
-- tnDS3ChannelCollectStats     OBJECT-TYPE
--     SYNTAX      TruthValue
--     MAX-ACCESS  read-create
--     STATUS      current
--     DESCRIPTION
--         "The value of tnDS3ChannelCollectStats specifies whether or not the
--          collection of accounting and statistical data for the network ds3
--          channel is collected.
--
--          When the value is set to false, the statistics are still accumulated
--          by the IOM cards, however, the CPM will not obtain the results and
--          write them to the billing file.
--
--          When applying accounting policies the data by default will be collected
--          in the appropriate records and written to the designated billing file."
--     DEFVAL { true }
--     ::= { tnDS3ChannelEntry 37 }
--
-- tnDS3ChannelClockSyncState    OBJECT-TYPE
--     SYNTAX      TmnxDSXClockSyncState
--     MAX-ACCESS  read-only
--     STATUS      current
--     DESCRIPTION
--         "The value of tnDS3ChannelClockSyncState indicates the current clock
--          synchronization state if tnDS3ChannelClockSource is 'adaptive' or
--          'differential'."
--     ::= { tnDS3ChannelEntry 38 }
--
-- tnDS3ChannelClockMasterPortId    OBJECT-TYPE
--     SYNTAX      TmnxPortID
--     MAX-ACCESS  read-only
--     STATUS      current
--     DESCRIPTION
--         "The value of tnDS3ChannelClockMasterPortId indicates the current
--          clock synchronization master port id if tnDS3ChannelClockSource
--          is 'adaptive' or 'differential'."
--     ::= { tnDS3ChannelEntry 39 }

--
-- DS1 table
--
-- tnDS1Table OBJECT-TYPE
--     SYNTAX      SEQUENCE OF TmnxDS1Entry
--     MAX-ACCESS  not-accessible
--     STATUS      current
--     DESCRIPTION
--         "The tnDS1Table has an entry for each DS1 channel."
--     ::= { tnPortObjs 12 }
--
-- tnDS1Entry       OBJECT-TYPE
--     SYNTAX      TmnxDS1Entry
--     MAX-ACCESS  not-accessible
--     STATUS      current
--     DESCRIPTION
--         "Each row entry represents a DS1 channel on a IOM card
--          in a chassis in the system.  DS1 channel entries for DS3
--          ports cannot be created and deleted via SNMP SET operations.
--          Entries in this table will be created automatically when
--          tnDS3ChannelChannelized is set to 'true'. DS1 channel entries
--          for DS1 ports can be created and deleted via SNMP SET operations.
--          For each tnDS1Entry, there will be a corresponding entry
--          in the tnPortTable and the ifTable."
--     INDEX       {  tnPortPortID }
--     ::= { tnDS1Table 1 }
--
-- TmnxDS1Entry ::=
--     SEQUENCE {
--         tnDS1RowStatus                RowStatus,
--         tnDS1Type                     INTEGER,
--         tnDS1Framing                  INTEGER,
-- ==        tnDS1IdleCycleFlags           TmnxDSXIdleCycleFlags,
--         tnDS1Loopback                 TmnxDS1Loopback,
--         tnDS1InvertData               TruthValue,
--         tnDS1BitErrorInsertionRate    Integer32,
--         tnDS1BERTPattern              TmnxDSXBertPattern,
--         tnDS1BERTDuration             Unsigned32,
--         tnDS1ReportAlarm              TmnxDSXReportAlarm,
--         tnDS1ReportAlarmStatus        TmnxDSXReportAlarm,
--         tnDS1LastChangeTime           TimeStamp,
--         tnDS1ClockSource              TmnxDSXClockSource,
--         tnDS1BERTOperStatus           TmnxDSXBertOperStatus,
--         tnDS1BERTSynched              Unsigned32,
--         tnDS1BERTErrors               Counter64,
--         tnDS1BERTTotalBits            Counter64,
--         tnDS1RemoteLoopRespond        TruthValue,
--         tnDS1InRemoteLoop             TruthValue,
--         tnDS1InsertSingleBitError     TmnxActionType,
--         tnDS1SignalMode               INTEGER,
--         tnDS1ClockSyncState           TmnxDSXClockSyncState,
--         tnDS1ClockMasterPortId        TmnxPortID,
--         tnDS1BerSdThreshold           Unsigned32,
--         tnDS1BerSfThreshold           Unsigned32,
--         tnDS1NationalUseBits          BITS
--     }
--
-- tnDS1RowStatus    OBJECT-TYPE
--     SYNTAX      RowStatus
--     MAX-ACCESS  read-create
--     STATUS      current
--     DESCRIPTION
--         "tnDS1RowStatus controls the creation and deletion of
--          row entries in the tnDS1Table.
--          For row creation, the manager has to first calculate the
--          tnPortPortID based on the TiMOS encoding scheme."
--     ::= { tnDS1Entry 1 }
--
-- tnDS1Type    OBJECT-TYPE
--     SYNTAX      INTEGER {
--                     ds1(1),
--                     e1 (2),
--                     j1 (3)
--                 }
--     MAX-ACCESS  read-only
--     STATUS      current
--     DESCRIPTION
--         "The value of tnDS1Type indicates whether the DS1 channel is
--          in DS1, E1 or J1 mode."
--     ::= { tnDS1Entry 2 }
--
-- tnDS1Framing    OBJECT-TYPE
--     SYNTAX      INTEGER {
--                     esf (1),
--                     sf  (2),
--                     g704-no-crc (3),
--                     g704 (4),
--                     e1-unframed (5),
--                     ds1-unframed (6)
--                 }
--     MAX-ACCESS  read-create
--     STATUS      current
--     DESCRIPTION
--         "The value of tnDS1Framing indicates the type of framing associated
--          with the channel:
--          esf            ESF (extended super frame) mode for T1 interfaces.
--          sf             SF (super frame) mode for T1 interfaces.
--          g704           G.704 framing format for E1 interfaces.
--          g704-no-crc4   G.704 framing with no CRC4 for E1 interfaces.
--          e1-unframed    E1 Unframed (G.703) mode for E1 interfaces.
--          ds1-unframed   Unframed mode for T1 interfaces.
--
--          If tnDS1Type is set to 'ds1', the default framing is 'esf'.
--          If tnDS1Type is set to 'e1', the default framing is 'g704'.
--
--          Changing the value of tnDS1Framing resets the values of
--          tnDS1BerSdThreshold and tnDS1BerSfThreshold to defaults
--          and turns off reporting of berSd and berSf alarms
--          in tnDS1ReportAlarm."
--     DEFVAL      { esf }
--     ::= { tnDS1Entry 3 }
--
-- == tnDS1IdleCycleFlags    OBJECT-TYPE
-- ==     SYNTAX      TmnxDSXIdleCycleFlags
-- ==     MAX-ACCESS  read-create
-- ==     STATUS      obsolete
-- ==     DESCRIPTION
-- ==         "tnDS1IdleCycleFlags configures the value that the DS1
-- ==          channel transmits during idle cycle."
-- ==     DEFVAL      { flags }
-- ==     ::= { tnDS1Entry 4 }
--
-- tnDS1Loopback    OBJECT-TYPE
--     SYNTAX      TmnxDS1Loopback
--     MAX-ACCESS  read-create
--     STATUS      current
--     DESCRIPTION
--         "tnDS1Loopback is used to put the channel into a loopback mode. The
--          value of tnPortAdminStatus should be set to 'outOfService' in order
--          for the loopback to be enabled.
--          A 'line' loopback loops frames received on this port back to the
--          remote system.
--          A 'internal' loopback loops frames from the local system back at
--          the framer.
--          A 'fdlAnsi' requests loopback of type FDL ANSI T1.403. This is valid
--          with tnDS1Framing set to 'esf' framing.
--          A 'fdlBellcore' requests loopback of type FDL Bellcore TR-TSY-000312.
--          This is valid with tnDS1Framing set to 'esf'.
--          A 'inbandAnsi' requests loopback of type inband ANSI T1.403. This is
--          valid with tnDS1Framing set to 'sf'."
--     DEFVAL      { none }
--     ::= { tnDS1Entry 5 }
--
-- tnDS1InvertData    OBJECT-TYPE
--     SYNTAX      TruthValue
--     MAX-ACCESS  read-create
--     STATUS      current
--     DESCRIPTION
--         "Setting tnDS1InvertData to 'true' causes all data bits to
--          be inverted, to guarantee ones density. It is typically used with
--          AMI line encoding."
--     DEFVAL      { false }
--     ::= { tnDS1Entry 6 }
--
-- tnDS1BitErrorInsertionRate    OBJECT-TYPE
--     SYNTAX      Integer32 (0 | 2..7)
--     MAX-ACCESS  read-create
--     STATUS      current
--     DESCRIPTION
--         "tnDS1BitErrorInsertionRate is used to insert bit errors for a
--          BERT test. The number of error corresponds to 10^(-rate). A rate of 7
--          will cause an error rate of 10^(-7), or 1 error in every 10
--          million bits transmitted.
--          If the value is set to 0, disables the insertion of bit errors into
--          the BERT.
--          Change in this value while the test is running is accepted but
--          does not take effect until the test gets restarted."
--     DEFVAL      { 0 }
--     ::= { tnDS1Entry 7 }
--
-- tnDS1BERTPattern    OBJECT-TYPE
--     SYNTAX      TmnxDSXBertPattern
--     MAX-ACCESS  read-create
--     STATUS      current
--     DESCRIPTION
--         "tnDS1BERTPattern object indicates the pattern used for the
--          Bit Error Rate Test (BERT). The value of tnDS1BERTDuration
--          indicates the duration of the test.
--          Setting the value to 'none' terminates the test."
--     DEFVAL      { none }
--     ::= { tnDS1Entry 8 }
--
-- tnDS1BERTDuration    OBJECT-TYPE
--     SYNTAX      Unsigned32 (0..86400)
--     UNITS       "seconds"
--     MAX-ACCESS  read-create
--     STATUS      current
--     DESCRIPTION
--         "tnDS1BERTDuration is used to set the duration of the BERT test."
--     ::= { tnDS1Entry 9 }
--
-- tnDS1ReportAlarm    OBJECT-TYPE
--     SYNTAX      TmnxDSXReportAlarm
--     MAX-ACCESS  read-create
--     STATUS      current
--     DESCRIPTION
--         "The value of tnDS1ReportAlarm determines when and if to
--          generate notifications for this channel:
--          ais - Reports alarm indication signal errors.
--                ais alarms are issued by default.
--          los - Reports loss of signal errors.
--                los alarms are issued by default.
--          oof - Reports out-of-frame errors.
--                oof alarms are not issued by default.
--          rai - Reports resource availability indicator events.
--                rai alarms are not issued by default.
--          looped - Reports if the far end has forced the near end to loopback.
--                looped alarms are not issued by default.
--          berSd - Reports DS1/E1/J1 signal degradation bit errors.
--                  berSd alarms are not issued by default.
--          berSf - Reports DS1/E1/J1 signal failure bit errors.
--                  berSf alarms are not issued by default"
--     DEFVAL      { {ais, los} }
--     ::= { tnDS1Entry 10 }
--
-- tnDS1ReportAlarmStatus    OBJECT-TYPE
--     SYNTAX      TmnxDSXReportAlarm
--     MAX-ACCESS  read-only
--     STATUS      current
--     DESCRIPTION
--         "The value of tnDS1ReportAlarmStatus indicates the current alarms
--          on this channel."
--     ::= { tnDS1Entry 11 }
--
-- tnDS1LastChangeTime    OBJECT-TYPE
--     SYNTAX      TimeStamp
--     MAX-ACCESS  read-only
--     STATUS      current
--     DESCRIPTION
--         "The tnDS1LastChangeTime variable contains the sysUpTime
--          value of the most recently modified writable variable in the
--          tnDS1Entry row for this channel."
--     ::= { tnDS1Entry 12 }
--
-- tnDS1ClockSource    OBJECT-TYPE
--     SYNTAX      TmnxDSXClockSource
--     MAX-ACCESS  read-create
--     STATUS      current
--     DESCRIPTION
--         "tnDS1ClockSource configures the clock for transmitted data from
--          either the internal clock ('nodeTimed'), or from a clock recovered
--          from the line's receive data stream ('loopTimed'), or recovered
--          adaptively from the rate at which the data that is received and not
--          from the physical layer ('adaptive'), or recovered from the
--          differential timestamp in the RTP header ('differential')."
--     DEFVAL      { loopTimed }
--     ::= { tnDS1Entry 13 }
--
-- tnDS1BERTOperStatus    OBJECT-TYPE
--     SYNTAX      TmnxDSXBertOperStatus
--     MAX-ACCESS  read-only
--     STATUS      current
--     DESCRIPTION
--         "tnDS1BERTOperStatus indicates the status of the BERT test as
--          specified by TmnxDSXBertOperStatus."
--     ::= { tnDS1Entry 14 }
--
-- tnDS1BERTSynched    OBJECT-TYPE
--     SYNTAX      Unsigned32
--     UNITS       "seconds"
--     MAX-ACCESS  read-only
--     STATUS      current
--     DESCRIPTION
--         "tnDS1BERTSynched is the number of seconds for which the
--          BERT hardware was synchronized. This will be less than or equal to
--          the duration of the last BERT test. It is valid only after
--          tnDS1BERTOperStatus transitioned from 'active' to 'idle'
--          the last time BERT was activated."
--     ::= { tnDS1Entry 15 }
--
-- tnDS1BERTErrors    OBJECT-TYPE
--     SYNTAX      Counter64
--     MAX-ACCESS  read-only
--     STATUS      current
--     DESCRIPTION
--         "tnDS1BERTErrors is the number of bit errors detected during
--          the last BERT test. It is valid only after tnDS1BERTOperStatus
--          transitioned from 'active' to 'idle' the last time BERT
--          was activated."
--     ::= { tnDS1Entry 16 }
--
-- tnDS1BERTTotalBits    OBJECT-TYPE
--     SYNTAX      Counter64
--     MAX-ACCESS  read-only
--     STATUS      current
--     DESCRIPTION
--         "tnDS1BERTTotalBits is the total number of bits received
--          during the last BERT test. Bits are only counted when the BERT
--          hardware is synchronized. It is valid only after
--          tnDS1BERTOperStatus transitioned from 'active' to 'idle'
--          the last time BERT was activated."
--     ::= { tnDS1Entry 17 }
--
-- tnDS1RemoteLoopRespond    OBJECT-TYPE
--     SYNTAX      TruthValue
--     MAX-ACCESS  read-create
--     STATUS      current
--     DESCRIPTION
--         "When tnDS1RemoteLoopRespond has a value of 'true', the channel
--         is enabled to respond to remote loop signals.  When it has
--         a value of 'false' the port will not respond."
--     DEFVAL      { false }
--     ::= { tnDS1Entry 18 }
--
-- tnDS1InRemoteLoop    OBJECT-TYPE
--     SYNTAX      TruthValue
--     MAX-ACCESS  read-only
--     STATUS      current
--     DESCRIPTION
--         "tnDS1InRemoteLoop indicates whether the remote end has put
--          this channel in remote loopback."
--     ::= { tnDS1Entry 19 }
--
-- tnDS1InsertSingleBitError    OBJECT-TYPE
--     SYNTAX      TmnxActionType
--     MAX-ACCESS  read-create
--     STATUS      current
--     DESCRIPTION
--         "tnDS1InsertSingleBitError is used to insert a single bit error for a
--          BERT test."
--     ::= { tnDS1Entry 20 }
--
-- tnDS1SignalMode    OBJECT-TYPE
--     SYNTAX      INTEGER {
--                     none (1),
--                     cas  (2)
--                 }
--     MAX-ACCESS  read-create
--     STATUS      current
--     DESCRIPTION
--         "The value of tnDS1SignalMode indicates the type of signalling
--          associated with the channel:
--          none  - Indicates no signalling on this channel.
--          cas   - Indicates Channel Associated Signalling (CAS) on this channel.
--          The default signalling is 'none'. "
--     DEFVAL      { none }
--     ::= { tnDS1Entry 21 }
--
-- tnDS1ClockSyncState    OBJECT-TYPE
--     SYNTAX      TmnxDSXClockSyncState
--     MAX-ACCESS  read-only
--     STATUS      current
--     DESCRIPTION
--         "The value of tnDS1ClockSyncState indicates the current clock
--          synchronization state if tnDS1ClockSource is 'adaptive' or
--          'differential'."
--     ::= { tnDS1Entry 22 }
--
-- tnDS1ClockMasterPortId    OBJECT-TYPE
--     SYNTAX      TmnxPortID
--     MAX-ACCESS  read-only
--     STATUS      current
--     DESCRIPTION
--         "The value of tnDS1ClockMasterPortId indicates the current clock
--          synchronization master port id if tnDS1ClockSource is 'adaptive'
--          or 'differential'."
--     ::= { tnDS1Entry 23 }
--
-- tnDS1BerSdThreshold       OBJECT-TYPE
--     SYNTAX      Unsigned32 (1|5|10|50|100)
--     UNITS       "error bits in million bits received"
--     MAX-ACCESS  read-create
--     STATUS      current
--     DESCRIPTION
--         "The value of tnDS1BerSdThreshold specifies a bit error rate (BER)
--          threshold used to determine when to send a tnEqPortDS1Alarm
--          notification for a BER SD failure and a tnEqPortDS1AlarmClear
--          notification for a BER SD failure clear. Bit error computed must
--          reach/exceed threshold value over a pre-defined period of time
--          for the tnEqPortSonetAlarm notification to be sent.
--
--          The value of tnDS1Framing defines how the bit error is
--          computed and what values of tnDS1BerSdThreshold are allowed.
--          The following table defines this dependency:
--
--          tnDS1Framing   Bit error calculation and value supported
--          ============   ============================================
--            esf  (1)       each CRC error is counted as one bit error
--            g704 (4)       values supported are 1,5,10,50,100
--
--            other values   bit error alarms not supported, value
--                           of tnDS1BerSdThreshold set to default and
--                           cannot be changed
--
--          tnDS1BerSdThreshold value must not exceed the value of
--          tnDS1BerSfThreshold."
--     DEFVAL { 5 }
--     ::= { tnDS1Entry 24 }
--
-- tnDS1BerSfThreshold       OBJECT-TYPE
--     SYNTAX      Unsigned32 (1|5|10|50|100)
--     UNITS       "error bits in million bits received"
--     MAX-ACCESS  read-create
--     STATUS      current
--     DESCRIPTION
--         "The value of tnDS1BerSfThreshold specifies a bit error rate (BER)
--          threshold used to determine when to send a tnEqPortDS1Alarm
--          notification for a BER SF failure and a tnEqPortDS1AlarmClear
--          notification for a BER SF failure clear. Bit error computed must
--          reach/exceed threshold value over a pre-defined period of time
--          for the tnEqPortSonetAlarm notification to be sent.
--
--          The value of tnDS1Framing defines how the bit errors are
--          computed and what values of tnDS1BerSfThreshold are allowed.
--          The following table defines this dependency:
--
--          tnDS1Framing   Bit error calculation and value supported
--          ============   ============================================
--            esf  (1)       each CRC error is counted as one bit error
--            g704 (4)       values supported are 1,5,10,50,100
--
--            other values   bit error alarms not supported, value
--                           of tnDS1BerSfThreshold set to default and
--                           cannot be changed
--
--          tnDS1BerSfThreshold value must not be smaller than
--          tnDS1BerSdThreshold value"
--     DEFVAL { 50 }
--     ::= { tnDS1Entry 25 }
--
-- tnDS1NationalUseBits           OBJECT-TYPE
--     SYNTAX      BITS {
--                     sa4 (0),
--                     sa5 (1),
--                     sa6 (2),
--                     sa7 (3),
--                     sa8 (4)
--                 }
--     MAX-ACCESS  read-create
--     STATUS      current
--     DESCRIPTION
--         "The tnDS1NationalUseBits specifies the transmitted value for each of
--          the E1 national use bits (Sa4 to Sa8).  This object is only
--          applicable on E1 channels with tnDS1Framing set to g704-no-crc (3),
--          or g704 (4)."
--     DEFVAL { {} }
--     ::= { tnDS1Entry 26 }

--
-- DS0 Channel Group Table
--
-- tnDS0ChanGroupTable   OBJECT-TYPE
--     SYNTAX      SEQUENCE OF TmnxDS0ChanGroupEntry
--     MAX-ACCESS  not-accessible
--     STATUS      current
--     DESCRIPTION
--         "The tnDS0ChanGroupTable has an entry for DS0 channels
--          grouped together and belonging to a particular DS1 channel."
--     ::= { tnPortObjs 13 }
--
-- tnDS0ChanGroupEntry       OBJECT-TYPE
--     SYNTAX      TmnxDS0ChanGroupEntry
--     MAX-ACCESS  not-accessible
--     STATUS      current
--     DESCRIPTION
--         "Each row entry represents one or more DS0 channels on a
--          DS1 interface.  tnDS0ChanGroupTimeSlots object is used to add or
--          remove DS0 channels from the group.
--
--          Entries can be created and deleted via SNMP SET operations
--          using the tnDS0ChanGroupRowStatus object.
--
--          For each tnDS0ChanGroupEntry, there will be a corresponding entry
--          in the tnPortTable and the ifTable."
--     INDEX       {  tnPortPortID }
--     ::= { tnDS0ChanGroupTable 1 }
--
-- TmnxDS0ChanGroupEntry ::=
--     SEQUENCE {
--         tnDS0ChanGroupRowStatus           RowStatus,
--         tnDS0ChanGroupTimeSlots           TmnxDs0ChannelList,
--         tnDS0ChanGroupSpeed               INTEGER,
--         tnDS0ChanGroupCRC                 INTEGER,
--         tnDS0ChanGroupMTU                 Unsigned32,
--         tnDS0ChanGroupOperMTU             Unsigned32,
--         tnDS0ChanGroupLastChangeTime      TimeStamp,
--         tnDS0ChanGroupIdleCycleFlags      TmnxDSXIdleCycleFlags,
--         tnDS0ChanGroupScramble            TruthValue,
--         tnDS0ChanGroupAcctPolicyId        Unsigned32,
--         tnDS0ChanGroupCollectStats        TruthValue,
--         tnDS0ChanGroupPayloadFillType     TmnxDSXIdleFillType,
--         tnDS0ChanGroupPayloadPattern      Unsigned32,
--         tnDS0ChanGroupSignalFillType      TmnxDSXIdleFillType,
--         tnDS0ChanGroupSignalPattern       Unsigned32,
--         tnDS0ChanGroupBerSfLinkDown       TruthValue
--     }
--
-- tnDS0ChanGroupRowStatus    OBJECT-TYPE
--     SYNTAX      RowStatus
--     MAX-ACCESS  read-create
--     STATUS      current
--     DESCRIPTION
--         "tnDS0ChanGroupRowStatus controls the creation and deletion of
--          row entries in the tnDS0ChanGroupTable. The tnPortPortID
--          for a channel group includes a group ID in the lower bits.
--          The manager has to first calculate the tnPortPortID based on the
--          TiMOS encoding scheme."
--     ::= { tnDS0ChanGroupEntry 1 }
--
-- tnDS0ChanGroupTimeSlots    OBJECT-TYPE
--     SYNTAX      TmnxDs0ChannelList
--     MAX-ACCESS  read-create
--     STATUS      current
--     DESCRIPTION
--         "tnDS0ChanGroupTimeSlots is a bitmap which is used to
--          add/remove DS0 timeslots from a channel group.
--          The description for TmnxDs0ChannelList contains details of the
--          bitmap organization.
--
--          When a channel group is created on unframed DS1/E1, all timeslots
--          as applicable to a given speed are auto-allocated and cannot be
--          changed.
--
--          When a channel group is created on a framed DS1/E1 or
--          existing channel group's encapsulation is changed from ATM,
--          the default of no timeslots is auto-assigned to the group.
--
--          When a channel group  on a framed DS1/E1 is configured for
--          ATM encapsulation, the ATM defaults of 0x00FFFFFF (DS1)
--          and 0XFFFEFFFE (E1) are auto-assigned and cannot be changed."
--     ::= { tnDS0ChanGroupEntry 2 }
--
-- tnDS0ChanGroupSpeed    OBJECT-TYPE
--     SYNTAX      INTEGER {
--                     speed-56 (1),
--                     speed-64 (2)
--                 }
--     MAX-ACCESS  read-create
--     STATUS      current
--     DESCRIPTION
--         "tnDS0ChanGroupSpeed configures the required link speed
--          for all the time slots included in this channel group."
--     ::= { tnDS0ChanGroupEntry 3 }
--
-- tnDS0ChanGroupCRC    OBJECT-TYPE
--     SYNTAX      INTEGER {
--                     crc16 (1),
--                     crc32 (2)
--                 }
--     MAX-ACCESS  read-create
--     STATUS      current
--     DESCRIPTION
--         "The value of tnDS0ChanGroupCRC variable indicates the precision of
--          the cyclic redundancy check.  A value of 'crc16' is a 16-bit
--          CRC calculation.  A value of 'crc32' is a 32-bit CRC
--          calculation.  32-bit CRC increases the error detection ability,
--          but it also adds some performance overhead.
--
--          For channel groups with encapsulation set to ATM, the default and
--          only supported value is crc32 and applies to AAL5 CRC calculations
--          on that channel group."
--     DEFVAL      { crc16 }
--     ::= { tnDS0ChanGroupEntry 4 }
--
-- tnDS0ChanGroupMTU  OBJECT-TYPE
--     SYNTAX      Unsigned32 (0|512..9208)
--     UNITS       "bytes"
--     MAX-ACCESS  read-create
--     STATUS      current
--     DESCRIPTION
--         "The size of the largest packet which can be sent/received
--          on the channel group, specified in octets.  For groups that
--          are used for transmitting network datagrams, this is the
--          size of the largest network datagram that can be sent.
--
--          Setting tnDS0ChanGroupMTU to a value of zero (0), causes the agent
--          to recalculate the default MTU size which can vary based on the
--          current setting of tnPortMode and tnPortEncapType variables.
--          Some typical default values are:
--                 1522 with mode access and encap-type bcp-null
--                 1526 with mode access and encap-type bcp-dot1q
--                 1502 with mode access and encap-type ipcp
--                 4474 with mode access and encap-type frame-relay
--                 1524 with mode access and encap-type atm
--                 2092 with mode access and encap-type cem
--         "
--     ::= { tnDS0ChanGroupEntry 5 }
--
-- tnDS0ChanGroupOperMTU    OBJECT-TYPE
--     SYNTAX      Unsigned32
--     UNITS       "bytes"
--     MAX-ACCESS  read-only
--     STATUS      current
--     DESCRIPTION
--         "The negotiated size of the largest packet which can be sent on
--          the channel group, specified in octets.  For channel groups that
--          are used for transmitting network datagrams, this is the size of
--          the largest network datagram that can be sent."
--     ::= { tnDS0ChanGroupEntry 6 }
--
-- tnDS0ChanGroupLastChangeTime    OBJECT-TYPE
--     SYNTAX      TimeStamp
--     MAX-ACCESS  read-only
--     STATUS      current
--     DESCRIPTION
--         "The tnDS0ChanGroupLastChangeTime variable contains the sysUpTime
--          value of the most recently modified writable variable in the
--          tnDS0ChanGroupEntry row for this channel group."
--     ::= { tnDS0ChanGroupEntry 7 }
--
-- tnDS0ChanGroupIdleCycleFlags    OBJECT-TYPE
--     SYNTAX      TmnxDSXIdleCycleFlags
--     MAX-ACCESS  read-create
--     STATUS      current
--     DESCRIPTION
--         "tnDS0ChanGroupIdleCycleFlags configures the value that the
--          channel group transmits during idle cycle.
--
--          The default value applies to HDLC channels only. For ATM and CEM
--          channels the object does not really apply so a default value of
--          'none' is used and cannot be changed."
--     DEFVAL      { flags }
--     ::= { tnDS0ChanGroupEntry 8 }
--
-- tnDS0ChanGroupScramble     OBJECT-TYPE
--     SYNTAX      TruthValue
--     MAX-ACCESS  read-create
--     STATUS      current
--     DESCRIPTION
--         "tnDS0ChanGroupScramble indicates whether payload scrambling
--          is enabled on this ATM channel.  Both ends of the connection
--          must use the same scrambling algorithm.  The default value
--          is 'true' if the tnPortEncapType is atmEncap for this
--          channel, otherwise the default is 'false' and not allowed to
--          change."
--     ::= { tnDS0ChanGroupEntry 9 }
--
-- tnDS0ChanGroupAcctPolicyId OBJECT-TYPE
--     SYNTAX      Unsigned32 (0..99)
--     MAX-ACCESS  read-create
--     STATUS      current
--     DESCRIPTION
--         "The value of tnDS0ChanGroupAcctPolicyId specifies an existing accounting
--          policy to use for the ds0 channel-group. Accounting policies can only
--          be associated with network ports or channels.
--
--          A non-zero value indicates the tmnxLogApPolicyId index identifying the
--          policy entry in the tmnxLogApTable from the TIMETRA-LOG-MIB which is
--          associated with this channel-group.  A zero value indicates that there is
--          no accounting policy associated with this channel"
--     DEFVAL { 0 }
--     ::= { tnDS0ChanGroupEntry 10 }
--
-- tnDS0ChanGroupCollectStats     OBJECT-TYPE
--     SYNTAX      TruthValue
--     MAX-ACCESS  read-create
--     STATUS      current
--     DESCRIPTION
--         "The value of tnDS0ChanGroupCollectStats specifies whether or not the
--          collection of accounting and statistical data for the network ds0
--          channel-group is collected.
--
--          When the value is set to false, the statistics are still accumulated
--          by the IOM cards, however, the CPM will not obtain the results and
--          write them to the billing file.
--
--          When applying accounting policies the data by default will be collected
--          in the appropriate records and written to the designated billing file."
--     DEFVAL { true }
--     ::= { tnDS0ChanGroupEntry 11 }
--
-- tnDS0ChanGroupPayloadFillType  OBJECT-TYPE
--     SYNTAX      TmnxDSXIdleFillType
--     MAX-ACCESS  read-create
--     STATUS      current
--     DESCRIPTION
--         "The value of tnDS0ChanGroupPayloadFillType specifies the type of
--          idle payload fill to be sent when the CEM channel group experiences
--          an underrun.
--
--          If the type is set to 'userDefinedPattern' then the value of
--          tnDS0ChanGroupPayloadPattern is used to define the payload pattern.
--
--          The default value depends on the encap type of the channel group:
--          For CEM encap           - 'allOnes'
--          For all other encaps    - 'notApplicable'
--
--          For a ds1-unframed and e1-unframed CEM encap DS0 channel group the
--          only supported value is 'allOnes'.
--
--          For non-CEM encap channel groups the value cannot be changed."
--     DEFVAL { notApplicable }
--     ::= { tnDS0ChanGroupEntry 12 }
--
-- tnDS0ChanGroupPayloadPattern   OBJECT-TYPE
--     SYNTAX      Unsigned32 (0..255)
--     MAX-ACCESS  read-create
--     STATUS      current
--     DESCRIPTION
--         "The value of tnDS0ChanGroupPayloadPattern specifies the idle payload
--          fill pattern when the CEM channel group experiences an underrun and
--          tnDS0ChanGroupPayloadFillType is set to 'userDefinedPattern'.
--
--          The default value depends on the encap type of the channel group:
--          For CEM encap channel group             - 255 (Valid range 0..255)
--          For non-CEM encap channel group         -   0 (Valid range 0..0)."
--     DEFVAL { 0 }
--     ::= { tnDS0ChanGroupEntry 13 }
--
-- tnDS0ChanGroupSignalFillType   OBJECT-TYPE
--     SYNTAX      TmnxDSXIdleFillType
--     MAX-ACCESS  read-create
--     STATUS      current
--     DESCRIPTION
--         "The value of tnDS0ChanGroupSignalFillType specifies the type of
--          idle signal fill to be sent when the CAS CEM channel group experiences
--          an underrun.
--
--          If the type is set to 'userDefinedPattern' then the value of
--          tnDS0ChanGroupSignalPattern is used to define the signal pattern.
--
--          The default value depends on the encap of the DS0 channel group and
--          the signal-mode of the DS1/E1:
--          For CEM encap on DS1/E1 with CAS signal mode    - 'allOnes'
--          For all other encaps or non-CAS CEM DS1/E1      - 'notApplicable'
--
--          For CEM channel groups on DS1/E1 with no CAS signalling and non-CEM
--          encap channel groups the value cannot be changed."
--     DEFVAL {  notApplicable }
--     ::= { tnDS0ChanGroupEntry 14 }
--
-- tnDS0ChanGroupSignalPattern   OBJECT-TYPE
--     SYNTAX      Unsigned32 (0..15)
--     MAX-ACCESS  read-create
--     STATUS      current
--     DESCRIPTION
--         "The value of tnDS0ChanGroupSignalPattern specifies the idle signal
--          fill pattern when the CAS CEM channel group experiences an underrun
--          and tnDS0ChanGroupSignalFillType is set to 'userDefinedPattern'.
--
--          CAS ESF DS1 and CAS E1 support 4 signalling bits per timeslot (ABCD)
--          CAS SF DS1 supports 2 signalling bits per timeslot (AB)
--
--          The default value depends on the type of channel group:
--          For CAS DS1 ESF or CAS E1 channel group -  15 (Valid range 0..15)
--          For CAS DS1 SF channel group            -   3 (Valid range 0..3)
--          For non-CAS or non-CEM channel group    -   0 (Valid range 0..0)"
--     DEFVAL { 0 }
--     ::= { tnDS0ChanGroupEntry 15 }
--
-- tnDS0ChanGroupBerSfLinkDown    OBJECT-TYPE
--     SYNTAX      TruthValue
--     MAX-ACCESS  read-create
--     STATUS      current
--     DESCRIPTION
--         "The value of tnDS0ChanGroupBerSfLinkDown specifies whether or not
--          the DS0 channel-group will become operationally down when a BER-SF
--          alarm is raised. If tnDS0ChanGroupBerSfLinkDown is false then the
--          channel-group will not operationally change state due to BER-SF
--          alarms."
--     DEFVAL { false }
--     ::= { tnDS0ChanGroupEntry 16 }

--
-- Bundle Table
--
-- tnBundleTable   OBJECT-TYPE
--     SYNTAX      SEQUENCE OF TmnxBundleEntry
--     MAX-ACCESS  not-accessible
--     STATUS      current
--     DESCRIPTION
--         "The tnBundleTable has an entry for a bundle created on the system."
--     ::= { tnPortObjs 14 }
--
-- tnBundleEntry       OBJECT-TYPE
--     SYNTAX      TmnxBundleEntry
--     MAX-ACCESS  not-accessible
--     STATUS      current
--     DESCRIPTION
--         "Each row entry represents a multilink bundle on a MDA.
--          Entries can be created and deleted via SNMP SET operations
--          using the tnBundleRowStatus object. The tnBundleBundleID will
--          contain the bundle number encoded in it. The bundle number is
--          unique for a MDA.
--          For each tnBundleEntry, there will be a corresponding entry
--          in the tnPortTable and the ifTable."
--     INDEX       {  tnBundleBundleID }
--     ::= { tnBundleTable 1 }
--
-- TmnxBundleEntry ::=
--     SEQUENCE {
--         tnBundleBundleID            TmnxBundleID,
--         tnBundleRowStatus           RowStatus,
--         tnBundleType                INTEGER,
--         tnBundleMinimumLinks        Unsigned32,
--         tnBundleNumLinks            Unsigned32,
--         tnBundleNumActiveLinks      Unsigned32,
--         tnBundleMRRU                Unsigned32,
--         tnBundleOperMRRU            Unsigned32,
--         tnBundlePeerMRRU            Unsigned32,
--         tnBundleOperMTU             Unsigned32,
--         tnBundleRedDiffDelay        Unsigned32,
--         tnBundleRedDiffDelayAction  INTEGER,
--         tnBundleYellowDiffDelay     Unsigned32,
--         tnBundleShortSequence       TruthValue,
--         tnBundleLastChangeTime      TimeStamp,
--         tnBundleFragmentThreshold   Unsigned32,
--         tnBundleUpTime              Unsigned32,
--         tnBundleInputDiscards       Counter32,
--         tnBundlePrimaryMemberPortID TmnxPortID,
--         tnBundleLFI                 TruthValue,
--         tnBundleProtectedType       INTEGER,
--         tnBundleParentBundle        TmnxBundleID
--    }
--
-- tnBundleBundleID    OBJECT-TYPE
--     SYNTAX      TmnxBundleID
--     MAX-ACCESS  not-accessible
--     STATUS      current
--     DESCRIPTION
--         "tnBundleBundleID identifies this multilink bundle. The value of
--          this object is calculated using the TiMOS encoding scheme described
--          in TmnxBundleID.
--          tnBundleBundleID is used as an index into the ifTable and the
--          tnPortTable to access an entry corresponding to this entry."
--     ::= { tnBundleEntry 1 }
--
-- tnBundleRowStatus    OBJECT-TYPE
--     SYNTAX      RowStatus
--     MAX-ACCESS  read-create
--     STATUS      current
--     DESCRIPTION
--         "tnBundleRowStatus controls the creation and deletion of
--          row entries in the tnBundleTable.
--
--          The manager has to first calculate the tnBundleBundleID
--          based on the TiMOS encoding."
--     ::= { tnBundleEntry 2 }
--
-- tnBundleType    OBJECT-TYPE
--     SYNTAX      INTEGER {
--                     mlppp (1),
--                     mlfr  (2),
--                     imagrp (3)
--                 }
--     MAX-ACCESS  read-create
--     STATUS      current
--     DESCRIPTION
--         "tnBundleType specifies the type of this multilink bundle.
--          It provides a reference as to the type of bundle this row
--          refers to but does not map to the direct value of
--          bndle type defined in TmnxBundleID."
--     DEFVAL      { mlppp }
--     ::= { tnBundleEntry 3 }
--
-- tnBundleMinimumLinks    OBJECT-TYPE
--     SYNTAX      Unsigned32 (1..8)
--     MAX-ACCESS  read-create
--     STATUS      current
--     DESCRIPTION
--         "tnBundleMinimumLinks is the minimum number of links that must be
--          active for a bundle to be active. If the number of links drop below
--          the given minimum then the multilink bundle will transition to an
--          operation down state."
--     ::= { tnBundleEntry 4 }
--
-- tnBundleNumLinks    OBJECT-TYPE
--     SYNTAX      Unsigned32
--     MAX-ACCESS  read-only
--     STATUS      current
--     DESCRIPTION
--         "tnBundleNumLinks indicates the total number of links configured
--          for this bundle."
--     ::= { tnBundleEntry 5 }
--
-- tnBundleNumActiveLinks    OBJECT-TYPE
--     SYNTAX      Unsigned32
--     MAX-ACCESS  read-only
--     STATUS      current
--     DESCRIPTION
--         "tnBundleNumActiveLinks indicates the current number of active links
--          belonging to this bundle."
--     ::= { tnBundleEntry 6 }
--
-- tnBundleMRRU    OBJECT-TYPE
--     SYNTAX      Unsigned32 (0|1500..9206)
--     UNITS       "bytes"
--     MAX-ACCESS  read-create
--     STATUS      current
--     DESCRIPTION
--         "tnBundleMRRU is used to configure the
--          Max Received Reconstructed Unit (MRRU). This is the maximum frame that
--          can be reconstructed from multilink fragments.
--          This object is only applicable to tnBundleType value of mlppp.
--          All non applicable types have a value of zero."
--     DEFVAL      { 1524 }
--     ::= { tnBundleEntry 7 }
--
-- tnBundleOperMRRU    OBJECT-TYPE
--     SYNTAX      Unsigned32
--     UNITS       "bytes"
--     MAX-ACCESS  read-only
--     STATUS      current
--     DESCRIPTION
--         "tnBundleOperMRRU indicates the operational value of
--          Max Received Reconstructed Unit (MRRU).
--          This object is only applicable to tnBundleType value of mlppp.
--          All non applicable types have a value of zero."
--     ::= { tnBundleEntry 8 }
--
-- tnBundlePeerMRRU    OBJECT-TYPE
--     SYNTAX      Unsigned32
--     UNITS       "bytes"
--     MAX-ACCESS  read-only
--     STATUS      current
--     DESCRIPTION
--         "tnBundlePeerMRRU indicates the MRRU value sent by the peer
--          during negotiation.
--          This object is only applicable to tnBundleType value of mlppp.
--          All non applicable types have a value of zero."
--     ::= { tnBundleEntry 9 }
--
-- tnBundleOperMTU    OBJECT-TYPE
--     SYNTAX      Unsigned32
--     UNITS       "bytes"
--     MAX-ACCESS  read-only
--     STATUS      current
--     DESCRIPTION
--         "tnBundleOperMTU indicates the operational MTU of the bundle."
--     ::= { tnBundleEntry 10 }
--
-- tnBundleRedDiffDelay    OBJECT-TYPE
--     SYNTAX      Unsigned32 (0..25|0..50)
--     UNITS       "milliseconds"
--     MAX-ACCESS  read-create
--     STATUS      current
--     DESCRIPTION
--         "tnBundleRedDiffDelay configures the maximum acceptable differential
--          delay for individual circuits within this multilink bundle. If
--          the delay exceeds this threshold, a tnEqPortBndlRedDiffExceeded
--          trap is issued.
--
--          For a tnBundleType value of 'imagrp' a range of 0 to 50 is supported,
--          0 to 25 otherwise."
--     ::= { tnBundleEntry 11 }
--
-- tnBundleRedDiffDelayAction    OBJECT-TYPE
--     SYNTAX      INTEGER {
--                     none (0),
--                     down (1)
--                 }
--     MAX-ACCESS  read-create
--     STATUS      current
--     DESCRIPTION
--         "tnBundleRedDiffDelayAction specifies the action to be taken
--          when the differential delay exceeds the threshold configured in
--          tnBundleRedDiffDelay.
--          For a tnBundleType value of 'imagrp', only the down action is
--          supported."
--     DEFVAL      { none }
--     ::= { tnBundleEntry 12 }
--
-- tnBundleYellowDiffDelay    OBJECT-TYPE
--     SYNTAX      Unsigned32 (0..25)
--     UNITS       "milliseconds"
--     MAX-ACCESS  read-create
--     STATUS      current
--     DESCRIPTION
--         "tnBundleYellowDiffDelay configures the yellow warning
--          threshold for the differential delay for the circuits
--          within a given multilink bundle. If the delay exceeds this
--          threshold, a tnEqPortBndlYellowDiffExceeded trap is issued.
--          This object is only applicable to tnBundleType values of
--          'mlppp' or 'mlfr'. All non applicable types have a value
--          of zero."
--     ::= { tnBundleEntry 13 }
--
-- tnBundleShortSequence    OBJECT-TYPE
--     SYNTAX      TruthValue
--     MAX-ACCESS  read-create
--     STATUS      current
--     DESCRIPTION
--         "tnBundleShortSequence command specifies that the MLPPP bundle
--          should use short (12 bit) sequence numbers. Instead of the
--          standard long (24 bits) sequence number.
--          This object is only applicable to tnBundleType value of mlppp."
--     DEFVAL      { false }
--     ::= { tnBundleEntry 14 }
--
-- tnBundleLastChangeTime    OBJECT-TYPE
--     SYNTAX      TimeStamp
--     MAX-ACCESS  read-only
--     STATUS      current
--     DESCRIPTION
--         "The tnBundleLastChangeTime variable contains the sysUpTime
--          value of the most recently modified writable variable in the
--          tnBundleEntry row for this channel group."
--     ::= { tnBundleEntry 15 }
--
-- tnBundleFragmentThreshold     OBJECT-TYPE
--     SYNTAX      Unsigned32(0|128..512)
--     UNITS       "bytes"
--     MAX-ACCESS  read-create
--     STATUS      current
--     DESCRIPTION
--         "The value of tnBundleFragmentThreshold specifies the maximum length
--          of a fragment transmitted across the multilink bundle. Values supported
--          within each bundle type are hardware dependent. The value of 0 specifies
--          no fragmentation.
--
--          Currently, the following values are supported depending upon the
--          tnBundleType value:
--
--              tnBundleType         tnBundleFragmentThreshold values supported
--               mlppp                   0; 128 to 512 inclusive
--               imagrp                  128
--               mlfr                    0; 128 to 512 inclusive"
--     DEFVAL      { 128 }
--     ::= { tnBundleEntry 16 }
--
-- tnBundleUpTime    OBJECT-TYPE
--     SYNTAX      Unsigned32
--     UNITS       "seconds"
--     MAX-ACCESS  read-only
--     STATUS      current
--     DESCRIPTION
--         "tnBundleUpTime indicates the time since the bundle is operationally
--          'inService'."
--     ::= { tnBundleEntry 17 }
--
-- tnBundleInputDiscards    OBJECT-TYPE
--     SYNTAX      Counter32
--     MAX-ACCESS  read-only
--     STATUS      current
--     DESCRIPTION
--         "tnBundleInputDiscards indicates the number of LCP packets that
--          were discarded. This object is only supported for a
--          tnBundleType value of mlppp."
--     ::= { tnBundleEntry 18 }
--
-- tnBundlePrimaryMemberPortID    OBJECT-TYPE
--     SYNTAX      TmnxPortID
--     MAX-ACCESS  read-only
--     STATUS      current
--     DESCRIPTION
--         "tnBundlePrimaryMemberPortID indicates the TmnxPortID of the primary
--          member of this bundle. The value of this object will be zero if
--          there are no members configured in this bundle."
--     ::= { tnBundleEntry 19 }
--
-- tnBundleLFI    OBJECT-TYPE
--     SYNTAX      TruthValue
--     MAX-ACCESS  read-create
--     STATUS      current
--     DESCRIPTION
--         "tnBundleLFI specifies if Link Fragmentation and
--          Interleaving is enabled on the multilink bundle. A value of 'false'
--          indicates that Link Fragmentation and Interleaving is disabled on the
--          multilink bundle while a value of 'true' indicates that Link
--          Fragmentation and Interleaving is enabled on the multilink bundle.
--
--          This object is only supported for tnBundleType value of mlppp.
--
--          The value of tnBundleLFI may be modified only when no members are
--          part of the bundle.
--
--          This object cannot be set to true when tnBundleMlpppClassCount object
--          value is set to enable Multiclass MLPPP on the bundle."
--     DEFVAL      { false }
--     ::= { tnBundleEntry 20 }
--
-- tnBundleProtectedType OBJECT-TYPE
--     SYNTAX      INTEGER {
--                     none       (0),
--                     working    (1),
--                     protection (2)
--                 }
--     MAX-ACCESS  read-create
--     STATUS      current
--     DESCRIPTION
--         "tnBundleProtectedType identifies how this bundle is part
--         of a tnBundleParentBundle. A value of 'none' identifies no protection,
--         'working' identifies it to be a working bundle of a tnBundleParentBundle and
--         'protection' identifies it to be a protection bundle of a tnBundleParentBundle.
--         tnBundleProtectedType can only be set at row creation."
--     DEFVAL { none }
--     ::= { tnBundleEntry 21 }
--
-- tnBundleParentBundle OBJECT-TYPE
--     SYNTAX      TmnxBundleID
--     MAX-ACCESS  read-create
--     STATUS      current
--     DESCRIPTION
--         "tnBundleParentBundle specifies the parent to which this bundle belongs.
--         A row for the given non zero walue of tnBundleParentBundle must exist for
--         this row to be successfully created. If a bundle has no parent, its value
--         is zero. tnBundleParentBundle can only be set at row creation."
--     DEFVAL { 0 }
--     ::= { tnBundleEntry 22 }

--
-- Bundle Link Table
--
-- tnBundleMemberTable   OBJECT-TYPE
--     SYNTAX      SEQUENCE OF TmnxBundleMemberEntry
--     MAX-ACCESS  not-accessible
--     STATUS      current
--     DESCRIPTION
--         "The tnBundleMemberTable has an entry for a member port
--          associated with a multilink bundle."
--     ::= { tnPortObjs 15 }
--
-- tnBundleMemberEntry       OBJECT-TYPE
--     SYNTAX      TmnxBundleMemberEntry
--     MAX-ACCESS  not-accessible
--     STATUS      current
--     DESCRIPTION
--         "Each row represents a port associated with a bundle. Entries
--          can be added or removed from this table using SNMP SET operation."
--     INDEX   { tnBundleBundleID, tnPortPortID }
--     ::= { tnBundleMemberTable 1 }
--
-- TmnxBundleMemberEntry ::=
--     SEQUENCE {
--         tnBundleMemberRowStatus           RowStatus,
--         tnBundleMemberActive              TruthValue,
--         tnBundleMemberDownReason          INTEGER,
--         tnBundleMemberUpTime              Unsigned32
--     }
--
-- tnBundleMemberRowStatus    OBJECT-TYPE
--     SYNTAX      RowStatus
--     MAX-ACCESS  read-create
--     STATUS      current
--     DESCRIPTION
--         "tnBundleMemberRowStatus controls the creation and deletion of
--          row entries in the tnBundleMemberTable.
--          tnPortPortID identifies the port to be associated with the bundle.
--          A bundle entry with tnBundleBundleID has to exist in the
--          tnBundleTable before creating an entry in this table."
--     ::= { tnBundleMemberEntry 1 }
--
-- tnBundleMemberActive    OBJECT-TYPE
--     SYNTAX      TruthValue
--     MAX-ACCESS  read-only
--     STATUS      current
--     DESCRIPTION
--         "tnBundleMemberActive is set to 'false' for one of reasons in
--          tnBundleMemberDownReason."
--     ::= { tnBundleMemberEntry 2 }
--
-- tnBundleMemberDownReason    OBJECT-TYPE
--     SYNTAX      INTEGER {
--                     none (0),
--                     outOfService (1),
--                     redDiffDelayExceeded (2),
--                     mismatchEndPtDiscriminator (3),
--                     peerNotBundleMember (4),
--                     underNegotiation (5),
--                     peerInvalidMlHdrFmt(6),
--                     other(7)
--                 }
--     MAX-ACCESS  read-only
--     STATUS      current
--     DESCRIPTION
--         "tnBundleMemberDownReason contains the reason code for marking
--          the member link of the bundle to down (i.e. tnBundleMemberActive
--          will be set to false):
--              none - The link is active and the value of tnBundleMemberActive
--                     is 'true'.
--              outOfService - The link operational status is down.
--              redDiffDelayExceeded - The differential delay of the link
--                     exceeded the configured value of red differential delay
--                     and tnBundleRedDiffDelayAction was configured as 'down'.
--              mismatchEndPtDiscriminator - Detected inconsistent peer endpoint
--                     discriminator for the bundle.
--              peerNotBundleMember - When the peer is either not added to the
--                     bundle or is removed from the bundle.
--              underNegotiation - When the local end is trying to negotiate with
--                     the peer.
--              peerInvalidMlHdrFmt - The peer does not support the required ML-PPP
--                     header format. The remote peer must support the same short/long
--                     sequence code, and at least as many classes as configured for the
--                     local bundle.
--              other - Refer to the corresponding member table, if any, for more
--                      information based on the tnBundleType.
--         "
--     ::= { tnBundleMemberEntry 3 }
--
-- tnBundleMemberUpTime    OBJECT-TYPE
--     SYNTAX      Unsigned32
--     UNITS       "seconds"
--     MAX-ACCESS  read-only
--     STATUS      current
--     DESCRIPTION
--         "tnBundleMemberUpTime indicates the time since the bundle member is
--          active as indicated by tnBundleMemberActive."
--     ::= { tnBundleMemberEntry 4 }

--
-- Physical Port to Channel Mapping Table
--
-- tnPortToChannelTable   OBJECT-TYPE
--     SYNTAX      SEQUENCE OF TmnxPortToChannelEntry
--     MAX-ACCESS  not-accessible
--     STATUS      current
--     DESCRIPTION
--         "The tnPortToChannelTable is a mapping table. Given a chassis index,
--          physical port index and channel string, it maps it to the index
--          of the channel. This channel index can then be used as an index
--          into the ifTable or the tnPortTable."
--     ::= { tnPortObjs 16 }
--
-- tnPortToChannelEntry       OBJECT-TYPE
--     SYNTAX      TmnxPortToChannelEntry
--     MAX-ACCESS  not-accessible
--     STATUS      current
--     DESCRIPTION
--         "Each row represents a mapping of the physical port index and the
--          channel index string to the index of the channel."
--     INDEX   {  tnPortPortID, tmnxChannelIdxString }
--     ::= { tnPortToChannelTable 1 }
--
-- TmnxPortToChannelEntry ::=
--     SEQUENCE {
--         tmnxChannelIdxString     DisplayString,
--         tmnxChannelPortID        TmnxPortID
--     }
--
-- tmnxChannelIdxString    OBJECT-TYPE
--     SYNTAX      DisplayString
--     MAX-ACCESS  not-accessible
--     STATUS      current
--     DESCRIPTION
--         "tmnxChannelIdxString is an index into the table. It contains
--          a string identifying a channel on the physical port."
--     ::= { tnPortToChannelEntry 1 }
--
-- tmnxChannelPortID    OBJECT-TYPE
--     SYNTAX      TmnxPortID
--     MAX-ACCESS  read-only
--     STATUS      current
--     DESCRIPTION
--         "tmnxChannelPortID contains the port ID of the channel. This value
--          is used to identify the entry for this channel in the ifTable or
--          the tnPortTable."
--     ::= { tnPortToChannelEntry 2 }

--
--  Network Port ingress MDA QoS queue drop Stats Table
--
-- tnPortIngrMdaQosStatTable OBJECT-TYPE
--     SYNTAX      SEQUENCE OF TmnxPortIngrMdaQosStatEntry
--     MAX-ACCESS  not-accessible
--     STATUS      current
--     DESCRIPTION
--         "The table tnPortIngrMdaQosStatTable contains a row for each ethernet
--          port located on an oversubscribed MDA."
--     ::= { tnPortObjs 17 }
--
-- tnPortIngrMdaQosStatEntry    OBJECT-TYPE
--     SYNTAX      TmnxPortIngrMdaQosStatEntry
--     MAX-ACCESS  not-accessible
--     STATUS      current
--     DESCRIPTION
--         "Each row entry indicates the MDA QoS discard statistics for an
--          ethernet port located on an oversubscribed MDA.
--          tnPortEtherIngressRate object in the tnPortEtherTable indicates
--          the ingress rate configured for the port."
--     INDEX   {  tnPortPortID }
--     ::= { tnPortIngrMdaQosStatTable 1 }
--
-- TmnxPortIngrMdaQosStatEntry ::=
--     SEQUENCE {
--         tnPortIngrMdaQos00StatDropPkts   Counter64,
--         tnPortIngrMdaQos00StatDropOcts   Counter64,
--         tnPortIngrMdaQos01StatDropPkts   Counter64,
--         tnPortIngrMdaQos01StatDropOcts   Counter64,
--         tnPortIngrMdaQos02StatDropPkts   Counter64,
--         tnPortIngrMdaQos02StatDropOcts   Counter64,
--         tnPortIngrMdaQos03StatDropPkts   Counter64,
--         tnPortIngrMdaQos03StatDropOcts   Counter64,
--         tnPortIngrMdaQos04StatDropPkts   Counter64,
--         tnPortIngrMdaQos04StatDropOcts   Counter64,
--         tnPortIngrMdaQos05StatDropPkts   Counter64,
--         tnPortIngrMdaQos05StatDropOcts   Counter64,
--         tnPortIngrMdaQos06StatDropPkts   Counter64,
--         tnPortIngrMdaQos06StatDropOcts   Counter64,
--         tnPortIngrMdaQos07StatDropPkts   Counter64,
--         tnPortIngrMdaQos07StatDropOcts   Counter64,
--         tnPortIngrMdaQos08StatDropPkts   Counter64,
--         tnPortIngrMdaQos08StatDropOcts   Counter64,
--         tnPortIngrMdaQos09StatDropPkts   Counter64,
--         tnPortIngrMdaQos09StatDropOcts   Counter64,
--         tnPortIngrMdaQos10StatDropPkts   Counter64,
--         tnPortIngrMdaQos10StatDropOcts   Counter64,
--         tnPortIngrMdaQos11StatDropPkts   Counter64,
--         tnPortIngrMdaQos11StatDropOcts   Counter64,
--         tnPortIngrMdaQos12StatDropPkts   Counter64,
--         tnPortIngrMdaQos12StatDropOcts   Counter64,
--         tnPortIngrMdaQos13StatDropPkts   Counter64,
--         tnPortIngrMdaQos13StatDropOcts   Counter64,
--         tnPortIngrMdaQos14StatDropPkts   Counter64,
--         tnPortIngrMdaQos14StatDropOcts   Counter64,
--         tnPortIngrMdaQos15StatDropPkts   Counter64,
--         tnPortIngrMdaQos15StatDropOcts   Counter64
--     }
--
-- tnPortIngrMdaQos00StatDropPkts OBJECT-TYPE
--     SYNTAX      Counter64
--     MAX-ACCESS  read-only
--     STATUS      current
--     DESCRIPTION
--         "tnPortIngrMdaQos00StatDropPkts indicates the number of
--          packets dropped on the oversubscribed MDA for given Qos
--          classifier result because of an overload condition on the MDA."
--     ::= { tnPortIngrMdaQosStatEntry 1 }
--
-- tnPortIngrMdaQos00StatDropOcts OBJECT-TYPE
--     SYNTAX      Counter64
--     MAX-ACCESS  read-only
--     STATUS      current
--     DESCRIPTION
--         "tnPortIngrMdaQos00StatDropOcts indicates the number of
--          octets dropped on the oversubscribed MDA for given Qos
--          classifier result because of an overload condition on the MDA."
--     ::= { tnPortIngrMdaQosStatEntry 2 }
--
-- tnPortIngrMdaQos01StatDropPkts OBJECT-TYPE
--     SYNTAX      Counter64
--     MAX-ACCESS  read-only
--     STATUS      current
--     DESCRIPTION
--         "tnPortIngrMdaQos01StatDropPkts indicates the number of
--          packets dropped on the oversubscribed MDA for given Qos
--          classifier result because of an overload condition on the MDA."
--     ::= { tnPortIngrMdaQosStatEntry 3 }
--
-- tnPortIngrMdaQos01StatDropOcts OBJECT-TYPE
--     SYNTAX      Counter64
--     MAX-ACCESS  read-only
--     STATUS      current
--     DESCRIPTION
--         "tnPortIngrMdaQos01StatDropOcts indicates the number of
--          octets dropped on the oversubscribed MDA for given Qos
--          classifier result because of an overload condition on the MDA."
--     ::= { tnPortIngrMdaQosStatEntry 4 }
--
-- tnPortIngrMdaQos02StatDropPkts OBJECT-TYPE
--     SYNTAX      Counter64
--     MAX-ACCESS  read-only
--     STATUS      current
--     DESCRIPTION
--         "tnPortIngrMdaQos02StatDropPkts indicates the number of
--          packets dropped on the oversubscribed MDA for given Qos
--          classifier result because of an overload condition on the MDA."
--     ::= { tnPortIngrMdaQosStatEntry 5 }
--
-- tnPortIngrMdaQos02StatDropOcts OBJECT-TYPE
--     SYNTAX      Counter64
--     MAX-ACCESS  read-only
--     STATUS      current
--     DESCRIPTION
--         "tnPortIngrMdaQos02StatDropOcts indicates the number of
--          octets dropped on the oversubscribed MDA for given Qos
--          classifier result because of an overload condition on the MDA."
--     ::= { tnPortIngrMdaQosStatEntry 6 }
--
-- tnPortIngrMdaQos03StatDropPkts OBJECT-TYPE
--     SYNTAX      Counter64
--     MAX-ACCESS  read-only
--     STATUS      current
--     DESCRIPTION
--         "tnPortIngrMdaQos03StatDropPkts indicates the number of
--          packets dropped on the oversubscribed MDA for given Qos
--          classifier result because of an overload condition on the MDA."
--     ::= { tnPortIngrMdaQosStatEntry 7 }
--
-- tnPortIngrMdaQos03StatDropOcts OBJECT-TYPE
--     SYNTAX      Counter64
--     MAX-ACCESS  read-only
--     STATUS      current
--     DESCRIPTION
--         "tnPortIngrMdaQos03StatDropOcts indicates the number of
--          octets dropped on the oversubscribed MDA for given Qos
--          classifier result because of an overload condition on the MDA."
--     ::= { tnPortIngrMdaQosStatEntry 8 }
--
-- tnPortIngrMdaQos04StatDropPkts OBJECT-TYPE
--     SYNTAX      Counter64
--     MAX-ACCESS  read-only
--     STATUS      current
--     DESCRIPTION
--         "tnPortIngrMdaQos04StatDropPkts indicates the number of
--          packets dropped on the oversubscribed MDA for given Qos
--          classifier result because of an overload condition on the MDA."
--     ::= { tnPortIngrMdaQosStatEntry 9 }
--
-- tnPortIngrMdaQos04StatDropOcts OBJECT-TYPE
--     SYNTAX      Counter64
--     MAX-ACCESS  read-only
--     STATUS      current
--     DESCRIPTION
--         "tnPortIngrMdaQos04StatDropOcts indicates the number of
--          octets dropped on the oversubscribed MDA for given Qos
--          classifier result because of an overload condition on the MDA."
--     ::= { tnPortIngrMdaQosStatEntry 10 }
--
-- tnPortIngrMdaQos05StatDropPkts OBJECT-TYPE
--     SYNTAX      Counter64
--     MAX-ACCESS  read-only
--     STATUS      current
--     DESCRIPTION
--         "tnPortIngrMdaQos05StatDropPkts indicates the number of
--          packets dropped on the oversubscribed MDA for given Qos
--          classifier result because of an overload condition on the MDA."
--     ::= { tnPortIngrMdaQosStatEntry 11 }
--
-- tnPortIngrMdaQos05StatDropOcts OBJECT-TYPE
--     SYNTAX      Counter64
--     MAX-ACCESS  read-only
--     STATUS      current
--     DESCRIPTION
--         "tnPortIngrMdaQos05StatDropOcts indicates the number of
--          octets dropped on the oversubscribed MDA for given Qos
--          classifier result because of an overload condition on the MDA."
--     ::= { tnPortIngrMdaQosStatEntry 12 }
--
-- tnPortIngrMdaQos06StatDropPkts OBJECT-TYPE
--     SYNTAX      Counter64
--     MAX-ACCESS  read-only
--     STATUS      current
--     DESCRIPTION
--         "tnPortIngrMdaQos06StatDropPkts indicates the number of
--          packets dropped on the oversubscribed MDA for given Qos
--          classifier result because of an overload condition on the MDA."
--     ::= { tnPortIngrMdaQosStatEntry 13 }
--
-- tnPortIngrMdaQos06StatDropOcts OBJECT-TYPE
--     SYNTAX      Counter64
--     MAX-ACCESS  read-only
--     STATUS      current
--     DESCRIPTION
--         "tnPortIngrMdaQos06StatDropOcts indicates the number of
--          octets dropped on the oversubscribed MDA for given Qos
--          classifier result because of an overload condition on the MDA."
--     ::= { tnPortIngrMdaQosStatEntry 14 }
--
-- tnPortIngrMdaQos07StatDropPkts OBJECT-TYPE
--     SYNTAX      Counter64
--     MAX-ACCESS  read-only
--     STATUS      current
--     DESCRIPTION
--         "tnPortIngrMdaQos07StatDropPkts indicates the number of
--          packets dropped on the oversubscribed MDA for given Qos
--          classifier result because of an overload condition on the MDA."
--     ::= { tnPortIngrMdaQosStatEntry 15 }
--
-- tnPortIngrMdaQos07StatDropOcts OBJECT-TYPE
--     SYNTAX      Counter64
--     MAX-ACCESS  read-only
--     STATUS      current
--     DESCRIPTION
--         "tnPortIngrMdaQos07StatDropOcts indicates the number of
--          octets dropped on the oversubscribed MDA for given Qos
--          classifier result because of an overload condition on the MDA."
--     ::= { tnPortIngrMdaQosStatEntry 16 }
--
-- tnPortIngrMdaQos08StatDropPkts OBJECT-TYPE
--     SYNTAX      Counter64
--     MAX-ACCESS  read-only
--     STATUS      current
--     DESCRIPTION
--         "tnPortIngrMdaQos08StatDropPkts indicates the number of
--          packets dropped on the oversubscribed MDA for given Qos
--          classifier result because of an overload condition on the MDA."
--     ::= { tnPortIngrMdaQosStatEntry 17 }
--
-- tnPortIngrMdaQos08StatDropOcts OBJECT-TYPE
--     SYNTAX      Counter64
--     MAX-ACCESS  read-only
--     STATUS      current
--     DESCRIPTION
--         "tnPortIngrMdaQos08StatDropOcts indicates the number of
--          octets dropped on the oversubscribed MDA for given Qos
--          classifier result because of an overload condition on the MDA."
--     ::= { tnPortIngrMdaQosStatEntry 18 }
--
-- tnPortIngrMdaQos09StatDropPkts OBJECT-TYPE
--     SYNTAX      Counter64
--     MAX-ACCESS  read-only
--     STATUS      current
--     DESCRIPTION
--         "tnPortIngrMdaQos09StatDropPkts indicates the number of
--          packets dropped on the oversubscribed MDA for given Qos
--          classifier result because of an overload condition on the MDA."
--     ::= { tnPortIngrMdaQosStatEntry 19 }
--
-- tnPortIngrMdaQos09StatDropOcts OBJECT-TYPE
--     SYNTAX      Counter64
--     MAX-ACCESS  read-only
--     STATUS      current
--     DESCRIPTION
--         "tnPortIngrMdaQos09StatDropOcts indicates the number of
--          octets dropped on the oversubscribed MDA for given Qos
--          classifier result because of an overload condition on the MDA."
--     ::= { tnPortIngrMdaQosStatEntry 20 }
--
-- tnPortIngrMdaQos10StatDropPkts OBJECT-TYPE
--     SYNTAX      Counter64
--     MAX-ACCESS  read-only
--     STATUS      current
--     DESCRIPTION
--         "tnPortIngrMdaQos10StatDropPkts indicates the number of
--          packets dropped on the oversubscribed MDA for given Qos
--          classifier result because of an overload condition on the MDA."
--     ::= { tnPortIngrMdaQosStatEntry 21 }
--
-- tnPortIngrMdaQos10StatDropOcts OBJECT-TYPE
--     SYNTAX      Counter64
--     MAX-ACCESS  read-only
--     STATUS      current
--     DESCRIPTION
--         "tnPortIngrMdaQos10StatDropOcts indicates the number of
--          octets dropped on the oversubscribed MDA for given Qos
--          classifier result because of an overload condition on the MDA."
--     ::= { tnPortIngrMdaQosStatEntry 22 }
--
-- tnPortIngrMdaQos11StatDropPkts OBJECT-TYPE
--     SYNTAX      Counter64
--     MAX-ACCESS  read-only
--     STATUS      current
--     DESCRIPTION
--         "tnPortIngrMdaQos11StatDropPkts indicates the number of
--          packets dropped on the oversubscribed MDA for given Qos
--          classifier result because of an overload condition on the MDA."
--     ::= { tnPortIngrMdaQosStatEntry 23 }
--
-- tnPortIngrMdaQos11StatDropOcts OBJECT-TYPE
--     SYNTAX      Counter64
--     MAX-ACCESS  read-only
--     STATUS      current
--     DESCRIPTION
--         "tnPortIngrMdaQos11StatDropOcts indicates the number of
--          octets dropped on the oversubscribed MDA for given Qos
--          classifier result because of an overload condition on the MDA."
--     ::= { tnPortIngrMdaQosStatEntry 24 }
--
-- tnPortIngrMdaQos12StatDropPkts OBJECT-TYPE
--     SYNTAX      Counter64
--     MAX-ACCESS  read-only
--     STATUS      current
--     DESCRIPTION
--         "tnPortIngrMdaQos12StatDropPkts indicates the number of
--          packets dropped on the oversubscribed MDA for given Qos
--          classifier result because of an overload condition on the MDA."
--     ::= { tnPortIngrMdaQosStatEntry 25 }
--
-- tnPortIngrMdaQos12StatDropOcts OBJECT-TYPE
--     SYNTAX      Counter64
--     MAX-ACCESS  read-only
--     STATUS      current
--     DESCRIPTION
--         "tnPortIngrMdaQos12StatDropOcts indicates the number of
--          octets dropped on the oversubscribed MDA for given Qos
--          classifier result because of an overload condition on the MDA."
--     ::= { tnPortIngrMdaQosStatEntry 26 }
--
-- tnPortIngrMdaQos13StatDropPkts OBJECT-TYPE
--     SYNTAX      Counter64
--     MAX-ACCESS  read-only
--     STATUS      current
--     DESCRIPTION
--         "tnPortIngrMdaQos13StatDropPkts indicates the number of
--          packets dropped on the oversubscribed MDA for given Qos
--          classifier result because of an overload condition on the MDA."
--     ::= { tnPortIngrMdaQosStatEntry 27 }
--
-- tnPortIngrMdaQos13StatDropOcts OBJECT-TYPE
--     SYNTAX      Counter64
--     MAX-ACCESS  read-only
--     STATUS      current
--     DESCRIPTION
--         "tnPortIngrMdaQos13StatDropOcts indicates the number of
--          octets dropped on the oversubscribed MDA for given Qos
--          classifier result because of an overload condition on the MDA."
--     ::= { tnPortIngrMdaQosStatEntry 28 }
--
-- tnPortIngrMdaQos14StatDropPkts OBJECT-TYPE
--     SYNTAX      Counter64
--     MAX-ACCESS  read-only
--     STATUS      current
--     DESCRIPTION
--         "tnPortIngrMdaQos14StatDropPkts indicates the number of
--          packets dropped on the oversubscribed MDA for given Qos
--          classifier result because of an overload condition on the MDA."
--     ::= { tnPortIngrMdaQosStatEntry 29 }
--
-- tnPortIngrMdaQos14StatDropOcts OBJECT-TYPE
--     SYNTAX      Counter64
--     MAX-ACCESS  read-only
--     STATUS      current
--     DESCRIPTION
--         "tnPortIngrMdaQos14StatDropOcts indicates the number of
--          octets dropped on the oversubscribed MDA for given Qos
--          classifier result because of an overload condition on the MDA."
--     ::= { tnPortIngrMdaQosStatEntry 30 }
--
-- tnPortIngrMdaQos15StatDropPkts OBJECT-TYPE
--     SYNTAX      Counter64
--     MAX-ACCESS  read-only
--     STATUS      current
--     DESCRIPTION
--         "tnPortIngrMdaQos15StatDropPkts indicates the number of
--          packets dropped on the oversubscribed MDA for given Qos
--          classifier result because of an overload condition on the MDA."
--     ::= { tnPortIngrMdaQosStatEntry 31 }
--
-- tnPortIngrMdaQos15StatDropOcts OBJECT-TYPE
--     SYNTAX      Counter64
--     MAX-ACCESS  read-only
--     STATUS      current
--     DESCRIPTION
--         "tnPortIngrMdaQos15StatDropOcts indicates the number of
--          octets dropped on the oversubscribed MDA for given Qos
--          classifier result because of an overload condition on the MDA."
--     ::= { tnPortIngrMdaQosStatEntry 32 }

--
--  Sonet Group Table
--

-- tnSonetGroupTable OBJECT-TYPE
--     SYNTAX      SEQUENCE OF TmnxSonetGroupEntry
--     MAX-ACCESS  not-accessible
--     STATUS      current
--     DESCRIPTION
--         "The tnSonetGroupTable has an entry for each
--          Tributary Unit Group(TUG3) on a path. On a port which supports
--          unchannelized STS-3's, rows in this table are created when a
--          channelized STS-3 has its tnSonetPathChildType set to sdhTug3.
--          On a port which does not support unchannelized STS-3's, the rows
--          in this table are implicitly created when a STS-3 is created
--          in the tnSonetPathTable.  Entries in this table are implicitly
--          deleted when the parent entry of this group is deleted from the
--          tnSonetPathTable or if the tnSonetPathChildType of the parent
--          is set to something other than sdhTug3."
--     ::= { tnPortObjs 18 }
--
-- tnSonetGroupEntry       OBJECT-TYPE
--     SYNTAX      TmnxSonetGroupEntry
--     MAX-ACCESS  not-accessible
--     STATUS      current
--     DESCRIPTION
--         "Each row entry represents a Tributary Unit Group(TUG3) on a path."
--     INDEX   {  tnPortPortID }
--     ::= { tnSonetGroupTable 1 }
--
-- TmnxSonetGroupEntry ::=
--     SEQUENCE {
-- ==        tnSonetGroupType              TmnxMDAChanType,
--         tnSonetGroupParentPortID      TmnxPortID,
-- ==        tnSonetGroupChildType         TmnxMDAChanType,
--         tnSonetGroupName              TNamedItemOrEmpty
--     }
--
-- == tnSonetGroupType     OBJECT-TYPE
-- ==     SYNTAX      TmnxMDAChanType
-- ==     MAX-ACCESS  read-only
-- ==     STATUS      current
-- ==     DESCRIPTION
-- ==         "tnSonetGroupType indicates the sonet group type of this entry.
-- ==          For STS-3/STM-1 channelization, the value of this object will
-- ==          be 'sdhTug3'."
-- ==     ::= { tnSonetGroupEntry 1 }
--
-- tnSonetGroupParentPortID     OBJECT-TYPE
--     SYNTAX      TmnxPortID
--     MAX-ACCESS  read-only
--     STATUS      current
--     DESCRIPTION
--         "tnSonetGroupParentPortID indicates the TmnxPortID of the parent of
--          this group."
--     ::= { tnSonetGroupEntry 2 }
--
-- == tnSonetGroupChildType     OBJECT-TYPE
-- ==     SYNTAX      TmnxMDAChanType
-- ==     MAX-ACCESS  read-write
-- ==     STATUS      current
-- ==     DESCRIPTION
-- ==         "tnSonetGroupChildType is used to configure the type of the children
-- ==          of this group. Based on the value of this object, entries of
-- ==          a certain channel type can be created in the tnSonetPathTable.
-- ==          For example, if the value of this object is set to 'sonetVt15',
-- ==          then 28 entries of type 'sonetVt15' can be created in
-- ==          the tnSonetPathTable."
-- ==     ::= { tnSonetGroupEntry 3 }
--
-- tnSonetGroupName     OBJECT-TYPE
--     SYNTAX      TNamedItemOrEmpty
--     MAX-ACCESS  read-only
--     STATUS      current
--     DESCRIPTION
--         "tnSonetGroupName is the textual name for this sonet group."
--     ::= { tnSonetGroupEntry 4 }

--
--      L4 Load Balancing
--

tnPortScalarObjs OBJECT IDENTIFIER ::= { tnPortObjs 19 }

-- tnL4LoadBalancing OBJECT-TYPE
--     SYNTAX      TruthValue
--     MAX-ACCESS  read-write
--     STATUS      current
--     DESCRIPTION
--         "The value of tnL4LoadBalancing specifies whether layer 4 information,
--          src and dst ports, should be used in the LAG and ECMP hashing
--          algorithm. This is the global system setting that all ports will
--          inherit. When set to 'true', src and dst ports are used in the hashing
--          algorithm. The per port setting of tnPortLoadBalanceAlgorithm can
--          override tnL4LoadBalancing."
--     DEFVAL { false }
--     ::= { tnPortScalarObjs 1 }
--
-- tnLsrIpLoadBalancing           OBJECT-TYPE
--     SYNTAX      INTEGER {
--                     label-only (1),
--                     label-ip   (2)
--                 }
--     MAX-ACCESS  read-write
--     STATUS      current
--     DESCRIPTION
--         "The value of tnLsrIpLoadBalancing specifies whether the IP Header is
--          used in the LAG and ECMP LSR hashing algorithm. This is the global
--          system setting that all ports will inherit. When set to 'label-ip (2)',
--          the IP Header is included in the hashing algorithm."
--     DEFVAL { label-only }
--     ::= { tnPortScalarObjs 2 }

--
-- Dummy Scalars
--
tnPortScalar1 OBJECT-TYPE
    SYNTAX      Unsigned32
    MAX-ACCESS  read-only
    STATUS      current
    DESCRIPTION
        "A dummy scalar that satisfies a SNMP get request quickly when
         there is no 11QPE24 card provisioned.  Otherwise, it has to
         traverse the remaining 11QPE24 MIB to get to the next applicable
         item."
    ::= { tnPortScalarObjs 11 }

tnPortScalar2 OBJECT-TYPE
    SYNTAX      Unsigned32
    MAX-ACCESS  read-only
    STATUS      current
    DESCRIPTION "."
    ::= { tnPortScalarObjs 12 }

tnPortScalar3 OBJECT-TYPE
    SYNTAX      Unsigned32
    MAX-ACCESS  read-only
    STATUS      current
    DESCRIPTION "."
    ::= { tnPortScalarObjs 13 }

tnPortScalar4 OBJECT-TYPE
    SYNTAX      Unsigned32
    MAX-ACCESS  read-only
    STATUS      current
    DESCRIPTION "."
    ::= { tnPortScalarObjs 14 }

tnPortScalar5 OBJECT-TYPE
    SYNTAX      Unsigned32
    MAX-ACCESS  read-only
    STATUS      current
    DESCRIPTION "."
    ::= { tnPortScalarObjs 15 }

tnPortScalar6 OBJECT-TYPE
    SYNTAX      Unsigned32
    MAX-ACCESS  read-only
    STATUS      current
    DESCRIPTION "."
    ::= { tnPortScalarObjs 16 }

tnPortScalar7 OBJECT-TYPE
    SYNTAX      Unsigned32
    MAX-ACCESS  read-only
    STATUS      current
    DESCRIPTION "."
    ::= { tnPortScalarObjs 17 }

tnPortScalar8 OBJECT-TYPE
    SYNTAX      Unsigned32
    MAX-ACCESS  read-only
    STATUS      current
    DESCRIPTION "."
    ::= { tnPortScalarObjs 18 }

tnPortScalar9 OBJECT-TYPE
    SYNTAX      Unsigned32
    MAX-ACCESS  read-only
    STATUS      current
    DESCRIPTION "."
    ::= { tnPortScalarObjs 19 }

tnPortScalar10 OBJECT-TYPE
    SYNTAX      Unsigned32
    MAX-ACCESS  read-only
    STATUS      current
    DESCRIPTION "."
    ::= { tnPortScalarObjs 20 }

tnPortScalar11 OBJECT-TYPE
    SYNTAX      Unsigned32
    MAX-ACCESS  read-only
    STATUS      current
    DESCRIPTION "."
    ::= { tnPortScalarObjs 21 }

tnPortScalar12 OBJECT-TYPE
    SYNTAX      Unsigned32
    MAX-ACCESS  read-only
    STATUS      current
    DESCRIPTION "."
    ::= { tnPortScalarObjs 22 }

tnPortScalar13 OBJECT-TYPE
    SYNTAX      Unsigned32
    MAX-ACCESS  read-only
    STATUS      current
    DESCRIPTION "."
    ::= { tnPortScalarObjs 23 }

tnPortScalar14 OBJECT-TYPE
    SYNTAX      Unsigned32
    MAX-ACCESS  read-only
    STATUS      current
    DESCRIPTION "."
    ::= { tnPortScalarObjs 24 }

tnPortScalar15 OBJECT-TYPE
    SYNTAX      Unsigned32
    MAX-ACCESS  read-only
    STATUS      current
    DESCRIPTION "."
    ::= { tnPortScalarObjs 25 }

tnPortScalar16 OBJECT-TYPE
    SYNTAX      Unsigned32
    MAX-ACCESS  read-only
    STATUS      current
    DESCRIPTION "."
    ::= { tnPortScalarObjs 26 }

tnPortScalar17 OBJECT-TYPE
    SYNTAX      Unsigned32
    MAX-ACCESS  read-only
    STATUS      current
    DESCRIPTION "."
    ::= { tnPortScalarObjs 27 }

tnPortScalar18 OBJECT-TYPE
    SYNTAX      Unsigned32
    MAX-ACCESS  read-only
    STATUS      current
    DESCRIPTION "."
    ::= { tnPortScalarObjs 28 }

tnPortScalar19 OBJECT-TYPE
    SYNTAX      Unsigned32
    MAX-ACCESS  read-only
    STATUS      current
    DESCRIPTION "."
    ::= { tnPortScalarObjs 29 }

tnPortScalar20 OBJECT-TYPE
    SYNTAX      Unsigned32
    MAX-ACCESS  read-only
    STATUS      current
    DESCRIPTION "."
    ::= { tnPortScalarObjs 30 }

tnPortScalar21 OBJECT-TYPE
    SYNTAX      Unsigned32
    MAX-ACCESS  read-only
    STATUS      current
    DESCRIPTION "."
    ::= { tnPortScalarObjs 31 }

tnPortScalar22 OBJECT-TYPE
    SYNTAX      Unsigned32
    MAX-ACCESS  read-only
    STATUS      current
    DESCRIPTION "."
    ::= { tnPortScalarObjs 32 }

tnPortScalar23 OBJECT-TYPE
    SYNTAX      Unsigned32
    MAX-ACCESS  read-only
    STATUS      current
    DESCRIPTION "."
    ::= { tnPortScalarObjs 33 }

tnPortScalar24 OBJECT-TYPE
    SYNTAX      Unsigned32
    MAX-ACCESS  read-only
    STATUS      current
    DESCRIPTION "."
    ::= { tnPortScalarObjs 34 }

tnPortScalar25 OBJECT-TYPE
    SYNTAX      Unsigned32
    MAX-ACCESS  read-only
    STATUS      current
    DESCRIPTION "."
    ::= { tnPortScalarObjs 35 }

tnPortScalar26 OBJECT-TYPE
    SYNTAX      Unsigned32
    MAX-ACCESS  read-only
    STATUS      current
    DESCRIPTION "."
    ::= { tnPortScalarObjs 36 }

tnPortScalar27 OBJECT-TYPE
    SYNTAX      Unsigned32
    MAX-ACCESS  read-only
    STATUS      current
    DESCRIPTION "."
    ::= { tnPortScalarObjs 37 }

tnPortScalar28 OBJECT-TYPE
    SYNTAX      Unsigned32
    MAX-ACCESS  read-only
    STATUS      current
    DESCRIPTION "."
    ::= { tnPortScalarObjs 38 }

tnPortScalar29 OBJECT-TYPE
    SYNTAX      Unsigned32
    MAX-ACCESS  read-only
    STATUS      current
    DESCRIPTION "."
    ::= { tnPortScalarObjs 39 }

tnPortScalar30 OBJECT-TYPE
    SYNTAX      Unsigned32
    MAX-ACCESS  read-only
    STATUS      current
    DESCRIPTION "."
    ::= { tnPortScalarObjs 40 }

--
--  Cisco HDLC Table
--

-- tnCiscoHDLCTable OBJECT-TYPE
--     SYNTAX      SEQUENCE OF TmnxCiscoHDLCEntry
--     MAX-ACCESS  not-accessible
--     STATUS      current
--     DESCRIPTION
--         "The tnCiscoHDLCTable has an entry for each port in the system
--          that is configured for Cisco HDLC. It contains the parameters related
--          to Cisco HDLC protocol on this port."
--     ::= { tnPortObjs 20 }
--
-- tnCiscoHDLCEntry       OBJECT-TYPE
--     SYNTAX      TmnxCiscoHDLCEntry
--     MAX-ACCESS  not-accessible
--     STATUS      current
--     DESCRIPTION
--         "The tnCiscoHDLCEntry specifies parameters for a particular
--          interfaces running Cisco HDLC encapsulation. Entries cannot be created
--          and deleted via SNMP SET operations."
--     INDEX   {  tnPortPortID }
--     ::= { tnCiscoHDLCTable 1 }
--
-- TmnxCiscoHDLCEntry ::=
--     SEQUENCE {
--         tnCiscoHDLCKeepAliveInt        Unsigned32,
--         tnCiscoHDLCUpCount             Unsigned32,
--         tnCiscoHDLCDownCount           Unsigned32,
--         tnCiscoHDLCOperState           TmnxOperState
--     }
--
-- tnCiscoHDLCKeepAliveInt      OBJECT-TYPE
--     SYNTAX      Unsigned32 (0..300)
--     UNITS       "seconds"
--     MAX-ACCESS  read-create
--     STATUS      current
--     DESCRIPTION
--         "tnCiscoHDLCKeepAliveInt specifies the interval in seconds
--          used for sending periodic keepalive packets. The default value is set
--          to 10 seconds. A value of 0 specifies that the keepalive function is
--          turned off.
--
--          It is expected that the nodes at the two endpoints of
--          the Cisco HDLC link are provisioned with the same values."
--     DEFVAL      {10}
--     ::= { tnCiscoHDLCEntry 1 }
--
-- tnCiscoHDLCUpCount      OBJECT-TYPE
--     SYNTAX        Unsigned32 (1..3)
--     MAX-ACCESS    read-create
--     STATUS        current
--     DESCRIPTION
--         "tnCiscoHDLCUpCount specifies the number of continual
--          keepalive packets that has to be received to declare the link up.
--
--          It is expected that the nodes at the two endpoints of
--          the Cisco HDLC link are provisioned with the same values."
--     DEFVAL      {1}
--     ::= { tnCiscoHDLCEntry 2 }
--
-- tnCiscoHDLCDownCount        OBJECT-TYPE
--     SYNTAX        Unsigned32 (3..16)
--     MAX-ACCESS    read-create
--     STATUS        current
--     DESCRIPTION
--         "tnCiscoHDLCDownCount specifies the number of
--          'tnCiscoHDLCKeepAliveInt' intervals that must
--          pass without receiving a keepalive packet before the
--          link is declared down.
--
--          It is expected that the nodes at the two endpoints of
--          the Cisco HDLC link are provisioned with the same values."
--     DEFVAL      {3}
--     ::= { tnCiscoHDLCEntry 3 }
--
-- tnCiscoHDLCOperState     OBJECT-TYPE
--     SYNTAX      TmnxOperState
--     MAX-ACCESS  read-only
--     STATUS      current
--     DESCRIPTION
--         "The value of tnCiscoHDLCOperState indicates the operational
--          status of the Cisco HDLC protocol for this port."
--     ::= { tnCiscoHDLCEntry 4 }

--
--  Cisco HDLC statisctics Table
--

-- tnCiscoHDLCStatsTable OBJECT-TYPE
--     SYNTAX  SEQUENCE OF TmnxCiscoHDLCStatsEntry
--     MAX-ACCESS  not-accessible
--     STATUS      current
--     DESCRIPTION
--         "The tnCiscoHDLCStatsTable has an entry for each port in the
--          system that is configured for Cisco HDLC encapsulation. It contains
--          Cisco HDLC protocol statistics for the particular port."
--     ::= { tnPortStatsObjs 3 }
--
-- tnCiscoHDLCStatsEntry OBJECT-TYPE
--     SYNTAX     TmnxCiscoHDLCStatsEntry
--     MAX-ACCESS not-accessible
--     STATUS     current
--     DESCRIPTION
--         "An entry in the tnCiscoHDLCStatsTable."
--     AUGMENTS      { tnCiscoHDLCEntry }
--     ::= { tnCiscoHDLCStatsTable 1 }
--
-- TmnxCiscoHDLCStatsEntry ::= SEQUENCE {
--     tnCiscoHDLCDiscardStatInPkts          Unsigned32,
--     tnCiscoHDLCDiscardStatOutPkts         Unsigned32,
--     tnCiscoHDLCStatInPkts                 Unsigned32,
--     tnCiscoHDLCStatOutPkts                Unsigned32,
--     tnCiscoHDLCStatInOctets               Unsigned32,
--     tnCiscoHDLCStatOutOctets              Unsigned32
-- }
--
-- tnCiscoHDLCDiscardStatInPkts      OBJECT-TYPE
--     SYNTAX        Unsigned32
--     MAX-ACCESS    read-only
--     STATUS        current
--     DESCRIPTION
--         "tnCiscoHDLCDiscardStatInPkts indicates the number of
--          inbound Cisco HDLC packets discarded."
--     ::= { tnCiscoHDLCStatsEntry 1 }
--
-- tnCiscoHDLCDiscardStatOutPkts     OBJECT-TYPE
--     SYNTAX        Unsigned32
--     MAX-ACCESS    read-only
--     STATUS        current
--     DESCRIPTION
--         "tnCiscoHDLCDiscardStatOutPkts indicates the number of
--          outbound Cisco HDLC packets discarded."
--     ::= { tnCiscoHDLCStatsEntry 2 }
--
-- tnCiscoHDLCStatInPkts         OBJECT-TYPE
--     SYNTAX        Unsigned32
--     MAX-ACCESS    read-only
--     STATUS        current
--     DESCRIPTION
--         "tnCiscoHDLCStatInPkts indicates the number of inbound Cisco
--          HDLC packets."
--     ::= { tnCiscoHDLCStatsEntry 3 }
--
-- tnCiscoHDLCStatOutPkts        OBJECT-TYPE
--     SYNTAX        Unsigned32
--     MAX-ACCESS    read-only
--     STATUS        current
--     DESCRIPTION
--         "tnCiscoHDLCStatOutPkts indicates the number of outbound Cisco
--          HDLC packets."
--     ::= { tnCiscoHDLCStatsEntry 4 }
--
-- tnCiscoHDLCStatInOctets     OBJECT-TYPE
--     SYNTAX        Unsigned32
--     MAX-ACCESS    read-only
--     STATUS        current
--     DESCRIPTION
--         "tnCiscoHDLCStatInOctets indicates the number of inbound Cisco
--          HDLC octets."
--     ::= { tnCiscoHDLCStatsEntry 5 }
--
-- tnCiscoHDLCStatOutOctets     OBJECT-TYPE
--     SYNTAX        Unsigned32
--     MAX-ACCESS    read-only
--     STATUS        current
--     DESCRIPTION
--         "tnCiscoHDLCStatOutOctets indicates the number of outbound
--          Cisco HDLC octets."
--     ::= { tnCiscoHDLCStatsEntry 6 }

--
--  Frame Relay Protocol Table
--
-- tmnxFRDlcmiTable OBJECT-TYPE
--     SYNTAX  SEQUENCE OF TmnxFRDlcmiEntry
--     MAX-ACCESS  not-accessible
--     STATUS      current
--     DESCRIPTION
--         "The tmnxFRDlcmiTable has an entry for each port in the
--          system that is configured for Frame Relay. It contains
--          the parameters for the Data Link Connection Management
--          Interface (DLCMI) for the frame relay service on this port."
--     ::= { tnFRObjs 1 }
--
-- tmnxFRDlcmiEntry       OBJECT-TYPE
--     SYNTAX      TmnxFRDlcmiEntry
--     MAX-ACCESS  not-accessible
--     STATUS      current
--     DESCRIPTION
--         "The Parameters for a particular Data Link Connection
--          Management Interface. Entries cannot be created and
--          deleted via SNMP SET operations."
--     INDEX   {  tnPortPortID }
--     ::= { tmnxFRDlcmiTable 1 }
--
-- TmnxFRDlcmiEntry ::=
--     SEQUENCE {
--         tmnxFRDlcmiMode                 INTEGER,
--         tmnxFRDlcmiN392Dce              INTEGER,
--         tmnxFRDlcmiN393Dce              INTEGER,
--         tmnxFRDlcmiT392Dce              INTEGER,
--         tmnxFRDlcmiTxStatusEnqMsgs      Counter32,
--         tmnxFRDlcmiRxStatusEnqMsgs      Counter32,
--         tmnxFRDlcmiStatusEnqMsgTimeouts Counter32,
--         tmnxFRDlcmiTxStatusMsgs         Counter32,
--         tmnxFRDlcmiRxStatusMsgs         Counter32,
--         tmnxFRDlcmiStatusMsgTimeouts    Counter32,
--         tmnxFRDlcmiDiscardedMsgs        Counter32,
--         tmnxFRDlcmiInvRxSeqNumMsgs      Counter32
--     }
--
-- tmnxFRDlcmiMode OBJECT-TYPE
--         SYNTAX      INTEGER {
--                         dte (1),
--                         dce (2),
--                         bidir(3)
--                     }
--         MAX-ACCESS  read-write
--         STATUS      current
--         DESCRIPTION
--             "tmnxFRDlcmiMode is used to set the mode of the interface.
--              It can be set as Data terminal equipment (dte),
--              Data circuit-terminating equipment (dce) or both as Data
--              terminal equipment and Data circuit-terminating
--              equipment (bidir). "
--         DEFVAL { dte }
--         ::= { tmnxFRDlcmiEntry 1 }
--
-- tmnxFRDlcmiN392Dce OBJECT-TYPE
--         SYNTAX      INTEGER (1..10)
--         MAX-ACCESS  read-write
--         STATUS      current
--         DESCRIPTION
--             "tmnxFRDlcmiN392Dce is used to configure the LMI error
--              threshold for DCE interface."
--         DEFVAL { 3 }
--         ::= { tmnxFRDlcmiEntry 2 }
--
-- tmnxFRDlcmiN393Dce OBJECT-TYPE
--         SYNTAX      INTEGER (1..10)
--         MAX-ACCESS  read-write
--         STATUS      current
--         DESCRIPTION
--             "tmnxFRDlcmiN393Dce is used to configure the LMI monitored
--              event count for DCE interface."
--         DEFVAL { 4 }
--         ::= { tmnxFRDlcmiEntry 3 }
--
-- tmnxFRDlcmiT392Dce OBJECT-TYPE
--         SYNTAX      INTEGER (5..30)
--         UNITS       "seconds"
--         MAX-ACCESS  read-write
--         STATUS      current
--         DESCRIPTION
--             "tmnxFRDlcmiT392Dce is used to configure the polling verification
--              timer for the Frame Relay DCE interface."
--         DEFVAL { 15 }
--         ::= { tmnxFRDlcmiEntry 4 }
--
-- tmnxFRDlcmiTxStatusEnqMsgs OBJECT-TYPE
--         SYNTAX      Counter32
--         UNITS       "messages"
--         MAX-ACCESS  read-only
--         STATUS      current
--         DESCRIPTION
--             "tmnxFRDlcmiTxStatusEnqMsgs indicates the number of LMI Status
--              Enquiry messages transmitted on this Frame Relay interface."
--         ::= { tmnxFRDlcmiEntry 5 }
--
-- tmnxFRDlcmiRxStatusEnqMsgs OBJECT-TYPE
--         SYNTAX      Counter32
--         UNITS       "messages"
--         MAX-ACCESS  read-only
--         STATUS      current
--         DESCRIPTION
--             "tmnxFRDlcmiRxStatusEnqMsgs indicates the number of LMI Status
--              Enquiry messages received on this Frame Relay interface."
--         ::= { tmnxFRDlcmiEntry 6 }
--
-- tmnxFRDlcmiStatusEnqMsgTimeouts OBJECT-TYPE
--         SYNTAX      Counter32
--         UNITS       "messages"
--         MAX-ACCESS  read-only
--         STATUS      current
--         DESCRIPTION
--             "tmnxFRDlcmiStatusEnqMsgTimeouts indicates the number of times
--              the LMI agent did not receive a Status Enquiry message within
--              the allotted time."
--         ::= { tmnxFRDlcmiEntry 7 }
--
-- tmnxFRDlcmiTxStatusMsgs OBJECT-TYPE
--         SYNTAX      Counter32
--         UNITS       "messages"
--         MAX-ACCESS  read-only
--         STATUS      current
--         DESCRIPTION
--             "tmnxFRDlcmiTxStatusMsgs indicates the number of LMI Status
--              messages transmitted on this Frame Relay interface."
--         ::= { tmnxFRDlcmiEntry 8 }
--
-- tmnxFRDlcmiRxStatusMsgs OBJECT-TYPE
--         SYNTAX      Counter32
--         UNITS       "messages"
--         MAX-ACCESS  read-only
--         STATUS      current
--         DESCRIPTION
--             "tmnxFRDlcmiRxStatusMsgs indicates the number of LMI Status
--              messages received on this Frame Relay interface."
--         ::= { tmnxFRDlcmiEntry 9 }
--
-- tmnxFRDlcmiStatusMsgTimeouts OBJECT-TYPE
--         SYNTAX      Counter32
--         UNITS       "messages"
--         MAX-ACCESS  read-only
--         STATUS      current
--         DESCRIPTION
--             "tmnxFRDlcmiStatusMsgTimeouts indicates the number of times
--              the LMI agent did not receive a Status message within the
--              allotted time."
--         ::= { tmnxFRDlcmiEntry 10 }
--
-- tmnxFRDlcmiDiscardedMsgs OBJECT-TYPE
--         SYNTAX      Counter32
--         UNITS       "messages"
--         MAX-ACCESS  read-only
--         STATUS      current
--         DESCRIPTION
--             "tmnxFRDlcmiDiscardedMsgs indicates the number of times
--              the LMI agent discarded a received message because it
--              wasn't expecting it, the type of message was incorrect,
--              or the contents of the message were invalid."
--         ::= { tmnxFRDlcmiEntry 11 }
--
-- tmnxFRDlcmiInvRxSeqNumMsgs OBJECT-TYPE
--         SYNTAX      Counter32
--         UNITS       "messages"
--         MAX-ACCESS  read-only
--         STATUS      current
--         DESCRIPTION
--             "tmnxFRDlcmiInvRxSeqNumMsgs indicates the number of times
--              the LMI agent received a message with an invalid receive
--              sequence number: i.e. a sequence number that does not
--              match the last transmitted sequence number of the agent."
--         ::= { tmnxFRDlcmiEntry 12 }

--
-- QoS Policy Application Table
--
tnQosPoolAppTable OBJECT-TYPE
    SYNTAX      SEQUENCE OF TmnxQosPoolAppEntry
    MAX-ACCESS  not-accessible
    STATUS      current
    DESCRIPTION
        "This table maintains associations of the buffer pools with the
        individual objects."
    ::= { tnQosAppObjs 2 }

tnQosPoolAppEntry OBJECT-TYPE
    SYNTAX      TmnxQosPoolAppEntry
    MAX-ACCESS  not-accessible
    STATUS      current
    DESCRIPTION
        "This entry maintains the specifics about the association of a
        buffer pool and an object."
    INDEX {
              tnObjectType,
              tnObjectId,
              tnObjectAppType,
              tnObjectAppPool
          }
    ::= { tnQosPoolAppTable 1 }

TmnxQosPoolAppEntry ::=
    SEQUENCE {
        tnObjectType               INTEGER,
        tnObjectId                 TmnxPortID,
        tnObjectAppType            INTEGER,
        tnObjectAppPool            TNamedItem,
        tnObjectAppPoolRowStatus   RowStatus,
        tnObjectAppResvCbs         Integer32,
        tnObjectAppSlopePolicy     TNamedItem,
        tnObjectAppPoolSize        Integer32
    }

tnObjectType OBJECT-TYPE
    SYNTAX      INTEGER {
                    mda (1),
                    port (2),
                    channel (3),
                    bundle (4),
                    mpointQueues (51)  -- for 7210-SAS-X
                }
    MAX-ACCESS  not-accessible
    STATUS      current
    DESCRIPTION
        "The object tnObjectType defines the type of object to which the
        pool is being setup for."
    ::= { tnQosPoolAppEntry 1 }

tnObjectId          OBJECT-TYPE
    SYNTAX      TmnxPortID
    MAX-ACCESS  not-accessible
    STATUS      current
    DESCRIPTION
        "tnObjectId is used to identify the specific object. If
        tnObjectType is 'mda', then the tnObjectId is encoded as a
        physical port with the port being '0'. For all other types the
        encoding is done as per the description of TmnxPortID."
    ::= { tnQosPoolAppEntry 2 }

tnObjectAppType OBJECT-TYPE
    SYNTAX      INTEGER {
                    accessIngress (1),
                    accessEgress (2),
                    networkIngress (3),
                    networkEgress (4),
                    system (51)  -- for 7210-SAS-X
                }
    MAX-ACCESS  not-accessible
    STATUS      current
    DESCRIPTION
        "The object tnObjectAppType specifies the nature of usage the pool
        would be used for. The pools could be used for access or network
        traffic at either ingress or egress.

        The value mpointQueues (51) is valid only for 7210-SAS-X platform."
    ::= { tnQosPoolAppEntry 3 }

tnObjectAppPool OBJECT-TYPE
    SYNTAX      TNamedItem
    MAX-ACCESS  not-accessible
    STATUS      current
    DESCRIPTION
        "tnObjectAppPool specifies the name of the pool to be used/created."
    ::= { tnQosPoolAppEntry 4 }

tnObjectAppPoolRowStatus OBJECT-TYPE
    SYNTAX      RowStatus
    MAX-ACCESS  read-write
    STATUS      current
    DESCRIPTION
        "The object tnObjectAppPoolRowStatus is used to create or remove a
        pool application to the object."
    ::= { tnQosPoolAppEntry 5 }

tnObjectAppResvCbs OBJECT-TYPE
    SYNTAX      Integer32 (-1|0..100)
    MAX-ACCESS  read-write
    STATUS      current
    DESCRIPTION
        "The percentage of pool size reserved for CBS. The value '-1'
        implies that the reserved CBS should be computed as the sum of
        the CBS requested by the entities using this pool if the application
        point is 'network'. For 'access' application points the value '-1'
        means a default of 30%."
    DEFVAL { -1 }
    ::= { tnQosPoolAppEntry 6 }

tnObjectAppSlopePolicy OBJECT-TYPE
    SYNTAX      TNamedItem
    MAX-ACCESS  read-write
    STATUS      current
    DESCRIPTION
        "tnObjectAppSlopePolicy specifies the slope policy being used for
        this pool. The Slope policies define the nature of the RED Slopes for
        the high and the low priority traffic."
    DEFVAL { "default" }
    ::= { tnQosPoolAppEntry 7 }

tnObjectAppPoolSize OBJECT-TYPE
    SYNTAX      Integer32 (-1|0..100)
    MAX-ACCESS  read-write
    STATUS      current
    DESCRIPTION
        "Size in percentage of buffer space. The value '-1' implies that
        the pool size should be computed as per fair weighing between
        all other pools."
    DEFVAL { -1 }
    ::= { tnQosPoolAppEntry 8 }

--
--  ATM Interface Table
--

-- tmnxATMIntfTable OBJECT-TYPE
--     SYNTAX  SEQUENCE OF TmnxATMIntfEntry
--     MAX-ACCESS  not-accessible
--     STATUS      current
--     DESCRIPTION
--         "The tmnxATMIntfTable has an entry for each port/channel in the
--          system that is configured for ATM. It contains ATM cell layer
--          configuration parameters."
--     ::= { tnATMObjs 1 }
--
-- tmnxATMIntfEntry       OBJECT-TYPE
--     SYNTAX      TmnxATMIntfEntry
--     MAX-ACCESS  not-accessible
--     STATUS      current
--     DESCRIPTION
--         "The Parameters for a particular ATM Cell
--          Management Interface. Entries cannot be created or
--          deleted via SNMP SET operations.
--          Entries will exist in this table when ATM encapsulation
--          is configured on the port/channel."
--     INDEX   {  tnPortPortID }
--     ::= { tmnxATMIntfTable 1 }
--
-- TmnxATMIntfEntry ::=
--     SEQUENCE {
--         tmnxATMIntfCellFormat          INTEGER,
--         tmnxATMIntfMinVpValue          Integer32,
--         tmnxATMIntfMapping             INTEGER,
--         tmnxATMIntfCustomBufferMode    TruthValue,
--         tmnxATMIntfBufferPool          Integer32,
--         tmnxATMIntfVcThreshold         Integer32
--     }
--
-- tmnxATMIntfCellFormat OBJECT-TYPE
--     SYNTAX      INTEGER {
--                     uni (1),
--                     nni (2)
--                 }
--     MAX-ACCESS  read-write
--     STATUS      current
--     DESCRIPTION
--         "tmnxATMIntfCellFormat is used to set the cell format
--          (UNI or NNI) that is to be used on the ATM interface."
--     DEFVAL { uni }
--     ::= { tmnxATMIntfEntry 1 }
--
-- tmnxATMIntfMinVpValue OBJECT-TYPE
--         SYNTAX      Integer32 (0..4095)
--         MAX-ACCESS  read-write
--         STATUS      current
--         DESCRIPTION
--             "tmnxATMIntfMinVpValue is used to set the minimum
--              allowable VPI value that can be used on the
--              ATM interface for a VPC."
--         DEFVAL { 0 }
--         ::= { tmnxATMIntfEntry 2 }
--
-- tmnxATMIntfMapping OBJECT-TYPE
--         SYNTAX      INTEGER {
--                         direct (1),
--                         plcp (2)
--                     }
--         MAX-ACCESS  read-write
--         STATUS      current
--         DESCRIPTION
--             "The value of tmnxATMIntfMapping specifies the cell
--              mapping that is to be used on this ATM interface.  When
--              tnPortChanType does not have a value of 'pdhDs3 (14)',
--              'inconsistentValue' error will be returned to SNMP SET
--              requests.  When tnPortChanType has a value of 'pdhDs3 (14)',
--              tmnxATMIntfMapping can be set to 'plcp (2)'."
--         DEFVAL { direct }
--         ::= { tmnxATMIntfEntry 3 }
--
-- tmnxATMIntfCustomBufferMode OBJECT-TYPE
--         SYNTAX      TruthValue
--         MAX-ACCESS  read-write
--         STATUS      current
--         DESCRIPTION
--             "The value of tmnxATMIntfCustomBufferMode specifies whether
--              port is in a mode that allows custom configuration of port buffer
--              pool and VC thresholds."
--         DEFVAL { false }
--         ::= { tmnxATMIntfEntry 4 }
--
-- tmnxATMIntfBufferPool OBJECT-TYPE
--         SYNTAX      Integer32 (1..100)
--         MAX-ACCESS  read-write
--         STATUS      current
--         DESCRIPTION
--             "The value of tmnxATMIntfBufferPool specifies the percentage
--              of the buffers configured on this interface over the
--              maximum allowed on this interface.
--
--              The value can only be changed if tmnxATMIntfCustomBufferMode
--              is set to 'true'.  Changing tmnxATMIntfCustomBufferMode to
--              'false' will reset tmnxATMIntfBufferPool back to the default
--              value."
--         DEFVAL { 100 }
--         ::= { tmnxATMIntfEntry 5 }
--
-- tmnxATMIntfVcThreshold OBJECT-TYPE
--         SYNTAX      Integer32 (190..117000)
--         MAX-ACCESS  read-write
--         STATUS      current
--         DESCRIPTION
--             "The value of tmnxATMIntfVcThreshold specifies the VC buffer
--              threshold for all VCs configured on this port.
--
--              The value can only be changed if tmnxATMIntfCustomBufferMode
--              is set to 'true'.  Changing tmnxATMIntfCustomBufferMode to
--              'false' will reset tmnxATMIntfVcThreshold back to the default
--              value."
--         DEFVAL { 190 }
--         ::= { tmnxATMIntfEntry 6 }

--
--  Network Port Ingress Stats Table
--
-- tnPortNetIngressStatsTable OBJECT-TYPE
--     SYNTAX      SEQUENCE OF TmnxPortNetIngressStatsEntry
--     MAX-ACCESS  not-accessible
--     STATUS      current
--     DESCRIPTION
--         "Defines the Nokia 7x50 SR series network port ingress
--          statistics table for providing, via SNMP, the capability of
--          retrieving the traffic statistics for the physical queues
--          being used for the ports to forward the network ingress
--          traffic."
--     ::= { tnPortStatsObjs 1 }
--
-- tnPortNetIngressStatsEntry    OBJECT-TYPE
--     SYNTAX      TmnxPortNetIngressStatsEntry
--     MAX-ACCESS  not-accessible
--     STATUS      current
--     DESCRIPTION
--         "Defines an entry in tnPortNetIngressStatsTable. Entries are
--          created and deleted by the system depending on the queue policy
--          being used at the specific port."
--     INDEX   {  tnPortPortID, tnPortNetIngressQueueIndex }
--     ::= { tnPortNetIngressStatsTable 1 }
--
-- TmnxPortNetIngressStatsEntry ::=
--     SEQUENCE {
--         tnPortNetIngressQueueIndex      TQueueId,
--         tnPortNetIngressFwdInProfPkts   Counter64,
--         tnPortNetIngressFwdOutProfPkts  Counter64,
--         tnPortNetIngressFwdInProfOcts   Counter64,
--         tnPortNetIngressFwdOutProfOcts  Counter64,
--         tnPortNetIngressDroInProfPkts   Counter64,
--         tnPortNetIngressDroOutProfPkts  Counter64,
--         tnPortNetIngressDroInProfOcts   Counter64,
--         tnPortNetIngressDroOutProfOcts  Counter64
--     }
--
-- tnPortNetIngressQueueIndex OBJECT-TYPE
--     SYNTAX      TQueueId (1..16)
--     MAX-ACCESS  not-accessible
--     STATUS      current
--     DESCRIPTION
--         "tnPortNetIngressQueueIndex serves as the tertiary index. When used
--          in conjunction with tnPortPortID, it uniquely
--          identifies a network ingress queue for the specified port in the
--          managed system."
--     ::= { tnPortNetIngressStatsEntry 1 }
--
-- tnPortNetIngressFwdInProfPkts OBJECT-TYPE
--     SYNTAX      Counter64
--     MAX-ACCESS  read-only
--     STATUS      current
--     DESCRIPTION
--         "tnPortNetIngressFwdInProfPkts indicates the number of conforming
--          network ingress packets forwarded on this port using this queue."
--     ::= { tnPortNetIngressStatsEntry 2 }
--
-- tnPortNetIngressFwdOutProfPkts OBJECT-TYPE
--     SYNTAX      Counter64
--     MAX-ACCESS  read-only
--     STATUS      current
--     DESCRIPTION
--         "tnPortNetIngressFwdOutProfPkts indicates the number of exceeding
--          network ingress packets forwarded on this port using this queue."
--     ::= { tnPortNetIngressStatsEntry 3 }
--
-- tnPortNetIngressFwdInProfOcts OBJECT-TYPE
--     SYNTAX      Counter64
--     MAX-ACCESS  read-only
--     STATUS      current
--     DESCRIPTION
--         "tnPortNetIngressFwdInProfOcts indicates the number of conforming
--          network ingress octets forwarded on this port using this queue."
--     ::= { tnPortNetIngressStatsEntry 4 }
--
-- tnPortNetIngressFwdOutProfOcts OBJECT-TYPE
--     SYNTAX      Counter64
--     MAX-ACCESS  read-only
--     STATUS      current
--     DESCRIPTION
--         "tnPortNetIngressFwdOutProfOcts indicates the number of exceeding
--          network ingress octets forwarded on this port using this queue."
--     ::= { tnPortNetIngressStatsEntry 5 }
--
-- tnPortNetIngressDroInProfPkts OBJECT-TYPE
--     SYNTAX      Counter64
--     MAX-ACCESS  read-only
--     STATUS      current
--     DESCRIPTION
--         "tnPortNetIngressDroInProfPkts indicates the number of conforming
--          network ingress packets dropped on this port using this queue."
--     ::= { tnPortNetIngressStatsEntry 6 }
--
-- tnPortNetIngressDroOutProfPkts OBJECT-TYPE
--     SYNTAX      Counter64
--     MAX-ACCESS  read-only
--     STATUS      current
--     DESCRIPTION
--         "tnPortNetIngressDroOutProfPkts indicates the number of exceeding
--          network ingress packets dropped on this port using this queue."
--     ::= { tnPortNetIngressStatsEntry 7 }
--
-- tnPortNetIngressDroInProfOcts OBJECT-TYPE
--     SYNTAX      Counter64
--     MAX-ACCESS  read-only
--     STATUS      current
--     DESCRIPTION
--         "tnPortNetIngressDroInProfOcts indicates the number of conforming
--          network ingress octets dropped on this port using this queue."
--     ::= { tnPortNetIngressStatsEntry 8 }
--
-- tnPortNetIngressDroOutProfOcts OBJECT-TYPE
--     SYNTAX      Counter64
--     MAX-ACCESS  read-only
--     STATUS      current
--     DESCRIPTION
--         "tnPortNetIngressDroOutProfOcts indicates the number of exceeding
--          network ingress octets dropped on this port using this queue."
--     ::= { tnPortNetIngressStatsEntry 9 }

--
--  Network Port Egress Stats Table
--
-- tnPortNetEgressStatsTable OBJECT-TYPE
--     SYNTAX      SEQUENCE OF TmnxPortNetEgressStatsEntry
--     MAX-ACCESS  not-accessible
--     STATUS      current
--     DESCRIPTION
--         "Defines the Nokia 7x50 SR series network port egress
--          statistics table for providing, via SNMP, the capability of
--          retrieving the traffic statistics for the physical queues
--          being used for the ports to forward the network egress
--          traffic."
--     ::= { tnPortStatsObjs 2 }
--
-- tnPortNetEgressStatsEntry    OBJECT-TYPE
--     SYNTAX      TmnxPortNetEgressStatsEntry
--     MAX-ACCESS  not-accessible
--     STATUS      current
--     DESCRIPTION
--         "Defines an entry in tnPortNetEgressStatsTable. Entries are
--          created and deleted by the system depending on the queue policy
--          being used at the specific port."
--     INDEX   {  tnPortPortID, tnPortNetEgressQueueIndex }
--     ::= { tnPortNetEgressStatsTable 1 }
--
-- TmnxPortNetEgressStatsEntry ::=
--     SEQUENCE {
--         tnPortNetEgressQueueIndex      TQueueId,
--         tnPortNetEgressFwdInProfPkts   Counter64,
--         tnPortNetEgressFwdOutProfPkts  Counter64,
--         tnPortNetEgressFwdInProfOcts   Counter64,
--         tnPortNetEgressFwdOutProfOcts  Counter64,
--         tnPortNetEgressDroInProfPkts   Counter64,
--         tnPortNetEgressDroOutProfPkts  Counter64,
--         tnPortNetEgressDroInProfOcts   Counter64,
--         tnPortNetEgressDroOutProfOcts  Counter64
--     }
--
-- tnPortNetEgressQueueIndex OBJECT-TYPE
--     SYNTAX      TQueueId (1..8)
--     MAX-ACCESS  not-accessible
--     STATUS      current
--     DESCRIPTION
--         "tnPortNetEgressQueueIndex serves as the tertiary index. When used
--          in conjunction with tnPortPortID, it uniquely
--          identifies a network egress queue for the specified port in the
--          managed system."
--     ::= { tnPortNetEgressStatsEntry 1 }
--
-- tnPortNetEgressFwdInProfPkts OBJECT-TYPE
--     SYNTAX      Counter64
--     MAX-ACCESS  read-only
--     STATUS      current
--     DESCRIPTION
--         "tnPortNetEgressFwdInProfPkts indicates the number of conforming
--          network egress packets forwarded on this port using this queue."
--     ::= { tnPortNetEgressStatsEntry 2 }
--
-- tnPortNetEgressFwdOutProfPkts OBJECT-TYPE
--     SYNTAX      Counter64
--     MAX-ACCESS  read-only
--     STATUS      current
--     DESCRIPTION
--         "tnPortNetEgressFwdOutProfPkts indicates the number of exceeding
--          network egress packets forwarded on this port using this queue."
--     ::= { tnPortNetEgressStatsEntry 3 }
--
-- tnPortNetEgressFwdInProfOcts OBJECT-TYPE
--     SYNTAX      Counter64
--     MAX-ACCESS  read-only
--     STATUS      current
--     DESCRIPTION
--         "tnPortNetEgressFwdInProfOcts indicates the number of conforming
--          network egress octets forwarded on this port using this queue."
--     ::= { tnPortNetEgressStatsEntry 4 }
--
-- tnPortNetEgressFwdOutProfOcts OBJECT-TYPE
--     SYNTAX      Counter64
--     MAX-ACCESS  read-only
--     STATUS      current
--     DESCRIPTION
--         "tnPortNetEgressFwdOutProfOcts indicates the number of exceeding
--          network egress octets forwarded on this port using this queue."
--     ::= { tnPortNetEgressStatsEntry 5 }
--
-- tnPortNetEgressDroInProfPkts OBJECT-TYPE
--     SYNTAX      Counter64
--     MAX-ACCESS  read-only
--     STATUS      current
--     DESCRIPTION
--         "tnPortNetEgressDroInProfPkts indicates the number of conforming
--          network egress packets dropped on this port using this queue."
--     ::= { tnPortNetEgressStatsEntry 6 }
--
-- tnPortNetEgressDroOutProfPkts OBJECT-TYPE
--     SYNTAX      Counter64
--     MAX-ACCESS  read-only
--     STATUS      current
--     DESCRIPTION
--         "tnPortNetEgressDroOutProfPkts indicates the number of exceeding
--          network egress packets dropped on this port using this queue."
--     ::= { tnPortNetEgressStatsEntry 7 }
--
-- tnPortNetEgressDroInProfOcts OBJECT-TYPE
--     SYNTAX      Counter64
--     MAX-ACCESS  read-only
--     STATUS      current
--     DESCRIPTION
--         "tnPortNetEgressDroInProfOcts indicates the number of conforming
--          network egress octets dropped on this port using this queue."
--     ::= { tnPortNetEgressStatsEntry 8 }
--
-- tnPortNetEgressDroOutProfOcts OBJECT-TYPE
--     SYNTAX      Counter64
--     MAX-ACCESS  read-only
--     STATUS      current
--     DESCRIPTION
--         "tnPortNetEgressDroOutProfOcts indicates the number of exceeding
--          network egress octets dropped on this port using this queue."
--     ::= { tnPortNetEgressStatsEntry 9 }

--
--  Multiclass MLPPP Bundle Stats Table
--
--  This table provides per MClass MLPPP Bundle traffic statistics
--  The rows are created when tnBundleMlpppEntry has tnBundleMlpppClassCount
--  value set to enable Mclass MLPPP on a given bundle.
--

-- tnMcMlpppStatsTable OBJECT-TYPE
--     SYNTAX      SEQUENCE OF TmnxMcMlpppStatsEntry
--     MAX-ACCESS  not-accessible
--     STATUS      current
--     DESCRIPTION
--         "Defines the Nokia 7x50 SR series Multiclass MLPPP
--          statistics table for providing the capability of
--          retrieving the traffic statistics for the physical queues
--          being used for a class of a multiclass MLPPP bundle to
--          forward the traffic."
--     ::= { tnPortStatsObjs 4 }
--
-- tnMcMlpppStatsEntry    OBJECT-TYPE
--     SYNTAX      TmnxMcMlpppStatsEntry
--     MAX-ACCESS  not-accessible
--     STATUS      current
--     DESCRIPTION
--         "Defines an entry in tnMcMlpppStatsTable. Entries are
--          created and deleted by the system depending on the number of
--          classes being used by a given MLPPP bundle."
--     INDEX   {  tnBundleBundleID, tnMcMlpppClassIndex }
--     ::= { tnMcMlpppStatsTable 1 }
--
-- TmnxMcMlpppStatsEntry ::=
--     SEQUENCE {
--         tnMcMlpppClassIndex          TmnxMcMlpppClassIndex,
--         tnMcMlpppStatsIngressOct     Counter32,
--         tnMcMlpppStatsIngressPkt     Counter32,
--         tnMcMlpppStatsIngressErrPkt  Counter32,
--         tnMcMlpppStatsEgressOct      Counter32,
--         tnMcMlpppStatsEgressPkt      Counter32,
--         tnMcMlpppStatsEgressErrPkt   Counter32
--     }
--
-- tnMcMlpppClassIndex  OBJECT-TYPE
--     SYNTAX      TmnxMcMlpppClassIndex
--     MAX-ACCESS  not-accessible
--     STATUS      current
--     DESCRIPTION
--         "tnMcMlpppClassIndex serves as the tertiary index. When used
--          in conjunction with tnBundleBundleID, it
--          uniquely identifies a class of a multiclass MLPPP bundle in the
--          managed system."
--     ::= { tnMcMlpppStatsEntry 1 }
--
--
-- tnMcMlpppStatsIngressOct OBJECT-TYPE
--     SYNTAX      Counter32
--     MAX-ACCESS  read-only
--     STATUS      current
--     DESCRIPTION
--         "The value of tnMcMlpppStatsIngressOct indicates the total
--          number of octets in all packets received on the bundle
--          for the given class on ingress before reassembly."
--     ::= { tnMcMlpppStatsEntry 2 }
--
-- tnMcMlpppStatsIngressPkt OBJECT-TYPE
--     SYNTAX      Counter32
--     MAX-ACCESS  read-only
--     STATUS      current
--     DESCRIPTION
--         "The value of tnMcMlpppStatsIngressPkt indicates the total
--          number of packets forwarded on the bundle for the given
--          class on ingress towards higher layer protocols."
--     ::= { tnMcMlpppStatsEntry 3 }
--
-- tnMcMlpppStatsIngressErrPkt OBJECT-TYPE
--     SYNTAX      Counter32
--     MAX-ACCESS  read-only
--     STATUS      current
--     DESCRIPTION
--         "The value of tnMcMlpppStatsIngressErrPkt indicates the total
--          number of packets discarded due to reassembly errors
--          on the bundle for the given class on ingress."
--     ::= { tnMcMlpppStatsEntry 4 }
--
-- tnMcMlpppStatsEgressOct OBJECT-TYPE
--     SYNTAX      Counter32
--     MAX-ACCESS  read-only
--     STATUS      current
--     DESCRIPTION
--         "The value of tnMcMlpppStatsEgressOct indicates the total
--          number of octets in all packets received on the bundle
--          for the given class on egress before segmentation."
--     ::= { tnMcMlpppStatsEntry 5 }
--
-- tnMcMlpppStatsEgressPkt OBJECT-TYPE
--     SYNTAX      Counter32
--     MAX-ACCESS  read-only
--     STATUS      current
--     DESCRIPTION
--         "The value of tnMcMlpppStatsEgressPkt indicates the total
--          number of packets forwarded on the bundle for the given
--          class on egress towards the line."
--     ::= { tnMcMlpppStatsEntry 6 }
--
-- tnMcMlpppStatsEgressErrPkt OBJECT-TYPE
--     SYNTAX      Counter32
--     MAX-ACCESS  read-only
--     STATUS      current
--     DESCRIPTION
--         "The value of tnMcMlpppStatsEgressErrPkt indicates the total
--          number of packets discarded due to segmentation errors
--          on the bundle for the given class on egress."
--     ::= { tnMcMlpppStatsEntry 7 }

--
-- IMA Group Bundle Table
--
--  Sparse Dependent Extension of the tnBundleTable.
--
--  The same indexes are used for both the base table tnBundleTable,
--  and the sparse dependent table, tnBundleImaGrpTable.
--
--  This in effect extends the tnBundleTable with additional columns.
--  Rows are created in the tnBundleImaGrpTable only for those entries
--  in the tnBundleTable for a value of 'imagrp' for the bundle type.
--
--  Deletion of a row in the tnBundleTable results in the
--  same fate for the row in the tnBundleImaGrpTable.
--
-- tnBundleImaGrpTable OBJECT-TYPE
--     SYNTAX      SEQUENCE OF TnBundleImaGrpEntry
--     MAX-ACCESS  not-accessible
--     STATUS      current
--     DESCRIPTION
--         "The tnBundleImaGrpTable contains IMA Group data"
--     ::= { tnPortObjs 21 }
--
-- tnBundleImaGrpEntry OBJECT-TYPE
--     SYNTAX      TnBundleImaGrpEntry
--     MAX-ACCESS  not-accessible
--     STATUS      current
--     DESCRIPTION
--         "Each row entry contains data on an IMA Group."
--     INDEX       {  tnBundleBundleID }
--     ::= { tnBundleImaGrpTable 1 }
--
-- TnBundleImaGrpEntry ::=
--     SEQUENCE {
--         tnBundleImaGrpLnkActTimer     Unsigned32,
--         tnBundleImaGrpLnkDeactTimer   Unsigned32,
--         tnBundleImaGrpSymmetryMode    INTEGER,
--         tnBundleImaGrpTxId            Integer32,
--         tnBundleImaGrpRxId            Integer32,
--         tnBundleImaGrpTxRefLnk        TmnxPortID,
--         tnBundleImaGrpRxRefLnk        TmnxPortID,
--         tnBundleImaGrpSmNeState       TmnxImaGrpState,
--         tnBundleImaGrpSmFeState       TmnxImaGrpState,
--         tnBundleImaGrpSmFailState     TmnxImaGrpFailState,
--         tnBundleImaGrpSmDownSecs      Counter32,
--         tnBundleImaGrpSmOperSecs      Counter32,
--         tnBundleImaGrpAvailTxCR       Gauge32,
--         tnBundleImaGrpAvailRxCR       Gauge32,
--         tnBundleImaGrpNeFails         Counter32,
--         tnBundleImaGrpFeFails         Counter32,
--         tnBundleImaGrpTxIcpCells      Counter32,
--         tnBundleImaGrpRxIcpCells      Counter32,
--         tnBundleImaGrpErrorIcpCells   Counter32,
--         tnBundleImaGrpLostRxIcpCells  Counter32,
--         tnBundleImaGrpTxOamLablVal    Integer32,
--         tnBundleImaGrpRxOamLablVal    Integer32,
--         tnBundleImaGrpAlphaValue      Integer32,
--         tnBundleImaGrpBetaValue       Integer32,
--         tnBundleImaGrpGammaValue      Integer32,
--         tnBundleImaGrpNeClockMode     TmnxImaGrpClockModes,
--         tnBundleImaGrpFeClockMode     TmnxImaGrpClockModes,
--         tnBundleImaGrpVersion         TmnxImaGrpVersion,
--         tnBundleImaGrpMaxConfBw       Unsigned32,
--         tnBundleImaGrpTestState       TmnxImaTestState,
--         tnBundleImaGrpTestMember      TmnxPortID,
--         tnBundleImaGrpTestPattern     INTEGER,
--         tnBundleImaGrpDiffDelayMaxObs Unsigned32,
--         tnBundleImaGrpLeastDelayLink  Unsigned32
--     }
--
-- tnBundleImaGrpLnkActTimer OBJECT-TYPE
--     SYNTAX      Unsigned32 (1..30000)
--     UNITS       "milliseconds"
--     MAX-ACCESS  read-create
--     STATUS      current
--     DESCRIPTION
--         "tnBundleImaGrpLnkActTimer specifies the Link Activation Timer
--          used to clear an existing LIF, LODS and FRI-IMA alarm. The time
--          specified determines how long is needed for member links to
--          stabilize before being activated."
--     DEFVAL { 10000 }
--     ::= { tnBundleImaGrpEntry 1 }
--
-- tnBundleImaGrpLnkDeactTimer OBJECT-TYPE
--     SYNTAX      Unsigned32 (1..30000)
--     UNITS       "milliseconds"
--     MAX-ACCESS  read-create
--     STATUS      current
--     DESCRIPTION
--         "tnBundleImaGrpLnkDeactTimer specifies the Link Deactivation Timer
--          used to raise an LIF, LODS and FRI-IMA alarm. The time
--          specified determines how long before a member link is declared in
--          error and is deactivated."
--     DEFVAL { 2000 }
--     ::= { tnBundleImaGrpEntry 2 }
--
-- tnBundleImaGrpSymmetryMode OBJECT-TYPE
--     SYNTAX      INTEGER {
--                     symmetric (1)
--                 }
--     MAX-ACCESS  read-create
--     STATUS      current
--     DESCRIPTION
--         "tnBundleImaGrpSymmetryMode specifies the type of cell rate
--          transfer over the virtual link."
--     DEFVAL { symmetric }
--     ::= { tnBundleImaGrpEntry 3 }
--
-- tnBundleImaGrpTxId OBJECT-TYPE
--     SYNTAX      Integer32
--     MAX-ACCESS  read-only
--     STATUS      current
--     DESCRIPTION
--         "tnBundleImaGrpTxId specifies the IMA Id generated at group
--          creation time used by the near-end."
--     ::= { tnBundleImaGrpEntry 4 }
--
-- tnBundleImaGrpRxId OBJECT-TYPE
--     SYNTAX      Integer32
--     MAX-ACCESS  read-only
--     STATUS      current
--     DESCRIPTION
--         "tnBundleImaGrpRxId specifies the IMA ID generated at group
--          creation time used by the far-end."
--     ::= { tnBundleImaGrpEntry 5 }
--
-- tnBundleImaGrpTxRefLnk OBJECT-TYPE
--     SYNTAX      TmnxPortID
--     MAX-ACCESS  read-only
--     STATUS      current
--     DESCRIPTION
--         "tnBundleImaGrpTxRefLnk specifies the IMA bundle member
--          that was selected to be the transmit timing reference link.
--          If no member has been selected as the reference link a value
--          of zero is returned. "
--     ::= { tnBundleImaGrpEntry 6 }
--
-- tnBundleImaGrpRxRefLnk OBJECT-TYPE
--     SYNTAX      TmnxPortID
--     MAX-ACCESS  read-only
--     STATUS      current
--     DESCRIPTION
--         "tnBundleImaGrpRxRefLnk specifies the IMA bundle member
--          that was detected to be the receive timing reference link.
--          If no member has been detected as the reference link a value
--          of zero is returned. "
--     ::= { tnBundleImaGrpEntry 7 }
--
-- tnBundleImaGrpSmNeState OBJECT-TYPE
--     SYNTAX      TmnxImaGrpState
--     MAX-ACCESS  read-only
--     STATUS      current
--     DESCRIPTION
--         "tnBundleImaGrpSmNeState specifies the current state
--          of the IMA Group for the near-end."
--     ::= { tnBundleImaGrpEntry 8 }
--
-- tnBundleImaGrpSmFeState OBJECT-TYPE
--     SYNTAX      TmnxImaGrpState
--     MAX-ACCESS  read-only
--     STATUS      current
--     DESCRIPTION
--         "tnBundleImaGrpSmFeState specifies the current state
--          of the IMA Group for the far-end."
--     ::= { tnBundleImaGrpEntry 9 }
--
-- tnBundleImaGrpSmFailState OBJECT-TYPE
--     SYNTAX      TmnxImaGrpFailState
--     MAX-ACCESS  read-only
--     STATUS      current
--     DESCRIPTION
--         "tnBundleImaGrpSmFailState specifies the current state
--          of the IMA Group."
--     ::= { tnBundleImaGrpEntry 10 }
--
-- tnBundleImaGrpSmDownSecs OBJECT-TYPE
--     SYNTAX      Counter32
--     MAX-ACCESS  read-only
--     STATUS      current
--     DESCRIPTION
--         "tnBundleImaGrpSmDownSecs specifies the number of seconds
--          that the IMA Group State Machine is not Operational."
--     ::= { tnBundleImaGrpEntry 11 }
--
-- tnBundleImaGrpSmOperSecs OBJECT-TYPE
--     SYNTAX      Counter32
--     MAX-ACCESS  read-only
--     STATUS      current
--     DESCRIPTION
--         "tnBundleImaGrpSmOperSecs specifies the number of seconds
--          that the IMA Group State Machine has been in the Operational
--          State."
--     ::= { tnBundleImaGrpEntry 12 }
--
-- tnBundleImaGrpAvailTxCR OBJECT-TYPE
--     SYNTAX      Gauge32
--     MAX-ACCESS  read-only
--     STATUS      current
--     DESCRIPTION
--         "tnBundleImaGrpAvailTxCR specifies the available transmit
--          bandwidth on this IMA group. It only considers members that
--          are in the Active State."
--     ::= { tnBundleImaGrpEntry 13 }
--
-- tnBundleImaGrpAvailRxCR OBJECT-TYPE
--     SYNTAX      Gauge32
--     MAX-ACCESS  read-only
--     STATUS      current
--     DESCRIPTION
--         "tnBundleImaGrpAvailRxCR specifies the available bandwidth
--          on this IMA group in the receive direction. It only considers
--          members that are in the Active State."
--     ::= { tnBundleImaGrpEntry 14 }
--
-- tnBundleImaGrpNeFails OBJECT-TYPE
--     SYNTAX      Counter32
--     MAX-ACCESS  read-only
--     STATUS      current
--     DESCRIPTION
--         "tnBundleImaGrpNeFails specifies the number of reported
--          IMA Group failures since boot time."
--     ::= { tnBundleImaGrpEntry 15 }
--
-- tnBundleImaGrpFeFails OBJECT-TYPE
--     SYNTAX      Counter32
--     MAX-ACCESS  read-only
--     STATUS      current
--     DESCRIPTION
--         "tnBundleImaGrpFeFails specifies the number of reported
--          IMA Group far-end failures since boot time."
--     ::= { tnBundleImaGrpEntry 16 }
--
-- tnBundleImaGrpTxIcpCells OBJECT-TYPE
--     SYNTAX      Counter32
--     MAX-ACCESS  read-only
--     STATUS      current
--     DESCRIPTION
--         "tnBundleImaGrpTxIcpCells specifies number of transmitted
--          ICP cells for this IMA Group."
--     ::= { tnBundleImaGrpEntry 17 }
--
-- tnBundleImaGrpRxIcpCells OBJECT-TYPE
--     SYNTAX      Counter32
--     MAX-ACCESS  read-only
--     STATUS      current
--     DESCRIPTION
--         "tnBundleImaGrpRxIcpCells specifies number of received
--          ICP cells for this IMA Group."
--     ::= { tnBundleImaGrpEntry 18 }
--
-- tnBundleImaGrpErrorIcpCells OBJECT-TYPE
--     SYNTAX      Counter32
--     MAX-ACCESS  read-only
--     STATUS      current
--     DESCRIPTION
--         "tnBundleImaGrpErrorIcpCells specifies number of
--          ICP cells with HEC or CRC-10 errors."
--     ::= { tnBundleImaGrpEntry 19 }
--
-- tnBundleImaGrpLostRxIcpCells OBJECT-TYPE
--     SYNTAX      Counter32
--     MAX-ACCESS  read-only
--     STATUS      current
--     DESCRIPTION
--         "tnBundleImaGrpLostRxIcpCells specifies the number of
--          missing ICP cells at the expected offset."
--     ::= { tnBundleImaGrpEntry 20 }
--
-- tnBundleImaGrpTxOamLablVal OBJECT-TYPE
--     SYNTAX      Integer32
--     MAX-ACCESS  read-only
--     STATUS      current
--     DESCRIPTION
--         "tnBundleImaGrpTxOamLablVal specifies near-end value
--          to be transmitted."
--     ::= { tnBundleImaGrpEntry 21 }
--
-- tnBundleImaGrpRxOamLablVal OBJECT-TYPE
--     SYNTAX      Integer32
--     MAX-ACCESS  read-only
--     STATUS      current
--     DESCRIPTION
--         "tnBundleImaGrpRxOamLablVal specifies far-end value
--          received."
--     ::= { tnBundleImaGrpEntry 22 }
--
-- tnBundleImaGrpAlphaValue OBJECT-TYPE
--     SYNTAX      Integer32
--     MAX-ACCESS  read-create
--     STATUS      current
--     DESCRIPTION
--         "tnBundleImaGrpAlphaValue specifies the number of
--          consecutive ICP cells that need to be detected
--          before moving from the IMA Sync State to the IMA Hunt
--          State."
--     DEFVAL { 2 }
--     ::= { tnBundleImaGrpEntry 23 }
--
-- tnBundleImaGrpBetaValue OBJECT-TYPE
--     SYNTAX      Integer32
--     MAX-ACCESS  read-create
--     STATUS      current
--     DESCRIPTION
--         "tnBundleImaGrpBetaValue specifies the number of
--          consecutive errored ICP cells that need to be detected
--          before moving from the IMA Sync State to the IMA Hunt
--          State"
--     DEFVAL { 2 }
--     ::= { tnBundleImaGrpEntry 24 }
--
-- tnBundleImaGrpGammaValue OBJECT-TYPE
--     SYNTAX      Integer32
--     MAX-ACCESS  read-create
--     STATUS      current
--     DESCRIPTION
--         "tnBundleImaGrpGammaValue specifies the number of
--          consecutive valid ICP cells that need to be detected
--          before moving from the IMA pre-Sync State to the
--          IMA Hunt State."
--     DEFVAL { 1 }
--     ::= { tnBundleImaGrpEntry 25 }
--
-- tnBundleImaGrpNeClockMode OBJECT-TYPE
--     SYNTAX      TmnxImaGrpClockModes
--     MAX-ACCESS  read-create
--     STATUS      current
--     DESCRIPTION
--         "tnBundleImaGrpNeClockMode specifies near-end transmit
--          clock mode."
--     DEFVAL { ctc }
--     ::= { tnBundleImaGrpEntry 26 }
--
-- tnBundleImaGrpFeClockMode OBJECT-TYPE
--     SYNTAX      TmnxImaGrpClockModes
--     MAX-ACCESS  read-create
--     STATUS      current
--     DESCRIPTION
--         "tnBundleImaGrpFeClockMode specifies far-end transmit
--          clock mode."
--     DEFVAL { ctc }
--     ::= { tnBundleImaGrpEntry 27 }
--
-- tnBundleImaGrpVersion OBJECT-TYPE
--     SYNTAX      TmnxImaGrpVersion
--     MAX-ACCESS  read-create
--     STATUS      current
--     DESCRIPTION
--         "tnBundleImaGrpVersion specifies the IMA Version for
--          this group."
--     DEFVAL { oneDotOne }
--     ::= { tnBundleImaGrpEntry 28 }
--
-- tnBundleImaGrpMaxConfBw OBJECT-TYPE
--     SYNTAX      Unsigned32 (1..8)
--     MAX-ACCESS  read-create
--     STATUS      current
--     DESCRIPTION
--         "tnBundleImaGrpMaxConfBw specifies the number of links
--          that is used to determine the maximum configurable
--          bandwidth that is allowed to be used for this IMA group."
--     DEFVAL { 8 }
--     ::= { tnBundleImaGrpEntry 29 }
--
-- tnBundleImaGrpTestState OBJECT-TYPE
--     SYNTAX      TmnxImaTestState
--     MAX-ACCESS  read-create
--     STATUS      current
--     DESCRIPTION
--         "tnBundleImaGrpTestState specifies the current state of
--          the test pattern procedure. A value of 'disabled' specifies
--          that the group is currently not running. A value of
--          'operating' enables the test pattern procedure. The test
--          pattern procedure continues until it is 'disabled'."
--     DEFVAL { disabled }
--     ::= { tnBundleImaGrpEntry 30 }
--
-- tnBundleImaGrpTestMember OBJECT-TYPE
--     SYNTAX      TmnxPortID
--     MAX-ACCESS  read-create
--     STATUS      current
--     DESCRIPTION
--         "tnBundleImaGrpTestMember specifies a member link to
--          be used for the test pattern procedure. A value of zero
--          indicates that no member link has been selected.
--
--          When tnBundleImaGrpTestState does not have the value
--          'disabled', an attempt to set this object will be
--          rejected with an inconsistentValue error."
--     DEFVAL { 0 }
--     ::= { tnBundleImaGrpEntry 31 }
--
-- tnBundleImaGrpTestPattern OBJECT-TYPE
--     SYNTAX      INTEGER (0..255)
--     MAX-ACCESS  read-create
--     STATUS      current
--     DESCRIPTION
--         "tnBundleImaGrpTestPattern specifies the Transmit Test
--          Pattern in an IMA group loopback operation. This value
--          may only be changed when tnBundleImaGrpTestState is
--          'disabled'."
--     DEFVAL { 0 }
--     ::= { tnBundleImaGrpEntry 32 }
--
-- tnBundleImaGrpDiffDelayMaxObs OBJECT-TYPE
--     SYNTAX      Unsigned32
--     UNITS       "milliseconds"
--     MAX-ACCESS  read-only
--     STATUS      current
--     DESCRIPTION
--         "tnBundleImaGrpDiffDelayMaxObs indicates the latest
--          maximum differential delay observed between links
--          having the least and most link propagation delay
--          among the received links configured in this IMA group."
--     ::= { tnBundleImaGrpEntry 33 }
--
-- tnBundleImaGrpLeastDelayLink OBJECT-TYPE
--     SYNTAX      Unsigned32
--     UNITS       "milliseconds"
--     MAX-ACCESS  read-only
--     STATUS      current
--     DESCRIPTION
--         "tnBundleImaGrpLeastDelayLink indicates a member link
--          which has the smallest link propagation delay. If this
--          delay has yet to be determined or no member link has
--          been configured, a value of zero is returned."
--     ::= { tnBundleImaGrpEntry 34 }

--
-- IMA Group Member Table
--
--  Sparse Dependent Extension of the tnBundleMemberTable.
--
--  The same indexes are used for both the base table tnBundleMemberTable,
--  and the sparse dependent table, tnBundleMemberImaTable.
--
--  This in effect extends the tnBundleMemberTable with additional columns.
--  Rows are created in the tnBundleMemberImaTable only for those entries
--  in the tnBundleMemberTable that were created and have a value of 'imagrp'
--  for the bundle type.
--
--  Deletion of a row in the tnBundleMemberTable results in the
--  same fate for the row in the tnBundleMemberImaTable.
--

-- tnBundleMemberImaTable OBJECT-TYPE
--     SYNTAX      SEQUENCE OF TmnxBundleMemberImaEntry
--     MAX-ACCESS  not-accessible
--     STATUS      current
--     DESCRIPTION
--         "The tnBundleMemberImaTable has an entry for an
--          IMA link associated with an IMA Group."
--     ::= { tnPortObjs 22 }
--
-- tnBundleMemberImaEntry  OBJECT-TYPE
--     SYNTAX      TmnxBundleMemberImaEntry
--     MAX-ACCESS  not-accessible
--     STATUS      current
--     DESCRIPTION
--         "Each row entry represents an IMA link associated with
--          an IMA Group."
--     INDEX   { tnBundleBundleID, tnPortPortID }
--     ::= { tnBundleMemberImaTable 1 }
--
-- TmnxBundleMemberImaEntry ::=
--     SEQUENCE {
--         tnBundleMemberImaNeTxState     TmnxImaLnkState,
--         tnBundleMemberImaNeRxState     TmnxImaLnkState,
--         tnBundleMemberImaFeTxState     TmnxImaLnkState,
--         tnBundleMemberImaFeRxState     TmnxImaLnkState,
--         tnBundleMemberImaNeRxFailState TmnxImaLnkFailState,
--         tnBundleMemberImaFeRxFailState TmnxImaLnkFailState,
--         tnBundleMemberImaTxLid         Integer32,
--         tnBundleMemberImaRxLid         Integer32,
--         tnBundleMemberImaViolations    Counter32,
--         tnBundleMemberImaNeSevErrSecs  Counter32,
--         tnBundleMemberImaFeSevErrSecs  Counter32,
--         tnBundleMemberImaNeUnavailSecs Counter32,
--         tnBundleMemberImaFeUnavailSecs Counter32,
--         tnBundleMemberImaNeTxUnuseSecs Counter32,
--         tnBundleMemberImaNeRxUnuseSecs Counter32,
--         tnBundleMemberImaFeTxUnuseSecs Counter32,
--         tnBundleMemberImaFeRxUnuseSecs Counter32,
--         tnBundleMemberImaNeTxNumFails  Counter32,
--         tnBundleMemberImaNeRxNumFails  Counter32,
--         tnBundleMemberImaFeTxNumFails  Counter32,
--         tnBundleMemberImaFeRxNumFails  Counter32,
--         tnBundleMemberImaTxIcpCells    Counter32,
--         tnBundleMemberImaRxIcpCells    Counter32,
--         tnBundleMemberImaErrorIcpCells Counter32,
--         tnBundleMemberImaLstRxIcpCells Counter32,
--         tnBundleMemberImaOifAnomalies  Counter32,
--         tnBundleMemberImaRxTestState   TmnxImaTestState,
--         tnBundleMemberImaRxTestPattern INTEGER,
--         tnBundleMemberImaRelDelay      Unsigned32
--     }
--
-- tnBundleMemberImaNeTxState    OBJECT-TYPE
--     SYNTAX      TmnxImaLnkState
--     MAX-ACCESS  read-only
--     STATUS      current
--     DESCRIPTION
--         "tnBundleMemberImaNeTxState indicates the state of near-end
--          transmit IMA link."
--     ::= { tnBundleMemberImaEntry 1 }
--
-- tnBundleMemberImaNeRxState    OBJECT-TYPE
--     SYNTAX      TmnxImaLnkState
--     MAX-ACCESS  read-only
--     STATUS      current
--     DESCRIPTION
--         "tnBundleMemberImaNeRxState indicates the state of near-end
--          receive IMA link."
--     ::= { tnBundleMemberImaEntry 2 }
--
-- tnBundleMemberImaFeTxState    OBJECT-TYPE
--     SYNTAX      TmnxImaLnkState
--     MAX-ACCESS  read-only
--     STATUS      current
--     DESCRIPTION
--         "tnBundleMemberImaFeTxState indicates the state of far-end
--          transmit IMA link."
--     ::= { tnBundleMemberImaEntry 3 }
--
-- tnBundleMemberImaFeRxState    OBJECT-TYPE
--     SYNTAX      TmnxImaLnkState
--     MAX-ACCESS  read-only
--     STATUS      current
--     DESCRIPTION
--         "tnBundleMemberImaFeRxState indicates the state of far-end
--          receive IMA link."
--     ::= { tnBundleMemberImaEntry 4 }
--
-- tnBundleMemberImaNeRxFailState    OBJECT-TYPE
--     SYNTAX      TmnxImaLnkFailState
--     MAX-ACCESS  read-only
--     STATUS      current
--     DESCRIPTION
--         "tnBundleMemberImaNeRxFailState indicates the IMA link failure
--          reason for the near-end."
--     ::= { tnBundleMemberImaEntry 5 }
--
-- tnBundleMemberImaFeRxFailState    OBJECT-TYPE
--     SYNTAX      TmnxImaLnkFailState
--     MAX-ACCESS  read-only
--     STATUS      current
--     DESCRIPTION
--         "tnBundleMemberImaFeRxFailState indicates the IMA link failure
--          reason for the far-end."
--     ::= { tnBundleMemberImaEntry 6 }
--
-- tnBundleMemberImaTxLid OBJECT-TYPE
--     SYNTAX      Integer32
--     MAX-ACCESS  read-only
--     STATUS      current
--     DESCRIPTION
--         "tnBundleMemberImaTxLid indicates the Link Identifier
--          assigned to the transmit IMA link."
--     ::= { tnBundleMemberImaEntry 7 }
--
-- tnBundleMemberImaRxLid OBJECT-TYPE
--     SYNTAX      Integer32
--     MAX-ACCESS  read-only
--     STATUS      current
--     DESCRIPTION
--         "tnBundleMemberImaRxLid indicates the Link Identifier
--          used on the receive IMA link."
--     ::= { tnBundleMemberImaEntry 8 }
--
-- tnBundleMemberImaViolations OBJECT-TYPE
--     SYNTAX      Counter32
--     MAX-ACCESS  read-only
--     STATUS      current
--     DESCRIPTION
--         "tnBundleMemberImaViolations indicates the number of
--          ICP violations including errored, invalid or missing ICP
--          cells."
--     ::= { tnBundleMemberImaEntry 9 }
--
-- tnBundleMemberImaNeSevErrSecs OBJECT-TYPE
--     SYNTAX      Counter32
--     MAX-ACCESS  read-only
--     STATUS      current
--     DESCRIPTION
--         "tnBundleMemberImaNeSevErrSecs indicates the number
--          of one second intervals in which thirty percent or
--          more of the near-end ICP cells are in violation, or
--          link defects have occurred."
--     ::= { tnBundleMemberImaEntry 10 }
--
-- tnBundleMemberImaFeSevErrSecs OBJECT-TYPE
--     SYNTAX      Counter32
--     MAX-ACCESS  read-only
--     STATUS      current
--     DESCRIPTION
--         "tnBundleMemberImaFeSevErrSecs indicates the number
--          of one second intervals in which the far-end contains
--          IMA-RDI defects."
--     ::= { tnBundleMemberImaEntry 11 }
--
-- tnBundleMemberImaNeUnavailSecs OBJECT-TYPE
--     SYNTAX      Counter32
--     MAX-ACCESS  read-only
--     STATUS      current
--     DESCRIPTION
--         "tnBundleMemberImaNeUnavailSecs indicates the number
--          of unavailable seconds at the near-end."
--     ::= { tnBundleMemberImaEntry 12 }
--
-- tnBundleMemberImaFeUnavailSecs OBJECT-TYPE
--     SYNTAX      Counter32
--     MAX-ACCESS  read-only
--     STATUS      current
--     DESCRIPTION
--         "tnBundleMemberImaFeUnavailSecs indicates the number
--          of unavailable seconds at the near-end."
--     ::= { tnBundleMemberImaEntry 13 }
--
-- tnBundleMemberImaNeTxUnuseSecs OBJECT-TYPE
--     SYNTAX      Counter32
--     MAX-ACCESS  read-only
--     STATUS      current
--     DESCRIPTION
--         "tnBundleMemberImaNeTxUnuseSecs indicates the number
--          of unavailable seconds at the near-end transmit link
--          state machine."
--     ::= { tnBundleMemberImaEntry 14 }
--
-- tnBundleMemberImaNeRxUnuseSecs OBJECT-TYPE
--     SYNTAX      Counter32
--     MAX-ACCESS  read-only
--     STATUS      current
--     DESCRIPTION
--         "tnBundleMemberImaNeRxUnuseSecs indicates the number
--          of unavailable seconds at the near-end receive link
--          state machine."
--     ::= { tnBundleMemberImaEntry 15 }
--
-- tnBundleMemberImaFeTxUnuseSecs OBJECT-TYPE
--     SYNTAX      Counter32
--     MAX-ACCESS  read-only
--     STATUS      current
--     DESCRIPTION
--         "tnBundleMemberImaFeTxUnuseSecs indicates the number
--          of unavailable seconds at the far-end transmit link
--          state machine."
--     ::= { tnBundleMemberImaEntry 16 }
--
-- tnBundleMemberImaFeRxUnuseSecs OBJECT-TYPE
--     SYNTAX      Counter32
--     MAX-ACCESS  read-only
--     STATUS      current
--     DESCRIPTION
--         "tnBundleMemberImaFeRxUnuseSecs indicates the number
--          of unavailable seconds at the far-end receive link
--          state machine."
--     ::= { tnBundleMemberImaEntry 17 }
--
-- tnBundleMemberImaNeTxNumFails OBJECT-TYPE
--     SYNTAX      Counter32
--     MAX-ACCESS  read-only
--     STATUS      current
--     DESCRIPTION
--         "tnBundleMemberImaNeTxNumFails indicates the number
--          of times that a near-end transmit alarm is set on the
--          IMA link."
--     ::= { tnBundleMemberImaEntry 18 }
--
-- tnBundleMemberImaNeRxNumFails OBJECT-TYPE
--     SYNTAX      Counter32
--     MAX-ACCESS  read-only
--     STATUS      current
--     DESCRIPTION
--         "tnBundleMemberImaNeRxNumFails indicates the number
--          of times that a near-end receive alarm is set on the
--          IMA link."
--     ::= { tnBundleMemberImaEntry 19 }
--
-- tnBundleMemberImaFeTxNumFails OBJECT-TYPE
--     SYNTAX      Counter32
--     MAX-ACCESS  read-only
--     STATUS      current
--     DESCRIPTION
--         "tnBundleMemberImaFeTxNumFails indicates the number
--          of times that a far-end transmit alarm is set on the
--          IMA link."
--     ::= { tnBundleMemberImaEntry 20 }
--
-- tnBundleMemberImaFeRxNumFails OBJECT-TYPE
--     SYNTAX      Counter32
--     MAX-ACCESS  read-only
--     STATUS      current
--     DESCRIPTION
--         "tnBundleMemberImaFeRxNumFails indicates the number
--          of times that a far-end receive alarm is set on the
--          IMA link."
--     ::= { tnBundleMemberImaEntry 21 }
--
-- tnBundleMemberImaTxIcpCells OBJECT-TYPE
--     SYNTAX      Counter32
--     MAX-ACCESS  read-only
--     STATUS      current
--     DESCRIPTION
--         "tnBundleMemberImaTxIcpCells indicates the number
--          of ICP cells that have been transmitted on the IMA
--          link."
--     ::= { tnBundleMemberImaEntry 22 }
--
-- tnBundleMemberImaRxIcpCells OBJECT-TYPE
--     SYNTAX      Counter32
--     MAX-ACCESS  read-only
--     STATUS      current
--     DESCRIPTION
--         "tnBundleMemberImaRxIcpCells indicates the number
--          of ICP cells that have been received on the IMA
--          link."
--     ::= { tnBundleMemberImaEntry 23 }
--
-- tnBundleMemberImaErrorIcpCells OBJECT-TYPE
--     SYNTAX      Counter32
--     MAX-ACCESS  read-only
--     STATUS      current
--     DESCRIPTION
--         "tnBundleMemberImaErrorIcpCells indicates the number
--          of ICP cells with HEC or CRC-10 errors."
--     ::= { tnBundleMemberImaEntry 24 }
--
-- tnBundleMemberImaLstRxIcpCells OBJECT-TYPE
--     SYNTAX      Counter32
--     MAX-ACCESS  read-only
--     STATUS      current
--     DESCRIPTION
--         "tnBundleMemberImaLstRxIcpCells indicates the number
--          of lost ICP cells at the expected offset."
--     ::= { tnBundleMemberImaEntry 25 }
--
-- tnBundleMemberImaOifAnomalies OBJECT-TYPE
--     SYNTAX      Counter32
--     MAX-ACCESS  read-only
--     STATUS      current
--     DESCRIPTION
--         "tnBundleMemberImaOifAnomalies indicates the number
--          of OIF anomalies at the near-end."
--     ::= { tnBundleMemberImaEntry 26 }
--
-- tnBundleMemberImaRxTestState OBJECT-TYPE
--     SYNTAX      TmnxImaTestState
--     MAX-ACCESS  read-only
--     STATUS      current
--     DESCRIPTION
--         "tnBundleMemberImaRxTestState indicates the current
--          state of the test pattern on this link."
--     ::= { tnBundleMemberImaEntry 27 }
--
-- tnBundleMemberImaRxTestPattern OBJECT-TYPE
--     SYNTAX      INTEGER (0..255)
--     MAX-ACCESS  read-only
--     STATUS      current
--     DESCRIPTION
--         "tnBundleMemberImaRxTestPattern indicates the received
--         test pattern value on this link."
--     ::= { tnBundleMemberImaEntry 28 }
--
-- tnBundleMemberImaRelDelay OBJECT-TYPE
--     SYNTAX      Unsigned32
--     UNITS       "milliseconds"
--     MAX-ACCESS  read-only
--     STATUS      current
--     DESCRIPTION
--         "tnBundleMemberImaRelDelay indicates the latest measured
--         delay on this member link relative to the member link with
--         the least delay within the same IMA group"
--     ::= { tnBundleMemberImaEntry 29 }

--
-- DS1 Port table
--
-- tnDS1PortTable OBJECT-TYPE
--     SYNTAX      SEQUENCE OF TmnxDS1PortEntry
--     MAX-ACCESS  not-accessible
--     STATUS      current
--     DESCRIPTION
--         "The tnDS1PortTable has an entry for a DS1 physical port."
--     ::= { tnPortObjs 23 }
--
-- tnDS1PortEntry       OBJECT-TYPE
--     SYNTAX      TmnxDS1PortEntry
--     MAX-ACCESS  not-accessible
--     STATUS      current
--     DESCRIPTION
--         "Each row entry represents a physical DS1 port on a
--          IOM card in a chassis in the system.  Entries cannot be created
--          and deleted via SNMP SET operations.  Entries in this table will
--          be created automatically when the tmnxMDAAssignedType object is
--          set to the DS1 MDA type The tnDS1PortEntry contains attributes
--          that are unique to the 'ds1e1' TmnxPortType. The tnPortPortID
--          contains the slot, mda and port numbers encoded into it.
--
--          For each tnDS1PortEntry, there will be a corresponding entry
--          in the tnPortTable and the ifTable."
--     INDEX       {  tnPortPortID }
--     ::= { tnDS1PortTable 1 }
--
-- TmnxDS1PortEntry ::=
--     SEQUENCE {
--         tnDS1PortBuildout             INTEGER,
--         tnDS1PortLastChangeTime       TimeStamp,
--         tnDS1PortType                 INTEGER,
--         tnDS1PortLineLength           INTEGER,
--         tnDS1PortLbo                  INTEGER,
--         tnDS1PortDbGain               Integer32
--     }
--
-- tnDS1PortBuildout       OBJECT-TYPE
--     SYNTAX      INTEGER {
--                     short (1),
--                     long  (2)
--                 }
--     MAX-ACCESS  read-create
--     STATUS      current
--     DESCRIPTION
--         "tnDS1PortBuildout configures the cable buildout length.  A ds1 port
--          has two settings for the DS1 cable buildout: a 'short' setting, for
--          cable lengths of less than or equal to 655 feet, and a 'long' setting
--          for cable lengths of greater than 655 feet.
--          This object applies to copper-cable-based DS1 ports only."
--     DEFVAL      { short }
--     ::= { tnDS1PortEntry 1 }
--
-- tnDS1PortLastChangeTime OBJECT-TYPE
--     SYNTAX      TimeStamp
--     MAX-ACCESS  read-only
--     STATUS      current
--     DESCRIPTION
--         "The tnDS1PortLastChangeTime variable contains the sysUpTime
--          value of the most recently modified writable variable in the
--          tnDS1PortEntry row for this port."
--     ::= { tnDS1PortEntry 2 }
--
-- tnDS1PortType           OBJECT-TYPE
--     SYNTAX      INTEGER {
--                     ds1(1),
--                     e1 (2),
--                     j1 (3)
--                 }
--     MAX-ACCESS  read-create
--     STATUS      current
--     DESCRIPTION
--         "tnDS1PortType configures the type of the physical port to 'ds1',
--          'e1' or 'j1'."
--     DEFVAL      { ds1 }
--     ::= { tnDS1PortEntry 3 }
--
-- tnDS1PortLineLength           OBJECT-TYPE
--     SYNTAX      INTEGER {
--                     lengthNotApplicable (1),
--                     length0To133        (2),
--                     length134To266      (3),
--                     length267To399      (4),
--                     length400To533      (5),
--                     length534To655      (6)
--                 }
--     MAX-ACCESS  read-create
--     STATUS      current
--     DESCRIPTION
--         "tnDS1PortLineLength configuration only applies to a ds1 port
--          configured with a 'short' buildout.  tnDS1PortLineLength configures
--          the length of the line (in feet).  For line lengths longer than 655
--          feet configure the ds1 port buildout as 'long'.
--          For 'long' buildout the following values are valid:
--              lengthNotApplicable - Not applicable
--          For 'short' buildout the following values are valid:
--              length0To133        - For line length from 0 to 133 feet
--              length134To266      - For line length from 134 to 266 feet
--              length267To399      - For line length from 267 to 399 feet
--              length400To533      - For line length from 400 to 533 feet
--              length534To655      - For line length from 534 to 655 feet
--          The default for 'long' buildout is 'lengthNotApplicable' while the
--          default for 'short' buildout is 'length0To133'."
--     ::= { tnDS1PortEntry 4 }
--
-- tnDS1PortLbo       OBJECT-TYPE
--     SYNTAX      INTEGER {
--                     lboNotApplicable (1),
--                     lbo0dB           (2),
--                     lboNeg7p5dB      (3),
--                     lboNeg15p0dB     (4),
--                     lboNeg22p5dB     (5)
--                 }
--     MAX-ACCESS  read-create
--     STATUS      current
--     DESCRIPTION
--         "tnDS1PortLbo configuration only applies to a ds1 port
--          configured with a 'long' buildout.  tnDS1PortLbo configures the
--          number of decibels(dB) the transmission signal decreases over the line.
--          For 'short' buildout the following values are valid:
--              lboNotApplicable - Not applicable
--          For 'long' buildout the following values are valid:
--              lbo0dB           - For 0 dB
--              lboNeg7p5dB      - For -7.5 dB
--              lboNeg15p0dB     - For -15.0 dB
--              lboNeg22p5dB     - For -22.5 dB
--          The default for 'short' build out is 'lboNotApplicable' while the
--          default for 'long' buildout is 'lbo0dB'"
--     ::= { tnDS1PortEntry 5 }
--
-- tnDS1PortDbGain       OBJECT-TYPE
--     SYNTAX      Integer32
--     UNITS       "db"
--     MAX-ACCESS  read-only
--     STATUS      current
--     DESCRIPTION
--         "tnDS1PortDbGain only applies to a ds1 port configured with a
--          'long' buildout.  tnDS1PortDbGain shows the number of decibels
--          the received signal is increased to compensate for loss."
--     ::= { tnDS1PortEntry 6 }

--
--      Port scheduler policy overrides
--

-- tnPortSchedOverrideTable OBJECT-TYPE
--     SYNTAX      SEQUENCE OF TmnxPortSchedOverrideEntry
--     MAX-ACCESS  not-accessible
--     STATUS      current
--     DESCRIPTION
--         "The tnPortSchedOverrideTable has an entry for each port
--          scheduler override configured on this system."
--     ::= { tnPortObjs 24 }
--
-- tnPortSchedOverrideEntry    OBJECT-TYPE
--     SYNTAX      TmnxPortSchedOverrideEntry
--     MAX-ACCESS  not-accessible
--     STATUS      current
--     DESCRIPTION
--         "Each row represents a particular port-scheduler override. Entries
--          are created and deleted by the user."
--     INDEX {  tnPortPortID }
--     ::= { tnPortSchedOverrideTable 1}
--
-- TmnxPortSchedOverrideEntry ::= SEQUENCE
--     {
--         tnPortSchedOverrideRowStatus          RowStatus,
--         tnPortSchedOverrideSchedName          DisplayString,
--         tnPortSchedOverrideLastChanged        TimeStamp,
--         tnPortSchedOverrideMaxRate            TPortSchedulerPIR,
--         tnPortSchedOverrideLvl1PIR            TPortSchedulerPIR,
--         tnPortSchedOverrideLvl1CIR            TPortSchedulerCIR,
--         tnPortSchedOverrideLvl2PIR            TPortSchedulerPIR,
--         tnPortSchedOverrideLvl2CIR            TPortSchedulerCIR,
--         tnPortSchedOverrideLvl3PIR            TPortSchedulerPIR,
--         tnPortSchedOverrideLvl3CIR            TPortSchedulerCIR,
--         tnPortSchedOverrideLvl4PIR            TPortSchedulerPIR,
--         tnPortSchedOverrideLvl4CIR            TPortSchedulerCIR,
--         tnPortSchedOverrideLvl5PIR            TPortSchedulerPIR,
--         tnPortSchedOverrideLvl5CIR            TPortSchedulerCIR,
--         tnPortSchedOverrideLvl6PIR            TPortSchedulerPIR,
--         tnPortSchedOverrideLvl6CIR            TPortSchedulerCIR,
--         tnPortSchedOverrideLvl7PIR            TPortSchedulerPIR,
--         tnPortSchedOverrideLvl7CIR            TPortSchedulerCIR,
--         tnPortSchedOverrideLvl8PIR            TPortSchedulerPIR,
--         tnPortSchedOverrideLvl8CIR            TPortSchedulerCIR,
--         tnPortSchedOverrideFlags              BITS
--     }
--
-- tnPortSchedOverrideRowStatus        OBJECT-TYPE
--     SYNTAX      RowStatus
--     MAX-ACCESS  read-create
--     STATUS      current
--     DESCRIPTION
--         "The value of tnPortSchedOverrideRowStatus is used for the
--          creation and deletion of port-scheduler overrides. When
--          tnPortEgrPortSchedPlcy of the tnPortEntry indexed by the
--          same indices of this table is an empty string, creation
--          will fail."
--     ::= { tnPortSchedOverrideEntry 1 }
--
-- tnPortSchedOverrideSchedName        OBJECT-TYPE
--     SYNTAX      DisplayString
--     MAX-ACCESS  read-only
--     STATUS      current
--     DESCRIPTION
--         "The value of tnPortSchedOverrideSchedName indicates the name
--          of the port scheduler policy that this row entry overrides."
--     ::= { tnPortSchedOverrideEntry 2 }
--
-- tnPortSchedOverrideLastChanged        OBJECT-TYPE
--     SYNTAX      TimeStamp
--     MAX-ACCESS  read-only
--     STATUS      current
--     DESCRIPTION
--         "The value of tnPortSchedOverrideLastChanged indicates the value
--          of sysUpTime at the time of the most recent management change to
--          this row."
--     ::= { tnPortSchedOverrideEntry 3 }
--
-- tnPortSchedOverrideMaxRate        OBJECT-TYPE
--     SYNTAX      TPortSchedulerPIR
--     UNITS       "kbps"
--     MAX-ACCESS  read-create
--     STATUS      current
--     DESCRIPTION
--         "The value of tnPortSchedOverrideMaxRate specifies the explicit
--          maximum frame based bandwidth limit. This object overrides
--          TIMETRA-QOS-MIB::tPortSchedulerPlcyMaxRate."
--     DEFVAL      { -1 }
--     ::= { tnPortSchedOverrideEntry 4 }
--
-- tnPortSchedOverrideLvl1PIR        OBJECT-TYPE
--     SYNTAX      TPortSchedulerPIR
--     UNITS       "kbps"
--     MAX-ACCESS  read-create
--     STATUS      current
--     DESCRIPTION
--         "The value of tnPortSchedOverrideLvl1PIR specifies the total
--          bandwidth limit, PIR, for priority level 1. This object
--          overrides TIMETRA-QOS-MIB::tPortSchedulerPlcyLvl1PIR."
--     DEFVAL      { -1 }
--     ::= { tnPortSchedOverrideEntry 5 }
--
-- tnPortSchedOverrideLvl1CIR        OBJECT-TYPE
--     SYNTAX      TPortSchedulerCIR
--     UNITS       "kbps"
--     MAX-ACCESS  read-create
--     STATUS      current
--     DESCRIPTION
--         "The value of tnPortSchedOverrideLvl1CIR specifies the within-cir
--          bandwidth limit for priority level 1. This object overrides
--          TIMETRA-QOS-MIB::tPortSchedulerPlcyLvl1CIR."
--     DEFVAL      { -1 }
--     ::= { tnPortSchedOverrideEntry 6 }
--
-- tnPortSchedOverrideLvl2PIR        OBJECT-TYPE
--     SYNTAX      TPortSchedulerPIR
--     UNITS       "kbps"
--     MAX-ACCESS  read-create
--     STATUS      current
--     DESCRIPTION
--         "The value of tnPortSchedOverrideLvl2PIR specifies the total
--          bandwidth limit, PIR, for priority level 2. This object
--          overrides TIMETRA-QOS-MIB::tPortSchedulerPlcyLvl2PIR."
--     DEFVAL      { -1 }
--     ::= { tnPortSchedOverrideEntry 7 }
--
-- tnPortSchedOverrideLvl2CIR        OBJECT-TYPE
--     SYNTAX      TPortSchedulerCIR
--     UNITS       "kbps"
--     MAX-ACCESS  read-create
--     STATUS      current
--     DESCRIPTION
--         "The value of tnPortSchedOverrideLvl2CIR specifies the within-cir
--          bandwidth limit for priority level 2. This object overrides
--          TIMETRA-QOS-MIB::tPortSchedulerPlcyLvl2CIR."
--     DEFVAL      { -1 }
--     ::= { tnPortSchedOverrideEntry 8 }
--
-- tnPortSchedOverrideLvl3PIR        OBJECT-TYPE
--     SYNTAX      TPortSchedulerPIR
--     UNITS       "kbps"
--     MAX-ACCESS  read-create
--     STATUS      current
--     DESCRIPTION
--         "The value of tnPortSchedOverrideLvl3PIR specifies the total
--          bandwidth limit, PIR, for priority level 3. This object
--          overrides TIMETRA-QOS-MIB::tPortSchedulerPlcyLvl3PIR."
--     DEFVAL      { -1 }
--     ::= { tnPortSchedOverrideEntry 9 }
--
-- tnPortSchedOverrideLvl3CIR        OBJECT-TYPE
--     SYNTAX      TPortSchedulerCIR
--     UNITS       "kbps"
--     MAX-ACCESS  read-create
--     STATUS      current
--     DESCRIPTION
--         "The value of tnPortSchedOverrideLvl3CIR specifies the within-cir
--          bandwidth limit for priority level 3. This object overrides
--          TIMETRA-QOS-MIB::tPortSchedulerPlcyLvl3CIR."
--     DEFVAL      { -1 }
--     ::= { tnPortSchedOverrideEntry 10 }
--
-- tnPortSchedOverrideLvl4PIR        OBJECT-TYPE
--     SYNTAX      TPortSchedulerPIR
--     UNITS       "kbps"
--     MAX-ACCESS  read-create
--     STATUS      current
--     DESCRIPTION
--         "The value of tnPortSchedOverrideLvl4PIR specifies the total
--          bandwidth limit, PIR, for priority level 4. This object
--          overrides TIMETRA-QOS-MIB::tPortSchedulerPlcyLvl4PIR."
--     DEFVAL      { -1 }
--     ::= { tnPortSchedOverrideEntry 11 }
--
-- tnPortSchedOverrideLvl4CIR        OBJECT-TYPE
--     SYNTAX      TPortSchedulerCIR
--     UNITS       "kbps"
--     MAX-ACCESS  read-create
--     STATUS      current
--     DESCRIPTION
--         "The value of tnPortSchedOverrideLvl4CIR specifies the within-cir
--          bandwidth limit for priority level 4. This object overrides
--          TIMETRA-QOS-MIB::tPortSchedulerPlcyLvl4CIR."
--     DEFVAL      { -1 }
--     ::= { tnPortSchedOverrideEntry 12 }
--
-- tnPortSchedOverrideLvl5PIR        OBJECT-TYPE
--     SYNTAX      TPortSchedulerPIR
--     UNITS       "kbps"
--     MAX-ACCESS  read-create
--     STATUS      current
--     DESCRIPTION
--         "The value of tnPortSchedOverrideLvl5PIR specifies the total
--          bandwidth limit, PIR, for priority level 5. This object
--          overrides TIMETRA-QOS-MIB::tPortSchedulerPlcyLvl5PIR."
--     DEFVAL      { -1 }
--     ::= { tnPortSchedOverrideEntry 13 }
--
-- tnPortSchedOverrideLvl5CIR        OBJECT-TYPE
--     SYNTAX      TPortSchedulerCIR
--     UNITS       "kbps"
--     MAX-ACCESS  read-create
--     STATUS      current
--     DESCRIPTION
--         "The value of tnPortSchedOverrideLvl5CIR specifies the within-cir
--          bandwidth limit for priority level 5. This object overrides
--          TIMETRA-QOS-MIB::tPortSchedulerPlcyLvl5CIR."
--     DEFVAL      { -1 }
--     ::= { tnPortSchedOverrideEntry 14 }
--
-- tnPortSchedOverrideLvl6PIR        OBJECT-TYPE
--     SYNTAX      TPortSchedulerPIR
--     UNITS       "kbps"
--     MAX-ACCESS  read-create
--     STATUS      current
--     DESCRIPTION
--         "The value of tnPortSchedOverrideLvl6PIR specifies the total
--          bandwidth limit, PIR, for priority level 6. This object
--          overrides TIMETRA-QOS-MIB::tPortSchedulerPlcyLvl6PIR."
--     DEFVAL      { -1 }
--     ::= { tnPortSchedOverrideEntry 15 }
--
-- tnPortSchedOverrideLvl6CIR        OBJECT-TYPE
--     SYNTAX      TPortSchedulerCIR
--     UNITS       "kbps"
--     MAX-ACCESS  read-create
--     STATUS      current
--     DESCRIPTION
--         "The value of tnPortSchedOverrideLvl6CIR specifies the within-cir
--          bandwidth limit for priority level 6. This object overrides
--          TIMETRA-QOS-MIB::tPortSchedulerPlcyLvl6CIR."
--     DEFVAL      { -1 }
--     ::= { tnPortSchedOverrideEntry 16 }
--
-- tnPortSchedOverrideLvl7PIR        OBJECT-TYPE
--     SYNTAX      TPortSchedulerPIR
--     UNITS       "kbps"
--     MAX-ACCESS  read-create
--     STATUS      current
--     DESCRIPTION
--         "The value of tnPortSchedOverrideLvl7PIR specifies the total
--          bandwidth limit, PIR, for priority level 7. This object
--          overrides TIMETRA-QOS-MIB::tPortSchedulerPlcyLvl7PIR."
--     DEFVAL      { -1 }
--     ::= { tnPortSchedOverrideEntry 17 }
--
-- tnPortSchedOverrideLvl7CIR        OBJECT-TYPE
--     SYNTAX      TPortSchedulerCIR
--     UNITS       "kbps"
--     MAX-ACCESS  read-create
--     STATUS      current
--     DESCRIPTION
--         "The value of tnPortSchedOverrideLvl7CIR specifies the within-cir
--          bandwidth limit for priority level 7. This object overrides
--          TIMETRA-QOS-MIB::tPortSchedulerPlcyLvl7CIR."
--     DEFVAL      { -1 }
--     ::= { tnPortSchedOverrideEntry 18 }
--
-- tnPortSchedOverrideLvl8PIR        OBJECT-TYPE
--     SYNTAX      TPortSchedulerPIR
--     UNITS       "kbps"
--     MAX-ACCESS  read-create
--     STATUS      current
--     DESCRIPTION
--         "The value of tnPortSchedOverrideLvl8PIR specifies the total
--          bandwidth limit, PIR, for priority level 8. This object
--          overrides TIMETRA-QOS-MIB::tPortSchedulerPlcyLvl8PIR."
--     DEFVAL      { -1 }
--     ::= { tnPortSchedOverrideEntry 19 }
--
-- tnPortSchedOverrideLvl8CIR        OBJECT-TYPE
--     SYNTAX      TPortSchedulerCIR
--     UNITS       "kbps"
--     MAX-ACCESS  read-create
--     STATUS      current
--     DESCRIPTION
--         "The value of tnPortSchedOverrideLvl8CIR specifies the within-cir
--          bandwidth limit for priority level 8. This object overrides
--          TIMETRA-QOS-MIB::tPortSchedulerPlcyLvl8CIR."
--     DEFVAL      { -1 }
--     ::= { tnPortSchedOverrideEntry 20 }
--
-- tnPortSchedOverrideFlags        OBJECT-TYPE
--     SYNTAX      BITS {
--                     maxRate(0),
--                     lvl1PIR(1),
--                     lvl1CIR(2),
--                     lvl2PIR(3),
--                     lvl2CIR(4),
--                     lvl3PIR(5),
--                     lvl3CIR(6),
--                     lvl4PIR(7),
--                     lvl4CIR(8),
--                     lvl5PIR(9),
--                     lvl5CIR(10),
--                     lvl6PIR(11),
--                     lvl6CIR(12),
--                     lvl7PIR(13),
--                     lvl7CIR(14),
--                     lvl8PIR(15),
--                     lvl8CIR(16)
--                 }
--     MAX-ACCESS  read-create
--     STATUS      current
--     DESCRIPTION
--         "The value of tnPortSchedOverrideFlags specifies the set of
--          attributes whose values have been overridden via management
--          on this port scheduler. Clearing a given flag will return the
--          corresponding overridden attribute to the value defined in
--          the port's port-scheduler policy."
--     ::= { tnPortSchedOverrideEntry 21 }

--
-- Bundle Protection Group Association Table
--
-- tnBPGrpAssocTable   OBJECT-TYPE
--     SYNTAX      SEQUENCE OF TmnxBPGrpAssocEntry
--     MAX-ACCESS  not-accessible
--     STATUS      current
--     DESCRIPTION
--         "The tnBPGrpAssocTable has an entry for each Bundle Protection Group created
--          on the system."
--     ::= { tnPortObjs 25 }
--
-- tnBPGrpAssocEntry       OBJECT-TYPE
--     SYNTAX      TmnxBPGrpAssocEntry
--     MAX-ACCESS  not-accessible
--     STATUS      current
--     DESCRIPTION
--         "Each row displays the relationship between a Bundle Protection
--          group and its working and protection bundle."
--     INDEX       {  tnBundleBundleID }
--     ::= { tnBPGrpAssocTable 1 }
--
-- TmnxBPGrpAssocEntry ::=
--     SEQUENCE {
--         tnBPGrpAssocWorkingBundleID  TmnxBundleID,
--         tnBPGrpAssocProtectBundleID  TmnxBundleID,
--         tnBPGrpAssocActiveBundleID   TmnxBundleID
--     }
--
-- tnBPGrpAssocWorkingBundleID    OBJECT-TYPE
--     SYNTAX      TmnxBundleID
--     MAX-ACCESS  read-only
--     STATUS      current
--     DESCRIPTION
--         "tnBPGrpAssocWorkingBundleID identifies the working bundle. A value
--          of zero is given if no working bundle is associated with the given
--          tnBundleBundleID."
--     ::= { tnBPGrpAssocEntry 1 }
--
-- tnBPGrpAssocProtectBundleID    OBJECT-TYPE
--     SYNTAX      TmnxBundleID
--     MAX-ACCESS  read-only
--     STATUS      current
--     DESCRIPTION
--         "tnBPGrpAssocProtectBundleID identifies the protection bundle. A value
--          of zero is given if no protection bundle is associated with the given
--          tnBundleBundleID."
--     ::= { tnBPGrpAssocEntry 2 }
--
-- tnBPGrpAssocActiveBundleID    OBJECT-TYPE
--     SYNTAX      TmnxBundleID
--     MAX-ACCESS  read-only
--     STATUS      current
--     DESCRIPTION
--         "tnBPGrpAssocActiveBundleID identifies the bundle that is considered
--          the active bundle. This bundle contains the members that are part of the
--          active aps port. A value of zero is given if no bundle is considered active."
--     ::= { tnBPGrpAssocEntry 3 }

--
-- MLPPP Bundle Table
--
--  Sparse Dependent Extension of the tnBundleTable.
--
--  The same indexes are used for both the base table tnBundleTable,
--  and the sparse dependent table, tnBundleMlpppTable.
--
--  This in effect extends the tnBundleTable with additional columns.
--  Rows are created in the tnBundleMlpppTable only for those entries
--  in the tnBundleTable for a value of 'mlppp' for the bundle type.
--
--  Deletion of a row in the tnBundleTable results in the
--  same fate for the row in the tnBundleMlpppTable.
--
-- tnBundleMlpppTable OBJECT-TYPE
--     SYNTAX      SEQUENCE OF TmnxBundleMlpppEntry
--     MAX-ACCESS  not-accessible
--     STATUS      current
--     DESCRIPTION
--         "The tnBundleMlpppTable contains MLPPP specific data."
--     ::= { tnPortObjs 26 }
--
-- tnBundleMlpppEntry OBJECT-TYPE
--     SYNTAX      TmnxBundleMlpppEntry
--     MAX-ACCESS  not-accessible
--     STATUS      current
--     DESCRIPTION
--         "Each row entry contains data on an MLPPP Bundle."
--     INDEX       {  tnBundleBundleID }
--     ::= { tnBundleMlpppTable 1 }
--
-- TmnxBundleMlpppEntry ::=
--     SEQUENCE {
--         tnBundleMlpppEndpointID         OCTET STRING,
--         tnBundleMlpppEndpointIDClass    TmnxMlpppEndpointIdClass,
--         tnBundleMlpppClassCount         INTEGER,
--         tnBundleMlpppIngQoSProfId       TMlpppQoSProfileId,
--         tnBundleMlpppEgrQoSProfId       TMlpppQoSProfileId,
--         tnBundleMlpppMagicNumber        TmnxEnabledDisabled,
--         tnBundleMlpppStatelessApsSwo    TmnxEnabledDisabled
--     }
--
-- tnBundleMlpppEndpointID OBJECT-TYPE
--     SYNTAX      OCTET STRING (SIZE (0..20))
--     MAX-ACCESS  read-create
--     STATUS      current
--     DESCRIPTION
--         "tnBundleMlpppEndpointID indentifies the Endpoint Discriminator
--          identifier value within the specified tnBundleMlpppEndpointIDClass.
--          The object tnPortAdminStatus must be set to 'outOfService' to
--          change this value."
--     ::= { tnBundleMlpppEntry 1 }
--
-- tnBundleMlpppEndpointIDClass OBJECT-TYPE
--     SYNTAX      TmnxMlpppEndpointIdClass
--     MAX-ACCESS  read-create
--     STATUS      current
--     DESCRIPTION
--         "tnBundleMlpppEndpointIDClass specifies the Link Control
--          Protocol Endpoint Descriminator Class field type of the
--          tnBundleMlpppEndpointID. The object tnPortAdminStatus
--          must be set to 'outOfService' to change this value.
--
--                     Bundle                     DEFVAL
--             Physical MLPPP Bundle           ieee802dot1GlobalMacAddress (3)
--             MLPPP Bundle Protection Group   ipAddress (2)"
--     ::= { tnBundleMlpppEntry 2 }
--
-- tnBundleMlpppClassCount OBJECT-TYPE
--     SYNTAX      INTEGER (0..16)
--     MAX-ACCESS  read-create
--     STATUS      current
--     DESCRIPTION
--         "The value of tnBundleMlpppClassCount specifies
--          whether Multiclass MLPPP is enabled on
--          a bundle with a tnBundleType of 'mlppp' and when enabled what is the
--          number of classes to be negotiated/supported over the MLPPP bundle.
--
--          The value of 0 disables multiclass MLPPP including negotiation in
--          the PPP protocol.
--          All other values specify the number of classes to be supported
--          on a given multiclass bundle and enable Multiclass MLPPP negotiation
--          on that bundle.
--
--          Non-zero values supported are platform/MDA specific.
--
--          The value of tnBundleMlpppClassCount must be set to 0 and cannot be
--          changed when LFI is enabled on the bundle (see tnBundleLFI object
--          in tnBundleTable).
--
--          The value of tnBundleMlpppClassCount may be modified only when
--          tnBundleNumLinks is zero.
--
--          To set the value of tnBundleMlpppClassCount to a value greater
--          than 4, the long sequence format must be enabled on the bundle (see
--          tnBundleShortSequence object in tnBundleTable).
--
--          Changing the value of tnBundleMlpppClassCount resets the values of
--          tnBundleMlpppIngQoSProfId and tnBundleMlpppEgrQoSProfId to their
--          defaults"
--     DEFVAL { 0 }
--     ::= { tnBundleMlpppEntry 3 }
--
-- tnBundleMlpppIngQoSProfId OBJECT-TYPE
--     SYNTAX      TMlpppQoSProfileId
--     MAX-ACCESS  read-create
--     STATUS      current
--     DESCRIPTION
--         "tnBundleMlpppIngQoSProfId specifies ingress QoS profile
--          to be used for the incoming traffic over this MLPPP
--          bundle.
--
--          The value of tnBundleMlpppIngQoSProfId may be modified only
--          when the value of tnBundleNumLinks is 0.
--
--          The value of tnBundleMlpppIngQoSProfId of 0 indicates
--          a default QoS profile is used as applicable to a given hardware
--          and the configured value of tnBundleMlpppClassCount."
--     DEFVAL { 0 }
--     ::= { tnBundleMlpppEntry 4 }
--
-- tnBundleMlpppEgrQoSProfId OBJECT-TYPE
--     SYNTAX      TMlpppQoSProfileId
--     MAX-ACCESS  read-create
--     STATUS      current
--     DESCRIPTION
--         "tnBundleMlpppEgrQoSProfId specifies egress QoS profile
--          to be used for the outgoing traffic over this MLPPP
--          bundle.
--
--          The value of tnBundleMlpppEgrQoSProfId may be modified only
--          when tnBundleNumLinks is zero.
--
--          The value of tnBundleMlpppEgrQoSProfId of 0 indicates
--          a default profile is used as applicable to a given hardware
--          and the configured value of tnBundleMlpppClassCount."
--     DEFVAL { 0 }
--     ::= { tnBundleMlpppEntry 5 }
--
-- tnBundleMlpppMagicNumber OBJECT-TYPE
--     SYNTAX      TmnxEnabledDisabled
--     MAX-ACCESS  read-create
--     STATUS      current
--     DESCRIPTION
--         "tnBundleMlpppMagicNumber specifies whether or not the bundle will detect
--          a loopback scenario on member links and take a looped back member links
--          out of service.
--          A value of 'enabled (1)' will detect loopbacks."
--     DEFVAL { disabled }
--     ::= { tnBundleMlpppEntry 6 }
--
-- tnBundleMlpppStatelessApsSwo OBJECT-TYPE
--     SYNTAX      TmnxEnabledDisabled
--     MAX-ACCESS  read-create
--     STATUS      current
--     DESCRIPTION
--         "tnBundleMlpppStatelessApsSwo specifies whether the bundle will
--          perform a statefull or a stateless APS switchover.
--
--          The value of tnBundleMlpppStatelessApsSwo must be set to 'disabled (2)' and
--          cannot be changed for normal mlppp bundles.
--
--          The value of tnBundleMlpppStatelessApsSwo may be changed
--          for APS bundle protection groups.
--
--          A stateless switchover implies that PPP is renegotiated on  each member
--          link after the switchover. PPP negotiations may take a few seconds
--          to complete.
--
--          A statefull switchover implies that after an APS switchover the PPP
--          state of the bundle will be restored based on the bpgrp bundle state
--          before the switchover.
--
--          A value of 'enabled (1)' will configure stateless APS switchovers."
--     DEFVAL { disabled }
--     ::= { tnBundleMlpppEntry 7 }

--
--      HSMDA scheduler policy overrides
--

-- tnHsmdaPortSchOvrTblLastChngd OBJECT-TYPE
--     SYNTAX      TimeStamp
--     MAX-ACCESS  read-only
--     STATUS      current
--     DESCRIPTION
--         "The value of tnHsmdaPortSchOvrTblLastChngd indicates the sysUpTime
--          at the time of the last modification of tnHsmdaPortSchOvrTable.
--
--          If no changes were made to the table since the last
--          re-initialization of the local network management subsystem,
--          then this object contains a zero value."
--     ::= { tnPortObjs 27 }

-- tnHsmdaPortSchOvrTable OBJECT-TYPE
--     SYNTAX      SEQUENCE OF TmnxHsmdaPortSchedOverEntry
--     MAX-ACCESS  not-accessible
--     STATUS      current
--     DESCRIPTION
--         "The tnHsmdaPortSchOvrTable has an entry for each port-level HSMDA
--          scheduler override configured on this system."
--     ::= { tnPortObjs 28 }
--
-- tnHsmdaPortSchOvrEntry    OBJECT-TYPE
--     SYNTAX      TmnxHsmdaPortSchedOverEntry
--     MAX-ACCESS  not-accessible
--     STATUS      current
--     DESCRIPTION
--         "Each row represents a particular port-level HSMDA scheduler override.
--          Entries are created and deleted by the user."
--     INDEX {  tnPortPortID }
--     ::= { tnHsmdaPortSchOvrTable 1}
--
-- TmnxHsmdaPortSchedOverEntry ::= SEQUENCE
--     {
--         tnHsmdaPortSchOvrRowStatus          RowStatus,
--         tnHsmdaPortSchOvrLastChanged        TimeStamp,
--         tnHsmdaPortSchOvrMaxRate            THsmdaPIRMRateOverride,
--         tnHsmdaPortSchOvrGrp1Rate           THsmdaPIRMRateOverride,
--         tnHsmdaPortSchOvrGrp2Rate           THsmdaPIRMRateOverride,
--         tnHsmdaPortSchOvrClass1Rate         THsmdaPIRMRateOverride,
--         tnHsmdaPortSchOvrClass1WtInGp     THsmdaWeightOverride,
--         tnHsmdaPortSchOvrClass2Rate         THsmdaPIRMRateOverride,
--         tnHsmdaPortSchOvrClass2WtInGp     THsmdaWeightOverride,
--         tnHsmdaPortSchOvrClass3Rate         THsmdaPIRMRateOverride,
--         tnHsmdaPortSchOvrClass3WtInGp     THsmdaWeightOverride,
--         tnHsmdaPortSchOvrClass4Rate         THsmdaPIRMRateOverride,
--         tnHsmdaPortSchOvrClass4WtInGp     THsmdaWeightOverride,
--         tnHsmdaPortSchOvrClass5Rate         THsmdaPIRMRateOverride,
--         tnHsmdaPortSchOvrClass5WtInGp     THsmdaWeightOverride,
--         tnHsmdaPortSchOvrClass6Rate         THsmdaPIRMRateOverride,
--         tnHsmdaPortSchOvrClass6WtInGp     THsmdaWeightOverride,
--         tnHsmdaPortSchOvrClass7Rate         THsmdaPIRMRateOverride,
--         tnHsmdaPortSchOvrClass7WtInGp     THsmdaWeightOverride,
--         tnHsmdaPortSchOvrClass8Rate         THsmdaPIRMRateOverride,
--         tnHsmdaPortSchOvrClass8WtInGp     THsmdaWeightOverride
--     }
--
-- tnHsmdaPortSchOvrRowStatus        OBJECT-TYPE
--     SYNTAX      RowStatus
--     MAX-ACCESS  read-create
--     STATUS      current
--     DESCRIPTION
--         "The value of tnHsmdaPortSchOvrRowStatus is used for the
--          creation and deletion of port-level HSMDA scheduler overrides.
--
--          When the tmnxMDAAssignedType of the tnPortEntry indexed
--          by the same indices of this table is a non-HSMDA MDA Type,
--          creation will fail and return a 'noCreation' error."
--     ::= { tnHsmdaPortSchOvrEntry 1 }
--
-- tnHsmdaPortSchOvrLastChanged        OBJECT-TYPE
--     SYNTAX      TimeStamp
--     MAX-ACCESS  read-only
--     STATUS      current
--     DESCRIPTION
--         "The value of tnHsmdaPortSchOvrLastChanged indicates the sysUpTime
--          at the time of the last modification of this entry.
--
--          If no changes were made to the entry since the last
--          re-initialization of the local network management subsystem,
--          then this object contains a zero value."
--     ::= { tnHsmdaPortSchOvrEntry 2 }
--
-- tnHsmdaPortSchOvrMaxRate        OBJECT-TYPE
--     SYNTAX      THsmdaPIRMRateOverride
--     UNITS       "Mbps"
--     MAX-ACCESS  read-create
--     STATUS      current
--     DESCRIPTION
--         "The value of tnHsmdaPortSchOvrMaxRate specifies the explicit
--          maximum frame based bandwidth limit for this HSMDA port
--          scheduler.
--
--          A value of -2 indicates no override.
--
--          This object overrides TIMETRA-QOS-MIB::tHsmdaSchedulerPlcyMaxRate."
--     DEFVAL      { -2 }
--     ::= { tnHsmdaPortSchOvrEntry 3 }
--
-- tnHsmdaPortSchOvrGrp1Rate          OBJECT-TYPE
--     SYNTAX      THsmdaPIRMRateOverride
--     UNITS       "Mbps"
--     MAX-ACCESS  read-create
--     STATUS      current
--     DESCRIPTION
--         "The value of tnHsmdaPortSchOvrGrp1Rate specifies the explicit
--          maximum frame based bandwidth limit, in megabits per second, for
--          group 1 for this HSMDA port scheduler.
--
--          A value of -2 indicates no override.
--
--          This object overrides TIMETRA-QOS-MIB::tHsmdaSchedulerPlcyGrp1Rate."
--     DEFVAL { -2 }
--     ::= { tnHsmdaPortSchOvrEntry 4 }
--
-- tnHsmdaPortSchOvrGrp2Rate           OBJECT-TYPE
--     SYNTAX      THsmdaPIRMRateOverride
--     UNITS       "Mbps"
--     MAX-ACCESS  read-create
--     STATUS      current
--     DESCRIPTION
--         "The value of tnHsmdaPortSchOvrGrp2Rate specifies the explicit
--          maximum frame based bandwidth limit, in megabits per second, for
--          group 2 for this HSMDA port scheduler.
--
--          A value of -2 indicates no override.
--
--          This object overrides TIMETRA-QOS-MIB::tHsmdaSchedulerPlcyGrp2Rate."
--     DEFVAL { -2 }
--     ::= { tnHsmdaPortSchOvrEntry 5 }
--
-- tnHsmdaPortSchOvrClass1Rate        OBJECT-TYPE
--     SYNTAX      THsmdaPIRMRateOverride
--     UNITS       "Mbps"
--     MAX-ACCESS  read-create
--     STATUS      current
--     DESCRIPTION
--         "The value of tnHsmdaPortSchOvrClass1Rate specifies the explicit
--          maximum frame based bandwidth limit, in megabits per second, for
--          this HSMDA port scheduler policy level.
--
--          A value of -2 indicates no override.
--
--          This object overrides TIMETRA-QOS-MIB::tHsmdaSchedulerPlcyLvl1Rate."
--     DEFVAL { -2 }
--     ::= { tnHsmdaPortSchOvrEntry 6 }
--
-- tnHsmdaPortSchOvrClass1WtInGp        OBJECT-TYPE
--     SYNTAX      THsmdaWeightOverride
--     MAX-ACCESS  read-create
--     STATUS      current
--     DESCRIPTION
--         "The value of tnHsmdaPortSchOvrClass1WtInGp specifies the weight
--          the HSMDA port scheduler policy should apply to this policy level
--          within the group it belongs to.
--
--          The value of tnHsmdaPortSchOvrClass1WtInGp will only be
--          used if this policy level has been assigned to a group
--          by setting tHsmdaSchedulerPlcyLvl1GrpId to a non-zero value.
--
--          A value of -2 indicates no override.
--
--          This object overrides
--          TIMETRA-QOS-MIB::tHsmdaSchedulerPlcyLvl1WgtInGrp."
--     DEFVAL { -2 }
--     ::= { tnHsmdaPortSchOvrEntry 7 }
--
-- tnHsmdaPortSchOvrClass2Rate        OBJECT-TYPE
--     SYNTAX      THsmdaPIRMRateOverride
--     UNITS       "Mbps"
--     MAX-ACCESS  read-create
--     STATUS      current
--     DESCRIPTION
--         "The value of tnHsmdaPortSchOvrClass2Rate specifies the explicit
--          maximum frame based bandwidth limit, in megabits per second, for
--          this HSMDA port scheduler policy level.
--
--          A value of -2 indicates no override.
--
--          This object overrides TIMETRA-QOS-MIB::tHsmdaSchedulerPlcyLvl2Rate."
--     DEFVAL { -2 }
--     ::= { tnHsmdaPortSchOvrEntry 8 }
--
-- tnHsmdaPortSchOvrClass2WtInGp        OBJECT-TYPE
--     SYNTAX      THsmdaWeightOverride
--     MAX-ACCESS  read-create
--     STATUS      current
--     DESCRIPTION
--         "The value of tnHsmdaPortSchOvrClass2WtInGp specifies the weight
--          the HSMDA port scheduler policy should apply to this policy level
--          within the group it belongs to.
--
--          The value of tnHsmdaPortSchOvrClass2WtInGp will only be
--          used if this policy level has been assigned to a group
--          by setting tHsmdaSchedulerPlcyLvl2GrpId to a non-zero value.
--
--          A value of -2 indicates no override.
--
--          This object overrides
--          TIMETRA-QOS-MIB::tHsmdaSchedulerPlcyLvl2WgtInGrp."
--     DEFVAL { -2 }
--     ::= { tnHsmdaPortSchOvrEntry 9 }
--
-- tnHsmdaPortSchOvrClass3Rate        OBJECT-TYPE
--     SYNTAX      THsmdaPIRMRateOverride
--     UNITS       "Mbps"
--     MAX-ACCESS  read-create
--     STATUS      current
--     DESCRIPTION
--         "The value of tnHsmdaPortSchOvrClass3Rate specifies the explicit
--          maximum frame based bandwidth limit, in megabits per second, for
--          this HSMDA port scheduler policy level.
--
--          A value of -2 indicates no override.
--
--          This object overrides TIMETRA-QOS-MIB::tHsmdaSchedulerPlcyLvl3Rate."
--     DEFVAL { -2 }
--     ::= { tnHsmdaPortSchOvrEntry 10 }
--
-- tnHsmdaPortSchOvrClass3WtInGp        OBJECT-TYPE
--     SYNTAX      THsmdaWeightOverride
--     MAX-ACCESS  read-create
--     STATUS      current
--     DESCRIPTION
--         "The value of tnHsmdaPortSchOvrClass3WtInGp specifies the weight
--          the HSMDA port scheduler policy should apply to this policy level
--          within the group it belongs to.
--
--          The value of tnHsmdaPortSchOvrClass3WtInGp will only be
--          used if this policy level has been assigned to a group
--          by setting tHsmdaSchedulerPlcyLvl3GrpId to a non-zero value.
--
--          A value of -2 indicates no override.
--
--          This object overrides
--          TIMETRA-QOS-MIB::tHsmdaSchedulerPlcyLvl3WgtInGrp."
--     DEFVAL { -2 }
--     ::= { tnHsmdaPortSchOvrEntry 11 }
--
-- tnHsmdaPortSchOvrClass4Rate        OBJECT-TYPE
--     SYNTAX      THsmdaPIRMRateOverride
--     UNITS       "Mbps"
--     MAX-ACCESS  read-create
--     STATUS      current
--     DESCRIPTION
--         "The value of tnHsmdaPortSchOvrClass4Rate specifies the explicit
--          maximum frame based bandwidth limit, in megabits per second, for
--          this HSMDA port scheduler policy level.
--
--          A value of -2 indicates no override.
--
--          This object overrides TIMETRA-QOS-MIB::tHsmdaSchedulerPlcyLvl4Rate."
--     DEFVAL { -2 }
--     ::= { tnHsmdaPortSchOvrEntry 12 }
--
-- tnHsmdaPortSchOvrClass4WtInGp        OBJECT-TYPE
--     SYNTAX      THsmdaWeightOverride
--     MAX-ACCESS  read-create
--     STATUS      current
--     DESCRIPTION
--         "The value of tnHsmdaPortSchOvrClass4WtInGp specifies the weight
--          the HSMDA port scheduler policy should apply to this policy level
--          within the group it belongs to.
--
--          The value of tnHsmdaPortSchOvrClass4WtInGp will only be
--          used if this policy level has been assigned to a group
--          by setting tHsmdaSchedulerPlcyLvl4GrpId to a non-zero value.
--
--          A value of -2 indicates no override.
--
--          This object overrides
--          TIMETRA-QOS-MIB::tHsmdaSchedulerPlcyLvl4WgtInGrp."
--     DEFVAL { -2 }
--     ::= { tnHsmdaPortSchOvrEntry 13 }
--
-- tnHsmdaPortSchOvrClass5Rate        OBJECT-TYPE
--     SYNTAX      THsmdaPIRMRateOverride
--     UNITS       "Mbps"
--     MAX-ACCESS  read-create
--     STATUS      current
--     DESCRIPTION
--         "The value of tnHsmdaPortSchOvrClass5Rate specifies the explicit
--          maximum frame based bandwidth limit, in megabits per second, for
--          this HSMDA port scheduler policy level.
--
--          A value of -2 indicates no override.
--
--          This object overrides TIMETRA-QOS-MIB::tHsmdaSchedulerPlcyLvl5Rate."
--     DEFVAL { -2 }
--     ::= { tnHsmdaPortSchOvrEntry 14 }
--
-- tnHsmdaPortSchOvrClass5WtInGp        OBJECT-TYPE
--     SYNTAX      THsmdaWeightOverride
--     MAX-ACCESS  read-create
--     STATUS      current
--     DESCRIPTION
--         "The value of tnHsmdaPortSchOvrClass5WtInGp specifies the weight
--          the HSMDA port scheduler policy should apply to this policy level
--          within the group it belongs to.
--
--          The value of tnHsmdaPortSchOvrClass5WtInGp will only be
--          used if this policy level has been assigned to a group
--          by setting tHsmdaSchedulerPlcyLvl5GrpId to a non-zero value.
--
--          A value of -2 indicates no override.
--
--          This object overrides
--          TIMETRA-QOS-MIB::tHsmdaSchedulerPlcyLvl5WgtInGrp."
--     DEFVAL { -2 }
--     ::= { tnHsmdaPortSchOvrEntry 15 }
--
-- tnHsmdaPortSchOvrClass6Rate        OBJECT-TYPE
--     SYNTAX      THsmdaPIRMRateOverride
--     UNITS       "Mbps"
--     MAX-ACCESS  read-create
--     STATUS      current
--     DESCRIPTION
--         "The value of tnHsmdaPortSchOvrClass6Rate specifies the explicit
--          maximum frame based bandwidth limit, in megabits per second, for
--          this HSMDA port scheduler policy level.
--
--          A value of -2 indicates no override.
--
--          This object overrides TIMETRA-QOS-MIB::tHsmdaSchedulerPlcyLvl6Rate."
--     DEFVAL { -2 }
--     ::= { tnHsmdaPortSchOvrEntry 16 }
--
-- tnHsmdaPortSchOvrClass6WtInGp        OBJECT-TYPE
--     SYNTAX      THsmdaWeightOverride
--     MAX-ACCESS  read-create
--     STATUS      current
--     DESCRIPTION
--         "The value of tnHsmdaPortSchOvrClass6WtInGp specifies the weight
--          the HSMDA port scheduler policy should apply to this policy level
--          within the group it belongs to.
--
--          The value of tnHsmdaPortSchOvrClass6WtInGp will only be
--          used if this policy level has been assigned to a group
--          by setting tHsmdaSchedulerPlcyLvl6GrpId to a non-zero value.
--
--          A value of -2 indicates no override.
--
--          This object overrides
--          TIMETRA-QOS-MIB::tHsmdaSchedulerPlcyLvl6WgtInGrp."
--     DEFVAL { -2 }
--     ::= { tnHsmdaPortSchOvrEntry 17 }
--
-- tnHsmdaPortSchOvrClass7Rate        OBJECT-TYPE
--     SYNTAX      THsmdaPIRMRateOverride
--     UNITS       "Mbps"
--     MAX-ACCESS  read-create
--     STATUS      current
--     DESCRIPTION
--         "The value of tnHsmdaPortSchOvrClass7Rate specifies the explicit
--          maximum frame based bandwidth limit, in megabits per second, for
--          this HSMDA port scheduler policy level.
--
--          A value of -2 indicates no override.
--
--          This object overrides TIMETRA-QOS-MIB::tHsmdaSchedulerPlcyLvl7Rate."
--     DEFVAL { -2 }
--     ::= { tnHsmdaPortSchOvrEntry 18 }
--
-- tnHsmdaPortSchOvrClass7WtInGp        OBJECT-TYPE
--     SYNTAX      THsmdaWeightOverride
--     MAX-ACCESS  read-create
--     STATUS      current
--     DESCRIPTION
--         "The value of tnHsmdaPortSchOvrClass7WtInGp specifies the weight
--          the HSMDA port scheduler policy should apply to this policy level
--          within the group it belongs to.
--
--          The value of tnHsmdaPortSchOvrClass7WtInGp will only be
--          used if this policy level has been assigned to a group
--          by setting tHsmdaSchedulerPlcyLvl7GrpId to a non-zero value.
--
--          A value of -2 indicates no override.
--
--          This object overrides
--          TIMETRA-QOS-MIB::tHsmdaSchedulerPlcyLvl7WgtInGrp."
--     DEFVAL { -2 }
--     ::= { tnHsmdaPortSchOvrEntry 19 }
--
-- tnHsmdaPortSchOvrClass8Rate        OBJECT-TYPE
--     SYNTAX      THsmdaPIRMRateOverride
--     UNITS       "Mbps"
--     MAX-ACCESS  read-create
--     STATUS      current
--     DESCRIPTION
--         "The value of tnHsmdaPortSchOvrClass8Rate specifies the explicit
--          maximum frame based bandwidth limit, in megabits per second, for
--          this HSMDA port scheduler policy level.
--
--          A value of -2 indicates no override.
--
--          This object overrides TIMETRA-QOS-MIB::tHsmdaSchedulerPlcyLvl8Rate."
--     DEFVAL { -2 }
--     ::= { tnHsmdaPortSchOvrEntry 20 }
--
-- tnHsmdaPortSchOvrClass8WtInGp        OBJECT-TYPE
--     SYNTAX      THsmdaWeightOverride
--     MAX-ACCESS  read-create
--     STATUS      current
--     DESCRIPTION
--         "The value of tnHsmdaPortSchOvrClass8WtInGp specifies the weight
--          the HSMDA port scheduler policy should apply to this policy level
--          within the group it belongs to.
--
--          The value of tnHsmdaPortSchOvrClass8WtInGp will only be
--          used if this policy level has been assigned to a group
--          by setting tHsmdaSchedulerPlcyLvl8GrpId to a non-zero value.
--
--          A value of -2 indicates no override.
--
--          This object overrides
--          TIMETRA-QOS-MIB::tHsmdaSchedulerPlcyLvl8WgtInGrp."
--     DEFVAL { -2 }
--     ::= { tnHsmdaPortSchOvrEntry 21 }

--
--  Port Egress Secondary Shaper
--
-- tnPortEgrShaperTblLastChanged OBJECT-TYPE
--     SYNTAX      TimeStamp
--     MAX-ACCESS  read-only
--     STATUS      current
--     DESCRIPTION
--         "The value of tnPortEgrShaperTblLastChanged indicates the sysUpTime
--          at the time of the last modification of tnPortEgrShaperTable.
--
--          If no changes were made to the table since the last
--          re-initialization of the local network management subsystem,
--          then this object contains a zero value."
--     ::= { tnPortObjs 29 }

-- tnPortEgrShaperTable OBJECT-TYPE
--     SYNTAX      SEQUENCE OF TmnxPortEgrShaperEntry
--     MAX-ACCESS  not-accessible
--     STATUS      current
--     DESCRIPTION
--         "The tnPortEgrShaperTable has an entry for each port-level egress
--          secondary shaper configured on this system."
--     ::= { tnPortObjs 30 }
--
-- tnPortEgrShaperEntry    OBJECT-TYPE
--     SYNTAX      TmnxPortEgrShaperEntry
--     MAX-ACCESS  not-accessible
--     STATUS      current
--     DESCRIPTION
--         "Each row represents a particular port-level egress secondary shaper.
--          Entries are created and deleted by the user."
--     INDEX {  tnPortPortID, tnPortEgrShaperName }
--     ::= { tnPortEgrShaperTable 1}
--
-- TmnxPortEgrShaperEntry ::= SEQUENCE
--     {
--         tnPortEgrShaperName            TNamedItem,
--         tnPortEgrShaperRowStatus       RowStatus,
--         tnPortEgrShaperLastChanged     TimeStamp,
--         tnPortEgrShaperRate            TSecondaryShaper10GPIRRate
--     }
--
-- tnPortEgrShaperName        OBJECT-TYPE
--     SYNTAX      TNamedItem
--     MAX-ACCESS  not-accessible
--     STATUS      current
--     DESCRIPTION
--         "The port egress shaper named is used an index to the table entry."
--     ::= { tnPortEgrShaperEntry 1 }
--
-- tnPortEgrShaperRowStatus        OBJECT-TYPE
--     SYNTAX      RowStatus
--     MAX-ACCESS  read-create
--     STATUS      current
--     DESCRIPTION
--         "The value of tnPortEgrShaperRowStatus is used for the creation
--          and deletion of entries in the tnPortEgrShaperTable."
--     ::= { tnPortEgrShaperEntry 2 }
--
-- tnPortEgrShaperLastChanged        OBJECT-TYPE
--     SYNTAX      TimeStamp
--     MAX-ACCESS  read-only
--     STATUS      current
--     DESCRIPTION
--         "The value of tnPortEgrShaperLastChanged indicates the sysUpTime
--          at the time of the last modification of this entry.
--
--          If no changes were made to the entry since the last
--          re-initialization of the local network management subsystem,
--          then this object contains a zero value."
--     ::= { tnPortEgrShaperEntry 3 }
--
-- tnPortEgrShaperRate        OBJECT-TYPE
--     SYNTAX      TSecondaryShaper10GPIRRate
--     UNITS       "Mbps"
--     MAX-ACCESS  read-create
--     STATUS      current
--     DESCRIPTION
--         "The value of tnPortEgrShaperRate specifies the explicit maximum
--          frame based bandwidth limit, in megabits per second, of this
--          egress port secondary shaper policy."
--     DEFVAL    { -1 }
--     ::= { tnPortEgrShaperEntry 4 }

--
--  Digital Diagnostic Monitor Table
--
-- tnDigitalDiagMonitorTable OBJECT-TYPE
--     SYNTAX  SEQUENCE OF TmnxDigitalDiagMonitorEntry
--     MAX-ACCESS  not-accessible
--     STATUS      current
--     DESCRIPTION
--         "The tnDigitalDiagMonitorTable has an entry for each SFP/XFP in the
--          system that supports Digital Diagnostic Monitoring (DDM). The table is
--          indexed by TmnxPortID. Each row in this table is dynamically added
--          and removed internally by the system based on the presence or absence
--          of DDM capable SFP/XFP components."
--     ::= { tnPortObjs 31 }
--
-- tnDigitalDiagMonitorEntry OBJECT-TYPE
--     SYNTAX      TmnxDigitalDiagMonitorEntry
--     MAX-ACCESS  not-accessible
--     STATUS      current
--     DESCRIPTION
--         "Each row represents a particular SFP/XFP that supports Digital
--          Diagnostic Monitoring.
--          Entries are created and deleted internally by the system."
--     INDEX {  tnPortPortID }
--     ::= { tnDigitalDiagMonitorTable 1}
--
-- TmnxDigitalDiagMonitorEntry ::= SEQUENCE
--     {
--         tnDDMTemperature                   Integer32,
--         tnDDMTempLowWarning                Integer32,
--         tnDDMTempLowAlarm                  Integer32,
--         tnDDMTempHiWarning                 Integer32,
--         tnDDMTempHiAlarm                   Integer32,
--         tnDDMSupplyVoltage                 Integer32,
--         tnDDMSupplyVoltageLowWarning       Integer32,
--         tnDDMSupplyVoltageLowAlarm         Integer32,
--         tnDDMSupplyVoltageHiWarning        Integer32,
--         tnDDMSupplyVoltageHiAlarm          Integer32,
--         tnDDMTxBiasCurrent                 Integer32,
--         tnDDMTxBiasCurrentLowWarning       Integer32,
--         tnDDMTxBiasCurrentLowAlarm         Integer32,
--         tnDDMTxBiasCurrentHiWarning        Integer32,
--         tnDDMTxBiasCurrentHiAlarm          Integer32,
--         tnDDMTxOutputPower                 Integer32,
--         tnDDMTxOutputPowerLowWarning       Integer32,
--         tnDDMTxOutputPowerLowAlarm         Integer32,
--         tnDDMTxOutputPowerHiWarning        Integer32,
--         tnDDMTxOutputPowerHiAlarm          Integer32,
--         tnDDMRxOpticalPower                Integer32,
--         tnDDMRxOpticalPowerLowWarning      Integer32,
--         tnDDMRxOpticalPowerLowAlarm        Integer32,
--         tnDDMRxOpticalPowerHiWarning       Integer32,
--         tnDDMRxOpticalPowerHiAlarm         Integer32,
--         tnDDMRxOpticalPowerType            INTEGER,
--         tnDDMAux1                          Integer32,
--         tnDDMAux1LowWarning                Integer32,
--         tnDDMAux1LowAlarm                  Integer32,
--         tnDDMAux1HiWarning                 Integer32,
--         tnDDMAux1HiAlarm                   Integer32,
--         tnDDMAux1Type                      INTEGER,
--         tnDDMAux2                          Integer32,
--         tnDDMAux2LowWarning                Integer32,
--         tnDDMAux2LowAlarm                  Integer32,
--         tnDDMAux2HiWarning                 Integer32,
--         tnDDMAux2HiAlarm                   Integer32,
--         tnDDMAux2Type                      INTEGER,
--         tnDDMFailedThresholds              BITS,
--         tnDDMExternallyCalibrated          TruthValue,
--         tnDDMExtCalRxPower4                Unsigned32,
--         tnDDMExtCalRxPower3                Unsigned32,
--         tnDDMExtCalRxPower2                Unsigned32,
--         tnDDMExtCalRxPower1                Unsigned32,
--         tnDDMExtCalRxPower0                Unsigned32,
--         tnDDMExtCalTxLaserBiasSlope        Unsigned32,
--         tnDDMExtCalTxLaserBiasOffset       Integer32,
--         tnDDMExtCalTxPowerSlope            Unsigned32,
--         tnDDMExtCalTxPowerOffset           Integer32,
--         tnDDMExtCalTemperatureSlope        Unsigned32,
--         tnDDMExtCalTemperatureOffset       Integer32,
--         tnDDMExtCalVoltageSlope            Unsigned32,
--         tnDDMExtCalVoltageOffset           Integer32
--     }
--
-- tnDDMTemperature                 OBJECT-TYPE
--     SYNTAX      Integer32
--     MAX-ACCESS  read-only
--     STATUS      current
--     DESCRIPTION
--         "The value of tnDDMTemperature indicates the current temperature
--          of the SFP/XFP in degrees Celsius."
--     ::= { tnDigitalDiagMonitorEntry 1 }
--
-- tnDDMTempLowWarning              OBJECT-TYPE
--     SYNTAX      Integer32
--     MAX-ACCESS  read-only
--     STATUS      current
--     DESCRIPTION
--         "The value of tnDDMTempLowWarning indicates the temperature
--          of the SFP/XFP in degrees Celsius that triggers a low-warning."
--     ::= { tnDigitalDiagMonitorEntry 2 }
--
-- tnDDMTempLowAlarm                OBJECT-TYPE
--     SYNTAX      Integer32
--     MAX-ACCESS  read-only
--     STATUS      current
--     DESCRIPTION
--         "The value of tnDDMTempLowAlarm indicates the temperature
--          of the SFP/XFP in degrees Celsius that triggers a low-alarm."
--     ::= { tnDigitalDiagMonitorEntry 3 }
--
-- tnDDMTempHiWarning               OBJECT-TYPE
--     SYNTAX      Integer32
--     MAX-ACCESS  read-only
--     STATUS      current
--     DESCRIPTION
--         "The value of tnDDMTempHiWarning indicates the temperature
--          of the SFP/XFP in degrees Celsius that triggers a hi-warning."
--     ::= { tnDigitalDiagMonitorEntry 4 }
--
-- tnDDMTempHiAlarm                 OBJECT-TYPE
--     SYNTAX      Integer32
--     MAX-ACCESS  read-only
--     STATUS      current
--     DESCRIPTION
--         "The value of tnDDMTempHiAlarm indicates the temperature
--          of the SFP/XFP in degrees Celsius that triggers a hi-alarm."
--     ::= { tnDigitalDiagMonitorEntry 5 }
--
-- tnDDMSupplyVoltage               OBJECT-TYPE
--     SYNTAX      Integer32
--     MAX-ACCESS  read-only
--     STATUS      current
--     DESCRIPTION
--         "The value of tnDDMSupplyVoltage indicates the current supply
--          voltage of the SFP/XFP in micro-Volts (uV)."
--     ::= { tnDigitalDiagMonitorEntry 6 }
--
-- tnDDMSupplyVoltageLowWarning     OBJECT-TYPE
--     SYNTAX      Integer32
--     MAX-ACCESS  read-only
--     STATUS      current
--     DESCRIPTION
--         "The value of tnDDMSupplyVoltageLowWarning indicates the supply
--          voltage of the SFP/XFP in micro-Volts (uV) that triggers a low-warning."
--     ::= { tnDigitalDiagMonitorEntry 7 }
--
-- tnDDMSupplyVoltageLowAlarm       OBJECT-TYPE
--     SYNTAX      Integer32
--     MAX-ACCESS  read-only
--     STATUS      current
--     DESCRIPTION
--         "The value of tnDDMSupplyVoltageLowAlarm indicates the supply
--          voltage of the SFP/XFP in micro-Volts (uV) that triggers a low-alarm."
--     ::= { tnDigitalDiagMonitorEntry 8 }
--
-- tnDDMSupplyVoltageHiWarning      OBJECT-TYPE
--     SYNTAX      Integer32
--     MAX-ACCESS  read-only
--     STATUS      current
--     DESCRIPTION
--         "The value of tnDDMSupplyVoltageHiWarning indicates the supply
--          voltage of the SFP/XFP in micro-Volts (uV) that triggers a hi-warning."
--     ::= { tnDigitalDiagMonitorEntry 9 }
--
-- tnDDMSupplyVoltageHiAlarm        OBJECT-TYPE
--     SYNTAX      Integer32
--     MAX-ACCESS  read-only
--     STATUS      current
--     DESCRIPTION
--         "The value of tnDDMSupplyVoltageHiAlarm indicates the supply
--          voltage of the SFP/XFP in micro-Volts (uV) that triggers a hi-alarm."
--     ::= { tnDigitalDiagMonitorEntry 10 }
--
-- tnDDMTxBiasCurrent               OBJECT-TYPE
--     SYNTAX      Integer32
--     MAX-ACCESS  read-only
--     STATUS      current
--     DESCRIPTION
--         "The value of tnDDMTxBiasCurrent indicates the current Transmit
--          Bias Current of the SFP/XFP in micro-Amperes (uA)."
--     ::= { tnDigitalDiagMonitorEntry 11 }
--
-- tnDDMTxBiasCurrentLowWarning     OBJECT-TYPE
--     SYNTAX      Integer32
--     MAX-ACCESS  read-only
--     STATUS      current
--     DESCRIPTION
--         "The value of tnDDMTxBiasCurrentLowWarning indicates the Transmit
--          Bias Current of the SFP/XFP in micro-Amperes (uA) that triggers a
--          low-warning."
--     ::= { tnDigitalDiagMonitorEntry 12 }
--
-- tnDDMTxBiasCurrentLowAlarm       OBJECT-TYPE
--     SYNTAX      Integer32
--     MAX-ACCESS  read-only
--     STATUS      current
--     DESCRIPTION
--         "The value of tnDDMTxBiasCurrentLowAlarm indicates the Transmit
--          Bias Current of the SFP/XFP in micro-Amperes (uA) that triggers a
--          low-alarm."
--     ::= { tnDigitalDiagMonitorEntry 13 }
--
-- tnDDMTxBiasCurrentHiWarning      OBJECT-TYPE
--     SYNTAX      Integer32
--     MAX-ACCESS  read-only
--     STATUS      current
--     DESCRIPTION
--         "The value of tnDDMTxBiasCurrentHiWarning indicates the Transmit
--          Bias Current of the SFP/XFP in micro-Amperes (uA) that triggers a
--          hi-warning."
--     ::= { tnDigitalDiagMonitorEntry 14 }
--
-- tnDDMTxBiasCurrentHiAlarm        OBJECT-TYPE
--     SYNTAX      Integer32
--     MAX-ACCESS  read-only
--     STATUS      current
--     DESCRIPTION
--         "The value of tnDDMTxBiasCurrentHiAlarm indicates the Transmit
--          Bias Current of the SFP/XFP in micro-Amperes (uA) that triggers a
--          hi-alarm."
--     ::= { tnDigitalDiagMonitorEntry 15 }
--
-- tnDDMTxOutputPower               OBJECT-TYPE
--     SYNTAX      Integer32
--     MAX-ACCESS  read-only
--     STATUS      current
--     DESCRIPTION
--         "The value of tnDDMTxOutputPower indicates the current Output
--          Power of the SFP/XFP in one tenths of a micro-Watt (uW).
--
--          For example:
--          Using the SNMP value of 790, and using units of tenths of microwatt,
--          790 becomes 79 microwatts or 0.079 milliwatts. Converting to dBm:
--                10 x log10(0.079) = -11.0 dBm"
--
--     ::= { tnDigitalDiagMonitorEntry 16 }
--
-- tnDDMTxOutputPowerLowWarning     OBJECT-TYPE
--     SYNTAX      Integer32
--     MAX-ACCESS  read-only
--     STATUS      current
--     DESCRIPTION
--         "The value of tnDDMTxOutputPowerLowWarning indicates the Output Power
--          of the SFP/XFP in one tenths of a micro-Watt (uW) that triggers a
--          low-warning."
--
--     ::= { tnDigitalDiagMonitorEntry 17 }
--
-- tnDDMTxOutputPowerLowAlarm       OBJECT-TYPE
--     SYNTAX      Integer32
--     MAX-ACCESS  read-only
--     STATUS      current
--     DESCRIPTION
--         "The value of tnDDMTxOutputPowerLowAlarm indicates the Output Power
--          of the SFP/XFP in one tenths of a micro-Watt (uW) that triggers a
--          low-alarm."
--     ::= { tnDigitalDiagMonitorEntry 18 }
--
-- tnDDMTxOutputPowerHiWarning      OBJECT-TYPE
--     SYNTAX      Integer32
--     MAX-ACCESS  read-only
--     STATUS      current
--     DESCRIPTION
--         "The value of tnDDMTxOutputPowerHiWarning indicates the Output Power
--          of the SFP/XFP in one tenths of a micro-Watt (uW) that triggers a
--          hi-alarm."
--     ::= { tnDigitalDiagMonitorEntry 19 }
--
-- tnDDMTxOutputPowerHiAlarm        OBJECT-TYPE
--     SYNTAX      Integer32
--     MAX-ACCESS  read-only
--     STATUS      current
--     DESCRIPTION
--         "The value of tnDDMTxOutputPowerHiAlarm indicates the Output Power
--          of the SFP/XFP in one tenths of a micro-Watt (uW) that triggers a
--          hi-alarm."
--     ::= { tnDigitalDiagMonitorEntry 20 }
--
-- tnDDMRxOpticalPower              OBJECT-TYPE
--     SYNTAX      Integer32
--     MAX-ACCESS  read-only
--     STATUS      current
--     DESCRIPTION
--         "The value of tnDDMRxOpticalPower indicates the current Received
--          Optical Power of the SFP/XFP in one tenths of a micro-Watt (uW).
--
--          For example:
--          Using the SNMP value of 790, and using units of tenths of microwatt,
--          790 becomes 79 microwatts or 0.079 milliwatts. Converting to dBm:
--                10 x log10(0.079) = -11.0 dBm"
--     ::= { tnDigitalDiagMonitorEntry 21 }
--
-- tnDDMRxOpticalPowerLowWarning    OBJECT-TYPE
--     SYNTAX      Integer32
--     MAX-ACCESS  read-only
--     STATUS      current
--     DESCRIPTION
--         "The value of tnDDMRxOpticalPowerLowWarning indicates the Received
--          Optical Power of the SFP/XFP in one tenths of a micro-Watt (uW) that
--          triggers a low-warning."
--     ::= { tnDigitalDiagMonitorEntry 22 }
--
-- tnDDMRxOpticalPowerLowAlarm      OBJECT-TYPE
--     SYNTAX      Integer32
--     MAX-ACCESS  read-only
--     STATUS      current
--     DESCRIPTION
--         "The value of tnDDMRxOpticalPowerLowAlarm indicates the Received
--          Optical Power of the SFP/XFP in one tenths of a micro-Watt (uW) that
--          triggers a low-alarm."
--     ::= { tnDigitalDiagMonitorEntry 23 }
--
-- tnDDMRxOpticalPowerHiWarning     OBJECT-TYPE
--     SYNTAX      Integer32
--     MAX-ACCESS  read-only
--     STATUS      current
--     DESCRIPTION
--         "The value of tnDDMRxOpticalPowerHiWarning indicates the Received
--          Optical Power of the SFP/XFP in one tenths of a micro-Watt (uW) that
--          triggers a hi-warning."
--     ::= { tnDigitalDiagMonitorEntry 24 }
--
-- tnDDMRxOpticalPowerHiAlarm       OBJECT-TYPE
--     SYNTAX      Integer32
--     MAX-ACCESS  read-only
--     STATUS      current
--     DESCRIPTION
--         "The value of tnDDMRxOpticalPowerHiAlarm indicates the Received
--          Optical Power of the SFP/XFP in one tenths of a micro-Watt (uW) that
--          triggers a hi-alarm."
--     ::= { tnDigitalDiagMonitorEntry 25 }
--
-- tnDDMRxOpticalPowerType          OBJECT-TYPE
--     SYNTAX      INTEGER {
--                     oma      (0),   == Optical Modulation Amplitude
--                     average  (1)    == Average rx optical power
--                 }
--     MAX-ACCESS  read-only
--     STATUS      current
--     DESCRIPTION
--         "The value of tnDDMRxOpticalPowerType indicates whether the
--          tnDDMRxOpticalPower was taken as an average, or as an Optical
--          Modulation Amplitude (OMA)."
--     ::= { tnDigitalDiagMonitorEntry 26 }
--
-- tnDDMAux1                        OBJECT-TYPE
--     SYNTAX      Integer32
--     MAX-ACCESS  read-only
--     STATUS      current
--     DESCRIPTION
--         "The value of tnDDMAux1 indicates the Manufacturer specific
--          Auxiliary 1 information of the XFP."
--     ::= { tnDigitalDiagMonitorEntry 27 }
--
-- tnDDMAux1LowWarning              OBJECT-TYPE
--     SYNTAX      Integer32
--     MAX-ACCESS  read-only
--     STATUS      current
--     DESCRIPTION
--         "The value of tnDDMAux1LowWarning indicates the Manufacturer specific
--          Auxiliary 1 low-warning threshold for the XFP."
--     ::= { tnDigitalDiagMonitorEntry 28 }
--
-- tnDDMAux1LowAlarm                OBJECT-TYPE
--     SYNTAX      Integer32
--     MAX-ACCESS  read-only
--     STATUS      current
--     DESCRIPTION
--         "The value of tnDDMAux1LowAlarm indicates the Manufacturer specific
--          Auxiliary 1 low-alarm threshold for the XFP."
--     ::= { tnDigitalDiagMonitorEntry 29 }
--
-- tnDDMAux1HiWarning               OBJECT-TYPE
--     SYNTAX      Integer32
--     MAX-ACCESS  read-only
--     STATUS      current
--     DESCRIPTION
--         "The value of tnDDMAux1HiWarning indicates the Manufacturer specific
--          Auxiliary 1 hi-warning threshold for the XFP."
--     ::= { tnDigitalDiagMonitorEntry 30 }
--
-- tnDDMAux1HiAlarm                 OBJECT-TYPE
--     SYNTAX      Integer32
--     MAX-ACCESS  read-only
--     STATUS      current
--     DESCRIPTION
--         "The value of tnDDMAux1HiAlarm indicates the Manufacturer specific
--          Auxiliary 1 hi-alarm threshold for the XFP."
--     ::= { tnDigitalDiagMonitorEntry 31 }
--
-- tnDDMAux1Type                    OBJECT-TYPE
--     SYNTAX      INTEGER {
--                     none             (0),
--                     adp-bias-voltage (1),
--                     reserved-2       (2),
--                     tec-current      (3),
--                     laser-temp       (4),
--                     laser-wavelength (5),
--                     voltage-50       (6),
--                     voltage-33       (7),
--                     voltage-18       (8),
--                     voltage-52       (9),
--                     current-50       (10),
--                     reserved-11      (11),
--                     reserved-12      (12),
--                     current-33       (13),
--                     current-18       (14),
--                     current-52       (15)
--                 }
--     MAX-ACCESS  read-only
--     STATUS      current
--     DESCRIPTION
--         "The value of tnDDMAux1Type indicates the measurement type of
--          the Manufacturer specific Auxiliary 1 information of the XFP:
--             none             (0)  - not specified.
--             adp-bias-voltage (1)  - LSB is 10mV.
--             reserved-2       (2)  - reserved for future use.
--             tec-current      (3)  - LSB is 100uA.
--             laser-temp       (4)  - degrees Celsius(C).
--             laser-wavelength (5)  - LSB is 0.05 nm.
--             voltage-50       (6)  - 5.0 supply voltage, LSB=100uV.
--             voltage-33       (7)  - 3.3 supply voltage, LSB=100uV.
--             voltage-18       (8)  - 1.8 supply voltage, LSB=100uV,
--             voltage-52       (9)  - -5.2 supply voltage, LSB=100uV.
--             current-50      (10)  - 5.0V supply current, LSB=100uA.
--             reserved-11     (11)  - reserved for future use.
--             reserved-12     (12)  - reserved for future use.
--             current-33      (13)  - 3.3V supply current, LSB=100uA.
--             current-18      (14)  - 1.8V supply current, LSB=100uA.
--             current-52      (15)  - -5.2V supply current, LSB=100uA."
--     ::= { tnDigitalDiagMonitorEntry 32 }
--
-- tnDDMAux2                        OBJECT-TYPE
--     SYNTAX      Integer32
--     MAX-ACCESS  read-only
--     STATUS      current
--     DESCRIPTION
--         "The value of tnDDMAux2 indicates the Manufacturer specific
--          Auxiliary 2 information of the SFP/XFP."
--     ::= { tnDigitalDiagMonitorEntry 33 }
--
-- tnDDMAux2LowWarning              OBJECT-TYPE
--     SYNTAX      Integer32
--     MAX-ACCESS  read-only
--     STATUS      current
--     DESCRIPTION
--         "The value of tnDDMAux2LowWarning indicates the Manufacturer specific
--          Auxiliary 2 low-warning threshold for the XFP."
--     ::= { tnDigitalDiagMonitorEntry 34 }
--
-- tnDDMAux2LowAlarm                OBJECT-TYPE
--     SYNTAX      Integer32
--     MAX-ACCESS  read-only
--     STATUS      current
--     DESCRIPTION
--         "The value of tnDDMAux2LowAlarm indicates the Manufacturer specific
--          Auxiliary 2 low-alarm threshold for the XFP."
--     ::= { tnDigitalDiagMonitorEntry 35 }
--
-- tnDDMAux2HiWarning               OBJECT-TYPE
--     SYNTAX      Integer32
--     MAX-ACCESS  read-only
--     STATUS      current
--     DESCRIPTION
--         "The value of tnDDMAux2HiWarning indicates the Manufacturer specific
--          Auxiliary 2 hi-warning threshold for the XFP."
--     ::= { tnDigitalDiagMonitorEntry 36 }
--
-- tnDDMAux2HiAlarm                 OBJECT-TYPE
--     SYNTAX      Integer32
--     MAX-ACCESS  read-only
--     STATUS      current
--     DESCRIPTION
--         "The value of tnDDMAux2HiAlarm indicates the Manufacturer specific
--          Auxiliary 2 hi-alarm threshold for the XFP."
--     ::= { tnDigitalDiagMonitorEntry 37 }
--
-- tnDDMAux2Type                    OBJECT-TYPE
--     SYNTAX      INTEGER {
--                     none             (0),
--                     adp-bias-voltage (1),
--                     reserved-2       (2),
--                     tec-current      (3),
--                     laser-temp       (4),
--                     laser-wavelength (5),
--                     voltage-50       (6),
--                     voltage-33       (7),
--                     voltage-18       (8),
--                     voltage-52       (9),
--                     current-50       (10),
--                     reserved-11      (11),
--                     reserved-12      (12),
--                     current-33       (13),
--                     current-18       (14),
--                     current-52       (15)
--                 }
--     MAX-ACCESS  read-only
--     STATUS      current
--     DESCRIPTION
--         "The value of tnDDMAux2Type indicates the measurement type of
--          the Manufacturer specific Auxiliary 2 information of the XFP:
--             none             (0)  - not specified.
--             adp-bias-voltage (1)  - LSB is 10mV.
--             reserved-2       (2)  - reserved for future use.
--             tec-current      (3)  - LSB is 100uA.
--             laser-temp       (4)  - degrees Celsius(C).
--             laser-wavelength (5)  - LSB is 0.05 nm.
--             voltage-50       (6)  - 5.0 supply voltage, LSB=100uV.
--             voltage-33       (7)  - 3.3 supply voltage, LSB=100uV.
--             voltage-18       (8)  - 1.8 supply voltage, LSB=100uV,
--             voltage-52       (9)  - -5.2 supply voltage, LSB=100uV.
--             current-50      (10)  - 5.0V supply current, LSB=100uA.
--             reserved-11     (11)  - reserved for future use.
--             reserved-12     (12)  - reserved for future use.
--             current-33      (13)  - 3.3V supply current, LSB=100uA.
--             current-18      (14)  - 1.8V supply current, LSB=100uA.
--             current-52      (15)  - -5.2V supply current, LSB=100uA."
--     ::= { tnDigitalDiagMonitorEntry 38 }
--
-- tnDDMFailedThresholds            OBJECT-TYPE
--     SYNTAX      BITS {
--                     unknown                      (0),
--                     temperature-low-warning      (1),
--                     temperature-low-alarm        (2),
--                     temperature-high-warning     (3),
--                     temperature-high-alarm       (4),
--                     supplyVoltage-low-warning    (5),
--                     supplyVoltage-low-alarm      (6),
--                     supplyVoltage-high-warning   (7),
--                     supplyVoltage-high-alarm     (8),
--                     txBiasCurrent-low-warning    (9),
--                     txBiasCurrent-low-alarm     (10),
--                     txBiasCurrent-high-warning  (11),
--                     txBiasCurrent-high-alarm    (12),
--                     txOutputPower-low-warning   (13),
--                     txOutputPower-low-alarm     (14),
--                     txOutputPower-high-warning  (15),
--                     txOutputPower-high-alarm    (16),
--                     rxOpticalPower-low-warning  (17),
--                     rxOpticalPower-low-alarm    (18),
--                     rxOpticalPower-high-warning (19),
--                     rxOpticalPower-high-alarm   (20),
--                     aux1-low-warning            (21),
--                     aux1-low-alarm              (22),
--                     aux1-high-warning           (23),
--                     aux1-high-alarm             (24),
--                     aux2-low-warning            (25),
--                     aux2-low-alarm              (26),
--                     aux2-high-warning           (27),
--                     aux2-high-alarm             (28)
--                 }
--     MAX-ACCESS  read-only
--     STATUS      current
--     DESCRIPTION
--         "The value of tnDDMFailedThresholds indicates which objects
--         of the monitored SFP/XFP is in a failed or cleared threshold state.
--         A set bit indicates that the specified threshold has been exceeded."
--     ::= { tnDigitalDiagMonitorEntry 39 }
--
-- tnDDMExternallyCalibrated        OBJECT-TYPE
--     SYNTAX      TruthValue
--     MAX-ACCESS  read-only
--     STATUS      current
--     DESCRIPTION
--         "The value of tnDDMExternallyCalibrated indicates whether the
--          SFP was externally calibrated (true) or internally calibrated (false)."
--     ::= { tnDigitalDiagMonitorEntry 40 }
--
-- tnDDMExtCalRxPower4              OBJECT-TYPE
--     SYNTAX      Unsigned32
--     MAX-ACCESS  read-only
--     STATUS      current
--     DESCRIPTION
--         "The value of tnDDMExtCalRxPower4 indicates the Rx_PWR(4)
--          value as specified in Table 3.16 in the SFF Committee Standard's
--          document SFF-8472 Rev 10.2."
--     REFERENCE "SFF-8472 Rev 10.2"
--     ::= { tnDigitalDiagMonitorEntry 41 }
--
-- tnDDMExtCalRxPower3              OBJECT-TYPE
--     SYNTAX      Unsigned32
--     MAX-ACCESS  read-only
--     STATUS      current
--     DESCRIPTION
--         "The value of tnDDMExtCalRxPower3 indicates the Rx_PWR(3)
--          value as specified in Table 3.16 in the SFF Committee Standard's
--          document SFF-8462 Rev 10.2."
--     REFERENCE "SFF-8472 Rev 10.2"
--     ::= { tnDigitalDiagMonitorEntry 42 }
--
-- tnDDMExtCalRxPower2              OBJECT-TYPE
--     SYNTAX      Unsigned32
--     MAX-ACCESS  read-only
--     STATUS      current
--     DESCRIPTION
--         "The value of tnDDMExtCalRxPower2 indicates the Rx_PWR(2)
--          value as specified in Table 3.16 in the SFF Committee Standard's
--          document SFF-8472 Rev 10.2."
--     REFERENCE "SFF-8472 Rev 10.2"
--     ::= { tnDigitalDiagMonitorEntry 43 }
--
-- tnDDMExtCalRxPower1              OBJECT-TYPE
--     SYNTAX      Unsigned32
--     MAX-ACCESS  read-only
--     STATUS      current
--     DESCRIPTION
--         "The value of tnDDMExtCalRxPower1 indicates the Rx_PWR(1)
--          value as specified in Table 3.16 in the SFF Committee Standard's
--          document SFF-8472 Rev 10.2."
--     REFERENCE "SFF-8472 Rev 10.2"
--     ::= { tnDigitalDiagMonitorEntry 44 }
--
-- tnDDMExtCalRxPower0              OBJECT-TYPE
--     SYNTAX      Unsigned32
--     MAX-ACCESS  read-only
--     STATUS      current
--     DESCRIPTION
--         "The value of tnDDMExtCalRxPower0 indicates the Rx_PWR(0)
--          value as specified in Table 3.16 in the SFF Committee Standard's
--          document SFF-8472 Rev 10.2."
--     REFERENCE "SFF-8472 Rev 10.2"
--     ::= { tnDigitalDiagMonitorEntry 45 }
--
-- tnDDMExtCalTxLaserBiasSlope      OBJECT-TYPE
--     SYNTAX      Unsigned32 (0..65535)
--     MAX-ACCESS  read-only
--     STATUS      current
--     DESCRIPTION
--         "The value of tnDDMExtCalTxLaserBiasSlope indicates the
--          Tx_l(Slope) value as specified in Table 3.16 in the SFF
--          Committee Standard's document SFF-8472 Rev 10.2."
--     REFERENCE "SFF-8472 Rev 10.2"
--     ::= { tnDigitalDiagMonitorEntry 46 }
--
-- tnDDMExtCalTxLaserBiasOffset     OBJECT-TYPE
--     SYNTAX      Integer32 (-32767..32768)
--     MAX-ACCESS  read-only
--     STATUS      current
--     DESCRIPTION
--         "The value of tnDDMExtCalTxLaserBiasOffset indicates the
--          Tx_l(Offset) value as specified in Table 3.16 in the SFF
--          Committee Standard's document SFF-8472 Rev 10.2."
--     REFERENCE "SFF-8472 Rev 10.2"
--     ::= { tnDigitalDiagMonitorEntry 47 }
--
-- tnDDMExtCalTxPowerSlope          OBJECT-TYPE
--     SYNTAX      Unsigned32 (0..65535)
--     MAX-ACCESS  read-only
--     STATUS      current
--     DESCRIPTION
--         "The value of tnDDMExtCalTxPowerSlope indicates the
--          Tx_PWR(Slope) value as specified in Table 3.16 in the
--          SFF Committee Standard's document SFF-8472 Rev 10.2."
--     REFERENCE "SFF-8472 Rev 10.2"
--     ::= { tnDigitalDiagMonitorEntry 48 }
--
-- tnDDMExtCalTxPowerOffset         OBJECT-TYPE
--     SYNTAX      Integer32 (-32767..32768)
--     MAX-ACCESS  read-only
--     STATUS      current
--     DESCRIPTION
--         "The value of tnDDMExtCalTxPowerOffset indicates the
--          Tx_PWR(Offset) value as specified in Table 3.16 in the
--          SFF Committee Standard's document SFF-8472 Rev 10.2."
--     REFERENCE "SFF-8472 Rev 10.2"
--     ::= { tnDigitalDiagMonitorEntry 49 }
--
-- tnDDMExtCalTemperatureSlope      OBJECT-TYPE
--     SYNTAX      Unsigned32 (0..65535)
--     MAX-ACCESS  read-only
--     STATUS      current
--     DESCRIPTION
--         "The value of tnDDMExtCalTemperatureSlope indicates the
--          T(Slope) value as specified in Table 3.16 in the SFF
--          Committee Standard's document SFF-8472 Rev 10.2."
--     REFERENCE "SFF-8472 Rev 10.2"
--     ::= { tnDigitalDiagMonitorEntry 50 }
--
-- tnDDMExtCalTemperatureOffset     OBJECT-TYPE
--     SYNTAX      Integer32 (-32767..32768)
--     MAX-ACCESS  read-only
--     STATUS      current
--     DESCRIPTION
--         "The value of tnDDMExtCalTemperatureOffset indicates the
--          T(Offset) value as specified in Table 3.16 in the SFF
--          Committee Standard's document SFF-8472 Rev 10.2."
--     REFERENCE "SFF-8472 Rev 10.2"
--     ::= { tnDigitalDiagMonitorEntry 51 }
--
-- tnDDMExtCalVoltageSlope          OBJECT-TYPE
--     SYNTAX      Unsigned32 (0..65535)
--     MAX-ACCESS  read-only
--     STATUS      current
--     DESCRIPTION
--         "The value of tnDDMExtCalVoltageSlope indicates the V(Slope)
--         value as specified in Table 3.16 in the SFF Committee Standard's
--         document SFF-8472 Rev 10.2."
--     REFERENCE "SFF-8472 Rev 10.2"
--     ::= { tnDigitalDiagMonitorEntry 52 }
--
-- tnDDMExtCalVoltageOffset         OBJECT-TYPE
--     SYNTAX      Integer32 (-32767..32768)
--     MAX-ACCESS  read-only
--     STATUS      current
--     DESCRIPTION
--         "The value of tnDDMExtCalVoltageOffset indicates the V(Slope)
--         value as specified in Table 3.16 in the SFF Committee Standard's
--         document SFF-8472 Rev 10.2."
--     REFERENCE "SFF-8472 Rev 10.2"
--     ::= { tnDigitalDiagMonitorEntry 53 }

--
-- access ingress queue group table
--

-- tnPortAccIngQGrpTableLastChgd OBJECT-TYPE
--     SYNTAX       TimeStamp
--     MAX-ACCESS   read-only
--     STATUS       current
--     DESCRIPTION
--         "The value of tnPortAccIngQGrpTableLastChgd indicates the
--         timestamp of last change to the tnPortAccIngQGrpTable."
--     ::= { tnPortObjs 32 }
--
-- tnPortAccIngQGrpTable OBJECT-TYPE
--     SYNTAX       SEQUENCE OF TPortAccIngQGrpEntry
--     MAX-ACCESS   not-accessible
--     STATUS       current
--     DESCRIPTION
--         "The value of tnPortAccIngQGrpTable defines access Ingress Queue Group
--         Table for providing, via SNMP, the capability of defining the port
--         specific queue groups from the queue-groups existing in the
--         TIMETRA-QOS-MIB::tQosIngQGroupTable."
--     ::= { tnPortObjs 33 }
--
-- tnPortAccIngQGrpEntry OBJECT-TYPE
--     SYNTAX       TPortAccIngQGrpEntry
--     MAX-ACCESS   not-accessible
--     STATUS       current
--     DESCRIPTION
--         "The value of tnPortAccIngQGrpEntry defines an entry in the
--         tnPortAccIngQGrpTable.
--
--         Entries are created/deleted in this table by SNMP sets to
--         tnPortAccIngQGrpRowStatus."
--     INDEX {  tnPortPortID, tnPortAccIngQGrpName }
--     ::= { tnPortAccIngQGrpTable 1 }
--
-- TPortAccIngQGrpEntry ::= SEQUENCE
--     {
--         tnPortAccIngQGrpName             TNamedItem,
--         tnPortAccIngQGrpRowStatus        RowStatus,
--         tnPortAccIngQGrpLastChgd         TimeStamp,
--         tnPortAccIngQGrpSchedPol         TNamedItemOrEmpty,
--         tnPortAccIngQGrpAcctgPolId       Unsigned32,
--         tnPortAccIngQGrpCollectStats     TruthValue,
--         tnPortAccIngQGrpDescr            TItemDescription
--     }
--
-- tnPortAccIngQGrpName OBJECT-TYPE
--     SYNTAX       TNamedItem
--     MAX-ACCESS   not-accessible
--     STATUS       current
--     DESCRIPTION
--         "The value of tnPortAccIngQGrpName defines the port Ingress
--         Queue Group name.  It uniquely identifies a port ingress queue group
--         in the managed system."
--     ::= { tnPortAccIngQGrpEntry 1 }
--
-- tnPortAccIngQGrpRowStatus OBJECT-TYPE
--     SYNTAX       RowStatus
--     MAX-ACCESS   read-create
--     STATUS       current
--     DESCRIPTION
--         "The value of tnPortAccIngQGrpRowStatus allows entries to be
--         created and deleted in the tnPortAccIngQGrpTable.
--
--         The creation of an entry in this table will succeed only if the
--         queue-group being created exists in
--         TIMETRA-QOS-MIB::tQosIngQGroupTable."
--     REFERENCE
--         "See definition of RowStatus in RFC 2579, 'Textual Conventions for
--          SMIv2.'"
--     ::= { tnPortAccIngQGrpEntry 2 }
--
-- tnPortAccIngQGrpLastChgd OBJECT-TYPE
--     SYNTAX       TimeStamp
--     MAX-ACCESS   read-only
--     STATUS       current
--     DESCRIPTION
--         "The value of tnPortAccIngQGrpLastChgd indicates the value of
--         sysUpTime when the queue entry was last modified."
--     ::= { tnPortAccIngQGrpEntry 3 }
--
-- tnPortAccIngQGrpSchedPol OBJECT-TYPE
--     SYNTAX       TNamedItemOrEmpty
--     MAX-ACCESS   read-create
--     STATUS       current
--     DESCRIPTION
--         "The value of tnPortAccIngQGrpSchedPol specifies the name of
--         the scheduler-policy to be used with this port ingress queue-group."
--     DEFVAL { ''H }
--     ::= { tnPortAccIngQGrpEntry 4 }
--
-- tnPortAccIngQGrpAcctgPolId OBJECT-TYPE
--     SYNTAX       Unsigned32 (0..99)
--     MAX-ACCESS   read-create
--     STATUS       current
--     DESCRIPTION
--         "The value of tnPortAccIngQGrpAcctgPolId specifies the accounting-policy
--         to be used with this port ingress queue-group.
--
--         A non-zero value indicates the tmnxLogApPolicyId index identifying the
--         policy entry in the tmnxLogApTable from the TIMETRA-LOG-MIB which is
--         associated with this queue-group.
--
--         The value zero indicates that the agent should use the default
--         accounting policy, if one exists."
--     DEFVAL { 0 }
--     ::= { tnPortAccIngQGrpEntry 5 }
--
-- tnPortAccIngQGrpCollectStats OBJECT-TYPE
--     SYNTAX       TruthValue
--     MAX-ACCESS   read-create
--     STATUS       current
--     DESCRIPTION
--         "The value of tnPortAccIngQGrpCollectStats specifies whether
--         statistics should be collected on this port ingress queue-group."
--     DEFVAL { false }
--     ::= { tnPortAccIngQGrpEntry 6 }
--
-- tnPortAccIngQGrpDescr OBJECT-TYPE
--     SYNTAX       TItemDescription
--     MAX-ACCESS   read-create
--     STATUS       current
--     DESCRIPTION
--         "The value of tnPortAccIngQGrpDescr specifies the description for
--         this port queue-group."
--     DEFVAL { ''H }
--     ::= { tnPortAccIngQGrpEntry 7 }

--
--      Port queue policy overrides
--

-- tnPortAccIngQOverTableLastChgd OBJECT-TYPE
--     SYNTAX       TimeStamp
--     MAX-ACCESS   read-only
--     STATUS       current
--     DESCRIPTION
--         "The value of tnPortAccIngQOverTableLastChgd indicates the
--         timestamp of last change to the tnPortAccIngQOverTable."
--     ::= { tnPortObjs 34 }
--
-- tnPortAccIngQOverTable OBJECT-TYPE
--     SYNTAX      SEQUENCE OF TPortAccIngQOverEntry
--     MAX-ACCESS  not-accessible
--     STATUS      current
--     DESCRIPTION
--         "The tnPortAccIngQOverTable has an entry for each access port queue
--         override configured on this system."
--     ::= { tnPortObjs 35 }
--
-- tnPortAccIngQOverEntry    OBJECT-TYPE
--     SYNTAX      TPortAccIngQOverEntry
--     MAX-ACCESS  not-accessible
--     STATUS      current
--     DESCRIPTION
--         "Each row represents a particular port-queue override. Entries are
--         created and deleted by the user."
--     INDEX {  tnPortPortID,
--             tnPortAccIngQGrpName, tnPortAccIngQOverQueue }
--     ::= { tnPortAccIngQOverTable 1}
--
-- TPortAccIngQOverEntry ::= SEQUENCE
--     {
--         tnPortAccIngQOverQueue              TIngressQueueId,
--         tnPortAccIngQOverRowStatus          RowStatus,
--         tnPortAccIngQOverLastChanged        TimeStamp,
--         tnPortAccIngQOverCBS                TBurstSizeOverride,
--         tnPortAccIngQOverMBS                TBurstSizeOverride,
--         tnPortAccIngQOverHiPrioOnly         TBurstPercentOrDefaultOverride,
--         tnPortAccIngQOverAdminPIR           TPIRRateOverride,
--         tnPortAccIngQOverAdminCIR           TCIRRateOverride,
--         tnPortAccIngQOverPIRAdaptation      TAdaptationRuleOverride,
--         tnPortAccIngQOverCIRAdaptation      TAdaptationRuleOverride
--     }
--
-- tnPortAccIngQOverQueue OBJECT-TYPE
--     SYNTAX       TIngressQueueId (1..32)
--     MAX-ACCESS   not-accessible
--     STATUS       current
--     DESCRIPTION
--         "The value of tnPortAccIngQOverQueue specifies the queue ID
--         which is used as the fourth index to the table entry."
--     ::= { tnPortAccIngQOverEntry 1 }
--
-- tnPortAccIngQOverRowStatus        OBJECT-TYPE
--     SYNTAX      RowStatus
--     MAX-ACCESS  read-create
--     STATUS      current
--     DESCRIPTION
--         "The value of tnPortAccIngQOverRowStatus is used for the creation
--         and deletion of port-queue overrides.
--
--         Row creation will fail if there is no entry in the
--         TIMETRA-QOS-MIB::tQosIngQueueTable with the same index values as the
--         last two indices of this table
--         (tnPortAccIngQGrpName.tnPortAccIngQOverQueue)."
--     ::= { tnPortAccIngQOverEntry 2 }
--
-- tnPortAccIngQOverLastChanged        OBJECT-TYPE
--     SYNTAX      TimeStamp
--     MAX-ACCESS  read-only
--     STATUS      current
--     DESCRIPTION
--         "The value of tnPortAccIngQOverLastChanged indicates the value
--         of sysUpTime at the time of the most recent management change to
--         this row."
--     ::= { tnPortAccIngQOverEntry 3 }
--
-- tnPortAccIngQOverCBS OBJECT-TYPE
--     SYNTAX       TBurstSizeOverride
--     UNITS        "kilo-bytes"
--     MAX-ACCESS   read-create
--     STATUS       current
--     DESCRIPTION
--         "The value of tnPortAccIngQOverCBS specifies the amount of reserved
--         buffer space for the queue."
--     DEFVAL { -2 }
--     ::= { tnPortAccIngQOverEntry 4 }
--
-- tnPortAccIngQOverMBS OBJECT-TYPE
--     SYNTAX       TBurstSizeOverride
--     UNITS        "kilo-bytes"
--     MAX-ACCESS   read-create
--     STATUS       current
--     DESCRIPTION
--         "The value of tnPortAccIngQOverMBS specifies the maximum amount of
--         buffer space allowed for the queue."
--     DEFVAL { -2 }
--     ::= { tnPortAccIngQOverEntry 5 }
--
-- tnPortAccIngQOverHiPrioOnly OBJECT-TYPE
--     SYNTAX       TBurstPercentOrDefaultOverride
--     MAX-ACCESS   read-create
--     STATUS       current
--     DESCRIPTION
--         "The value of tnPortAccIngQOverHiPrioOnly specifies the percentage of
--         buffer space for the queue, used exclusively by high priority packets."
--     DEFVAL { -2 }
--     ::= { tnPortAccIngQOverEntry 6 }
--
-- tnPortAccIngQOverAdminPIR OBJECT-TYPE
--     SYNTAX       TPIRRateOverride
--     UNITS        "kbps"
--     MAX-ACCESS   read-create
--     STATUS       current
--     DESCRIPTION
--         "The value of tnPortAccIngQOverAdminPIR specifies the administrative
--         PIR specified by the user."
--     DEFVAL { -2 }
--     ::= { tnPortAccIngQOverEntry 7 }
--
-- tnPortAccIngQOverAdminCIR OBJECT-TYPE
--     SYNTAX       TCIRRateOverride
--     UNITS        "kbps"
--     MAX-ACCESS   read-create
--     STATUS       current
--     DESCRIPTION
--         "The value of tnPortAccIngQOverAdminCIR specifies the administrative
--         CIR specified by the user."
--     DEFVAL { -2 }
--     ::= { tnPortAccIngQOverEntry 8 }
--
-- tnPortAccIngQOverPIRAdaptation OBJECT-TYPE
--     SYNTAX       TAdaptationRuleOverride
--     MAX-ACCESS   read-create
--     STATUS       current
--     DESCRIPTION
--         "The value of tnPortAccIngQOverPIRAdaptation specifies the adaptation
--          rule to be used while computing the operational PIR
--          value. The adaptation rule specifies the rules to compute the
--          operational values while maintaining minimum offset."
--     DEFVAL { noOverride }
--     ::= { tnPortAccIngQOverEntry 9 }
--
-- tnPortAccIngQOverCIRAdaptation OBJECT-TYPE
--     SYNTAX       TAdaptationRuleOverride
--     MAX-ACCESS   read-create
--     STATUS       current
--     DESCRIPTION
--         "The value of tnPortAccIngQOverCIRAdaptation specifies the adaptation
--          rule to be used while computing the operational CIR
--          value. The adaptation rule specifies the rules to compute the
--          operational values while maintaining minimum offset."
--     DEFVAL { noOverride }
--     ::= { tnPortAccIngQOverEntry 10 }

--
-- access egress queue group table
--

-- tnPortAccEgrQGrpTableLastChgd OBJECT-TYPE
--     SYNTAX       TimeStamp
--     MAX-ACCESS   read-only
--     STATUS       current
--     DESCRIPTION
--         "The value of tnPortAccEgrQGrpTableLastChgd indicates the
--         timestamp of last change to the tnPortAccEgrQGrpTable."
--     ::= { tnPortObjs 36 }
--
-- tnPortAccEgrQGrpTable OBJECT-TYPE
--     SYNTAX       SEQUENCE OF TPortAccEgrQGrpEntry
--     MAX-ACCESS   not-accessible
--     STATUS       current
--     DESCRIPTION
--         "The value of tnPortAccEgrQGrpTable defines access Egress Queue Group
--         Table for providing, via SNMP, the capability of defining the port
--         specific queue groups from the queue-groups existing in the
--         TIMETRA-QOS-MIB::tQosEgrQGroupTable."
--     ::= { tnPortObjs 37 }
--
-- tnPortAccEgrQGrpEntry OBJECT-TYPE
--     SYNTAX       TPortAccEgrQGrpEntry
--     MAX-ACCESS   not-accessible
--     STATUS       current
--     DESCRIPTION
--         "The value of tnPortAccEgrQGrpEntry defines an entry in the
--         tnPortAccEgrQGrpTable.
--
--         Entries are created/deleted in this table by SNMP sets to
--         tnPortAccEgrQGrpRowStatus."
--     INDEX {  tnPortPortID, tnPortAccEgrQGrpName }
--     ::= { tnPortAccEgrQGrpTable 1 }
--
-- TPortAccEgrQGrpEntry ::= SEQUENCE
--     {
--         tnPortAccEgrQGrpName             TNamedItem,
--         tnPortAccEgrQGrpRowStatus        RowStatus,
--         tnPortAccEgrQGrpLastChgd         TimeStamp,
--         tnPortAccEgrQGrpSchedPol         TNamedItemOrEmpty,
--         tnPortAccEgrQGrpAggRateLimit     TPortSchedulerPIR,
--         tnPortAccEgrQGrpAcctgPolId       Unsigned32,
--         tnPortAccEgrQGrpCollectStats     TruthValue,
--         tnPortAccEgrQGrpFrameBaseActg    TruthValue,
--         tnPortAccEgrQGrpDescr            TItemDescription
--     }
--
-- tnPortAccEgrQGrpName OBJECT-TYPE
--     SYNTAX       TNamedItem
--     MAX-ACCESS   not-accessible
--     STATUS       current
--     DESCRIPTION
--         "The value of tnPortAccEgrQGrpName defines the port Egress Queue
--         Group name.  It uniquely identifies a port egress queue group in the
--         managed system."
--     ::= { tnPortAccEgrQGrpEntry 1 }
--
-- tnPortAccEgrQGrpRowStatus OBJECT-TYPE
--     SYNTAX       RowStatus
--     MAX-ACCESS   read-create
--     STATUS       current
--     DESCRIPTION
--         "The value of tnPortAccEgrQGrpRowStatus allows entries to be
--         created and deleted in the tnPortAccEgrQGrpTable.
--
--         The creation of an entry in this table will succeed only if the
--         queue-group being created exist in TIMETRA-QOS-MIB::tQosEgrQGroupTable."
--     REFERENCE
--         "See definition of RowStatus in RFC 2579, 'Textual Conventions for
--          SMIv2.'"
--     ::= { tnPortAccEgrQGrpEntry 2 }
--
-- tnPortAccEgrQGrpLastChgd OBJECT-TYPE
--     SYNTAX       TimeStamp
--     MAX-ACCESS   read-only
--     STATUS       current
--     DESCRIPTION
--         "The value of tnPortAccEgrQGrpLastChgd indicates the value of
--         sysUpTime when the queue entry was last modified."
--     ::= { tnPortAccEgrQGrpEntry 3 }
--
-- tnPortAccEgrQGrpSchedPol OBJECT-TYPE
--     SYNTAX       TNamedItemOrEmpty
--     MAX-ACCESS   read-create
--     STATUS       current
--     DESCRIPTION
--         "The value of tnPortAccEgrQGrpSchedPol specifies the name of the
--         scheduler-policy to be used with this port egress queue-group."
--     DEFVAL { ''H }
--     ::= { tnPortAccEgrQGrpEntry 4 }
--
-- tnPortAccEgrQGrpAggRateLimit   OBJECT-TYPE
--     SYNTAX          TPortSchedulerPIR
--     UNITS           "kbps"
--     MAX-ACCESS      read-create
--     STATUS          current
--     DESCRIPTION
--         "The value of tnPortAccEgrQGrpAggRateLimit specifies the maximum
--         total rate of all egress queues in this queue-group. The
--         value '-1' means that there is no limit."
--     DEFVAL          { -1 }
--     ::= { tnPortAccEgrQGrpEntry 5 }
--
-- tnPortAccEgrQGrpAcctgPolId OBJECT-TYPE
--     SYNTAX       Unsigned32 (0..99)
--     MAX-ACCESS   read-create
--     STATUS       current
--     DESCRIPTION
--         "The value of tnPortAccEgrQGrpAcctgPolId specifies the accounting-policy
--         to be used with this port egress queue-group.
--
--         A non-zero value indicates the tmnxLogApPolicyId index identifying the
--         policy entry in the tmnxLogApTable from the TIMETRA-LOG-MIB which is
--         associated with this queue-group.
--
--         The value zero indicates that the agent should use the default
--         accounting policy, if one exists."
--     DEFVAL { 0 }
--     ::= { tnPortAccEgrQGrpEntry 6 }
--
-- tnPortAccEgrQGrpCollectStats OBJECT-TYPE
--     SYNTAX       TruthValue
--     MAX-ACCESS   read-create
--     STATUS       current
--     DESCRIPTION
--         "The value of tnPortAccEgrQGrpCollectStats specifies whether
--         statistics should be collected on this port egress queue-group."
--     DEFVAL { false }
--     ::= { tnPortAccEgrQGrpEntry 7 }
--
-- tnPortAccEgrQGrpFrameBaseActg OBJECT-TYPE
--     SYNTAX       TruthValue
--     MAX-ACCESS   read-create
--     STATUS       current
--     DESCRIPTION
--         "The value of tnPortAccEgrQGrpFrameBaseActg specifies whether
--          to use frame-based accounting for this port egress queue-group.
--
--          If the value is 'false', the default packet-based accounting
--          method will be used."
--     DEFVAL { false }
--     ::= { tnPortAccEgrQGrpEntry 8 }
--
-- tnPortAccEgrQGrpDescr OBJECT-TYPE
--     SYNTAX       TItemDescription
--     MAX-ACCESS   read-create
--     STATUS       current
--     DESCRIPTION
--         "The value of tnPortAccEgrQGrpDescr specifies the description for
--         this port queue-group."
--     DEFVAL { ''H }
--     ::= { tnPortAccEgrQGrpEntry 9 }

--
--      Port queue policy overrides
--

-- tnPortAccEgrQOverTableLastChgd OBJECT-TYPE
--     SYNTAX       TimeStamp
--     MAX-ACCESS   read-only
--     STATUS       current
--     DESCRIPTION
--         "The value of tnPortAccEgrQOverTableLastChgd indicates the timestamp
--         of last change to the tnPortAccEgrQOverTable."
--     ::= { tnPortObjs 38 }
--
-- tnPortAccEgrQOverTable OBJECT-TYPE
--     SYNTAX      SEQUENCE OF TPortAccEgrQOverEntry
--     MAX-ACCESS  not-accessible
--     STATUS      current
--     DESCRIPTION
--         "The tnPortAccEgrQOverTable has an entry for each access port queue
--         override configured on this system."
--     ::= { tnPortObjs 39 }
--
-- tnPortAccEgrQOverEntry    OBJECT-TYPE
--     SYNTAX      TPortAccEgrQOverEntry
--     MAX-ACCESS  not-accessible
--     STATUS      current
--     DESCRIPTION
--         "Each row represents a particular port-queue override. Entries
--         are created and deleted by the user."
--     INDEX {  tnPortPortID,
--             tnPortAccEgrQGrpName, tnPortAccEgrQOverQueue }
--     ::= { tnPortAccEgrQOverTable 1}
--
-- TPortAccEgrQOverEntry ::= SEQUENCE
--     {
--         tnPortAccEgrQOverQueue              TEgressQueueId,
--         tnPortAccEgrQOverRowStatus          RowStatus,
--         tnPortAccEgrQOverLastChanged        TimeStamp,
--         tnPortAccEgrQOverCBS                TBurstSizeOverride,
--         tnPortAccEgrQOverMBS                TBurstSizeOverride,
--         tnPortAccEgrQOverHiPrioOnly         TBurstPercentOrDefaultOverride,
--         tnPortAccEgrQOverAdminPIR           TPIRRateOverride,
--         tnPortAccEgrQOverAdminCIR           TCIRRateOverride,
--         tnPortAccEgrQOverPIRAdaptation      TAdaptationRuleOverride,
--         tnPortAccEgrQOverCIRAdaptation      TAdaptationRuleOverride
--     }
--
-- tnPortAccEgrQOverQueue OBJECT-TYPE
--     SYNTAX       TEgressQueueId (1..8)
--     MAX-ACCESS   not-accessible
--     STATUS       current
--     DESCRIPTION
--         "The value of tnPortAccEgrQOverQueue specifies the queue ID which is
--         used as the fourth index to the table entry."
--     ::= { tnPortAccEgrQOverEntry 1 }
--
-- tnPortAccEgrQOverRowStatus  OBJECT-TYPE
--     SYNTAX      RowStatus
--     MAX-ACCESS  read-create
--     STATUS      current
--     DESCRIPTION
--         "The value of tnPortAccEgrQOverRowStatus is used for the
--          creation and deletion of port-queue overrides.
--
--         Row creation will fail if there is no entry in the
--         TIMETRA-QOS-MIB::tQosEgrQueueTable with the same index values as the
--         last two indices of this table
--         (tnPortAccEgrQGrpName.tnPortAccEgrQOverQueue)."
--     ::= { tnPortAccEgrQOverEntry 2 }
--
-- tnPortAccEgrQOverLastChanged  OBJECT-TYPE
--     SYNTAX      TimeStamp
--     MAX-ACCESS  read-only
--     STATUS      current
--     DESCRIPTION
--         "The value of tnPortAccEgrQOverLastChanged indicates the value
--         of sysUpTime at the time of the most recent management change to
--         this row."
--     ::= { tnPortAccEgrQOverEntry 3 }
--
-- tnPortAccEgrQOverCBS OBJECT-TYPE
--     SYNTAX       TBurstSizeOverride
--     UNITS        "kilo-bytes"
--     MAX-ACCESS   read-create
--     STATUS       current
--     DESCRIPTION
--         "The value of tnPortAccEgrQOverCBS specifies the amount of reserved
--         buffer space for the queue."
--     DEFVAL { -2 }
--     ::= { tnPortAccEgrQOverEntry 4 }
--
-- tnPortAccEgrQOverMBS OBJECT-TYPE
--     SYNTAX       TBurstSizeOverride
--     UNITS        "kilo-bytes"
--     MAX-ACCESS   read-create
--     STATUS       current
--     DESCRIPTION
--         "The value of tnPortAccEgrQOverMBS specifies the maximum amount of
--         buffer space allowed for the queue."
--     DEFVAL { -2 }
--     ::= { tnPortAccEgrQOverEntry 5 }
--
-- tnPortAccEgrQOverHiPrioOnly OBJECT-TYPE
--     SYNTAX       TBurstPercentOrDefaultOverride
--     MAX-ACCESS   read-create
--     STATUS       current
--     DESCRIPTION
--         "The value of tnPortAccEgrQOverHiPrioOnly specifies the percentage of
--         buffer space for the queue, used exclusively by high priority packets."
--     DEFVAL { -2 }
--     ::= { tnPortAccEgrQOverEntry 6 }
--
-- tnPortAccEgrQOverAdminPIR OBJECT-TYPE
--     SYNTAX       TPIRRateOverride
--     UNITS        "kbps"
--     MAX-ACCESS   read-create
--     STATUS       current
--     DESCRIPTION
--         "The value of tnPortAccEgrQOverAdminPIR specifies the administrative
--         PIR specified by the user."
--     DEFVAL { -2 }
--     ::= { tnPortAccEgrQOverEntry 7 }
--
-- tnPortAccEgrQOverAdminCIR OBJECT-TYPE
--     SYNTAX       TCIRRateOverride
--     UNITS        "kbps"
--     MAX-ACCESS   read-create
--     STATUS       current
--     DESCRIPTION
--         "The value of tnPortAccEgrQOverAdminCIR specifies the administrative
--         CIR specified by the user."
--     DEFVAL { -2 }
--     ::= { tnPortAccEgrQOverEntry 8 }
--
-- tnPortAccEgrQOverPIRAdaptation OBJECT-TYPE
--     SYNTAX       TAdaptationRuleOverride
--     MAX-ACCESS   read-create
--     STATUS       current
--     DESCRIPTION
--         "The value of tnPortAccEgrQOverPIRAdaptation specifies the adaptation
--          rule to be used while computing the operational PIR
--          value. The adaptation rule specifies the rules to compute the
--          operational values while maintaining minimum offset."
--     DEFVAL { noOverride }
--     ::= { tnPortAccEgrQOverEntry 9 }
--
-- tnPortAccEgrQOverCIRAdaptation OBJECT-TYPE
--     SYNTAX       TAdaptationRuleOverride
--     MAX-ACCESS   read-create
--     STATUS       current
--     DESCRIPTION
--         "The value of tnPortAccEgrQOverCIRAdaptation specifies the adaptation
--          rule to be used while computing the operational CIR
--          value. The adaptation rule specifies the rules to compute the
--          operational values while maintaining minimum offset."
--     DEFVAL { noOverride }
--     ::= { tnPortAccEgrQOverEntry 10 }

--
-- network egress queue group table
--

-- tnPortNetEgrQGrpTableLastChgd OBJECT-TYPE
--     SYNTAX       TimeStamp
--     MAX-ACCESS   read-only
--     STATUS       current
--     DESCRIPTION
--         "The value of tnPortNetEgrQGrpTableLastChgd indicates the
--         timestamp of last change to the tnPortNetEgrQGrpTable."
--     ::= { tnPortObjs 40 }
--
-- tnPortNetEgrQGrpTable OBJECT-TYPE
--     SYNTAX       SEQUENCE OF TPortNetEgrQGrpEntry
--     MAX-ACCESS   not-accessible
--     STATUS       current
--     DESCRIPTION
--         "The value of tnPortNetEgrQGrpTable defines network Egress Queue Group
--         Table for providing, via SNMP, the capability of defining the port
--         specific queue groups from the queue-groups existing in the
--         TIMETRA-QOS-MIB::tQosEgrQGroupTable."
--     ::= { tnPortObjs 41 }
--
-- tnPortNetEgrQGrpEntry OBJECT-TYPE
--     SYNTAX       TPortNetEgrQGrpEntry
--     MAX-ACCESS   not-accessible
--     STATUS       current
--     DESCRIPTION
--         "The value of tnPortNetEgrQGrpEntry defines an entry in the
--         tnPortNetEgrQGrpTable.
--
--         Entries are created/deleted in this table by SNMP sets to
--         tnPortNetEgrQGrpRowStatus."
--     INDEX {  tnPortPortID, tnPortNetEgrQGrpName }
--     ::= { tnPortNetEgrQGrpTable 1 }
--
-- TPortNetEgrQGrpEntry ::= SEQUENCE
--     {
--         tnPortNetEgrQGrpName             TNamedItem,
--         tnPortNetEgrQGrpRowStatus        RowStatus,
--         tnPortNetEgrQGrpLastChgd         TimeStamp,
--         tnPortNetEgrQGrpSchedPol         TNamedItemOrEmpty,
--         tnPortNetEgrQGrpAggRateLimit     TPortSchedulerPIR,
--         tnPortNetEgrQGrpAcctgPolId       Unsigned32,
--         tnPortNetEgrQGrpCollectStats     TruthValue,
--         tnPortNetEgrQGrpFrameBaseActg    TruthValue,
--         tnPortNetEgrQGrpDescr            TItemDescription
--     }
--
-- tnPortNetEgrQGrpName OBJECT-TYPE
--     SYNTAX       TNamedItem
--     MAX-ACCESS   not-accessible
--     STATUS       current
--     DESCRIPTION
--         "The value of tnPortNetEgrQGrpName defines the port Egress Queue
--         Group name.  It uniquely identifies a port egress queue group in the
--         managed system."
--     ::= { tnPortNetEgrQGrpEntry 1 }
--
-- tnPortNetEgrQGrpRowStatus OBJECT-TYPE
--     SYNTAX       RowStatus
--     MAX-ACCESS   read-create
--     STATUS       current
--     DESCRIPTION
--         "The value of tnPortNetEgrQGrpRowStatus allows entries to be
--         created and deleted in the tnPortNetEgrQGrpTable.
--
--         The creation of an entry in this table will succeed only if the
--         queue-group being created exist in TIMETRA-QOS-MIB::tQosEgrQGroupTable."
--     REFERENCE
--         "See definition of RowStatus in RFC 2579, 'Textual Conventions for
--          SMIv2.'"
--     ::= { tnPortNetEgrQGrpEntry 2 }
--
-- tnPortNetEgrQGrpLastChgd OBJECT-TYPE
--     SYNTAX       TimeStamp
--     MAX-ACCESS   read-only
--     STATUS       current
--     DESCRIPTION
--         "The value of tnPortNetEgrQGrpLastChgd indicates the value of
--         sysUpTime when the queue entry was last modified."
--     ::= { tnPortNetEgrQGrpEntry 3 }
--
-- tnPortNetEgrQGrpSchedPol OBJECT-TYPE
--     SYNTAX       TNamedItemOrEmpty
--     MAX-ACCESS   read-create
--     STATUS       current
--     DESCRIPTION
--         "The value of tnPortNetEgrQGrpSchedPol specifies the name of the
--         scheduler-policy to be used with this port egress queue-group."
--     DEFVAL { ''H }
--     ::= { tnPortNetEgrQGrpEntry 4 }
--
-- tnPortNetEgrQGrpAggRateLimit   OBJECT-TYPE
--     SYNTAX          TPortSchedulerPIR
--     UNITS           "kbps"
--     MAX-ACCESS      read-create
--     STATUS          current
--     DESCRIPTION
--         "The value of tnPortNetEgrQGrpAggRateLimit specifies the maximum
--         total rate of all egress queues in this queue-group. The
--         value '-1' means that there is no limit."
--     DEFVAL          { -1 }
--     ::= { tnPortNetEgrQGrpEntry 5 }
--
-- tnPortNetEgrQGrpAcctgPolId OBJECT-TYPE
--     SYNTAX       Unsigned32 (0..99)
--     MAX-ACCESS   read-create
--     STATUS       current
--     DESCRIPTION
--         "The value of tnPortNetEgrQGrpAcctgPolId specifies the accounting-policy
--         to be used with this port egress queue-group.
--
--         A non-zero value indicates the tmnxLogApPolicyId index identifying the
--         policy entry in the tmnxLogApTable from the TIMETRA-LOG-MIB which is
--         associated with this queue-group.
--
--         The value zero indicates that the agent should use the default
--         accounting policy, if one exists."
--     DEFVAL { 0 }
--     ::= { tnPortNetEgrQGrpEntry 6 }
--
-- tnPortNetEgrQGrpCollectStats OBJECT-TYPE
--     SYNTAX       TruthValue
--     MAX-ACCESS   read-create
--     STATUS       current
--     DESCRIPTION
--         "The value of tnPortNetEgrQGrpCollectStats specifies whether
--         statistics should be collected on this port egress queue-group."
--     DEFVAL { false }
--     ::= { tnPortNetEgrQGrpEntry 7 }
--
-- tnPortNetEgrQGrpFrameBaseActg    OBJECT-TYPE
--     SYNTAX       TruthValue
--     MAX-ACCESS   read-create
--     STATUS       current
--     DESCRIPTION
--         "The value of tnPortNetEgrQGrpFrameBaseActg specifies whether
--          to use frame-based accounting for this port egress queue-group.
--
--          If the value is 'false', the default packet-based accounting
--          method will be used."
--     DEFVAL { false }
--     ::= { tnPortNetEgrQGrpEntry 8 }
--
-- tnPortNetEgrQGrpDescr OBJECT-TYPE
--     SYNTAX       TItemDescription
--     MAX-ACCESS   read-create
--     STATUS       current
--     DESCRIPTION
--         "The value of tnPortNetEgrQGrpDescr specifies the description for
--         this port queue-group."
--     DEFVAL { ''H }
--     ::= { tnPortNetEgrQGrpEntry 9 }

--
--  network port queue policy overrides
--

-- tnPortNetEgrQOverTableLastChgd OBJECT-TYPE
--     SYNTAX       TimeStamp
--     MAX-ACCESS   read-only
--     STATUS       current
--     DESCRIPTION
--         "The value of tnPortNetEgrQOverTableLastChgd indicates the timestamp
--         of last change to the tnPortNetEgrQOverTable."
--     ::= { tnPortObjs 42 }
--
-- tnPortNetEgrQOverTable OBJECT-TYPE
--     SYNTAX      SEQUENCE OF TPortNetEgrQOverEntry
--     MAX-ACCESS  not-accessible
--     STATUS      current
--     DESCRIPTION
--         "The tnPortNetEgrQOverTable has an entry for each port queue override
--         configured on this system."
--     ::= { tnPortObjs 43 }
--
-- tnPortNetEgrQOverEntry    OBJECT-TYPE
--     SYNTAX      TPortNetEgrQOverEntry
--     MAX-ACCESS  not-accessible
--     STATUS      current
--     DESCRIPTION
--         "Each row represents a particular port-queue override. Entries
--         are created and deleted by the user."
--     INDEX {  tnPortPortID,
--             tnPortNetEgrQGrpName, tnPortNetEgrQOverQueue }
--     ::= { tnPortNetEgrQOverTable 1}
--
-- TPortNetEgrQOverEntry ::= SEQUENCE
--     {
--         tnPortNetEgrQOverQueue              TEgressQueueId,
--         tnPortNetEgrQOverRowStatus          RowStatus,
--         tnPortNetEgrQOverLastChanged        TimeStamp,
--         tnPortNetEgrQOverCBS                TBurstSizeOverride,
--         tnPortNetEgrQOverMBS                TBurstSizeOverride,
--         tnPortNetEgrQOverHiPrioOnly         TBurstPercentOrDefaultOverride,
--         tnPortNetEgrQOverAdminPIR           TPIRRateOverride,
--         tnPortNetEgrQOverAdminCIR           TCIRRateOverride,
--         tnPortNetEgrQOverPIRAdaptation      TAdaptationRuleOverride,
--         tnPortNetEgrQOverCIRAdaptation      TAdaptationRuleOverride
--     }
--
-- tnPortNetEgrQOverQueue OBJECT-TYPE
--     SYNTAX       TEgressQueueId (1..8)
--     MAX-ACCESS   not-accessible
--     STATUS       current
--     DESCRIPTION
--         "The value of tnPortNetEgrQOverQueue specifies the queue ID which is
--         used as the fourth index to the table entry."
--     ::= { tnPortNetEgrQOverEntry 1 }
--
-- tnPortNetEgrQOverRowStatus  OBJECT-TYPE
--     SYNTAX      RowStatus
--     MAX-ACCESS  read-create
--     STATUS      current
--     DESCRIPTION
--         "The value of tnPortNetEgrQOverRowStatus is used for the
--          creation and deletion of port-queue overrides.
--
--         Row creation will fail if there is no entry in the
--         TIMETRA-QOS-MIB::tQosEgrQueueTable with the same index values as the
--         last two indices of this table
--         (tnPortNetEgrQGrpName.tnPortNetEgrQOverQueue)."
--     ::= { tnPortNetEgrQOverEntry 2 }
--
-- tnPortNetEgrQOverLastChanged  OBJECT-TYPE
--     SYNTAX      TimeStamp
--     MAX-ACCESS  read-only
--     STATUS      current
--     DESCRIPTION
--         "The value of tnPortNetEgrQOverLastChanged indicates the value
--         of sysUpTime at the time of the most recent management change to
--         this row."
--     ::= { tnPortNetEgrQOverEntry 3 }
--
-- tnPortNetEgrQOverCBS OBJECT-TYPE
--     SYNTAX       TBurstSizeOverride
--     UNITS        "kilo-bytes"
--     MAX-ACCESS   read-create
--     STATUS       current
--     DESCRIPTION
--         "The value of tnPortNetEgrQOverCBS specifies the amount of reserved
--         buffer space for the queue."
--     DEFVAL { -2 }
--     ::= { tnPortNetEgrQOverEntry 4 }
--
-- tnPortNetEgrQOverMBS OBJECT-TYPE
--     SYNTAX       TBurstSizeOverride
--     UNITS        "kilo-bytes"
--     MAX-ACCESS   read-create
--     STATUS       current
--     DESCRIPTION
--         "The value of tnPortNetEgrQOverMBS specifies the maximum amount of
--         buffer space allowed for the queue."
--     DEFVAL { -2 }
--     ::= { tnPortNetEgrQOverEntry 5 }
--
-- tnPortNetEgrQOverHiPrioOnly OBJECT-TYPE
--     SYNTAX       TBurstPercentOrDefaultOverride
--     MAX-ACCESS   read-create
--     STATUS       current
--     DESCRIPTION
--         "The value of tnPortNetEgrQOverHiPrioOnly specifies the percentage of
--         buffer space for the queue, used exclusively by high priority packets."
--     DEFVAL { -2 }
--     ::= { tnPortNetEgrQOverEntry 6 }
--
-- tnPortNetEgrQOverAdminPIR OBJECT-TYPE
--     SYNTAX       TPIRRateOverride
--     UNITS        "kbps"
--     MAX-ACCESS   read-create
--     STATUS       current
--     DESCRIPTION
--         "The value of tnPortNetEgrQOverAdminPIR specifies the administrative
--         PIR specified by the user."
--     DEFVAL { -2 }
--     ::= { tnPortNetEgrQOverEntry 7 }
--
-- tnPortNetEgrQOverAdminCIR OBJECT-TYPE
--     SYNTAX       TCIRRateOverride
--     UNITS        "kbps"
--     MAX-ACCESS   read-create
--     STATUS       current
--     DESCRIPTION
--         "The value of tnPortNetEgrQOverAdminCIR specifies the administrative
--         CIR specified by the user."
--     DEFVAL { -2 }
--     ::= { tnPortNetEgrQOverEntry 8 }
--
-- tnPortNetEgrQOverPIRAdaptation OBJECT-TYPE
--     SYNTAX       TAdaptationRuleOverride
--     MAX-ACCESS   read-create
--     STATUS       current
--     DESCRIPTION
--         "The value of tnPortNetEgrQOverPIRAdaptation specifies the adaptation
--          rule to be used while computing the operational PIR
--          value. The adaptation rule specifies the rules to compute the
--          operational values while maintaining minimum offset."
--     DEFVAL { noOverride }
--     ::= { tnPortNetEgrQOverEntry 9 }
--
-- tnPortNetEgrQOverCIRAdaptation OBJECT-TYPE
--     SYNTAX       TAdaptationRuleOverride
--     MAX-ACCESS   read-create
--     STATUS       current
--     DESCRIPTION
--         "The value of tnPortNetEgrQOverCIRAdaptation specifies the adaptation
--          rule to be used while computing the operational CIR
--          value. The adaptation rule specifies the rules to compute the
--          operational values while maintaining minimum offset."
--     DEFVAL { noOverride }
--     ::= { tnPortNetEgrQOverEntry 10 }

--
--  Multi-Link Frame-Relay (MLFR) Bundle Table
--
--  Sparse Dependent Extension of the tnBundleTable.
--
--  The same indexes are used for both the base table tnBundleTable,
--  and the sparse dependent table, tnBundleMlfrTable.
--
--  This in effect extends the tnBundleTable with additional columns.
--  Rows are created in the tnBundleMlfrTable only for those entries
--  in the tnBundleTable for a value of 'mlfr' for the bundle type.
--
--  Deletion of a row in the tnBundleTable results in the
--  same fate for the row in the tnBundleMlfrTable.
--
-- tnBundleMlfrTable OBJECT-TYPE
--     SYNTAX      SEQUENCE OF TmnxBundleMlfrEntry
--     MAX-ACCESS  not-accessible
--     STATUS      current
--     DESCRIPTION
--         "The tnBundleMlfrTable contains MLFR specific data."
--     ::= { tnPortObjs 44 }
--
-- tnBundleMlfrEntry OBJECT-TYPE
--     SYNTAX      TmnxBundleMlfrEntry
--     MAX-ACCESS  not-accessible
--     STATUS      current
--     DESCRIPTION
--         "Each row entry contains data on an MLFR Bundle."
--     INDEX       {  tnBundleBundleID }
--     ::= { tnBundleMlfrTable 1 }
--
-- TmnxBundleMlfrEntry ::=
--     SEQUENCE {
--         tnBundleMlfrBundleId           SnmpAdminString,
--         tnBundleMlfrIngQoSProfId       TMcFrQoSProfileId,
--         tnBundleMlfrEgrQoSProfId       TMcFrQoSProfileId,
--         tnBundleMlfrHelloTimer         Unsigned32,
--         tnBundleMlfrHelloRetryCount    Unsigned32,
--         tnBundleMlfrAckTimer           Unsigned32,
--         tnBundleMlfrLastChanged        TimeStamp
--     }
--
-- tnBundleMlfrBundleId OBJECT-TYPE
--     SYNTAX      SnmpAdminString (SIZE (0..49))
--     MAX-ACCESS  read-create
--     STATUS      current
--     DESCRIPTION
--         "The value of tnBundleMlfrBundleId is the Bundle Identifier
--          sent with each Link Integrity Protocol message for each member
--          of a tnBundleBundleID.
--
--          The object tnPortAdminStatus must be set to 'outOfService' to
--          change this value."
--     DEFVAL { "" }
--     ::= { tnBundleMlfrEntry 1 }
--
-- tnBundleMlfrIngQoSProfId OBJECT-TYPE
--     SYNTAX      TMcFrQoSProfileId
--     MAX-ACCESS  read-create
--     STATUS      current
--     DESCRIPTION
--         "The value of tnBundleMlfrIngQoSProfId specifies the ingress
--          QoS profile to be used for the incoming traffic over this MLFR
--          bundle.
--
--          The value of tnBundleMlfrIngQoSProfId of 0 indicates
--          a default QoS profile is used as applicable to given hardware."
--     DEFVAL { 0 }
--     ::= { tnBundleMlfrEntry 4 }
--
-- tnBundleMlfrEgrQoSProfId OBJECT-TYPE
--     SYNTAX      TMcFrQoSProfileId
--     MAX-ACCESS  read-create
--     STATUS      current
--     DESCRIPTION
--         "The value of tnBundleMlfrEgrQoSProfId specifies the egress
--          QoS profile to be used for the outgoing traffic over this MLFR
--          bundle.
--
--          The value of tnBundleMlfrEgrQoSProfId of 0 indicates
--          a default profile is used as applicable to given hardware."
--     DEFVAL { 0 }
--     ::= { tnBundleMlfrEntry 5 }
--
-- tnBundleMlfrHelloTimer OBJECT-TYPE
--     SYNTAX      Unsigned32 (1..180)
--     UNITS       "seconds"
--     MAX-ACCESS  read-create
--     STATUS      current
--     DESCRIPTION
--         "The value of tnBundleMlfrHelloTimer specifies the rate
--          at which hello messages are sent across a member link."
--     DEFVAL { 10 }
--     ::= { tnBundleMlfrEntry 6 }
--
-- tnBundleMlfrHelloRetryCount OBJECT-TYPE
--     SYNTAX      Unsigned32 (1..5)
--     UNITS       "seconds"
--     MAX-ACCESS  read-create
--     STATUS      current
--     DESCRIPTION
--         "The value of tnBundleMlfrHelloTimer specifies the number
--          of times to attempt to resend hello messages when the
--          tnBundleMlfrAckTimer has expired before taking action."
--     DEFVAL { 2 }
--     ::= { tnBundleMlfrEntry 7 }
--
-- tnBundleMlfrAckTimer OBJECT-TYPE
--     SYNTAX      Unsigned32 (1..10)
--     UNITS       "seconds"
--     MAX-ACCESS  read-create
--     STATUS      current
--     DESCRIPTION
--         "The value of tnBundleMlfrAckTimer specifies the length
--          of time to wait for acknowledgment of a hello message
--          before declaring the hello message has not been received."
--     DEFVAL { 4 }
--     ::= { tnBundleMlfrEntry 8 }
--
-- tnBundleMlfrLastChanged    OBJECT-TYPE
--     SYNTAX      TimeStamp
--     MAX-ACCESS  read-only
--     STATUS      current
--     DESCRIPTION
--         "The value of tnBundleMlfrLastChanged indicates the value
--          of sysUpTime at the time of the most recent management change to
--          this row."
--     ::= { tnBundleMlfrEntry 9 }

--
--  FR Interface Table
--

-- tmnxFrIntfTable OBJECT-TYPE
--     SYNTAX  SEQUENCE OF TmnxFrIntfEntry
--     MAX-ACCESS  not-accessible
--     STATUS      current
--     DESCRIPTION
--         "The tmnxFrIntfTable has an entry for each port/channel in the
--          system that is configured for Frame Relay. It contains Frame Relay
--          configuration parameters."
--     ::= { tnFRObjs 2 }
--
-- tmnxFrIntfEntry       OBJECT-TYPE
--     SYNTAX      TmnxFrIntfEntry
--     MAX-ACCESS  not-accessible
--     STATUS      current
--     DESCRIPTION
--         "The Parameters for a particular FR Interface. Entries cannot be
--          created or deleted via SNMP SET operations.
--
--          Entries will exist in this table when tnPortEncapType is set
--          to frEncap."
--     INDEX   {  tnPortPortID }
--     ::= { tmnxFrIntfTable 1 }
--
-- TmnxFrIntfEntry ::=
--     SEQUENCE {
--         tmnxFrIntfFrf12Mode     TmnxEnabledDisabled,
--         tmnxFrIntfLinkId        SnmpAdminString,
--         tmnxFrIntfLastChanged   TimeStamp
--     }
--
-- tmnxFrIntfFrf12Mode OBJECT-TYPE
--     SYNTAX      TmnxEnabledDisabled
--     MAX-ACCESS  read-create
--     STATUS      current
--     DESCRIPTION
--         "The value of tmnxFrIntfFrf12Mode enables or disables the
--          use of FRF12 headers. This cannot be set to 'enabled'
--          for entries with a tnPortBundleNumber set or bundles with
--          a tnBundleType of mlfr."
--      DEFVAL { disabled }
--     ::= { tmnxFrIntfEntry 1 }
--
-- tmnxFrIntfLinkId OBJECT-TYPE
--     SYNTAX      SnmpAdminString (SIZE (0..49))
--     MAX-ACCESS  read-create
--     STATUS      current
--     DESCRIPTION
--         "The value of tmnxFrIntfLinkId is a Link Identifier
--          that is used when this entry is added to a MLFR bundle."
--     DEFVAL { "" }
--     ::= { tmnxFrIntfEntry 2 }
--
-- tmnxFrIntfLastChanged OBJECT-TYPE
--     SYNTAX      TimeStamp
--     MAX-ACCESS  read-only
--     STATUS      current
--     DESCRIPTION
--         "The value of tmnxFrIntfLastChanged indicates the value
--          of sysUpTime at the time of the most recent management change to
--          this row."
--     ::= { tmnxFrIntfEntry 3 }

--
-- Frame Relay Fragmentation (FRF12) Interface Table
--
-- tmnxFrf12IntfTable   OBJECT-TYPE
--     SYNTAX      SEQUENCE OF TmnxFrf12IntfEntry
--     MAX-ACCESS  not-accessible
--     STATUS      current
--     DESCRIPTION
--         "The tmnxFrf12IntfTable contains entries for a port/channel
--          that has frf12 mode 'enabled'."
--     ::= { tnFRObjs 3 }
--
-- tmnxFrf12IntfEntry       OBJECT-TYPE
--     SYNTAX      TmnxFrf12IntfEntry
--     MAX-ACCESS  not-accessible
--     STATUS      current
--     DESCRIPTION
--         "Each row represents a particular frame-relay interface that has
--          enabled frf12 on a port/channel.
--
--          Each row in this table is added/removed when frf12 is enabled
--          on a port/channel."
--     INDEX {  tnPortPortID }
--     ::= { tmnxFrf12IntfTable 1 }
--
-- TmnxFrf12IntfEntry ::=
--     SEQUENCE {
--         tmnxFrf12IntfFragmentThreshold     Unsigned32,
--         tmnxFrf12IntfEgrQoSProfId          TMcFrQoSProfileId,
--         tmnxFrf12IntfLastChanged           TimeStamp
--     }
--
-- tmnxFrf12IntfFragmentThreshold    OBJECT-TYPE
--     SYNTAX      Unsigned32(128..512)
--     MAX-ACCESS  read-create
--     STATUS      current
--     DESCRIPTION
--         "The value of tmnxFrf12IntfFragmentThreshold specifies the
--          maximum length of a fragment to be transmitted.
--          A value of 0 specifies no fragmentation."
--     DEFVAL      { 128 }
--     ::= { tmnxFrf12IntfEntry 1 }
--
-- tmnxFrf12IntfEgrQoSProfId    OBJECT-TYPE
--     SYNTAX      TMcFrQoSProfileId
--     MAX-ACCESS  read-create
--     STATUS      current
--     DESCRIPTION
--         "The value of tmnxFrf12IntfEgrQoSProfId specifies the egress
--          QoS profile to be used for the outgoing traffic over this frf12
--          frame-relay interface.
--
--          The value of tmnxFrf12IntfEgrQoSProfId of 0 indicates
--          a default QoS profile is used as applicable to given hardware."
--     DEFVAL      { 0 }
--     ::= { tmnxFrf12IntfEntry 2 }
--
-- tmnxFrf12IntfLastChanged    OBJECT-TYPE
--     SYNTAX      TimeStamp
--     MAX-ACCESS  read-only
--     STATUS      current
--     DESCRIPTION
--         "The value of tmnxFrf12IntfLastChanged indicates the value
--          of sysUpTime at the time of the most recent management change to
--          this row."
--     ::= { tmnxFrf12IntfEntry 3 }

-- ----------------------------------------
-- Ingress QoS Queue port Statistics Table
-- ----------------------------------------
-- tnPortIngQosQStatTable OBJECT-TYPE
--     SYNTAX          SEQUENCE OF TmnxPortIngQosQStatEntry
--     MAX-ACCESS      not-accessible
--     STATUS          current
--     DESCRIPTION     "A table that contains ingress QoS queue-group queue
--                      port statistics."
--     ::= { tnPortObjs 45 }
--
-- tnPortIngQosQStatEntry OBJECT-TYPE
--     SYNTAX          TmnxPortIngQosQStatEntry
--     MAX-ACCESS      not-accessible
--     STATUS          current
--     DESCRIPTION     "Ingress statistics about a specific port's
--                      QoS queue-group queue."
--     INDEX {  tnPortPortID,
--             tnPortAccIngQGrpName, tnPortIngQosQStatQueueId }
--     ::= { tnPortIngQosQStatTable 1 }
--
-- TmnxPortIngQosQStatEntry ::=
--     SEQUENCE {
--         tnPortIngQosQStatQueueId          TIngressQueueId,
--         tnPortIngQosQStatOffHiPrioPkts    Counter64,
--         tnPortIngQosQStatDpdHiPrioPkts    Counter64,
--         tnPortIngQosQStatOffLoPrioPkts    Counter64,
--         tnPortIngQosQStatDpdLoPrioPkts    Counter64,
--         tnPortIngQosQStatOffHiPrioOcts    Counter64,
--         tnPortIngQosQStatDpdHiPrioOcts    Counter64,
--         tnPortIngQosQStatOffLoPrioOcts    Counter64,
--         tnPortIngQosQStatDpdLoPrioOcts    Counter64,
--         tnPortIngQosQStatFwdInProfPkts    Counter64,
--         tnPortIngQosQStatFwdOutProfPkts   Counter64,
--         tnPortIngQosQStatFwdInProfOcts    Counter64,
--         tnPortIngQosQStatFwdOutProfOcts   Counter64,
--         tnPortIngQosQStatUncolPktsOff     Counter64,
--         tnPortIngQosQStatUncolOctsOff     Counter64
--     }
--
-- tnPortIngQosQStatQueueId OBJECT-TYPE
--     SYNTAX       TIngressQueueId (1..32)
--     MAX-ACCESS   not-accessible
--     STATUS       current
--     DESCRIPTION
--         "The value of tnPortIngQosQStatQueueId specifies the queue-group
--         queue ID which is used as the fourth index to the table entry."
--     ::= { tnPortIngQosQStatEntry 1 }
--
-- tnPortIngQosQStatOffHiPrioPkts OBJECT-TYPE
--     SYNTAX          Counter64
--     MAX-ACCESS      read-only
--     STATUS          current
--     DESCRIPTION
--        "The value of tnPortIngQosQStatOffHiPrioPkts indicates the number of
--        high priority packets, as determined by the port ingress QoS
--        policy, offered by the Pchip to the Qchip."
--     ::= { tnPortIngQosQStatEntry 2 }
--
-- tnPortIngQosQStatDpdHiPrioPkts OBJECT-TYPE
--     SYNTAX          Counter64
--     MAX-ACCESS      read-only
--     STATUS          current
--     DESCRIPTION
--         "The value of tnPortIngQosQStatDpdHiPrioPkts indicates the number of
--         high priority packets, as determined by the port ingress QoS
--         policy, dropped by the Qchip due to: MBS exceeded, buffer pool limit
--         exceeded, etc."
--     ::= { tnPortIngQosQStatEntry 3 }
--
-- tnPortIngQosQStatOffLoPrioPkts OBJECT-TYPE
--     SYNTAX          Counter64
--     MAX-ACCESS      read-only
--     STATUS          current
--     DESCRIPTION
--         "The value of tnPortIngQosQStatOffLoPrioPkts indicates the number of
--         low priority packets, as determined by the port ingress QoS
--         policy, offered by the Pchip to the Qchip."
--     ::= { tnPortIngQosQStatEntry 4 }
--
-- tnPortIngQosQStatDpdLoPrioPkts OBJECT-TYPE
--     SYNTAX          Counter64
--     MAX-ACCESS      read-only
--     STATUS          current
--     DESCRIPTION
--         "The value of tnPortIngQosQStatDpdLoPrioPkts indicates the number of
--         low priority packets, as determined by the port ingress QoS
--         policy, dropped by the Qchip due to: MBS exceeded, buffer pool limit
--         exceeded, etc."
--     ::= { tnPortIngQosQStatEntry 5 }
--
-- tnPortIngQosQStatOffHiPrioOcts OBJECT-TYPE
--     SYNTAX          Counter64
--     MAX-ACCESS      read-only
--     STATUS          current
--     DESCRIPTION
--         "The value of tnPortIngQosQStatOffHiPrioOcts indicates the number of
--         high priority octets, as determined by the port ingress QoS
--         policy, offered by the Pchip to the Qchip."
--     ::= { tnPortIngQosQStatEntry 6 }
--
-- tnPortIngQosQStatDpdHiPrioOcts OBJECT-TYPE
--     SYNTAX          Counter64
--     MAX-ACCESS      read-only
--     STATUS          current
--     DESCRIPTION
--         "The value of tnPortIngQosQStatDpdHiPrioOcts indicates the number of
--         high priority octets, as determined by the port ingress QoS
--         policy, dropped by the Qchip due to: MBS exceeded, buffer pool limit
--         exceeded, etc."
--     ::= { tnPortIngQosQStatEntry 7 }
--
-- tnPortIngQosQStatOffLoPrioOcts OBJECT-TYPE
--     SYNTAX          Counter64
--     MAX-ACCESS      read-only
--     STATUS          current
--     DESCRIPTION
--         "The value of tnPortIngQosQStatOffLoPrioOcts indicates the number of
--         low priority octets, as determined by the port ingress QoS
--         policy, offered by the Pchip to the Qchip."
--     ::= { tnPortIngQosQStatEntry 8 }
--
-- tnPortIngQosQStatDpdLoPrioOcts OBJECT-TYPE
--     SYNTAX          Counter64
--     MAX-ACCESS      read-only
--     STATUS          current
--     DESCRIPTION
--         "The value of tnPortIngQosQStatDpdLoPrioOcts indicates the number of
--         low priority octets, as determined by the port ingress QoS
--         policy, dropped by the Qchip due to: MBS exceeded, buffer pool limit
--         exceeded, etc."
--     ::= { tnPortIngQosQStatEntry 9 }
--
-- tnPortIngQosQStatFwdInProfPkts OBJECT-TYPE
--     SYNTAX          Counter64
--     MAX-ACCESS      read-only
--     STATUS          current
--     DESCRIPTION
--         "The value of tnPortIngQosQStatFwdInProfPkts indicates the number of
--         in-profile packets (rate below CIR) forwarded by the ingress Qchip."
--     ::= { tnPortIngQosQStatEntry 10 }
--
-- tnPortIngQosQStatFwdOutProfPkts OBJECT-TYPE
--     SYNTAX          Counter64
--     MAX-ACCESS      read-only
--     STATUS          current
--     DESCRIPTION
--         "The value of tnPortIngQosQStatFwdOutProfPkts indicates the number of
--         out-of-profile packets (rate above CIR) forwarded by the ingress Qchip."
--     ::= { tnPortIngQosQStatEntry 11 }
--
-- tnPortIngQosQStatFwdInProfOcts OBJECT-TYPE
--     SYNTAX          Counter64
--     MAX-ACCESS      read-only
--     STATUS          current
--     DESCRIPTION
--         "The value of tnPortIngQosQStatFwdInProfOcts indicates the number of
--         in-profile octets (rate below CIR) forwarded by the ingress Qchip."
--     ::= { tnPortIngQosQStatEntry 12 }
--
-- tnPortIngQosQStatFwdOutProfOcts OBJECT-TYPE
--     SYNTAX          Counter64
--     MAX-ACCESS      read-only
--     STATUS          current
--     DESCRIPTION
--         "The value of tnPortIngQosQStatFwdOutProfOcts indicates the number of
--         out-of-profile octets (rate above CIR) forwarded by the ingress Qchip."
--     ::= { tnPortIngQosQStatEntry 13 }
--
-- tnPortIngQosQStatUncolPktsOff OBJECT-TYPE
--     SYNTAX          Counter64
--     MAX-ACCESS      read-only
--     STATUS          current
--     DESCRIPTION
--         "The value of tnPortIngQosQStatUncolPktsOff indicates the number of
--         uncolored packets offered to the ingress Qchip."
--     ::= { tnPortIngQosQStatEntry 14 }
--
-- tnPortIngQosQStatUncolOctsOff OBJECT-TYPE
--     SYNTAX          Counter64
--     MAX-ACCESS      read-only
--     STATUS          current
--     DESCRIPTION
--         "The value of tnPortIngQosQStatUncolOctsOff indicates the number of
--         uncolored octets offered to the ingress Qchip."
--     ::= { tnPortIngQosQStatEntry 15 }

-- ----------------------------------------
-- Egress QoS Queue port Statistics Table
-- ----------------------------------------
-- tnPortEgrQosQStatTable OBJECT-TYPE
--     SYNTAX          SEQUENCE OF TmnxPortEgrQosQStatEntry
--     MAX-ACCESS      not-accessible
--     STATUS          current
--     DESCRIPTION     "A table that contains egress QoS queue-group queue
--                      port statistics."
--     ::= { tnPortObjs 46 }
--
-- tnPortEgrQosQStatEntry OBJECT-TYPE
--     SYNTAX          TmnxPortEgrQosQStatEntry
--     MAX-ACCESS      not-accessible
--     STATUS          current
--     DESCRIPTION     "Egress statistics about a specific port's
--                      QoS queue-group queue."
--     INDEX {  tnPortPortID,
--             tnPortAccEgrQGrpName, tnPortEgrQosQStatQueueId }
--     ::= { tnPortEgrQosQStatTable 1 }
--
-- TmnxPortEgrQosQStatEntry ::=
--     SEQUENCE {
--         tnPortEgrQosQStatQueueId          TEgressQueueId,
--         tnPortEgrQosQStatFwdInProfPkts    Counter64,
--         tnPortEgrQosQStatDpdInProfPkts    Counter64,
--         tnPortEgrQosQStatFwdOutProfPkts   Counter64,
--         tnPortEgrQosQStatDpdOutProfPkts   Counter64,
--         tnPortEgrQosQStatFwdInProfOcts    Counter64,
--         tnPortEgrQosQStatDpdInProfOcts    Counter64,
--         tnPortEgrQosQStatFwdOutProfOcts   Counter64,
--         tnPortEgrQosQStatDpdOutProfOcts   Counter64
--     }
--
-- tnPortEgrQosQStatQueueId OBJECT-TYPE
--     SYNTAX       TEgressQueueId (1..8)
--     MAX-ACCESS   not-accessible
--     STATUS       current
--     DESCRIPTION
--         "The value of tnPortEgrQosQStatQueueId specifies the queue-group
--         queue ID which is used as the fourth index to the table entry."
--     ::= { tnPortEgrQosQStatEntry 1 }
--
-- tnPortEgrQosQStatFwdInProfPkts OBJECT-TYPE
--     SYNTAX          Counter64
--     MAX-ACCESS      read-only
--     STATUS          current
--     DESCRIPTION
--         "The value of tnPortEgrQosQStatFwdInProfPkts indicates the number of
--         in-profile packets (rate below CIR) forwarded by the egress Qchip."
--     ::= { tnPortEgrQosQStatEntry 2 }
--
-- tnPortEgrQosQStatDpdInProfPkts OBJECT-TYPE
--     SYNTAX          Counter64
--     MAX-ACCESS      read-only
--     STATUS          current
--     DESCRIPTION
--         "The value of tnPortEgrQosQStatDpdInProfPkts indicates the number of
--         in-profile packets discarded by the egress Qchip due to: MBS exceeded,
--         buffer pool limit exceeded, etc."
--     ::= { tnPortEgrQosQStatEntry 3 }
--
-- tnPortEgrQosQStatFwdOutProfPkts OBJECT-TYPE
--     SYNTAX          Counter64
--     MAX-ACCESS      read-only
--     STATUS          current
--     DESCRIPTION
--         "The value of tnPortEgrQosQStatFwdOutProfPkts indicates the number of
--         out-of-profile packets (rate above CIR) forwarded by the egress Qchip."
--     ::= { tnPortEgrQosQStatEntry 4 }
--
-- tnPortEgrQosQStatDpdOutProfPkts OBJECT-TYPE
--     SYNTAX          Counter64
--     MAX-ACCESS      read-only
--     STATUS          current
--     DESCRIPTION
--         "The value of tnPortEgrQosQStatDpdOutProfPkts indicates the number of
--         out-of-profile packets discarded by the egress Qchip due to:
--         MBS exceeded, buffer pool limit exceeded, etc."
--     ::= { tnPortEgrQosQStatEntry 5 }
--
-- tnPortEgrQosQStatFwdInProfOcts OBJECT-TYPE
--     SYNTAX          Counter64
--     MAX-ACCESS      read-only
--     STATUS          current
--     DESCRIPTION
--         "The value of tnPortEgrQosQStatFwdInProfOcts indicates the number of
--         in-profile octets (rate below CIR) forwarded by the egress Qchip."
--     ::= { tnPortEgrQosQStatEntry 6 }
--
-- tnPortEgrQosQStatDpdInProfOcts OBJECT-TYPE
--     SYNTAX          Counter64
--     MAX-ACCESS      read-only
--     STATUS          current
--     DESCRIPTION
--         "The value of tnPortEgrQosQStatDpdInProfOcts indicates the number of
--         in-profile octets discarded by the egress Qchip due to:
--         MBS exceeded, buffer pool limit exceeded, etc."
--     ::= { tnPortEgrQosQStatEntry 7 }
--
-- tnPortEgrQosQStatFwdOutProfOcts OBJECT-TYPE
--     SYNTAX          Counter64
--     MAX-ACCESS      read-only
--     STATUS          current
--     DESCRIPTION
--         "The value of tnPortEgrQosQStatFwdOutProfOcts indicates the number of
--         out-of-profile octets (rate above CIR) forwarded by the egress Qchip."
--     ::= { tnPortEgrQosQStatEntry 8 }
--
-- tnPortEgrQosQStatDpdOutProfOcts OBJECT-TYPE
--     SYNTAX          Counter64
--     MAX-ACCESS      read-only
--     STATUS          current
--     DESCRIPTION
--         "The value of tnPortEgrQosQStatDpdOutProfOcts indicates the number of
--         out-of-profile octets discarded by the egress Qchip due to:
--         MBS exceeded, buffer pool limit exceeded, etc."
--     ::= { tnPortEgrQosQStatEntry 9 }

--
--  Network Port Egress Stats Per Queue Group Queue Table
--
-- tnPortNetEgrQStatTable OBJECT-TYPE
--     SYNTAX      SEQUENCE OF TmnxPortNetEgrQStatEntry
--     MAX-ACCESS  not-accessible
--     STATUS      current
--     DESCRIPTION
--         "Defines the Nokia 7x50 SR series network port egress
--          statistics table for providing, via SNMP, the capability of
--          retrieving the traffic statistics for the queue-group queues
--          being used for the ports to forward the network egress
--          traffic."
--     ::= { tnPortStatsObjs 5 }
--
-- tnPortNetEgrQStatEntry    OBJECT-TYPE
--     SYNTAX      TmnxPortNetEgrQStatEntry
--     MAX-ACCESS  not-accessible
--     STATUS      current
--     DESCRIPTION
--         "Defines an entry in tnPortNetEgrQStatTable. Entries are
--          created and deleted by the system depending on the queue policy
--          being used at the specific port."
--     INDEX   {  tnPortPortID,
--               tnPortNetEgrQGrpName, tnPortEgrQosQStatQueueId }
--     ::= { tnPortNetEgrQStatTable 1 }
--
-- TmnxPortNetEgrQStatEntry ::=
--     SEQUENCE {
--         tnPortNetEgrQFwdInProfPkts   Counter64,
--         tnPortNetEgrQFwdOutProfPkts  Counter64,
--         tnPortNetEgrQFwdInProfOcts   Counter64,
--         tnPortNetEgrQFwdOutProfOcts  Counter64,
--         tnPortNetEgrQDroInProfPkts   Counter64,
--         tnPortNetEgrQDroOutProfPkts  Counter64,
--         tnPortNetEgrQDroInProfOcts   Counter64,
--         tnPortNetEgrQDroOutProfOcts  Counter64
--     }
--
-- tnPortNetEgrQFwdInProfPkts OBJECT-TYPE
--     SYNTAX      Counter64
--     MAX-ACCESS  read-only
--     STATUS      current
--     DESCRIPTION
--         "The value of tnPortNetEgrQFwdInProfPkts indicates the number of
--         conforming network egress packets forwarded on this port using this
--         queue-group queue."
--     ::= { tnPortNetEgrQStatEntry 1 }
--
-- tnPortNetEgrQFwdOutProfPkts OBJECT-TYPE
--     SYNTAX      Counter64
--     MAX-ACCESS  read-only
--     STATUS      current
--     DESCRIPTION
--         "The value of tnPortNetEgrQFwdOutProfPkts indicates the number of
--         exceeding network egress packets forwarded on this port using this
--         queue-group queue."
--     ::= { tnPortNetEgrQStatEntry 2 }
--
-- tnPortNetEgrQFwdInProfOcts OBJECT-TYPE
--     SYNTAX      Counter64
--     MAX-ACCESS  read-only
--     STATUS      current
--     DESCRIPTION
--         "The value of tnPortNetEgrQFwdInProfOcts indicates the number of
--         conforming network egress octets forwarded on this port using this
--         queue-group queue."
--     ::= { tnPortNetEgrQStatEntry 3 }
--
-- tnPortNetEgrQFwdOutProfOcts OBJECT-TYPE
--     SYNTAX      Counter64
--     MAX-ACCESS  read-only
--     STATUS      current
--     DESCRIPTION
--         "The value of tnPortNetEgrQFwdOutProfOcts indicates the number of
--         exceeding network egress octets forwarded on this port using this
--         queue-group queue."
--     ::= { tnPortNetEgrQStatEntry 4 }
--
-- tnPortNetEgrQDroInProfPkts OBJECT-TYPE
--     SYNTAX      Counter64
--     MAX-ACCESS  read-only
--     STATUS      current
--     DESCRIPTION
--         "The value of tnPortNetEgrQDroInProfPkts indicates the number of
--         conforming network egress packets dropped on this port using this
--         queue-group queue."
--     ::= { tnPortNetEgrQStatEntry 5 }
--
-- tnPortNetEgrQDroOutProfPkts OBJECT-TYPE
--     SYNTAX      Counter64
--     MAX-ACCESS  read-only
--     STATUS      current
--     DESCRIPTION
--         "The value of tnPortNetEgrQDroOutProfPkts indicates the number of
--         exceeding network egress packets dropped on this port using this
--         queue-group queue."
--     ::= { tnPortNetEgrQStatEntry 6 }
--
-- tnPortNetEgrQDroInProfOcts OBJECT-TYPE
--     SYNTAX      Counter64
--     MAX-ACCESS  read-only
--     STATUS      current
--     DESCRIPTION
--         "The value of tnPortNetEgrQDroInProfOcts indicates the number of
--         conforming network egress octets dropped on this port using this
--         queue-group queue."
--     ::= { tnPortNetEgrQStatEntry 7 }
--
-- tnPortNetEgrQDroOutProfOcts OBJECT-TYPE
--     SYNTAX      Counter64
--     MAX-ACCESS  read-only
--     STATUS      current
--     DESCRIPTION
--         "The value of tnPortNetEgrQDroOutProfOcts indicates the number of
--         exceeding network egress octets dropped on this port using this
--         queue-group queue."
--     ::= { tnPortNetEgrQStatEntry 8 }

--
-- MLFR Member Table
--
--  Sparse Dependent Extension of the tnBundleMemberTable.
--
--  The same indexes are used for both the base table tnBundleMemberTable,
--  and the sparse dependent table, tnBundleMemberMlfrTable.
--
--  This in effect extends the tnBundleMemberTable with additional columns.
--  Rows are created in the tnBundleMemberMlfrTable only for those entries
--  in the tnBundleMemberTable that were created and have a value of 'mlfr'
--  for the bundle type.
--
--  Deletion of a row in the tnBundleMemberTable results in the
--  same fate for the row in the tnBundleMemberMlfrTable.
--

-- tnBundleMemberMlfrTable OBJECT-TYPE
--     SYNTAX      SEQUENCE OF TmnxBundleMemberMlfrEntry
--     MAX-ACCESS  not-accessible
--     STATUS      current
--     DESCRIPTION
--         "The tnBundleMemberMlfrTable has an entry for a
--          frame-relay link associated with an MLFR Bundle."
--     ::= { tnPortObjs 47 }
--
-- tnBundleMemberMlfrEntry  OBJECT-TYPE
--     SYNTAX      TmnxBundleMemberMlfrEntry
--     MAX-ACCESS  not-accessible
--     STATUS      current
--     DESCRIPTION
--         "Each row entry represents an frame-relay link associated with
--          a MLFR Bundle."
--     INDEX   { tnBundleBundleID, tnPortPortID }
--     ::= { tnBundleMemberMlfrTable 1 }
--
-- TmnxBundleMemberMlfrEntry ::=
--     SEQUENCE {
--         tnBundleMemberMlfrDownReason      TmnxMlfrLinkDownReason
--     }
--
-- tnBundleMemberMlfrDownReason    OBJECT-TYPE
--     SYNTAX      TmnxMlfrLinkDownReason
--     MAX-ACCESS  read-only
--     STATUS      current
--     DESCRIPTION
--         "The value of tnBundleMemberMlfrDownReason indicates the reason code for marking
--          the MLFR member link of the bundle to down (i.e. tnBundleMemberActive
--          will be set to false)."
--     ::= { tnBundleMemberMlfrEntry 1 }

--
-- PacketSwitch Port Table
--
-- This table can be used to find the all the ports that belong to a packetswitch
--

tnPacketSwitchPortTable OBJECT-TYPE
    SYNTAX          SEQUENCE OF TnPacketSwitchPortEntry
    MAX-ACCESS      not-accessible
    STATUS          current
    DESCRIPTION     "A table that can be used to find all the ports that belong to
                     packetswitch."
    ::= { tnPortObjs 99 }   -- Gap intentionally left to accomodate merges from future SAS releases.

tnPacketSwitchPortEntry OBJECT-TYPE
    SYNTAX          TnPacketSwitchPortEntry
    MAX-ACCESS      not-accessible
    STATUS          current
    DESCRIPTION     "Entries represent ports withing a packetswitch"
    INDEX           { tnSysSwitchId, tnPortPortID }
    ::= { tnPacketSwitchPortTable 1 }

TnPacketSwitchPortEntry ::=
    SEQUENCE {
        tnPacketSwitchPortName          TNamedItemOrEmpty
    }

tnPacketSwitchPortName        OBJECT-TYPE
    SYNTAX      TNamedItemOrEmpty
    MAX-ACCESS  read-only
    STATUS      current
    DESCRIPTION
        "This is a duplication of tnPortName and is only used to
         provide a mechanism for UI's to iterate through all
         the ports in a packetswitch.

         The textual name of the interface.  The value of this
         object should be the name of the interface as assigned by
         the local device and should be suitable for use in commands
         entered at the device's `console'.  This might be a text
         name, such as `le0' or 'sys171-2/1."
    ::= { tnPacketSwitchPortEntry 1 }

-- EMAC configuation Table
--
tnEMACTable OBJECT-TYPE
    SYNTAX          SEQUENCE OF TnEMACEntry
    MAX-ACCESS      not-accessible
    STATUS          current
    DESCRIPTION     "A table that can be used to configure EMAC."
    ::= { tnPortObjs 100 }

tnEMACEntry OBJECT-TYPE
    SYNTAX          TnEMACEntry
    MAX-ACCESS      not-accessible
    STATUS          current
    DESCRIPTION     "Entries for EMAC configuration"
    INDEX           { tnSysSwitchId, tnEMACID }
    ::= { tnEMACTable 1 }

TnEMACEntry ::=
    SEQUENCE {
        tnEMACID               TmnxPortID,
        tnEMACAcctPolicyId     Unsigned32
    }

    tnEMACID    OBJECT-TYPE
    SYNTAX      TmnxPortID
    MAX-ACCESS  not-accessible
    STATUS      current
    DESCRIPTION
        "tnEMACID is an index into this table. It maps this port to its
         entry in the mib-2 interfaces table."
    ::= { tnEMACEntry 1 }

    tnEMACAcctPolicyId  OBJECT-TYPE
    SYNTAX      Unsigned32 (0..99)
    MAX-ACCESS  read-write
    STATUS      current
    DESCRIPTION
        "The value of the accounting policy must be defined prior to associating
         the policy with the emac port. Accounting policies can only be
         associated with network ports.
         A non-zero value indicates the tmnxLogApPolicyId index identifying the
         policy entry in the tmnxLogApTable from the TIMETRA-LOG-MIB which is
         associated with this port.  A zero value indicates that there is no
         accounting policy associated with this port"
    DEFVAL { 0 }
    ::= { tnEMACEntry 2 }

--
-- PMAC configuation Table
--
tnPMACTable OBJECT-TYPE
    SYNTAX          SEQUENCE OF TnPMACEntry
    MAX-ACCESS      not-accessible
    STATUS          current
    DESCRIPTION     "A table that can be used to configure PMAC."
    ::= { tnPortObjs 101 }

tnPMACEntry OBJECT-TYPE
    SYNTAX          TnPMACEntry
    MAX-ACCESS      not-accessible
    STATUS          current
    DESCRIPTION     "Entries for PMAC configuration"
    INDEX           { tnSysSwitchId, tnPMACID }
    ::= { tnPMACTable 1 }

TnPMACEntry ::=
    SEQUENCE {
        tnPMACID               TmnxPortID,
        tnPMACAcctPolicyId     Unsigned32
    }

    tnPMACID    OBJECT-TYPE
    SYNTAX      TmnxPortID
    MAX-ACCESS  not-accessible
    STATUS      current
    DESCRIPTION
        "tnPMACID is an index into this table. It maps this port to its
         entry in the mib-2 interfaces table."
    ::= { tnPMACEntry 1 }

    tnPMACAcctPolicyId  OBJECT-TYPE
    SYNTAX      Unsigned32 (0..99)
    MAX-ACCESS  read-write
    STATUS      current
    DESCRIPTION
        "The value of the accounting policy must be defined prior to associating
         the policy with the pmac port. Accounting policies can only be
         associated with network ports.
         A non-zero value indicates the tmnxLogApPolicyId index identifying the
         policy entry in the tmnxLogApTable from the TIMETRA-LOG-MIB which is
         associated with this port.  A zero value indicates that there is no
         accounting policy associated with this port"
    DEFVAL { 0 }
    ::= { tnPMACEntry 2 }

--
-- MMAC configuation Table
--
tnMMACTable OBJECT-TYPE
    SYNTAX          SEQUENCE OF TnMMACEntry
    MAX-ACCESS      not-accessible
    STATUS          current
    DESCRIPTION     "A table that can be used to configure PMAC."
    ::= { tnPortObjs 102 }

tnMMACEntry OBJECT-TYPE
    SYNTAX          TnMMACEntry
    MAX-ACCESS      not-accessible
    STATUS          current
    DESCRIPTION     "Entries for MMAC configuration"
    INDEX           { tnSysSwitchId, tnMMACID }
    ::= { tnMMACTable 1 }

TnMMACEntry ::=
    SEQUENCE {
        tnMMACID               TmnxPortID,
        tnMMACAcctPolicyId     Unsigned32
    }

    tnMMACID    OBJECT-TYPE
    SYNTAX      TmnxPortID
    MAX-ACCESS  not-accessible
    STATUS      current
    DESCRIPTION
        "tnMMACID is an index into this table. It maps this port to its
         entry in the mib-2 interfaces table."
    ::= { tnMMACEntry 1 }

    tnMMACAcctPolicyId  OBJECT-TYPE
    SYNTAX      Unsigned32 (0..99)
    MAX-ACCESS  read-write
    STATUS      current
    DESCRIPTION
        "The value of the accounting policy must be defined prior to associating
         the policy with the mmac port. Accounting policies can only be
         associated with network ports.
         A non-zero value indicates the tmnxLogApPolicyId index identifying the
         policy entry in the tmnxLogApTable from the TIMETRA-LOG-MIB which is
         associated with this port.  A zero value indicates that there is no
         accounting policy associated with this port"
    DEFVAL { 0 }
    ::= { tnMMACEntry 2 }

--
--
--  Port Notification Objects
--
-- tnPortNotifyPortId  OBJECT-TYPE
--     SYNTAX      TmnxPortID
--     MAX-ACCESS  accessible-for-notify
--     STATUS      current
--     DESCRIPTION
--         "Used by tmnx port Notifications, the OID indicates the
--          port or sonet path associated with the alarm."
--     ::= { tnPortNotificationObjects 1 }
--
-- tnPortNotifySonetAlarmReason  OBJECT-TYPE
--     SYNTAX      INTEGER {
--                     notUsed (0),
--                     loc(1),
--                     lais(2),
--                     lrdi(3),
--                     ss1f(4),
--                     sb1err(5),
--                     lb2erSd(6),
--                     lb2erSf(7),
--                     slof(8),
--                     slos(9),
--                     stxptr(10),
--                     srxptr(11),
--                     lrei(12)
--                 }
--     MAX-ACCESS   accessible-for-notify
--     STATUS       current
--     DESCRIPTION
--         "Used by tmnx sonet Port Notifications, the value of
--          tnPortNotifySonetAlarmReason indicates the reason a sonet port
--          alarm has been raised."
--     ::= { tnPortNotificationObjects 2 }
--
-- tnPortNotifySonetPathAlarmReason  OBJECT-TYPE
--     SYNTAX      INTEGER {
--                     notUsed (0),
--                     pais(1),
--                     plop(2),
--                     prdi(3),
--                     pb3err(4),
--                     pplm(5),
--                     prei(6),
--                     puneq(7),
--                     plcd(8)
--                 }
--     MAX-ACCESS  accessible-for-notify
--     STATUS      current
--     DESCRIPTION
--         "Used by tmnx sonet path Notifications, the value of
--          tnPortNotifySonetPathAlarmReason indicates the reason a sonet path
--          alarm has been raised."
--     ::= { tnPortNotificationObjects 3 }
--
-- tnPortNotifyError  OBJECT-TYPE
--     SYNTAX      INTEGER {
--                     txClockError (1),
--                     rxClockError(2),
--                     txFifoError(3),
--                     laserError(4),
--                     miscError(5)
--                 }
--     MAX-ACCESS  accessible-for-notify
--     STATUS      current
--     DESCRIPTION
--         "Used by tnEqPortError notification, the value of
--          tnPortNotifyError indicates the reason a port has
--          an error."
--     ::= { tnPortNotificationObjects 4 }
--
-- tnPortNotifyDS3AlarmReason  OBJECT-TYPE
--     SYNTAX      INTEGER {
--                     notUsed (0),
--                     ais (1),
--                     los (2),
--                     oof (3),
--                     rai (4),
--                     looped (5)
--                 }
--     MAX-ACCESS   accessible-for-notify
--     STATUS       current
--     DESCRIPTION
--         "Used by tmnx DS3 Port Notifications, the value of
--          tnPortNotifyDS3AlarmReason indicates the reason a DS3 interface
--          alarm has been raised."
--     ::= { tnPortNotificationObjects 5 }
--
-- tnPortNotifyDS1AlarmReason  OBJECT-TYPE
--     SYNTAX      INTEGER {
--                     notUsed (0),
--                     ais (1),
--                     los (2),
--                     oof (3),
--                     rai (4),
--                     looped (5),
--                     berSd (6),
--                     berSf (7)
--                 }
--     MAX-ACCESS   accessible-for-notify
--     STATUS       current
--     DESCRIPTION
--         "Used by tmnx DS1 Port Notifications, the value of
--          tnPortNotifyDS1AlarmReason indicates the reason a DS1 interface
--          alarm has been raised."
--     ::= { tnPortNotificationObjects 6 }
--
-- tnPortNotifyBundleId  OBJECT-TYPE
--     SYNTAX      TmnxBundleID
--     MAX-ACCESS  accessible-for-notify
--     STATUS      current
--     DESCRIPTION
--         "Used by tmnx bundle Notifications, the value indicates the
--          bundle associated with the alarm."
--     ::= { tnPortNotificationObjects 7 }
--
-- tnPortNotifyEtherAlarmReason  OBJECT-TYPE
--     SYNTAX       TmnxPortEtherReportValue
--     MAX-ACCESS   accessible-for-notify
--     STATUS       current
--     DESCRIPTION
--         "Used by tmnx ethernet Port Notifications, the value of
--          tnPortNotifyEtherAlarmReason indicates the reason a ethernet port
--          alarm has been raised."
--     ::= { tnPortNotificationObjects 8 }
--
-- tnDDMFailedObject OBJECT-TYPE
--     SYNTAX      INTEGER {
--                     unknown                      (0),
--                     temperature-low-warning      (1),
--                     temperature-low-alarm        (2),
--                     temperature-high-warning     (3),
--                     temperature-high-alarm       (4),
--                     supplyVoltage-low-warning    (5),
--                     supplyVoltage-low-alarm      (6),
--                     supplyVoltage-high-warning   (7),
--                     supplyVoltage-high-alarm     (8),
--                     txBiasCurrent-low-warning    (9),
--                     txBiasCurrent-low-alarm     (10),
--                     txBiasCurrent-high-warning  (11),
--                     txBiasCurrent-high-alarm    (12),
--                     txOutputPower-low-warning   (13),
--                     txOutputPower-low-alarm     (14),
--                     txOutputPower-high-warning  (15),
--                     txOutputPower-high-alarm    (16),
--                     rxOpticalPower-low-warning  (17),
--                     rxOpticalPower-low-alarm    (18),
--                     rxOpticalPower-high-warning (19),
--                     rxOpticalPower-high-alarm   (20),
--                     aux1-low-warning            (21),
--                     aux1-low-alarm              (22),
--                     aux1-high-warning           (23),
--                     aux1-high-alarm             (24),
--                     aux2-low-warning            (25),
--                     aux2-low-alarm              (26),
--                     aux2-high-warning           (27),
--                     aux2-high-alarm             (28)
--                 }
--     MAX-ACCESS   accessible-for-notify
--     STATUS       current
--     DESCRIPTION
--         "Used by Digital Diagnostic Monitoring (DDM) Notifications, the
--          value of tnDDMFailedObject indicates which object of the
--          monitored SFP/XFP is in a failed or cleared threshold state."
--     ::= { tnPortNotificationObjects 9 }
--
--  tmnxDSXClockSyncStateObject  OBJECT-TYPE
--     SYNTAX       TmnxDSXClockSyncState
--     MAX-ACCESS   accessible-for-notify
--     STATUS       current
--     DESCRIPTION
--         "Used by tmnxDSXClockSyncStateChange.  The value of
--          tmnxDSXClockSyncStateObject indicates the clock sync state
--          of a DS3 or DS1 channel with clock source adaptive or
--          differential."
--     ::= { tnPortNotificationObjects 10 }
--
-- tnPortNotifyDescription  OBJECT-TYPE
--     SYNTAX       DisplayString
--     MAX-ACCESS   accessible-for-notify
--     STATUS       current
--     DESCRIPTION
--         "The object tnPortNotifyDescription is a printable character
--          string."
--     ::= { tnPortNotificationObjects 11 }

--
--  TIMETRA-PORT-MIB Notifications
--

--
--  Equipment Alarms
--
--  tnEqOobPortFailure   NOTIFICATION-TYPE
--     OBJECTS {
--         tnPortNotifyPortId
--     }
--     STATUS  obsolete
--     DESCRIPTION
--         "Generated when the out-of-band Ethernet port has failed.  On the
--          Nokia 7x50 SR system, the out-of-band port is the CPM management
--          interface.
--
--          This notification was made obsolete in the 2.1 release.
--
--          The Out-of-band, OOB, port is what id refered to as the
--          management port or cpm port.  It has an entry in ifTable
--          and linkup, linkDown and tnEqPortError notifications
--          are sent for the management port just as for any other
--          port in the system."
--     ::= { tnPortNotification 1 }
--
--  tnEqPortFailure  NOTIFICATION-TYPE
--     OBJECTS {
--         tnPortNotifyPortId
--     }
--     STATUS  obsolete
--     DESCRIPTION
--         "Generated when a port has failed.
--
--          This notification was made obsolete in the 2.1 release.
--
--          tnEqPortError is used instead of tnEqPortFailure.
--
--          Standard IETF linkDown notification is sent when a
--          physical port failure is detected.  tnEqPortError is
--          sent with a ASCII reason message when port errors are
--          detected.
--
--          It was originally intended that tnEqPortError be used
--          to report errors that do not cause port state change to
--          'down'.
--
--          tnEqPortFailure was intended to report errors that
--          do cause the port state change to 'down'.
--
--          However, in the implementation tnEqPortError is used
--          for both fatal and non-fatal errors."
--     ::= { tnPortNotification 2 }

-- tnEqPortSonetAlarm     NOTIFICATION-TYPE
--     OBJECTS {
--         tnPortNotifyPortId,
--         tnPortNotifySonetAlarmReason
--     }
--     STATUS  current
--     DESCRIPTION
--         "Generated when a SONET/SDH port alarm condition is detected.
--          It is generated only when the type of alarm being raised is enabled
--          in tnSonetReportAlarm."
--     ::= { tnPortNotification 4 }
--
-- tnEqPortSonetAlarmClear        NOTIFICATION-TYPE
--     OBJECTS {
--         tnPortNotifyPortId,
--         tnPortNotifySonetAlarmReason
--     }
--     STATUS  current
--     DESCRIPTION
--         "Generated when a SONET/SDH port alarm condition is cleared.
--          It is generated only when the type of alarm being cleared is enabled
--          in tnSonetReportAlarm."
--     ::= { tnPortNotification 5 }
--
-- tnEqPortSonetPathAlarm   NOTIFICATION-TYPE
--     OBJECTS {
--         tnPortNotifyPortId,
--         tnPortNotifySonetPathAlarmReason
--     }
--     STATUS  current
--     DESCRIPTION
--         "Generated when a SONET/SDH path alarm condition is detected.
--          It is generated only when the type of alarm being raised is enabled
--          in tnSonetPathReportAlarm."
--     ::= { tnPortNotification 6 }
--
-- tnEqPortSonetPathAlarmClear      NOTIFICATION-TYPE
--     OBJECTS {
--         tnPortNotifyPortId,
--         tnPortNotifySonetPathAlarmReason
--     }
--     STATUS  current
--     DESCRIPTION
--         "Generated when a SONET/SDH path alarm condition is cleared.
--          It is generated only when the type of alarm being cleared is enabled
--          in tnSonetPathReportAlarm."
--     ::= { tnPortNotification 7 }
--
-- tnEqPortSFPInserted NOTIFICATION-TYPE
--     OBJECTS {
--         tnPortNotifyPortId
--     }
--     STATUS  current
--     DESCRIPTION
--         "Generated when a SFP is inserted in the port."
--     ::= { tnPortNotification 8 }
--
-- tnEqPortSFPRemoved NOTIFICATION-TYPE
--     OBJECTS {
--         tnPortNotifyPortId
--     }
--     STATUS  current
--     DESCRIPTION
--         "Generated when a SFP is removed from the port."
--     ::= { tnPortNotification 9 }

--  tnEqPortWrongSFP NOTIFICATION-TYPE
--     OBJECTS {
--         tnPortNotifyPortId
--     }
--     STATUS  obsolete
--     DESCRIPTION
--         "Generated when a wrong type of SFP optics module
--          is plugged into a 1 Gig MDA, SONET MDA, or 100FX MDA.
--
--          Because of the large variety of SFPs now supported and
--          their different encoding schemes for compliance bits, the
--          check for wrong SFP has been removed. As a result,
--          tnEqPortWrongSFP notification is no longer generated.
--
--          However, wrong SFP can be inferred from port statistics."
--     ::= { tnPortNotification 10 }
--
-- tnEqPortSFPCorrupted  NOTIFICATION-TYPE
--     OBJECTS {
--         tnPortNotifyPortId
--     }
--     STATUS  obsolete
--     DESCRIPTION
--         "Generated when SFP information stored in the EPROM
--          on the SFP is corrupt. This notification was made
--          obsolete for revision 6.0 on Nokia 7x50 SR series
--          systems; it was replaced by tnEqPortSFPStatusFailure."
--     ::= { tnPortNotification 11 }
--
--  tnPortNotifyBerSdTca NOTIFICATION-TYPE
--     OBJECTS {
--         tnPortNotifyPortId,
--         tnSonetBerSdThreshold
--     }
--     STATUS  obsolete
--     DESCRIPTION
--         "Generated when a SONET/SDH port's signal degradation bit error
--          rate is greater than the configured error rate threshold.
--
--          This notification was made obsolete in the 2.1 release."
--         ::= { tnPortNotification 12 }
--
--  tnPortNotifyBerSfTca NOTIFICATION-TYPE
--     OBJECTS {
--         tnPortNotifyPortId,
--         tnSonetBerSfThreshold
--     }
--     STATUS  obsolete
--     DESCRIPTION
--         "Generated when a SONET/SDH port's signal failure bit error
--          rate is greater than the configured error rate threshold.
--
--          This notification was made obsolete in the 2.1 release."
--     ::= { tnPortNotification 13 }

-- tnEqPortError NOTIFICATION-TYPE
--     OBJECTS {
--         tnPortNotifyPortId,
--         tnPortNotifyError
--     }
--     STATUS  current
--     DESCRIPTION
--         "Generated when an error listed in tnPortNotifyError
--          is detected on the port."
--     ::= { tnPortNotification 14 }
--
-- tnEqPortDS3Alarm   NOTIFICATION-TYPE
--     OBJECTS {
--         tnPortNotifyPortId,
--         tnPortNotifyDS3AlarmReason
--     }
--     STATUS  current
--     DESCRIPTION
--         "Generated when a DS3 interface alarm condition is detected.
--          It is generated only when the type of alarm being raised is enabled
--          in tnDS3ChannelReportAlarm."
--     ::= { tnPortNotification 15 }
--
-- tnEqPortDS3AlarmClear      NOTIFICATION-TYPE
--     OBJECTS {
--         tnPortNotifyPortId,
--         tnPortNotifyDS3AlarmReason
--     }
--     STATUS  current
--     DESCRIPTION
--         "Generated when a DS3 interface alarm condition is cleared.
--          It is generated only when the type of alarm being cleared is enabled
--          in tnDS3ChannelReportAlarm."
--     ::= { tnPortNotification 16 }
--
-- tnEqPortDS1Alarm   NOTIFICATION-TYPE
--     OBJECTS {
--         tnPortNotifyPortId,
--         tnPortNotifyDS1AlarmReason
--     }
--     STATUS  current
--     DESCRIPTION
--         "Generated when a DS1 interface alarm condition is detected.
--          It is generated only when the type of alarm being raised is enabled
--          in tnDS1ReportAlarm."
--     ::= { tnPortNotification 17 }
--
-- tnEqPortDS1AlarmClear      NOTIFICATION-TYPE
--     OBJECTS {
--         tnPortNotifyPortId,
--         tnPortNotifyDS1AlarmReason
--     }
--     STATUS  current
--     DESCRIPTION
--         "Generated when a DS1 interface alarm condition is cleared.
--          It is generated only when the type of alarm being cleared is enabled
--          in tnDS1ReportAlarm."
--     ::= { tnPortNotification 18 }

-- tnEqPortBndlYellowDiffExceeded   NOTIFICATION-TYPE
--    OBJECTS {
--        tnPortNotifyPortId,
--        tnBundleYellowDiffDelay
--    }
--    STATUS  current
--    DESCRIPTION
--        "Generated when the differential delay of a port in the bundle
--         exceeds the configured value in tnBundleYellowDiffDelay."
--    ::= { tnPortNotification 19 }

-- tnEqPortBndlRedDiffExceeded   NOTIFICATION-TYPE
--    OBJECTS {
--        tnPortNotifyPortId,
--        tnBundleRedDiffDelay
--    }
--    STATUS  current
--    DESCRIPTION
--        "Generated when the differential delay of a port in the bundle
--         exceeds the configured value in tnBundleRedDiffDelay."
--    ::= { tnPortNotification 20 }

-- tnEqPortBndlBadEndPtDiscr  NOTIFICATION-TYPE
--    OBJECTS {
--        tnBundleMemberDownReason
--    }
--    STATUS  current
--    DESCRIPTION
--        "Generated when the port detected mismatched peer endpoint
--         discriminator for the bundle."
--    ::= { tnPortNotification 21 }

-- tnEqPortEtherAlarm     NOTIFICATION-TYPE
--     OBJECTS {
--         tnPortNotifyPortId,
--         tnPortNotifyEtherAlarmReason
--     }
--     STATUS  current
--     DESCRIPTION
--         "tnEqPortEtherAlarm is generated when a ethernet port alarm
--          condition is detected. It is generated only when the type of
--          alarm being raised is enabled in tnPortEtherReportAlarm."
--     ::= { tnPortNotification 22 }
--
-- tnEqPortEtherAlarmClear        NOTIFICATION-TYPE
--     OBJECTS {
--         tnPortNotifyPortId,
--         tnPortNotifyEtherAlarmReason
--     }
--     STATUS  current
--     DESCRIPTION
--         "tnEqPortEtherAlarmClear is generated when a ethernet port alarm
--          condition is cleared. It is generated only when the type of alarm
--          being cleared is enabled in tnPortEtherReportAlarm."
--     ::= { tnPortNotification 23 }

-- tnDS1E1LoopbackStarted        NOTIFICATION-TYPE
--    OBJECTS {
--        tnPortNotifyPortId,
--        tnDS1Loopback
--    }
--    STATUS          current
--    DESCRIPTION
--        "The tnDS1E1LoopbackStarted notification is generated when a
--         loopback is provisioned on a DS1/E1 port."
--    ::= { tnPortNotification 24 }

-- tnDS1E1LoopbackStopped NOTIFICATION-TYPE
--    OBJECTS {
--        tnPortNotifyPortId,
--        tnDS1Loopback
--    }
--    STATUS          current
--    DESCRIPTION
--        "The tnDS1E1LoopbackStopped notification is generated when a
--         loopback is removed on a DS1/E1 port. The value of
--         tnSonetLoopback specifies the type of loopback that was
--         configured and has now been removed."
--    ::= { tnPortNotification 25 }

-- tnDS3E3LoopbackStarted NOTIFICATION-TYPE
--    OBJECTS {
--        tnPortNotifyPortId,
--        tnDS3ChannelLoopback
--    }
--    STATUS          current
--    DESCRIPTION
--        "The tnDS3E3LoopbackStarted notification is generated when a
--         loopback is provisioned on a DS3/E3 port."
--    ::= { tnPortNotification 26 }

-- tnDS3E3LoopbackStopped NOTIFICATION-TYPE
--    OBJECTS {
--        tnPortNotifyPortId,
--        tnDS3ChannelLoopback
--    }
--    STATUS          current
--    DESCRIPTION
--        "The tnDS3E3LoopbackStopped notification is generated when a
--         loopback is removed on a DS3/E3 port. The value of
--         tnDS3ChannelLoopback specifies the type of loopback that was
--         configured and has now been removed."
--    ::= { tnPortNotification 27 }

-- tnSonetSDHLoopbackStarted NOTIFICATION-TYPE
--     OBJECTS {
--         tnPortNotifyPortId,
--         tnSonetLoopback
--     }
--     STATUS          current
--     DESCRIPTION
--         "The tnSonetSDHLoopbackStarted notification is generated when a
--          loopback is provisioned on a Sonet-SDH port."
--     ::= { tnPortNotification 28 }
--
-- tnSonetSDHLoopbackStopped NOTIFICATION-TYPE
--     OBJECTS {
--         tnPortNotifyPortId,
--         tnSonetLoopback
--     }
--     STATUS          current
--     DESCRIPTION
--         "The tnSonetSDHLoopbackStopped notification is generated when a
--          loopback test is removed on a Sonet-SDH port. The value of
--          tnDS1Loopback specifies the type of loopback that was
--          configured and has now been removed."
--     ::= { tnPortNotification 29 }

--
--  Down-when-looped Alarm
--
-- tnEqPortEtherLoopDetected  NOTIFICATION-TYPE
--     OBJECTS {
--         tnPortNotifyPortId
--     }
--     STATUS  current
--     DESCRIPTION
--         "The tnEqPortEtherLoopDetected notification is genereated when
--          down-when-looped detects an Ethernet port is receiving PDUs that
--          it transmitted and tnPortEtherDownWhenLoopedEnabled is set to
--          'true'."
--     ::= { tnPortNotification 30 }
--
-- tnEqPortEtherLoopCleared  NOTIFICATION-TYPE
--     OBJECTS {
--         tnPortNotifyPortId
--     }
--     STATUS  current
--     DESCRIPTION
--         "The tnEqPortEtherLoopCleared notification is generated when
--          down-when-looped detects an Ethernet port has stopped receiving
--          PDUs that it transmitted and tnPortEtherDownWhenLoopedEnabled
--          is set to 'true'.  Setting tnPortEtherDownWhenLoopedEnabled to
--          'false' will also cause this notification to be generated if
--          tnEqPortEtherLoopDetected had previously been raised."
--     ::= { tnPortNotification 31 }
--
-- tnEqPortSpeedCfgNotCompatible  NOTIFICATION-TYPE
--     OBJECTS {
--         tnPortNotifyPortId,
--         tnPortEtherSpeed
--     }
--     STATUS  current
--     DESCRIPTION
--         "Generated when a supported MDA is inserted into a slot of an
--          IOM, the MDA is compatible with the currently provisioned MDA,
--          but the currently configured speed on an MDA port is not
--          compatible with the inserted MDA."
--     ::= { tnPortNotification 32 }
--
-- tnEqPortDuplexCfgNotCompatible  NOTIFICATION-TYPE
--     OBJECTS {
--         tnPortNotifyPortId,
--         tnPortEtherDuplex
--     }
--     STATUS  current
--     DESCRIPTION
--         "Generated when a supported MDA is inserted into a slot of an
--          IOM, the MDA is compatible with the currently provisioned MDA,
--          but the currently configured duplex on an MDA port is not
--          compatible with the inserted MDA."
--     ::= { tnPortNotification 33 }
--
-- tnEqPortIngressRateCfgNotCompatible  NOTIFICATION-TYPE
--     OBJECTS {
--         tnPortNotifyPortId
--     }
--     STATUS  current
--     DESCRIPTION
--         "Generated when a supported MDA is inserted into a slot of an
--          IOM, the MDA is compatible with the currently provisioned MDA,
--          but the currently configured ingress rate on an MDA port is not
--          compatible with the inserted MDA."
--     ::= { tnPortNotification 34 }
--
-- tnEqDigitalDiagMonitorFailure NOTIFICATION-TYPE
--     OBJECTS {
--         tnPortNotifyPortId,
--         tnDDMFailedObject
--     }
--     STATUS  current
--     DESCRIPTION
--         "Generated when an SFP/XFP that supports Digital Diagnostic
--          Monitoring (DDM) enters a failed state."
--     ::= { tnPortNotification 35 }
--
-- tnEqPortSFPStatusFailure NOTIFICATION-TYPE
--     OBJECTS {
--         tnPortNotifyPortId,
--         tnPortSFPStatus
--     }
--     STATUS  current
--     DESCRIPTION
--         "Generated when the tnPortSFPStatus of an SFP/XFP results in
--          a value other than 'not-equipped (0)', or 'operational (1)'.
--          tnEqPortSFPStatusFailure obsoleted tnEqPortSFPCorrupted for
--          revision 6.0 on Nokia 7x50 SR series systems."
--     ::= { tnPortNotification 36 }
--
-- tmnxDSXClockSyncStateChange NOTIFICATION-TYPE
--     OBJECTS {
--         tnPortNotifyPortId,
--         tmnxDSXClockSyncStateObject
--     }
--     STATUS  current
--     DESCRIPTION
--         "Generated when the tnDS3ChannelClockSyncState changes for a DS3 or
--          DS1 channel with adaptive or differentical clock source."
--     ::= { tnPortNotification 37 }

--
--  Quality of Service Alarm
--
-- tnQosServiceDegraded     NOTIFICATION-TYPE
--     OBJECTS {
--         tnPortNotifyPortId
--     }
--     STATUS  obsolete
--     DESCRIPTION
--         "Generated when the port is unable to provided the specified
--          quality of service level."
--     ::= { tnPortNotification 3 }

--
--  Functional Alarm
--

-- tnPortUnsupportedFunction NOTIFICATION-TYPE
--     OBJECTS {
--         tnPortNotifyPortId,
--         tnPortNotifyDescription
--     }
--     STATUS  current
--     DESCRIPTION
--         "Generated when a functionality is required from this port that it
--          cannot support.
--
--          The object tnPortNotifyDescription explains what function is affected."
--     ::= { tnPortNotification 38 }

-- tnBundleMemberMlfrLoopback     NOTIFICATION-TYPE
--     OBJECTS {
--         tnBundleMemberMlfrDownReason
--     }
--     STATUS  current
--     DESCRIPTION
--         "Generated when a Multilink Frame-Relay Bundle Member enters or leaves
--          the 'loopback (3)' state."
--     ::= { tnPortNotification 39 }

--%%%%%%%%%%%%%%%%%%%%%%%%%%%%%%%%%%%%%%%%%%%%%%%%%%%%%%%%%%%%%%%%%%%%%
--
--      The compliance specifications.
--

-- tnPortCompliances     OBJECT IDENTIFIER ::= { tnPortConformance 1 }
-- tnPortGroups            OBJECT IDENTIFIER ::= { tnPortConformance 2 }

-- tnPortComp7750        OBJECT IDENTIFIER ::= { tnPortCompliances 3 }
--  tnPortComp7750V3v0  OBJECT IDENTIFIER ::= { tnPortComp7750 1}

-- tnPortComp7450        OBJECT IDENTIFIER ::= { tnPortCompliances 4 }
--  tnPortComp7450V3v0  OBJECT IDENTIFIER ::= { tnPortComp7450 1 }

-- tnPortComp7710        OBJECT IDENTIFIER ::= { tnPortCompliances 5 }
--  tnPortComp7710V3v0  OBJECT IDENTIFIER ::= { tnPortComp7710 1 }

-- tnPortCompliance  MODULE-COMPLIANCE
--    ::= { tnPortCompliances 1 }

-- tnPortR2r1Compliance  MODULE-COMPLIANCE
--    ::= { tnPortCompliances 2 }

-- tnPortComp7750V3v0  MODULE-COMPLIANCE
--    ::= { tnPortComp7750 1 }

-- tnPortComp7750V4v0  MODULE-COMPLIANCE
--    STATUS  obsolete
--    DESCRIPTION
--            "The compliance statement for revision 4.0 of TIMETRA-PORT-MIB on
--             the Nokia 7750 SR series systems.
--
--             tmnxMlImaBundleGroup was added as of R4."
--    MODULE  this module
--        MANDATORY-GROUPS {
--            tnPortGroupV4v0,
--            tnPortEthernetV3v0Group,
--            tnPortSonetV3v0Group,
--            tnPortTDMGroupV4v0,
--            tnPortFRGroup,
--            tnQosAppObjsGroup,
--            tnPortTestGroup,
--            tnPortNotificationGroupV3v0,
--            tnPortIngrMdaQosStatR2r1Group,
--            tnPortATMGroupV4v0,
--            tnPortStatsR2r1Group,
--            tnCiscoHDLCGroup,
--            tmnxScalarPortV3v0Group,
--            tmnxMlBundleGroupV4v0,
--            tmnxMlImaBundleGroup
--        }
--    ::= { tnPortComp7750 2 }

-- tnPortComp7750V5v0  MODULE-COMPLIANCE
--    STATUS  obsolete
--    DESCRIPTION
--            "The compliance statement for revision 5.0 of TIMETRA-PORT-MIB on
--             the Nokia 7750 SR series systems."
--    MODULE  this module
--        MANDATORY-GROUPS {
--            tnPortGroupV5v0,
--            tnPortSonetV3v0Group,
--            tnPortTDMGroupV5v0,
--            tnPortFRGroup,
--            tnQosAppObjsGroup,
--            tnPortTestGroup,
--            tnPortNotificationGroupV5v0,
--            tnPortIngrMdaQosStatR2r1Group,
--            tnPortATMGroupV4v0,
--            tnPortStatsR2r1Group,
--            tnCiscoHDLCGroup,
--            tmnxScalarPortV3v0Group,
--            tmnxMlBundleGroupV5v0,
--            tmnxMlImaBundleGroup,
--            tnPortSchedV5v0Group,
--            tnPortEthernetV5v0Group
--        }
--    ::= { tnPortComp7750 3 }

-- tnPortComp7750V6v0  MODULE-COMPLIANCE
--    STATUS  obsolete
--    DESCRIPTION
--            "The compliance statement for revision 6.0 of TIMETRA-PORT-MIB on
--             the Nokia 7750 SR series systems."
--    MODULE  this module
--        MANDATORY-GROUPS {
--            tnPortGroupV6v0,
--            tnPortSonetV3v0Group,
--            tnPortTDMGroupV6v0,
--            tnPortFRGroup,
--            tnQosAppObjsGroup,
--            tnPortTestGroup,
--            tnPortNotificationGroupV6v0,
--            tnPortIngrMdaQosStatR2r1Group,
--            tnPortATMGroupV4v0,
--            tnPortStatsR2r1Group,
--            tnCiscoHDLCGroup,
--            tmnxScalarPortV3v0Group,
--            tmnxMlBundleGroupV6v0,
--            tmnxMlImaBundleGroup,
--            tnPortSchedV5v0Group,
--            tnPortEthernetV6v0Group,
--            tnPortCemGroupV6v0,
--            tnMcMlpppBundleGroup,
--            tmnxMlpppBundleGroup,
--            tnHsmdaGroupV6v0,
--            tnDigitalDiagMonitorGroup
--        }
--    ::= { tnPortComp7750 4 }

-- tnPortComp7750V6v1  MODULE-COMPLIANCE
--    STATUS  obsolete
--    DESCRIPTION
--            "The compliance statement for revision 6.0 of TIMETRA-PORT-MIB on
--             the Nokia 7750 SR series systems."
--    MODULE  this module
--        MANDATORY-GROUPS {
--            tnPortGroupV6v0,
--            tnPortSonetV3v0Group,
--            tnPortTDMGroupV6v0,
--            tnPortTDME1GroupV6v1,
--            tnPortFRGroup,
--            tnQosAppObjsGroup,
--            tnPortTestGroup,
--            tnPortNotificationGroupV6v0,
--            tnPortIngrMdaQosStatR2r1Group,
--            tnPortATMGroupV4v0,
--            tnPortStatsR2r1Group,
--            tnCiscoHDLCGroup,
--            tmnxScalarPortV3v0Group,
--            tmnxMlBundleGroupV6v0,
--            tmnxMlImaBundleGroup,
--            tnPortSchedV5v0Group,
--            tnPortEthernetV6v1Group,
--            tnPortCemGroupV6v0,
--            tnMcMlpppBundleGroup,
--            tmnxMlpppBundleGroup,
--            tnHsmdaGroupV6v0,
--            tmnxNamedPoolGroupV6v0,
--            tnDigitalDiagMonitorGroup
--        }
--    ::= { tnPortComp7750 5 }

-- tnPortComp7750V7v0  MODULE-COMPLIANCE
--    STATUS  current
--    DESCRIPTION
--            "The compliance statement for revision 6.0 of TIMETRA-PORT-MIB on
--             the Nokia 7750 SR series systems."
--    MODULE  this module
--        MANDATORY-GROUPS {
--            tnPortGroupV7v0,
--            tnPortSonetV3v0Group,
--            tnPortTDMGroupV7v0,
--            tnPortFRGroup,
--            tnQosAppObjsGroup,
--            tnPortTestGroup,
--            tnPortNotificationGroupV7v0,
--            tnPortIngrMdaQosStatR2r1Group,
--            tnPortATMGroupV7v0,
--            tnPortStatsR2r1Group,
--            tnCiscoHDLCGroup,
--            tnScalarPortV3v0Group,
--            tnMlBundleGroupV6v0,
--            tnMlImaBundleGroup,
--            tnPortSchedV5v0Group,
--            tnPortEthernetV7v0Group,
--            tnPortCemGroupV6v0,
--            tnMcMlpppBundleGroup,
--            tnMlpppBundleGroup,
--            tnMlpppBundleGroupV7v0,
--            tnHsmdaGroupV6v0,
--            tmnxNamedPoolGroupV6v0,
--            tnDigitalDiagMonitorGroup,
--            tnPortQV7v0Group,
--            tnPortQStatV7v0Group,
--            tmnxMcMfrBundleGroup,
--            tmnxFrIntfGroup,
--            tmnxFrf12IntfGroup
--        }
--    ::= { tnPortComp7750 6 }

-- tnPortComp7450V3v0  MODULE-COMPLIANCE
--    ::= { tnPortComp7450 1 }

-- tnPortComp7450V4v0  MODULE-COMPLIANCE
--    STATUS  obsolete
--    DESCRIPTION
--            "The compliance statement for revision 4.0 of TIMETRA-PORT-MIB on
--             the Nokia 7450 SR series systems."
--    MODULE  this module
--        MANDATORY-GROUPS {
--            tnPortGroupV4v0,
--            tnPortEthernetV3v0Group,
--            tnPortSonetV3v0Group,
--            tnPortTDMGroupV4v0,
--            tnPortFRGroup,
--            tnQosAppObjsGroup,
--            tnPortTestGroup,
--            tnPortNotificationGroupV3v0,
--            tnPortIngrMdaQosStatR2r1Group,
--            tnPortStatsR2r1Group,
--            tmnxScalarPortV3v0Group
--            tnPortATMGroupV7v0,         No ATM on 7450
--            tnCiscoHDLCGroup,           No Cisco HDLC on 7450
--            tmnxMlBundleGroupV4v0         No ML Bundles on 7450
--            tmnxMlImaBundleGroup          No IMA Bundles on 7450
--        }
--    ::= { tnPortComp7450 2 }

-- tnPortComp7450V5v0  MODULE-COMPLIANCE
--    STATUS  obsolete
--    DESCRIPTION
--            "The compliance statement for revision 5.0 of TIMETRA-PORT-MIB on
--             the Nokia 7450 SR series systems."
--    MODULE  this module
--        MANDATORY-GROUPS {
--            tnPortGroupV5v0,
--            tnPortSonetV3v0Group,
--            tnPortTDMGroupV5v0,         No TDM interfaces
--            tnPortFRGroup,
--            tnQosAppObjsGroup,
--            tnPortTestGroup,
--            tnPortNotificationGroupV5v0,
--            tnPortIngrMdaQosStatR2r1Group,
--            tnPortStatsR2r1Group,
--            tmnxScalarPortV3v0Group,
--            tnPortATMGroupV4v0,         No ATM on 7450
--            tnCiscoHDLCGroup,           No Cisco HDLC on 7450
--            tmnxMlBundleGroupV5v0         No ML Bundles on 7450
--            tmnxMlImaBundleGroup          No IMA Bundles on 7450
--            tnPortSchedV5v0Group,
--            tnPortEthernetV5v0Group
--        }
--    ::= { tnPortComp7450 3 }

-- tnPortComp7450V6v0  MODULE-COMPLIANCE
--    STATUS  obsolete
--    DESCRIPTION
--            "The compliance statement for revision 5.0 of TIMETRA-PORT-MIB on
--             the Nokia 7450 SR series systems."
--    MODULE  this module
--        MANDATORY-GROUPS {
--            tnPortGroupV6v0,
--            tnPortSonetV3v0Group,
--            tnPortTDMGroupV6v0,         No TDM interfaces
--            tnPortTDME1GroupV6v1,
--            tnPortFRGroup,
--            tnQosAppObjsGroup,
--            tnPortTestGroup,
--            tnPortNotificationGroupV6v0,
--            tnPortIngrMdaQosStatR2r1Group,
--            tnPortStatsR2r1Group,
--            tmnxScalarPortV3v0Group,
--            tnPortATMGroupV4v0,         No ATM on 7450
--            tnCiscoHDLCGroup,           No Cisco HDLC on 7450
--            tmnxMlBundleGroupV5v0         No ML Bundles on 7450
--            tmnxMlImaBundleGroup          No IMA Bundles on 7450
--            tnPortSchedV5v0Group,
--            tnPortEthernetV6v0Group,
--            tnPortCemGroupV6v0          No CEM on 7450
--            tnMcMlpppBundleGroup        No Multiclass MLPPP Bundles on 7450
--            tmnxMlpppBundleGroup          No MLPPP Bundles on 7450
--            tmnxMlpppBundleGroupV7v0,
--            tnHsmdaGroupV6v0,
--            tnDigitalDiagMonitorGroup
--        }
--    ::= { tnPortComp7450 4 }

-- tnPortComp7450V6v1  MODULE-COMPLIANCE
--    STATUS  obsolete
--    DESCRIPTION
--            "The compliance statement for revision 5.0 of TIMETRA-PORT-MIB on
--             the Nokia 7450 SR series systems."
--    MODULE  this module
--        MANDATORY-GROUPS {
--            tnPortGroupV6v0,
--            tnPortSonetV3v0Group,
--            tnPortTDMGroupV6v0,         No TDM interfaces
--            tnPortTDME1GroupV6v1,
--            tnPortFRGroup,
--            tnQosAppObjsGroup,
--            tnPortTestGroup,
--            tnPortNotificationGroupV6v0,
--            tnPortIngrMdaQosStatR2r1Group,
--            tnPortStatsR2r1Group,
--            tmnxScalarPortV3v0Group,
--            tnPortATMGroupV4v0,         No ATM on 7450
--            tnCiscoHDLCGroup,           No Cisco HDLC on 7450
--            tmnxMlBundleGroupV5v0         No ML Bundles on 7450
--            tmnxMlImaBundleGroup          No IMA Bundles on 7450
--            tnPortSchedV5v0Group,
--            tnPortEthernetV6v1Group,
--            tnPortCemGroupV6v0          No CEM on 7450
--            tnMcMlpppBundleGroup        No Multiclass MLPPP Bundles on 7450
--            tmnxMlpppBundleGroup          No MLPPP Bundles on 7450
--            tnHsmdaGroupV6v0,
--            tmnxNamedPoolGroupV6v0,
--            tnDigitalDiagMonitorGroup
--        }
--    ::= { tnPortComp7450 5 }

-- tnPortComp7450V7v0  MODULE-COMPLIANCE
--    STATUS  current
--    DESCRIPTION
--            "The compliance statement for revision 5.0 of TIMETRA-PORT-MIB on
--             the Nokia 7450 SR series systems."
--    MODULE  this module
--        MANDATORY-GROUPS {
--            tnPortGroupV7v0,
--            tnPortSonetV3v0Group,
--            tnPortTDMGroupV6v0,         No TDM interfaces
--            tnPortTDME1GroupV6v1,
--            tnPortFRGroup,
--            tnQosAppObjsGroup,
--            tnPortTestGroup,
--            tnPortNotificationGroupV7v0,
--            tnPortIngrMdaQosStatR2r1Group,
--            tnPortStatsR2r1Group,
--            tmnxScalarPortV3v0Group,
--            tnPortATMGroupV4v0,         No ATM on 7450
--            tnCiscoHDLCGroup,           No Cisco HDLC on 7450
--            tmnxMlBundleGroupV5v0         No ML Bundles on 7450
--            tmnxMlImaBundleGroup          No IMA Bundles on 7450
--            tnPortSchedV5v0Group,
--            tnPortEthernetV7v0Group,
--            tnPortCemGroupV6v0          No CEM on 7450
--            tnMcMlpppBundleGroup        No Multiclass MLPPP Bundles on 7450
--            tmnxMlpppBundleGroup          No MLPPP Bundles on 7450
--            tnHsmdaGroupV6v0,
--            tmnxNamedPoolGroupV6v0,
--            tnDigitalDiagMonitorGroup,
--            tnPortQV7v0Group,
--            tnPortQStatV7v0Group
--        }
--    ::= { tnPortComp7450 6 }

-- tnPortComp7710V3v0  MODULE-COMPLIANCE
--    STATUS  obsolete
--    DESCRIPTION
--            "The compliance statement for revision 3.0 of TIMETRA-PORT-MIB."
--    MODULE  this module
--        MANDATORY-GROUPS {
--            tnPortV3v0Group,
--            tnPortEthernetV3v0Group,
--            tnPortSonetV3v0Group,
--            tnPortTDMV3v0Group,
--            tnPortFRGroup,
--            tnQosAppObjsGroup,
--            tnPortTestGroup,
--            tnPortNotificationGroupR2r1,
--            tnPortIngrMdaQosStatR2r1Group,
--            tnPortATMV3v0Group,
--            tnPortStatsR2r1Group,
--            tnCiscoHDLCGroup,
--            tmnxScalarPortV3v0Group,
--            tmnxMlBundleV3v0Group,
--            tmnx7710PortTDMGroupV3v0
--        }
--    ::= { tnPortComp7710 1 }

-- tnPortComp7710V5v0  MODULE-COMPLIANCE
--    STATUS  obsolete
--    DESCRIPTION
--            "The compliance statement for revision 5.0 of TIMETRA-PORT-MIB."
--    MODULE  this module
--        MANDATORY-GROUPS {
--            tnPortGroupV5v0,
--            tnPortEthernetV5v0Group,
--            tnPortSonetV3v0Group,
--            tnPortTDMGroupV5v0,
--            tnPortFRGroup,
--            tnQosAppObjsGroup,
--            tnPortTestGroup,
--            tnPortNotificationGroupV5v0,
--            tnPortIngrMdaQosStatR2r1Group,
--            tnPortATMGroupV4v0,
--            tnPortStatsR2r1Group,
--            tnCiscoHDLCGroup,
--            tmnxScalarPortV3v0Group,
--            tmnxMlBundleGroupV5v0,
--            tnPortSchedV5v0Group,
--            tmnx7710PortTDMGroupV5v0
--        }
--    ::= { tnPortComp7710 2 }
--
-- tnPortComp7710V6v0  MODULE-COMPLIANCE
--    STATUS  obsolete
--    DESCRIPTION
--            "The compliance statement for revision 6.0 of TIMETRA-PORT-MIB."
--    MODULE  this module
--        MANDATORY-GROUPS {
--            tnPortGroupV6v0,
--            tnPortEthernetV6v0Group,
--            tnPortSonetV3v0Group,
--            tnPortTDMGroupV6v0,
--            tnPortFRGroup,
--            tnQosAppObjsGroup,
--            tnPortTestGroup,
--            tnPortNotificationGroupV6v0,
--            tnPortIngrMdaQosStatR2r1Group,
--            tnPortATMGroupV4v0,
--            tnPortStatsR2r1Group,
--            tnCiscoHDLCGroup,
--            tmnxScalarPortV3v0Group,
--            tmnxMlBundleGroupV6v0,
--            tnPortSchedV5v0Group,
--            tmnx7710PortTDMGroupV5v0,
--            tnPortCemGroupV6v0,
--            tnMcMlpppBundleGroup,
--            tmnxMlpppBundleGroup,
--            tnHsmdaGroupV6v0,
--            tnDigitalDiagMonitorGroup
--        }
--    ::= { tnPortComp7710 3 }

-- tnPortComp7710V6v1  MODULE-COMPLIANCE
--    STATUS  obsolete
--    DESCRIPTION
--            "The compliance statement for revision 6.0 of TIMETRA-PORT-MIB."
--    MODULE  this module
--        MANDATORY-GROUPS {
--            tnPortGroupV6v0,
--            tnPortEthernetV6v1Group,
--            tnPortSonetV3v0Group,
--            tnPortTDMGroupV6v0,
--            tnPortTDME1GroupV6v1,
--            tnPortFRGroup,
--            tnQosAppObjsGroup,
--            tnPortTestGroup,
--            tnPortNotificationGroupV6v0,
--            tnPortIngrMdaQosStatR2r1Group,
--            tnPortATMGroupV4v0,
--            tnPortStatsR2r1Group,
--            tnCiscoHDLCGroup,
--            tmnxScalarPortV3v0Group,
--            tmnxMlBundleGroupV6v0,
--            tnPortSchedV5v0Group,
--            tmnx7710PortTDMGroupV5v0,
--            tnPortCemGroupV6v0,
--            tnMcMlpppBundleGroup,
--            tmnxMlpppBundleGroup,
--            tnHsmdaGroupV6v0,
--            tmnxNamedPoolGroupV6v0
--            tnDigitalDiagMonitorGroup
--        }
--    ::= { tnPortComp7710 4 }

-- tnPortComp7710V7v0  MODULE-COMPLIANCE
--    STATUS  current
--    DESCRIPTION
--            "The compliance statement for revision 6.0 of TIMETRA-PORT-MIB."
--    MODULE  this module
--        MANDATORY-GROUPS {
--            tnPortGroupV7v0,
--            tnPortEthernetV7v0Group,
--            tnPortSonetV3v0Group,
--            tnPortTDMGroupV6v0,
--            tnPortTDMGroupV7v0,
--            tnPortFRGroup,
--            tnQosAppObjsGroup,
--            tnPortTestGroup,
--            tnPortNotificationGroupV7v0,
--            tnPortIngrMdaQosStatR2r1Group,
--            tnPortATMGroupV7v0,
--            tnPortStatsR2r1Group,
--            tnCiscoHDLCGroup,
--            tmnxScalarPortV3v0Group,
--            tmnxMlBundleGroupV6v0,
--            tnPortSchedV5v0Group,
--            tmnx7710PortTDMGroupV5v0,
--            tnPortCemGroupV6v0,
--            tnMcMlpppBundleGroup,
--            tmnxMlpppBundleGroup,
--            tmnxMlpppBundleGroupV7v0,
--            tnHsmdaGroupV6v0,
--            tmnxNamedPoolGroupV6v0
--            tnDigitalDiagMonitorGroup,
--            tnPortQV7v0Group,
--            tnPortQStatV7v0Group
--        }
--    ::= { tnPortComp7710 5 }

-- units of conformance

-- tnPortGroup   OBJECT-GROUP
--    ::= { tnPortGroups 1 }

-- tnPortEthernetGroup       OBJECT-GROUP
--    ::= { tnPortGroups 2 }

-- tnPortSONETGroup      OBJECT-GROUP
--    ::= { tnPortGroups 3 }

-- tnPortTDMGroup    OBJECT-GROUP
--    ::= { tnPortGroups 4 }

-- tnPortFRGroup     OBJECT-GROUP
--    OBJECTS {   tmnxFRDlcmiMode,
--                tmnxFRDlcmiN392Dce,
--                tmnxFRDlcmiN393Dce,
--                tmnxFRDlcmiT392Dce,
--                tmnxFRDlcmiTxStatusEnqMsgs,
--                tmnxFRDlcmiRxStatusEnqMsgs,
--                tmnxFRDlcmiStatusEnqMsgTimeouts,
--                tmnxFRDlcmiTxStatusMsgs,
--                tmnxFRDlcmiRxStatusMsgs,
--                tmnxFRDlcmiStatusMsgTimeouts,
--                tmnxFRDlcmiDiscardedMsgs,
--                tmnxFRDlcmiInvRxSeqNumMsgs
--            }
--    STATUS      current
--    DESCRIPTION
--        "The group of objects supporting management of Frame Relay DLCMI
--         on Nokia 7x50 SR series systems."
--    ::= { tnPortGroups 5 }

-- tnQosAppObjsGroup     OBJECT-GROUP
--    OBJECTS {   tnObjectAppPoolRowStatus,
--                tnObjectAppResvCbs,
--                tnObjectAppSlopePolicy,
--                tnObjectAppPoolSize
--            }
--    STATUS      current
--    DESCRIPTION
--        "The group of objects supporting management of Qos associations of
--         the buffer pools to mdas, ports, channels and bundles on
--         Nokia 7x50 SR series systems."
--    ::= { tnPortGroups 6 }

-- tnPortTestGroup       OBJECT-GROUP
--    OBJECTS {   tnPortTestState,
--                tnPortTestMode,
--                tnPortTestParameter,
--                tnPortTestLastResult,
--                tnPortTestStartTime,
--                tnPortTestEndTime,
--                tnPortTestDuration,
--                tnPortTestAction
--            }
--    STATUS      current
--    DESCRIPTION
--        "The group of objects supporting management of port testing
--         on Nokia 7x50 SR series system."
--    ::= { tnPortGroups 7 }

-- tnPortNotifyObjsGroup   OBJECT-GROUP
--    ::= { tnPortGroups 8 }

-- tnPortNotificationGroup NOTIFICATION-GROUP
--    ::= { tnPortGroups 9 }

-- tnPortATMGroup     OBJECT-GROUP
--    ::= { tnPortGroups 10 }

-- tnPortObsoleteGroup    OBJECT-GROUP
--    OBJECTS {
--                tnDS1IdleCycleFlags,
--                tnSonetPathType,
--                tnPortFCStatsIngFwdInProfPkts,
--                tnPortFCStatsIngFwdOutProfPkts,
--                tnPortFCStatsIngFwdInProfOcts,
--                tnPortFCStatsIngFwdOutProfOcts,
--                tnPortFCStatsIngDroInProfPkts,
--                tnPortFCStatsIngDroOutProfPkts,
--                tnPortFCStatsIngDroInProfOcts,
--                tnPortFCStatsIngDroOutProfOcts,
--                tnPortFCStatsEgrFwdInProfPkts,
--                tnPortFCStatsEgrFwdOutProfPkts,
--                tnPortFCStatsEgrFwdInProfOcts,
--                tnPortFCStatsEgrFwdOutProfOcts,
--                tnPortFCStatsEgrDroInProfPkts,
--                tnPortFCStatsEgrDroOutProfPkts,
--                tnPortFCStatsEgrDroInProfOcts,
--                tnPortFCStatsEgrDroOutProfOcts
--            }
--    STATUS      current
--    DESCRIPTION
--        "The group of objects in TIMETRA-PORT-MIB which are obsoleted."
--    ::= { tnPortGroups 11 }

-- tnPortR2r1Group   OBJECT-GROUP
--    ::= { tnPortGroups 12 }

-- tnPortEthernetR2r1Group       OBJECT-GROUP
--    ::= { tnPortGroups 13 }

-- tnPortIngrMdaQosStatR2r1Group OBJECT-GROUP
--    OBJECTS {
--             tnPortIngrMdaQos00StatDropPkts,
--             tnPortIngrMdaQos00StatDropOcts,
--             tnPortIngrMdaQos01StatDropPkts,
--             tnPortIngrMdaQos01StatDropOcts,
--             tnPortIngrMdaQos02StatDropPkts,
--             tnPortIngrMdaQos02StatDropOcts,
--             tnPortIngrMdaQos03StatDropPkts,
--             tnPortIngrMdaQos03StatDropOcts,
--             tnPortIngrMdaQos04StatDropPkts,
--             tnPortIngrMdaQos04StatDropOcts,
--             tnPortIngrMdaQos05StatDropPkts,
--             tnPortIngrMdaQos05StatDropOcts,
--             tnPortIngrMdaQos06StatDropPkts,
--             tnPortIngrMdaQos06StatDropOcts,
--             tnPortIngrMdaQos07StatDropPkts,
--             tnPortIngrMdaQos07StatDropOcts,
--             tnPortIngrMdaQos08StatDropPkts,
--             tnPortIngrMdaQos08StatDropOcts,
--             tnPortIngrMdaQos09StatDropPkts,
--             tnPortIngrMdaQos09StatDropOcts,
--             tnPortIngrMdaQos10StatDropPkts,
--             tnPortIngrMdaQos10StatDropOcts,
--             tnPortIngrMdaQos11StatDropPkts,
--             tnPortIngrMdaQos11StatDropOcts,
--             tnPortIngrMdaQos12StatDropPkts,
--             tnPortIngrMdaQos12StatDropOcts,
--             tnPortIngrMdaQos13StatDropPkts,
--             tnPortIngrMdaQos13StatDropOcts,
--             tnPortIngrMdaQos14StatDropPkts,
--             tnPortIngrMdaQos14StatDropOcts,
--             tnPortIngrMdaQos15StatDropPkts,
--             tnPortIngrMdaQos15StatDropOcts
--            }
--    STATUS        current
--    DESCRIPTION
--        "The group of objects that describe the MDA QoS discard
--         statistics for an ethernet port located on an oversubscribed MDA
--         for revision 2.1 on Nokia 7x50 SR series systems."
--    ::= { tnPortGroups 14 }

-- tnPortSONETR2r1Group      OBJECT-GROUP
--    ::= { tnPortGroups 15 }

-- tnPortStatsR2r1Group      OBJECT-GROUP
--    OBJECTS {
--                tnPortNetIngressFwdInProfPkts,
--                tnPortNetIngressFwdOutProfPkts,
--                tnPortNetIngressFwdInProfOcts,
--                tnPortNetIngressFwdOutProfOcts,
--                tnPortNetIngressDroInProfPkts,
--                tnPortNetIngressDroOutProfPkts,
--                tnPortNetIngressDroInProfOcts,
--                tnPortNetIngressDroOutProfOcts,
--                tnPortNetEgressFwdInProfPkts,
--                tnPortNetEgressFwdOutProfPkts,
--                tnPortNetEgressFwdInProfOcts,
--                tnPortNetEgressFwdOutProfOcts,
--                tnPortNetEgressDroInProfPkts,
--                tnPortNetEgressDroOutProfPkts,
--                tnPortNetEgressDroInProfOcts,
--                tnPortNetEgressDroOutProfOcts
--            }
--    STATUS      current
--    DESCRIPTION
--        "The group of objects supporting port statistics
--         for revision 2.1 on Nokia 7x50 SR series systems."
--    ::= { tnPortGroups 16 }

-- tnPortNotificationGroupR2r1 NOTIFICATION-GROUP
--    NOTIFICATIONS   {   tnEqPortSonetAlarm,
--                        tnEqPortSonetAlarmClear,
--                        tnEqPortSonetPathAlarm,
--                        tnEqPortSonetPathAlarmClear,
--                        tnEqPortSFPInserted,
--                        tnEqPortSFPRemoved,
--                        tnEqPortSFPCorrupted,
--                        tnEqPortError,
--                        tnEqPortDS3Alarm,
--                        tnEqPortDS3AlarmClear,
--                        tnEqPortDS1Alarm,
--                        tnEqPortDS1AlarmClear,
--                        tnEqPortBndlYellowDiffExceeded,
--                        tnEqPortBndlRedDiffExceeded,
--                        tnEqPortBndlBadEndPtDiscr,
--                        tnEqPortEtherAlarm,
--                        tnEqPortEtherAlarmClear
--                    }
--    STATUS        obsolete
--    DESCRIPTION
--        "The group of notifications supporting the management of physical
--         ports for revision 2.1 on Nokia 7x50 SR series systems."
--    ::= { tnPortGroups 17 }

-- tnPortNotifyObjsGroupR2r1   OBJECT-GROUP
--    OBJECTS {   tnPortNotifyPortId,
--                tnPortNotifySonetAlarmReason,
--                tnPortNotifySonetPathAlarmReason,
--                tnPortNotifyError,
--                tnPortNotifyDS3AlarmReason,
--                tnPortNotifyDS1AlarmReason,
--                tnPortNotifyBundleId,
--                tnPortNotifyEtherAlarmReason
--            }
--    STATUS        current
--    DESCRIPTION
--        "The group of objects supporting physical port notifications
--          for revision 2.1 on Nokia 7x50 SR series systems."
--    ::= { tnPortGroups 18 }

-- tnPortTDMGroupR2r1    OBJECT-GROUP
--    ::= { tnPortGroups 19 }

-- tnPortNotifyObsoleteGroup NOTIFICATION-GROUP
--    NOTIFICATIONS   {   tnEqOobPortFailure,
--                        tnEqPortFailure,
--                        tnQosServiceDegraded,
--                        tnPortNotifyBerSdTca,
--                        tnPortNotifyBerSfTca,
--                        tnEqPortWrongSFP,
--                        tnEqPortSFPCorrupted
--
--                    }
--    STATUS        current
--    DESCRIPTION
--        "The group of notifications supporting the management of physical
--         ports made obsolete for revision 2.1 on Nokia 7x50 SR series
--         systems. tnEqPortSFPCorrupted was made obsolete for revision 6.0
--         on Nokia 7x50 SR series systems."
--    ::= { tnPortGroups 20 }

-- tnPortSonetV3v0Group      OBJECT-GROUP
--    OBJECTS {   tnSonetSpeed,
--                tnSonetClockSource,
--                tnSonetFraming,
--                tnSonetReportAlarm,
--                tnSonetBerSdThreshold,
--                tnSonetBerSfThreshold,
--                tnSonetLoopback,
--                tnSonetReportAlarmStatus,
--                tnSonetSectionTraceMode,
--                tnSonetJ0String,
--                tnSonetMonS1Byte,
--                tnSonetMonJ0String,
--                tnSonetMonK1Byte,
--                tnSonetMonK2Byte,
--                tnSonetSingleFiber,
--                tnSonetHoldTimeUp,
--                tnSonetHoldTimeDown,
--                tnSonetPathRowStatus,
--                tnSonetPathLastChangeTime,
--                tnSonetPathMTU,
--                tnSonetPathScramble,
--                tnSonetPathC2Byte,
--                tnSonetPathJ1String,
--                tnSonetPathCRC,
--                tnSonetPathOperMTU,
--                tnSonetPathOperMRU,
--                tnSonetPathReportAlarm,
--                tnSonetPathAcctPolicyId,
--                tnSonetPathCollectStats,
--                tnSonetPathReportAlarmStatus,
--                tnSonetPathMonC2Byte,
--                tnSonetPathMonJ1String,
--                tnSonetPathChildType,
--                tnSonetGroupType,
--                tnSonetGroupParentPortID,
--                tnSonetGroupChildType,
--                tnSonetGroupName
--            }
--    STATUS      current
--    DESCRIPTION
--        "The group of objects supporting management of SONET type ports
--         for revision 3.0 on Nokia 7x50 SR series systems."
--    ::= { tnPortGroups 21 }

-- tnPortTDMV3v0Group    OBJECT-GROUP
--    OBJECTS {   tnDS3Buildout,
--                tnDS3Type,
--                tnDS3LastChangeTime,
--                tnDS3ChannelRowStatus,
--                tnDS3ChannelType,
--                tnDS3ChannelFraming,
--                tnDS3ChannelClockSource,
--                tnDS3ChannelChannelized,
--                tnDS3ChannelSubrateCSUMode,
--                tnDS3ChannelSubrate,
--                tnDS3ChannelIdleCycleFlags,
--                tnDS3ChannelLoopback,
--                tnDS3ChannelBitErrorInsertionRate,
--                tnDS3ChannelBERTPattern,
--                tnDS3ChannelBERTDuration,
--                tnDS3ChannelMDLEicString,
--                tnDS3ChannelMDLLicString,
--                tnDS3ChannelMDLFicString,
--                tnDS3ChannelMDLUnitString,
--                tnDS3ChannelMDLPfiString,
--                tnDS3ChannelMDLPortString,
--                tnDS3ChannelMDLGenString,
--                tnDS3ChannelMDLMessageType,
--                tnDS3ChannelFEACLoopRespond,
--                tnDS3ChannelCRC,
--                tnDS3ChannelMTU,
--                tnDS3ChannelOperMTU,
--                tnDS3ChannelReportAlarm,
--                tnDS3ChannelReportAlarmStatus,
--                tnDS3ChannelLastChangeTime,
--                tnDS3ChannelInFEACLoop,
--                tnDS3ChannelMDLMonPortString,
--                tnDS3ChannelMDLMonGenString,
--                tnDS3ChannelBERTOperStatus,
--                tnDS3ChannelBERTSynched,
--                tnDS3ChannelBERTErrors,
--                tnDS3ChannelBERTTotalBits,
--                tnDS1RowStatus,
--                tnDS1Type,
--                tnDS1Framing,
--                tnDS1Loopback,
--                tnDS1InvertData,
--                tnDS1BitErrorInsertionRate,
--                tnDS1BERTPattern,
--                tnDS1BERTDuration,
--                tnDS1ReportAlarm,
--                tnDS1ReportAlarmStatus,
--                tnDS1LastChangeTime,
--                tnDS1ClockSource,
--                tnDS1BERTOperStatus,
--                tnDS1BERTSynched,
--                tnDS1BERTErrors,
--                tnDS1BERTTotalBits,
--                tnDS1RemoteLoopRespond,
--                tnDS1InRemoteLoop,
--                tnDS0ChanGroupRowStatus,
--                tnDS0ChanGroupTimeSlots,
--                tnDS0ChanGroupSpeed,
--                tnDS0ChanGroupCRC,
--                tnDS0ChanGroupMTU,
--                tnDS0ChanGroupOperMTU,
--                tnDS0ChanGroupLastChangeTime,
--                tnDS0ChanGroupIdleCycleFlags
--            }
--    STATUS      obsolete
--    DESCRIPTION
--        "The group of objects supporting management of TDM type ports
--         for revision 3.0 on the Nokia 7x50 SR series systems."
--    ::= { tnPortGroups 22 }

-- tnPortATMV3v0Group     OBJECT-GROUP
--    OBJECTS {
--                tmnxATMIntfCellFormat,
--                tmnxATMIntfMinVpValue
--            }
--    STATUS      obsolete
--    DESCRIPTION
--        "The group of objects supporting management of ATM interfaces
--         for version 3.0 on Nokia 7x50 SR series systems."
--    ::= { tnPortGroups 23 }

-- tmnxScalarPortV3v0Group         OBJECT-GROUP
--    OBJECTS { tnL4LoadBalancing }
--    STATUS      current
--    DESCRIPTION
--        "The group of objects supporting management for general port
--         settings for revision 3.0 on Nokia 7x50 series systems."
--    ::= { tnPortGroups 24 }

-- tnPortV3v0Group   OBJECT-GROUP
--    OBJECTS {   tnPortTableLastChange,
--                tnPortLastChangeTime,
--                tnPortType,
--                tnPortClass,
--                tnPortDescription,
--                tnPortName,
--                tnPortAlias,
--                tnPortUserAssignedMac,
--                tnPortMacAddress,
--                tnPortHwMacAddress,
--                tnPortMode,
--                tnPortEncapType,
--                tnPortLagId,
--                tnPortHoldTimeUp,
--                tnPortHoldTimeDown,
--                tnPortUpProtocols,
--                tnPortConnectorType,
--                tnPortTransceiverType,
--                tnPortTransceiverCode,
--                tnPortTransceiverLaserWaveLen,
--                tnPortTransceiverDiagCapable,
--                tnPortTransceiverModelNumber,
--                tnPortSFPConnectorCode,
--                tnPortSFPVendorOUI,
--                tnPortSFPVendorManufactureDate,
--                tnPortSFPMedia,
--                tnPortSFPEquipped,
--                tnPortSFPVendorSerialNum,
--                tnPortSFPVendorPartNum,
--                tnPortEquipped,
--                tnPortLinkStatus,
--                tnPortAdminStatus,
--                tnPortOperStatus,
--                tnPortState,
--                tnPortPrevState,
--                tnPortNumAlarms,
--                tnPortAlarmState,
--                tnPortLastAlarmEvent,
--                tnPortClearAlarms,
--                tnPortLastStateChanged,
--                tnPortNumChannels,
--                tnPortNetworkEgrQueues,
--                tnPortIsLeaf,
--                tnPortChanType,
--                tnPortParentPortID,
--                tnPortLoadBalanceAlgorithm,
--                tnPortTypeName,
--                tnPortTypeDescription,
--                tnPortTypeStatus,
--                tnPortConnectTypeName,
--                tnPortConnectTypeDescription,
--                tnPortConnectTypeStatus,
--                tmnxChannelPortID,
--                tnPortOpticalCompliance,
--                tnL4LoadBalancing
--            }
--    STATUS        obsolete
--    DESCRIPTION
--        "The group of objects supporting management of physical port
--         capabilities for revision 3.0 on Nokia 7x50 SR series systems."
--    ::= { tnPortGroups 25 }

-- tnCiscoHDLCGroup      OBJECT-GROUP
--    OBJECTS {   tnCiscoHDLCKeepAliveInt,
--                tnCiscoHDLCUpCount,
--                tnCiscoHDLCDownCount,
--                tnCiscoHDLCOperState,
--                tnCiscoHDLCDiscardStatInPkts,
--                tnCiscoHDLCDiscardStatOutPkts,
--                tnCiscoHDLCStatInPkts,
--                tnCiscoHDLCStatOutPkts,
--                tnCiscoHDLCStatInOctets,
--                tnCiscoHDLCStatOutOctets
--           }
--    STATUS     current
--    DESCRIPTION
--        "The group of objects supporting Cisco HDLC encapsulation on Nokia
--         7750 SR series systems."
--    ::= { tnPortGroups 26 }

-- tmnxMlBundleV3v0Group    OBJECT-GROUP
--    OBJECTS {   tnBundleRowStatus,
--                tnBundleType,
--                tnBundleMinimumLinks,
--                tnBundleNumLinks,
--                tnBundleNumActiveLinks,
--                tnBundleMRRU,
--                tnBundleOperMRRU,
--                tnBundlePeerMRRU,
--                tnBundleOperMTU,
--                tnBundleRedDiffDelay,
--                tnBundleRedDiffDelayAction,
--                tnBundleYellowDiffDelay,
--                tnBundleShortSequence,
--                tnBundleLastChangeTime,
--                tnBundleFragmentThreshold,
--                tnBundleUpTime,
--                tnBundleMemberRowStatus,
--                tnBundleMemberActive,
--                tnBundleMemberDownReason,
--                tnBundleMemberUpTime,
--                tnBundleInputDiscards,
--                tnBundlePrimaryMemberPortID,
--                tnBundleLFI,
--                tnPortBundleNumber
--            }
--    STATUS      obsolete
--    DESCRIPTION
--        "The group of objects supporting management MLBUNDLES
--         for revision 3.0 on the Nokia 7x50 SR series systems."
--    ::= { tnPortGroups 27 }

-- tmnxObsoleteGroupV3v0    OBJECT-GROUP
--    OBJECTS {   tnSonetAps,
--                tnSonetApsAdminStatus,
--                tnSonetApsOperStatus,
--                tnSonetApsAuthKey,
--                tnSonetApsNeighborAddr,
--                tnSonetApsAdvertiseInterval,
--                tnSonetApsAdvertiseTimeLeft,
--                tnSonetApsHoldTime,
--                tnSonetApsHoldTimeLeft
--            }
--    STATUS      current
--    DESCRIPTION
--        "The group of objects obsoleted in the 7x50 SR series 3.0 release"
--    ::= { tnPortGroups 28 }

-- tnPortEthernetV3v0Group       OBJECT-GROUP
--    OBJECTS {  tnPortEtherMTU,
--                tnPortEtherDuplex,
--                tnPortEtherSpeed,
--                tnPortEtherAutoNegotiate,
--                tnPortEtherOperDuplex,
--                tnPortEtherOperSpeed,
--                tnPortEtherAcctPolicyId,
--                tnPortEtherCollectStats,
--                tnPortEtherMDIMDIX,
--                tnPortEtherXGigMode,
--                tnPortEtherEgressRate,
--                tnPortEtherDot1qEtype,
--                tnPortEtherQinqEtype,
--                tnPortEtherIngressRate,
--                tnPortEtherReportAlarm,
--                tnPortEtherReportAlarmStatus,
--                tnPortEtherPkts1519toMax,
--                tnPortEtherHCOverPkts1519toMax,
--                tnPortEtherHCPkts1519toMax
--            }
--    STATUS      obsolete
--    DESCRIPTION
--        "The group of objects supporting management of Ethernet ports
--         for revision 3.0 on Nokia 7x50 SR series systems."
--    ::= { tnPortGroups 29 }

-- tnPortTDMGroupV4v0    OBJECT-GROUP
--    OBJECTS {   tnDS3Buildout,
--                tnDS3Type,
--                tnDS3LastChangeTime,
--                tnDS3ChannelRowStatus,
--                tnDS3ChannelType,
--                tnDS3ChannelFraming,
--                tnDS3ChannelClockSource,
--                tnDS3ChannelChannelized,
--                tnDS3ChannelSubrateCSUMode,
--                tnDS3ChannelSubrate,
--                tnDS3ChannelIdleCycleFlags,
--                tnDS3ChannelLoopback,
--                tnDS3ChannelBitErrorInsertionRate,
--                tnDS3ChannelBERTPattern,
--                tnDS3ChannelBERTDuration,
--                tnDS3ChannelMDLEicString,
--                tnDS3ChannelMDLLicString,
--                tnDS3ChannelMDLFicString,
--                tnDS3ChannelMDLUnitString,
--                tnDS3ChannelMDLPfiString,
--                tnDS3ChannelMDLPortString,
--                tnDS3ChannelMDLGenString,
--                tnDS3ChannelMDLMessageType,
--                tnDS3ChannelFEACLoopRespond,
--                tnDS3ChannelCRC,
--                tnDS3ChannelMTU,
--                tnDS3ChannelOperMTU,
--                tnDS3ChannelReportAlarm,
--                tnDS3ChannelReportAlarmStatus,
--                tnDS3ChannelLastChangeTime,
--                tnDS3ChannelInFEACLoop,
--                tnDS3ChannelMDLMonPortString,
--                tnDS3ChannelMDLMonGenString,
--                tnDS3ChannelBERTOperStatus,
--                tnDS3ChannelBERTSynched,
--                tnDS3ChannelBERTErrors,
--                tnDS3ChannelBERTTotalBits,
--                tnDS3ChannelScramble,
--                tnDS1RowStatus,
--                tnDS1Type,
--                tnDS1Framing,
--                tnDS1Loopback,
--                tnDS1InvertData,
--                tnDS1BitErrorInsertionRate,
--                tnDS1BERTPattern,
--                tnDS1BERTDuration,
--                tnDS1ReportAlarm,
--                tnDS1ReportAlarmStatus,
--                tnDS1LastChangeTime,
--                tnDS1ClockSource,
--                tnDS1BERTOperStatus,
--                tnDS1BERTSynched,
--                tnDS1BERTErrors,
--                tnDS1BERTTotalBits,
--                tnDS1RemoteLoopRespond,
--                tnDS1InRemoteLoop,
--                tnDS0ChanGroupRowStatus,
--                tnDS0ChanGroupTimeSlots,
--                tnDS0ChanGroupSpeed,
--                tnDS0ChanGroupCRC,
--                tnDS0ChanGroupMTU,
--                tnDS0ChanGroupOperMTU,
--                tnDS0ChanGroupLastChangeTime,
--                tnDS0ChanGroupIdleCycleFlags,
--                tnDS0ChanGroupScramble
--            }
--    STATUS      obsolete
--    DESCRIPTION
--        "The group of objects supporting management of TDM type ports
--         for version 4.0 on the Nokia 7x50 SR series systems."
--    ::= { tnPortGroups 30 }

-- tnPortATMGroupV4v0     OBJECT-GROUP
--    OBJECTS {
--                tmnxATMIntfCellFormat,
--                tmnxATMIntfMinVpValue,
--                tmnxATMIntfMapping
--            }
--    STATUS     obsolete
--    DESCRIPTION
--        "The group of objects supporting management of ATM interfaces
--         for version 4.0 on Nokia 7x50 SR series systems."
--    ::= { tnPortGroups 31 }

-- tmnxMlBundleGroupV4v0    OBJECT-GROUP
--    OBJECTS {   tnBundleRowStatus,
--                tnBundleType,
--                tnBundleMinimumLinks,
--                tnBundleNumLinks,
--                tnBundleNumActiveLinks,
--                tnBundleMRRU,
--                tnBundleOperMRRU,
--                tnBundlePeerMRRU,
--                tnBundleOperMTU,
--                tnBundleRedDiffDelay,
--                tnBundleRedDiffDelayAction,
--                tnBundleYellowDiffDelay,
--                tnBundleShortSequence,
--                tnBundleLastChangeTime,
--                tnBundleFragmentThreshold,
--                tnBundleUpTime,
--                tnBundleMemberRowStatus,
--                tnBundleMemberActive,
--                tnBundleMemberDownReason,
--                tnBundleMemberUpTime,
--                tnBundleInputDiscards,
--                tnBundlePrimaryMemberPortID,
--                tnBundleLFI,
--                tnPortBundleNumber
--            }
--    STATUS      obsolete
--    DESCRIPTION
--        "The group of objects supporting management MLBUNDLES
--         for revision 4.0 on the Nokia 7x50 SR series systems."
--    ::= { tnPortGroups 32 }

-- tmnxMlImaBundleGroup    OBJECT-GROUP
--    OBJECTS {
--                tnBundleImaGrpLnkActTimer,
--                tnBundleImaGrpLnkDeactTimer,
--                tnBundleImaGrpSymmetryMode,
--                tnBundleImaGrpTxId,
--                tnBundleImaGrpRxId,
--                tnBundleImaGrpTxRefLnk,
--                tnBundleImaGrpRxRefLnk,
--                tnBundleImaGrpSmNeState,
--                tnBundleImaGrpSmFeState,
--                tnBundleImaGrpSmFailState,
--                tnBundleImaGrpSmDownSecs,
--                tnBundleImaGrpSmOperSecs,
--                tnBundleImaGrpAvailTxCR,
--                tnBundleImaGrpAvailRxCR,
--                tnBundleImaGrpNeFails,
--                tnBundleImaGrpFeFails,
--                tnBundleImaGrpTxIcpCells,
--                tnBundleImaGrpRxIcpCells,
--                tnBundleImaGrpErrorIcpCells,
--                tnBundleImaGrpLostRxIcpCells,
--                tnBundleImaGrpTxOamLablVal,
--                tnBundleImaGrpRxOamLablVal,
--                tnBundleImaGrpAlphaValue,
--                tnBundleImaGrpBetaValue,
--                tnBundleImaGrpGammaValue,
--                tnBundleImaGrpNeClockMode,
--                tnBundleImaGrpFeClockMode,
--                tnBundleImaGrpVersion,
--                tnBundleImaGrpMaxConfBw,
--                tnBundleImaGrpTestState,
--                tnBundleImaGrpTestMember,
--                tnBundleImaGrpTestPattern,
--                tnBundleImaGrpDiffDelayMaxObs,
--                tnBundleImaGrpLeastDelayLink,
--                tnBundleMemberImaNeTxState,
--                tnBundleMemberImaNeRxState,
--                tnBundleMemberImaFeTxState,
--                tnBundleMemberImaFeRxState,
--                tnBundleMemberImaNeRxFailState,
--                tnBundleMemberImaFeRxFailState,
--                tnBundleMemberImaTxLid,
--                tnBundleMemberImaRxLid,
--                tnBundleMemberImaViolations,
--                tnBundleMemberImaNeSevErrSecs,
--                tnBundleMemberImaFeSevErrSecs,
--                tnBundleMemberImaNeUnavailSecs,
--                tnBundleMemberImaFeUnavailSecs,
--                tnBundleMemberImaNeTxUnuseSecs,
--                tnBundleMemberImaNeRxUnuseSecs,
--                tnBundleMemberImaFeTxUnuseSecs,
--                tnBundleMemberImaFeRxUnuseSecs,
--                tnBundleMemberImaNeTxNumFails,
--                tnBundleMemberImaNeRxNumFails,
--                tnBundleMemberImaFeTxNumFails,
--                tnBundleMemberImaFeRxNumFails,
--                tnBundleMemberImaTxIcpCells,
--                tnBundleMemberImaRxIcpCells,
--                tnBundleMemberImaErrorIcpCells,
--                tnBundleMemberImaLstRxIcpCells,
--                tnBundleMemberImaOifAnomalies,
--                tnBundleMemberImaRxTestState,
--                tnBundleMemberImaRxTestPattern,
--                tnBundleMemberImaRelDelay
--            }
--    STATUS      current
--    DESCRIPTION
--        "The group of objects supporting management of Ima Groups
--         and Members on the Nokia 7x50 SR series systems."
--    ::= { tnPortGroups 33 }

-- tmnx7710PortTDMGroupV3v0   OBJECT-GROUP
--    OBJECTS {
--                tnDS3ChannelAcctPolicyId,
--                tnDS3ChannelCollectStats,
--                tnDS1PortBuildout,
--                tnDS1PortLastChangeTime,
--                tnDS1PortType,
--                tnDS1PortLineLength,
--                tnDS1PortLbo,
--                tnDS1PortDbGain,
--                tnDS1InsertSingleBitError,
--                tnDS0ChanGroupAcctPolicyId,
--                tnDS0ChanGroupCollectStats
--           }
--    STATUS     obsolete
--    DESCRIPTION
--        "The group of objects supporting management of TDM type ports
--         specific to the Nokia 7710 SR series systems for revision 3.0."
--    ::= { tnPortGroups 34 }

-- tnPortGroupV4v0   OBJECT-GROUP
--    OBJECTS {   tnPortTableLastChange,
--                tnPortLastChangeTime,
--                tnPortType,
--                tnPortClass,
--                tnPortDescription,
--                tnPortName,
--                tnPortAlias,
--                tnPortUserAssignedMac,
--                tnPortMacAddress,
--                tnPortHwMacAddress,
--                tnPortMode,
--                tnPortEncapType,
--                tnPortLagId,
--                tnPortHoldTimeUp,
--                tnPortHoldTimeDown,
--                tnPortUpProtocols,
--                tnPortConnectorType,
--                tnPortTransceiverType,
--                tnPortTransceiverCode,
--                tnPortTransceiverLaserWaveLen,
--                tnPortTransceiverDiagCapable,
--                tnPortTransceiverModelNumber,
--                tnPortSFPConnectorCode,
--                tnPortSFPVendorOUI,
--                tnPortSFPVendorManufactureDate,
--                tnPortSFPMedia,
--                tnPortSFPEquipped,
--                tnPortSFPVendorSerialNum,
--                tnPortSFPVendorPartNum,
--                tnPortEquipped,
--                tnPortLinkStatus,
--                tnPortAdminStatus,
--                tnPortOperStatus,
--                tnPortState,
--                tnPortPrevState,
--                tnPortNumAlarms,
--                tnPortAlarmState,
--                tnPortLastAlarmEvent,
--                tnPortClearAlarms,
--                tnPortLastStateChanged,
--                tnPortNumChannels,
--                tnPortNetworkEgrQueues,
--                tnPortIsLeaf,
--                tnPortChanType,
--                tnPortParentPortID,
--                tnPortLoadBalanceAlgorithm,
--                tnPortTypeName,
--                tnPortTypeDescription,
--                tnPortTypeStatus,
--                tnPortConnectTypeName,
--                tnPortConnectTypeDescription,
--                tnPortConnectTypeStatus,
--                tmnxChannelPortID,
--                tnPortOpticalCompliance,
--                tnL4LoadBalancing
--            }
--    STATUS        obsolete
--    DESCRIPTION
--        "The group of objects supporting management of physical port
--         capabilities for revision 4.0 on Nokia 7x50 SR series systems."
--    ::= { tnPortGroups 35 }

-- tmnxObsoleteGroupV5v0    OBJECT-GROUP
--    OBJECTS {
--                tnPortTransceiverCode
--            }
--    STATUS      current
--    DESCRIPTION
--        "The group of objects obsoleted in the 7x50 SR series 5.0 release"
--    ::= { tnPortGroups 36 }

-- tnPortSchedV5v0Group  OBJECT-GROUP
--    OBJECTS {
--                tnPortEgrPortSchedPlcy,
--                tnPortSchedOverrideRowStatus,
--                tnPortSchedOverrideSchedName,
--                tnPortSchedOverrideLastChanged,
--                tnPortSchedOverrideMaxRate,
--                tnPortSchedOverrideLvl1PIR,
--                tnPortSchedOverrideLvl1CIR,
--                tnPortSchedOverrideLvl2PIR,
--                tnPortSchedOverrideLvl2CIR,
--                tnPortSchedOverrideLvl3PIR,
--                tnPortSchedOverrideLvl3CIR,
--                tnPortSchedOverrideLvl4PIR,
--                tnPortSchedOverrideLvl4CIR,
--                tnPortSchedOverrideLvl5PIR,
--                tnPortSchedOverrideLvl5CIR,
--                tnPortSchedOverrideLvl6PIR,
--                tnPortSchedOverrideLvl6CIR,
--                tnPortSchedOverrideLvl7PIR,
--                tnPortSchedOverrideLvl7CIR,
--                tnPortSchedOverrideLvl8PIR,
--                tnPortSchedOverrideLvl8CIR,
--                tnPortSchedOverrideFlags
--            }
--    STATUS        current
--    DESCRIPTION
--        "The group of objects supporting management of physical port
--         virtual scheduler capabilities for revision 5.0 on Nokia
--         7x50 SR series systems."
--    ::= { tnPortGroups 37 }

-- tnPortEthernetV5v0Group       OBJECT-GROUP
--    OBJECTS {  tnPortEtherMTU,
--                tnPortEtherDuplex,
--                tnPortEtherSpeed,
--                tnPortEtherAutoNegotiate,
--                tnPortEtherOperDuplex,
--                tnPortEtherOperSpeed,
--                tnPortEtherAcctPolicyId,
--                tnPortEtherCollectStats,
--                tnPortEtherMDIMDIX,
--                tnPortEtherXGigMode,
--                tnPortEtherEgressRate,
--                tnPortEtherDot1qEtype,
--                tnPortEtherQinqEtype,
--                tnPortEtherIngressRate,
--                tnPortEtherReportAlarm,
--                tnPortEtherReportAlarmStatus,
--                tnPortEtherPkts1519toMax,
--                tnPortEtherHCOverPkts1519toMax,
--                tnPortEtherHCPkts1519toMax,
--                tnPortEtherLacpTunnel
--            }
--    STATUS      obsolete
--    DESCRIPTION
--        "The group of objects supporting management of Ethernet ports
--         for revision 5.0 on Nokia 7x50 SR series systems."
--    ::= { tnPortGroups 38 }

-- tnPortGroupV5v0   OBJECT-GROUP
--    OBJECTS {   tnPortTableLastChange,
--                tnPortLastChangeTime,
--                tnPortType,
--                tnPortClass,
--                tnPortDescription,
--                tnPortName,
--                tnPortAlias,
--                tnPortUserAssignedMac,
--                tnPortMacAddress,
--                tnPortHwMacAddress,
--                tnPortMode,
--                tnPortEncapType,
--                tnPortLagId,
--                tnPortHoldTimeUp,
--                tnPortHoldTimeDown,
--                tnPortUpProtocols,
--                tnPortConnectorType,
--                tnPortTransceiverType,
--                tnPortTransceiverCode,
--                tnPortTransceiverLaserWaveLen,
--                tnPortTransceiverDiagCapable,
--                tnPortTransceiverModelNumber,
--                tnPortSFPConnectorCode,
--                tnPortSFPVendorOUI,
--                tnPortSFPVendorManufactureDate,
--                tnPortSFPMedia,
--                tnPortSFPEquipped,
--                tnPortSFPVendorSerialNum,
--                tnPortSFPVendorPartNum,
--                tnPortEquipped,
--                tnPortLinkStatus,
--                tnPortAdminStatus,
--                tnPortOperStatus,
--                tnPortState,
--                tnPortPrevState,
--                tnPortNumAlarms,
--                tnPortAlarmState,
--                tnPortLastAlarmEvent,
--                tnPortClearAlarms,
--                tnPortLastStateChanged,
--                tnPortNumChannels,
--                tnPortNetworkEgrQueues,
--                tnPortIsLeaf,
--                tnPortChanType,
--                tnPortParentPortID,
--                tnPortLoadBalanceAlgorithm,
--                tnPortTypeName,
--                tnPortTypeDescription,
--                tnPortTypeStatus,
--                tnPortConnectTypeName,
--                tnPortConnectTypeDescription,
--                tnPortConnectTypeStatus,
--                tmnxChannelPortID,
--                tnPortOpticalCompliance,
--                tnL4LoadBalancing,
--                tnPortLastClearedTime
--            }
--    STATUS        obsolete
--    DESCRIPTION
--        "The group of objects supporting management of physical port
--         capabilities for revision 5.0 on Nokia 7x50 SR series systems."
--    ::= { tnPortGroups 39 }

-- tmnxMlBundleGroupV5v0    OBJECT-GROUP
--    OBJECTS {   tnBundleRowStatus,
--                tnBundleType,
--                tnBundleMinimumLinks,
--                tnBundleNumLinks,
--                tnBundleNumActiveLinks,
--                tnBundleMRRU,
--                tnBundleOperMRRU,
--                tnBundlePeerMRRU,
--                tnBundleOperMTU,
--                tnBundleRedDiffDelay,
--                tnBundleRedDiffDelayAction,
--                tnBundleYellowDiffDelay,
--                tnBundleShortSequence,
--                tnBundleLastChangeTime,
--                tnBundleFragmentThreshold,
--                tnBundleUpTime,
--                tnBundleMemberRowStatus,
--                tnBundleMemberActive,
--                tnBundleMemberDownReason,
--                tnBundleMemberUpTime,
--                tnBundleInputDiscards,
--                tnBundlePrimaryMemberPortID,
--                tnBundleLFI,
--                tnPortBundleNumber,
--                tnBundleProtectedType,
--                tnBundleParentBundle,
--                tnBPGrpAssocWorkingBundleID,
--                tnBPGrpAssocProtectBundleID,
--                tnBPGrpAssocActiveBundleID
--            }
--    STATUS      obsolete
--    DESCRIPTION
--        "The group of objects supporting management MLBUNDLES
--         for revision 5.0 on the Nokia 7x50 SR series systems."
--    ::= { tnPortGroups 40 }

-- tnPortNotificationGroupV5v0 NOTIFICATION-GROUP
--    NOTIFICATIONS   {   tnEqPortSonetAlarm,
--                        tnEqPortSonetAlarmClear,
--                        tnEqPortSonetPathAlarm,
--                        tnEqPortSonetPathAlarmClear,
--                        tnEqPortSFPInserted,
--                        tnEqPortSFPRemoved,
--                        tnEqPortSFPCorrupted,
--                        tnEqPortError,
--                        tnEqPortDS3Alarm,
--                        tnEqPortDS3AlarmClear,
--                        tnEqPortDS1Alarm,
--                        tnEqPortDS1AlarmClear,
--                        tnEqPortBndlYellowDiffExceeded,
--                        tnEqPortBndlRedDiffExceeded,
--                        tnEqPortBndlBadEndPtDiscr,
--                        tnEqPortEtherAlarm,
--                        tnEqPortEtherAlarmClear,
--                        tnDS1E1LoopbackStarted,
--                        tnDS1E1LoopbackStopped,
--                        tnDS3E3LoopbackStarted,
--                        tnDS3E3LoopbackStopped,
--                        tnSonetSDHLoopbackStarted,
--                        tnSonetSDHLoopbackStopped,
--                        tnEqPortSpeedCfgNotCompatible,
--                        tnEqPortDuplexCfgNotCompatible,
--                        tnEqPortIngressRateCfgNotCompatible
--                    }
--    STATUS        obsolete
--    DESCRIPTION
--        "The group of notifications supporting the management of physical
--         ports for revision 5.0 on Nokia 7x50 SR series systems."
--    ::= { tnPortGroups 41 }

-- tnPortTDMGroupV5v0    OBJECT-GROUP
--    OBJECTS {   tnDS3ChannelAcctPolicyId,
--                tnDS3ChannelCollectStats,
--                tnDS3Buildout,
--                tnDS3Type,
--                tnDS3LastChangeTime,
--                tnDS3ChannelRowStatus,
--                tnDS3ChannelType,
--                tnDS3ChannelFraming,
--                tnDS3ChannelClockSource,
--                tnDS3ChannelChannelized,
--                tnDS3ChannelSubrateCSUMode,
--                tnDS3ChannelSubrate,
--                tnDS3ChannelIdleCycleFlags,
--                tnDS3ChannelLoopback,
--                tnDS3ChannelBitErrorInsertionRate,
--                tnDS3ChannelBERTPattern,
--                tnDS3ChannelBERTDuration,
--                tnDS3ChannelMDLEicString,
--                tnDS3ChannelMDLLicString,
--                tnDS3ChannelMDLFicString,
--                tnDS3ChannelMDLUnitString,
--                tnDS3ChannelMDLPfiString,
--                tnDS3ChannelMDLPortString,
--                tnDS3ChannelMDLGenString,
--                tnDS3ChannelMDLMessageType,
--                tnDS3ChannelFEACLoopRespond,
--                tnDS3ChannelCRC,
--                tnDS3ChannelMTU,
--                tnDS3ChannelOperMTU,
--                tnDS3ChannelReportAlarm,
--                tnDS3ChannelReportAlarmStatus,
--                tnDS3ChannelLastChangeTime,
--                tnDS3ChannelInFEACLoop,
--                tnDS3ChannelMDLMonPortString,
--                tnDS3ChannelMDLMonGenString,
--                tnDS3ChannelBERTOperStatus,
--                tnDS3ChannelBERTSynched,
--                tnDS3ChannelBERTErrors,
--                tnDS3ChannelBERTTotalBits,
--                tnDS3ChannelScramble,
--                tnDS1RowStatus,
--                tnDS1Type,
--                tnDS1Framing,
--                tnDS1Loopback,
--                tnDS1InvertData,
--                tnDS1BitErrorInsertionRate,
--                tnDS1BERTPattern,
--                tnDS1BERTDuration,
--                tnDS1ReportAlarm,
--                tnDS1ReportAlarmStatus,
--                tnDS1LastChangeTime,
--                tnDS1ClockSource,
--                tnDS1BERTOperStatus,
--                tnDS1BERTSynched,
--                tnDS1BERTErrors,
--                tnDS1BERTTotalBits,
--                tnDS1RemoteLoopRespond,
--                tnDS1InRemoteLoop,
--                tnDS0ChanGroupRowStatus,
--                tnDS0ChanGroupTimeSlots,
--                tnDS0ChanGroupSpeed,
--                tnDS0ChanGroupCRC,
--                tnDS0ChanGroupMTU,
--                tnDS0ChanGroupOperMTU,
--                tnDS0ChanGroupLastChangeTime,
--                tnDS0ChanGroupIdleCycleFlags,
--                tnDS0ChanGroupScramble
--            }
--    STATUS      obsolete
--    DESCRIPTION
--        "The group of objects supporting management of TDM type ports
--         for version 5.0 on the Nokia 7x50 SR series systems."
--    ::= { tnPortGroups 42 }

-- tmnx7710PortTDMGroupV5v0   OBJECT-GROUP
--    OBJECTS {
--                tnDS1PortBuildout,
--                tnDS1PortLastChangeTime,
--                tnDS1PortType,
--                tnDS1PortLineLength,
--                tnDS1PortLbo,
--                tnDS1PortDbGain,
--                tnDS1InsertSingleBitError,
--                tnDS0ChanGroupAcctPolicyId,
--                tnDS0ChanGroupCollectStats
--            }
--    STATUS     current
--    DESCRIPTION
--        "The group of objects supporting management of TDM type ports
--         specific to the revision 5.0 on Nokia 7710 SR series systems."
--    ::= { tnPortGroups 43 }
--
-- tnPortCemGroupV6v0   OBJECT-GROUP
--    OBJECTS {
--                tnDS3ChannelClockSyncState,
--                tnDS3ChannelClockMasterPortId,
--                tnDS1SignalMode,
--                tnDS1ClockSyncState,
--                tnDS1ClockMasterPortId,
--                tnDS0ChanGroupPayloadFillType,
--                tnDS0ChanGroupPayloadPattern,
--                tnDS0ChanGroupSignalFillType,
--                tnDS0ChanGroupSignalPattern
--            }
--    STATUS     current
--    DESCRIPTION
--        "The group of objects supporting management of CEM encapsulation TDM
--         type ports specific to the Nokia 7750 and 7710 SR series systems
--         for revision 6.0."
--    ::= { tnPortGroups 44 }

-- tnMcMlpppBundleGroup    OBJECT-GROUP
--    OBJECTS {   tnBundleMlpppClassCount,
--                tnBundleMlpppIngQoSProfId,
--                tnBundleMlpppEgrQoSProfId,
--                tnMcMlpppStatsIngressOct,
--                tnMcMlpppStatsIngressPkt,
--                tnMcMlpppStatsIngressErrPkt,
--                tnMcMlpppStatsEgressOct,
--                tnMcMlpppStatsEgressPkt,
--                tnMcMlpppStatsEgressErrPkt
--            }
--    STATUS      current
--    DESCRIPTION
--        "The group of objects supporting management of MClass MLPPP BUNDLES
--         for revision 6.0 on the Nokia 7x50 SR series systems."
--    ::= { tnPortGroups 45 }

-- tnPortNotificationGroupV6v0 NOTIFICATION-GROUP
--    NOTIFICATIONS   {   tnEqPortSonetAlarm,
--                        tnEqPortSonetAlarmClear,
--                        tnEqPortSonetPathAlarm,
--                        tnEqPortSonetPathAlarmClear,
--                        tnEqPortSFPInserted,
--                        tnEqPortSFPRemoved,
--                        tnEqPortError,
--                        tnEqPortDS3Alarm,
--                        tnEqPortDS3AlarmClear,
--                        tnEqPortDS1Alarm,
--                        tnEqPortDS1AlarmClear,
--                        tnEqPortBndlYellowDiffExceeded,
--                        tnEqPortBndlRedDiffExceeded,
--                        tnEqPortBndlBadEndPtDiscr,
--                        tnEqPortEtherAlarm,
--                        tnEqPortEtherAlarmClear,
--                        tnDS1E1LoopbackStarted,
--                        tnDS1E1LoopbackStopped,
--                        tnDS3E3LoopbackStarted,
--                        tnDS3E3LoopbackStopped,
--                        tnSonetSDHLoopbackStarted,
--                        tnSonetSDHLoopbackStopped,
--                        tnEqPortEtherLoopDetected,
--                        tnEqPortEtherLoopCleared,
--                        tnEqPortSpeedCfgNotCompatible,
--                        tnEqPortDuplexCfgNotCompatible,
--                        tnEqPortIngressRateCfgNotCompatible,
--                        tnEqDigitalDiagMonitorFailure,
--                        tnEqPortSFPStatusFailure,
--                        tmnxDSXClockSyncStateChange
--                    }
--    STATUS        obsolete
--    DESCRIPTION
--        "The group of notifications supporting the management of physical
--         ports for revision 6.0 on Nokia 7x50 SR series systems."
--    ::= { tnPortGroups 46 }
--
-- tnPortEthernetV6v0Group       OBJECT-GROUP
--    OBJECTS {  tnPortEtherMTU,
--                tnPortEtherDuplex,
--                tnPortEtherSpeed,
--                tnPortEtherAutoNegotiate,
--                tnPortEtherOperDuplex,
--                tnPortEtherOperSpeed,
--                tnPortEtherAcctPolicyId,
--                tnPortEtherCollectStats,
--                tnPortEtherMDIMDIX,
--                tnPortEtherXGigMode,
--                tnPortEtherEgressRate,
--                tnPortEtherDot1qEtype,
--                tnPortEtherQinqEtype,
--                tnPortEtherIngressRate,
--                tnPortEtherReportAlarm,
--                tnPortEtherReportAlarmStatus,
--                tnPortEtherPkts1519toMax,
--                tnPortEtherHCOverPkts1519toMax,
--                tnPortEtherHCPkts1519toMax,
--                tnPortEtherLacpTunnel,
--                tnPortEtherDownWhenLoopedEnabled,
--                tnPortEtherDownWhenLoopedKeepAlive,
--                tnPortEtherDownWhenLoopedRetry,
--                tnPortEtherDownWhenLoopedState,
--                tnPortEtherPBBEtype,
--                tnPortEtherReasonDownFlags
--            }
--    STATUS      obsolete
--    DESCRIPTION
--        "The group of objects supporting management of Ethernet ports
--         for revision 6.0 on Nokia 7x50 SR series systems."
--    ::= { tnPortGroups 47 }

-- tmnxMlBundleGroupV6v0    OBJECT-GROUP
--    OBJECTS {   tnBundleRowStatus,
--                tnBundleType,
--                tnBundleMinimumLinks,
--                tnBundleNumLinks,
--                tnBundleNumActiveLinks,
--                tnBundleRedDiffDelay,
--                tnBundleRedDiffDelayAction,
--                tnBundleLastChangeTime,
--                tnBundleFragmentThreshold,
--                tnBundleUpTime,
--                tnBundleMemberRowStatus,
--                tnBundleMemberActive,
--                tnBundleMemberDownReason,
--                tnBundleMemberUpTime,
--                tnBundleInputDiscards,
--                tnBundlePrimaryMemberPortID,
--                tnPortBundleNumber,
--                tnBundleProtectedType,
--                tnBundleParentBundle,
--                tnBPGrpAssocWorkingBundleID,
--                tnBPGrpAssocProtectBundleID,
--                tnBPGrpAssocActiveBundleID
--            }
--    STATUS      current
--    DESCRIPTION
--        "The group of objects supporting management MLBUNDLES
--         for revision 6.0 on the Nokia 7x50 SR series systems."
--    ::= { tnPortGroups 48 }
--
-- tmnxMlpppBundleGroup    OBJECT-GROUP
--    OBJECTS {
--                tnBundleMlpppEndpointID,
--                tnBundleMlpppEndpointIDClass,
--                tnBundleYellowDiffDelay,
--                tnBundleShortSequence,
--                tnBundleMRRU,
--                tnBundleOperMRRU,
--                tnBundlePeerMRRU,
--                tnBundleOperMTU,
--                tnBundleLFI,
--                tnBundleMlpppMagicNumber
--            }
--    STATUS      current
--    DESCRIPTION
--        "The group of objects supporting management of MLPPP Bundles
--         on the Nokia 7x50 SR series systems."
--    ::= { tnPortGroups 49 }

-- tnPortNotificationGroupV3v0 NOTIFICATION-GROUP
--    NOTIFICATIONS   {   tnEqPortSonetAlarm,
--                        tnEqPortSonetAlarmClear,
--                        tnEqPortSonetPathAlarm,
--                        tnEqPortSonetPathAlarmClear,
--                        tnEqPortSFPInserted,
--                        tnEqPortSFPRemoved,
--                        tnEqPortSFPCorrupted,
--                        tnEqPortError,
--                        tnEqPortDS3Alarm,
--                        tnEqPortDS3AlarmClear,
--                        tnEqPortDS1Alarm,
--                        tnEqPortDS1AlarmClear,
--                        tnEqPortBndlYellowDiffExceeded,
--                        tnEqPortBndlRedDiffExceeded,
--                        tnEqPortBndlBadEndPtDiscr,
--                        tnEqPortEtherAlarm,
--                        tnEqPortEtherAlarmClear,
--                        tnEqPortSpeedCfgNotCompatible,
--                        tnEqPortDuplexCfgNotCompatible,
--                        tnEqPortIngressRateCfgNotCompatible
--                    }
--    STATUS        obsolete
--    DESCRIPTION
--        "The group of notifications supporting the management of physical
--         ports for revision 3.0 on Nokia 7x50 SR series systems."
--    ::= { tnPortGroups 50 }


-- tnHsmdaGroupV6v0 OBJECT-GROUP
--    OBJECTS   {
--                  tnPortEgrHsmdaSchedPlcy,
--                  tnHsmdaPortSchOvrTblLastChngd,
--                  tnHsmdaPortSchOvrRowStatus,
--                  tnHsmdaPortSchOvrLastChanged,
--                  tnHsmdaPortSchOvrMaxRate,
--                  tnHsmdaPortSchOvrGrp1Rate,
--                  tnHsmdaPortSchOvrGrp2Rate,
--                  tnHsmdaPortSchOvrClass1Rate,
--                  tnHsmdaPortSchOvrClass1WtInGp,
--                  tnHsmdaPortSchOvrClass2Rate,
--                  tnHsmdaPortSchOvrClass2WtInGp,
--                  tnHsmdaPortSchOvrClass3Rate,
--                  tnHsmdaPortSchOvrClass3WtInGp,
--                  tnHsmdaPortSchOvrClass4Rate,
--                  tnHsmdaPortSchOvrClass4WtInGp,
--                  tnHsmdaPortSchOvrClass5Rate,
--                  tnHsmdaPortSchOvrClass5WtInGp,
--                  tnHsmdaPortSchOvrClass6Rate,
--                  tnHsmdaPortSchOvrClass6WtInGp,
--                  tnHsmdaPortSchOvrClass7Rate,
--                  tnHsmdaPortSchOvrClass7WtInGp,
--                  tnHsmdaPortSchOvrClass8Rate,
--                  tnHsmdaPortSchOvrClass8WtInGp,
--                  tnPortEgrShaperTblLastChanged,
--                  tnPortEgrShaperRowStatus,
--                  tnPortEgrShaperLastChanged,
--                  tnPortEgrShaperRate
--              }
--    STATUS        current
--    DESCRIPTION
--        "The group of objects supporting the management of HSMDA
--         ports for revision 6.0 on Nokia 7x50 SR series systems."
--    ::= { tnPortGroups 51 }

-- tnPortTDMGroupV6v0    OBJECT-GROUP
--    OBJECTS {   tnDS3ChannelAcctPolicyId,
--                tnDS3ChannelCollectStats,
--                tnDS3Buildout,
--                tnDS3Type,
--                tnDS3LastChangeTime,
--                tnDS3ChannelRowStatus,
--                tnDS3ChannelType,
--                tnDS3ChannelFraming,
--                tnDS3ChannelClockSource,
--                tnDS3ChannelChannelized,
--                tnDS3ChannelSubrateCSUMode,
--                tnDS3ChannelSubrate,
--                tnDS3ChannelIdleCycleFlags,
--                tnDS3ChannelLoopback,
--                tnDS3ChannelBitErrorInsertionRate,
--                tnDS3ChannelBERTPattern,
--                tnDS3ChannelBERTDuration,
--                tnDS3ChannelMDLEicString,
--                tnDS3ChannelMDLLicString,
--                tnDS3ChannelMDLFicString,
--                tnDS3ChannelMDLUnitString,
--                tnDS3ChannelMDLPfiString,
--                tnDS3ChannelMDLPortString,
--                tnDS3ChannelMDLGenString,
--                tnDS3ChannelMDLMessageType,
--                tnDS3ChannelFEACLoopRespond,
--                tnDS3ChannelCRC,
--                tnDS3ChannelMTU,
--                tnDS3ChannelOperMTU,
--                tnDS3ChannelReportAlarm,
--                tnDS3ChannelReportAlarmStatus,
--                tnDS3ChannelLastChangeTime,
--                tnDS3ChannelInFEACLoop,
--                tnDS3ChannelMDLMonPortString,
--                tnDS3ChannelMDLMonGenString,
--                tnDS3ChannelBERTOperStatus,
--                tnDS3ChannelBERTSynched,
--                tnDS3ChannelBERTErrors,
--                tnDS3ChannelBERTTotalBits,
--                tnDS3ChannelScramble,
--                tnDS1RowStatus,
--                tnDS1Type,
--                tnDS1Framing,
--                tnDS1Loopback,
--                tnDS1InvertData,
--                tnDS1BitErrorInsertionRate,
--                tnDS1BERTPattern,
--                tnDS1BERTDuration,
--                tnDS1ReportAlarm,
--                tnDS1ReportAlarmStatus,
--                tnDS1LastChangeTime,
--                tnDS1ClockSource,
--                tnDS1BERTOperStatus,
--                tnDS1BERTSynched,
--                tnDS1BERTErrors,
--                tnDS1BERTTotalBits,
--                tnDS1RemoteLoopRespond,
--                tnDS1InRemoteLoop,
--                tnDS1BerSdThreshold,
--                tnDS1BerSfThreshold,
--                tnDS0ChanGroupRowStatus,
--                tnDS0ChanGroupTimeSlots,
--                tnDS0ChanGroupSpeed,
--                tnDS0ChanGroupCRC,
--                tnDS0ChanGroupMTU,
--                tnDS0ChanGroupOperMTU,
--                tnDS0ChanGroupLastChangeTime,
--                tnDS0ChanGroupIdleCycleFlags,
--                tnDS0ChanGroupScramble
--            }
--    STATUS      current
--    DESCRIPTION
--        "The group of objects supporting management of TDM type ports
--         for version 6.0 on the Nokia 7x50 SR series systems."
--    ::= { tnPortGroups 52 }

-- tnDigitalDiagMonitorGroup OBJECT-GROUP
--    OBJECTS   {
--                  tnDDMTemperature,
--                  tnDDMTempLowWarning,
--                  tnDDMTempLowAlarm,
--                  tnDDMTempHiWarning,
--                  tnDDMTempHiAlarm,
--                  tnDDMSupplyVoltage,
--                  tnDDMSupplyVoltageLowWarning,
--                  tnDDMSupplyVoltageLowAlarm,
--                  tnDDMSupplyVoltageHiWarning,
--                  tnDDMSupplyVoltageHiAlarm,
--                  tnDDMTxBiasCurrent,
--                  tnDDMTxBiasCurrentLowWarning,
--                  tnDDMTxBiasCurrentLowAlarm,
--                  tnDDMTxBiasCurrentHiWarning,
--                  tnDDMTxBiasCurrentHiAlarm,
--                  tnDDMTxOutputPower,
--                  tnDDMTxOutputPowerLowWarning,
--                  tnDDMTxOutputPowerLowAlarm,
--                  tnDDMTxOutputPowerHiWarning,
--                  tnDDMTxOutputPowerHiAlarm,
--                  tnDDMRxOpticalPower,
--                  tnDDMRxOpticalPowerLowWarning,
--                  tnDDMRxOpticalPowerLowAlarm,
--                  tnDDMRxOpticalPowerHiWarning,
--                  tnDDMRxOpticalPowerHiAlarm,
--                  tnDDMRxOpticalPowerType,
--                  tnDDMAux1,
--                  tnDDMAux1LowWarning,
--                  tnDDMAux1LowAlarm,
--                  tnDDMAux1HiWarning,
--                  tnDDMAux1HiAlarm,
--                  tnDDMAux1Type,
--                  tnDDMAux2,
--                  tnDDMAux2LowWarning,
--                  tnDDMAux2LowAlarm,
--                  tnDDMAux2HiWarning,
--                  tnDDMAux2HiAlarm,
--                  tnDDMAux2Type,
--                  tnDDMFailedThresholds,
--                  tnDDMExternallyCalibrated,
--                  tnDDMExtCalRxPower4,
--                  tnDDMExtCalRxPower3,
--                  tnDDMExtCalRxPower2,
--                  tnDDMExtCalRxPower1,
--                  tnDDMExtCalRxPower0,
--                  tnDDMExtCalTxLaserBiasSlope,
--                  tnDDMExtCalTxLaserBiasOffset,
--                  tnDDMExtCalTxPowerSlope,
--                  tnDDMExtCalTxPowerOffset,
--                  tnDDMExtCalTemperatureSlope,
--                  tnDDMExtCalTemperatureOffset,
--                  tnDDMExtCalVoltageSlope,
--                  tnDDMExtCalVoltageOffset
--              }
--    STATUS        current
--    DESCRIPTION
--        "The group of objects supporting the management of
--         Digital Diagnostic Monitoring SFP/XFPs for revision 6.0 on
--         Nokia 7x50 SR series systems."
--    ::= { tnPortGroups 53 }
--
-- tnPortGroupV6v0   OBJECT-GROUP
--    OBJECTS {   tnPortTableLastChange,
--                tnPortLastChangeTime,
--                tnPortType,
--                tnPortClass,
--                tnPortDescription,
--                tnPortName,
--                tnPortAlias,
--                tnPortUserAssignedMac,
--                tnPortMacAddress,
--                tnPortHwMacAddress,
--                tnPortMode,
--                tnPortEncapType,
--                tnPortLagId,
--                tnPortHoldTimeUp,
--                tnPortHoldTimeDown,
--                tnPortUpProtocols,
--                tnPortConnectorType,
--                tnPortTransceiverType,
--                tnPortTransceiverLaserWaveLen,
--                tnPortTransceiverDiagCapable,
--                tnPortTransceiverModelNumber,
--                tnPortSFPConnectorCode,
--                tnPortSFPVendorOUI,
--                tnPortSFPVendorManufactureDate,
--                tnPortSFPMedia,
--                tnPortSFPEquipped,
--                tnPortSFPVendorSerialNum,
--                tnPortSFPVendorPartNum,
--                tnPortEquipped,
--                tnPortLinkStatus,
--                tnPortAdminStatus,
--                tnPortOperStatus,
--                tnPortState,
--                tnPortPrevState,
--                tnPortNumAlarms,
--                tnPortAlarmState,
--                tnPortLastAlarmEvent,
--                tnPortClearAlarms,
--                tnPortLastStateChanged,
--                tnPortNumChannels,
--                tnPortNetworkEgrQueues,
--                tnPortIsLeaf,
--                tnPortChanType,
--                tnPortParentPortID,
--                tnPortLoadBalanceAlgorithm,
--                tnPortTypeName,
--                tnPortTypeDescription,
--                tnPortTypeStatus,
--                tnPortConnectTypeName,
--                tnPortConnectTypeDescription,
--                tnPortConnectTypeStatus,
--                tmnxChannelPortID,
--                tnPortOpticalCompliance,
--                tnL4LoadBalancing,
--                tnPortLastClearedTime,
--                tnPortDDMEventSuppression,
--                tnPortSFPStatus,
--                tnPortReasonDownFlags
--            }
--    STATUS        obsolete
--    DESCRIPTION
--        "The group of objects supporting management of physical port
--         capabilities for revision 6.0 on Nokia 7x50 SR series systems."
--    ::= { tnPortGroups 54 }

-- tmnxNamedPoolGroupV6v0 OBJECT-GROUP
--    OBJECTS {
--                tnPortIngNamedPoolPlcy,
--                tnPortEgrNamedPoolPlcy,
--                tnPortIngPoolPercentRate,
--                tnPortEgrPoolPercentRate
--            }
--    STATUS        current
--    DESCRIPTION
--        "The group of objects supporting the Named Pool feature
--         for revision 6.0 on Nokia 7x50 SR series systems."
--    ::= { tnPortGroups 55 }

-- tnPortEthernetV6v1Group       OBJECT-GROUP
--    OBJECTS {   tnPortEtherMTU,
--                tnPortEtherDuplex,
--                tnPortEtherSpeed,
--                tnPortEtherAutoNegotiate,
--                tnPortEtherOperDuplex,
--                tnPortEtherOperSpeed,
--                tnPortEtherAcctPolicyId,
--                tnPortEtherCollectStats,
--                tnPortEtherMDIMDIX,
--                tnPortEtherXGigMode,
--                tnPortEtherEgressRate,
--                tnPortEtherDot1qEtype,
--                tnPortEtherQinqEtype,
--                tnPortEtherIngressRate,
--                tnPortEtherReportAlarm,
--                tnPortEtherReportAlarmStatus,
--                tnPortEtherPkts1519toMax,
--                tnPortEtherHCOverPkts1519toMax,
--                tnPortEtherHCPkts1519toMax,
--                tnPortEtherLacpTunnel,
--                tnPortEtherDownWhenLoopedEnabled,
--                tnPortEtherDownWhenLoopedKeepAlive,
--                tnPortEtherDownWhenLoopedRetry,
--                tnPortEtherDownWhenLoopedState,
--                tnPortEtherPBBEtype,
--                tnPortEtherReasonDownFlags,
--                tnPortEtherSingleFiber
--            }
--    STATUS      obsolete
--    DESCRIPTION
--        "The group of objects supporting management of Ethernet ports
--         for revision 6.1 on Nokia 7x50 SR series systems."
--    ::= { tnPortGroups 56 }

-- tnPortNotifyObjsGroupV6v0     OBJECT-GROUP
--    OBJECTS {
--                tnDDMFailedObject,
--                tmnxDSXClockSyncStateObject
--            }
--    STATUS        current
--    DESCRIPTION
--        "The group of objects supporting physical port notifications
--         for revision 6.0 on Nokia 7x50 SR series systems."
--    ::= { tnPortGroups 57 }

-- tnPortQV7v0Group       OBJECT-GROUP
--    OBJECTS {
--        tnPortAccEgrQGrpAggRateLimit,
--        tnPortAccEgrQGrpLastChgd,
--        tnPortAccEgrQGrpRowStatus,
--        tnPortAccEgrQGrpSchedPol,
--        tnPortAccEgrQGrpAcctgPolId,
--        tnPortAccEgrQGrpCollectStats,
--        tnPortAccEgrQGrpFrameBaseActg,
--        tnPortAccEgrQGrpTableLastChgd,
--        tnPortAccEgrQOverLastChanged,
--        tnPortAccEgrQOverRowStatus,
--        tnPortAccEgrQOverTableLastChgd,
--        tnPortAccEgrQOverAdminCIR,
--        tnPortAccEgrQOverAdminPIR,
--        tnPortAccEgrQOverCBS,
--        tnPortAccEgrQOverHiPrioOnly,
--        tnPortAccEgrQOverMBS,
--        tnPortAccIngQGrpLastChgd,
--        tnPortAccIngQGrpRowStatus,
--        tnPortAccIngQGrpSchedPol,
--        tnPortAccIngQGrpAcctgPolId,
--        tnPortAccIngQGrpCollectStats,
--        tnPortAccIngQGrpTableLastChgd,
--        tnPortAccIngQOverLastChanged,
--        tnPortAccIngQOverRowStatus,
--        tnPortAccIngQOverTableLastChgd,
--        tnPortAccIngQOverAdminCIR,
--        tnPortAccIngQOverAdminPIR,
--        tnPortAccIngQOverCBS,
--        tnPortAccIngQOverHiPrioOnly,
--        tnPortAccIngQOverMBS,
--        tnPortNetEgrQGrpAcctgPolId,
--        tnPortNetEgrQGrpAggRateLimit,
--        tnPortNetEgrQGrpCollectStats,
--        tnPortNetEgrQGrpFrameBaseActg,
--        tnPortNetEgrQGrpLastChgd,
--        tnPortNetEgrQGrpRowStatus,
--        tnPortNetEgrQGrpSchedPol,
--        tnPortNetEgrQGrpTableLastChgd,
--        tnPortNetEgrQOverAdminCIR,
--        tnPortNetEgrQOverAdminPIR,
--        tnPortNetEgrQOverCBS,
--        tnPortNetEgrQOverHiPrioOnly,
--        tnPortNetEgrQOverLastChanged,
--        tnPortNetEgrQOverMBS,
--        tnPortNetEgrQOverRowStatus,
--        tnPortNetEgrQOverTableLastChgd,
--        tnPortAccEgrQOverCIRAdaptation,
--        tnPortAccEgrQOverPIRAdaptation,
--        tnPortAccIngQOverCIRAdaptation,
--        tnPortAccIngQOverPIRAdaptation,
--        tnPortNetEgrQOverCIRAdaptation,
--        tnPortNetEgrQOverPIRAdaptation,
--        tnPortAccIngQGrpDescr,
--        tnPortAccEgrQGrpDescr,
--        tnPortNetEgrQGrpDescr
--    }
--    STATUS      current
--    DESCRIPTION
--        "The group of objects supporting management of Ethernet ports
--         for revision 7.0 on Nokia 7x50 SR series systems."
--    ::= { tnPortGroups 58 }

-- tmnxMcMfrBundleGroup    OBJECT-GROUP
--    OBJECTS {
--        tnBundleMlfrBundleId,
--        tnBundleMlfrIngQoSProfId,
--        tnBundleMlfrEgrQoSProfId,
--        tnBundleMlfrHelloTimer,
--        tnBundleMlfrHelloRetryCount,
--        tnBundleMlfrAckTimer,
--        tnBundleMlfrLastChanged,
--        tnBundleMemberMlfrDownReason
--            }
--    STATUS      current
--    DESCRIPTION
--        "The group of objects supporting management of MClass Mlfr Bundles
--         for revision 7.0 on the Nokia 7x50 SR series systems."
--    ::= { tnPortGroups 59 }

-- tmnxFrIntfGroup    OBJECT-GROUP
--    OBJECTS {
--        tmnxFrIntfFrf12Mode,
--        tmnxFrIntfLinkId,
--        tmnxFrIntfLastChanged
--            }
--    STATUS      current
--    DESCRIPTION
--        "The group of objects supporting management of Frame-Relay
--         Interfaces for revision 7.0 on the Nokia 7x50 SR series systems."
--    ::= { tnPortGroups 60 }
--
-- tmnxFrf12IntfGroup    OBJECT-GROUP
--    OBJECTS {
--        tmnxFrf12IntfFragmentThreshold,
--        tmnxFrf12IntfEgrQoSProfId,
--        tmnxFrf12IntfLastChanged
--            }
--    STATUS      current
--    DESCRIPTION
--        "The group of objects supporting management of Frame-Relay Frf12
--         Interfaces for revision 7.0 on the Nokia 7x50 SR series systems."
--    ::= { tnPortGroups 61 }
--
-- tnPortQStatV7v0Group       OBJECT-GROUP
--    OBJECTS {
--       tnPortEgrQosQStatDpdInProfOcts,
--       tnPortEgrQosQStatDpdInProfPkts,
--       tnPortEgrQosQStatDpdOutProfOcts,
--       tnPortEgrQosQStatDpdOutProfPkts,
--       tnPortEgrQosQStatFwdInProfOcts,
--       tnPortEgrQosQStatFwdInProfPkts,
--       tnPortEgrQosQStatFwdOutProfOcts,
--       tnPortEgrQosQStatFwdOutProfPkts,
--       tnPortIngQosQStatDpdHiPrioOcts,
--       tnPortIngQosQStatDpdHiPrioPkts,
--       tnPortIngQosQStatDpdLoPrioOcts,
--       tnPortIngQosQStatDpdLoPrioPkts,
--       tnPortIngQosQStatFwdInProfOcts,
--       tnPortIngQosQStatFwdInProfPkts,
--       tnPortIngQosQStatFwdOutProfOcts,
--       tnPortIngQosQStatFwdOutProfPkts,
--       tnPortIngQosQStatOffHiPrioOcts,
--       tnPortIngQosQStatOffHiPrioPkts,
--       tnPortIngQosQStatOffLoPrioOcts,
--       tnPortIngQosQStatOffLoPrioPkts,
--       tnPortIngQosQStatUncolOctsOff,
--       tnPortIngQosQStatUncolPktsOff,
--       tnPortNetEgrQDroInProfOcts,
--       tnPortNetEgrQDroInProfPkts,
--       tnPortNetEgrQDroOutProfOcts,
--       tnPortNetEgrQDroOutProfPkts,
--       tnPortNetEgrQFwdInProfOcts,
--       tnPortNetEgrQFwdInProfPkts,
--       tnPortNetEgrQFwdOutProfOcts,
--       tnPortNetEgrQFwdOutProfPkts
--    }
--    STATUS      current
--    DESCRIPTION
--        "The group of objects supporting management of ethernet port
--         queue group statistics on the Nokia 7x50 SR series systems."
--    ::= { tnPortGroups 62 }

-- tnPortEthernetV7v0Group       OBJECT-GROUP
--    OBJECTS {   tnPortEtherMTU,
--                tnPortEtherDuplex,
--                tnPortEtherSpeed,
--                tnPortEtherAutoNegotiate,
--                tnPortEtherOperDuplex,
--                tnPortEtherOperSpeed,
--                tnPortEtherAcctPolicyId,
--                tnPortEtherCollectStats,
--                tnPortEtherMDIMDIX,
--                tnPortEtherXGigMode,
--                tnPortEtherEgressRate,
--                tnPortEtherDot1qEtype,
--                tnPortEtherQinqEtype,
--                tnPortEtherIngressRate,
--                tnPortEtherReportAlarm,
--                tnPortEtherReportAlarmStatus,
--                tnPortEtherPkts1519toMax,
--                tnPortEtherHCOverPkts1519toMax,
--                tnPortEtherHCPkts1519toMax,
--                tnPortEtherLacpTunnel,
--                tnPortEtherDownWhenLoopedEnabled,
--                tnPortEtherDownWhenLoopedKeepAlive,
--                tnPortEtherDownWhenLoopedRetry,
--                tnPortEtherDownWhenLoopedState,
--                tnPortEtherPBBEtype,
--                tnPortEtherSingleFiber,
--                tnPortEtherSSM,
--                tnPortEtherDWLUseBroadcastAddr
--            }
--    STATUS      current
--    DESCRIPTION
--        "The group of objects supporting management of Ethernet ports
--         for revision 7.0 on Nokia 7x50 SR series systems."
--    ::= { tnPortGroups 63 }
--
-- tnPortGroupV7v0   OBJECT-GROUP
--    OBJECTS {   tnPortTableLastChange,
--                tnPortLastChangeTime,
--                tnPortType,
--                tnPortClass,
--                tnPortDescription,
--                tnPortName,
--                tnPortAlias,
--                tnPortUserAssignedMac,
--                tnPortMacAddress,
--                tnPortHwMacAddress,
--                tnPortMode,
--                tnPortEncapType,
--                tnPortLagId,
--                tnPortHoldTimeUp,
--                tnPortHoldTimeDown,
--                tnPortUpProtocols,
--                tnPortConnectorType,
--                tnPortTransceiverType,
--                tnPortTransceiverLaserWaveLen,
--                tnPortTransceiverDiagCapable,
--                tnPortTransceiverModelNumber,
--                tnPortSFPConnectorCode,
--                tnPortSFPVendorOUI,
--                tnPortSFPVendorManufactureDate,
--                tnPortSFPMedia,
--                tnPortSFPEquipped,
--                tnPortSFPVendorSerialNum,
--                tnPortSFPVendorPartNum,
--                tnPortEquipped,
--                tnPortLinkStatus,
--                tnPortAdminStatus,
--                tnPortOperStatus,
--                tnPortState,
--                tnPortPrevState,
--                tnPortNumAlarms,
--                tnPortAlarmState,
--                tnPortLastAlarmEvent,
--                tnPortClearAlarms,
--                tnPortLastStateChanged,
--                tnPortNumChannels,
--                tnPortNetworkEgrQueues,
--                tnPortIsLeaf,
--                tnPortChanType,
--                tnPortParentPortID,
--                tnPortLoadBalanceAlgorithm,
--                tnPortTypeName,
--                tnPortTypeDescription,
--                tnPortTypeStatus,
--                tnPortConnectTypeName,
--                tnPortConnectTypeDescription,
--                tnPortConnectTypeStatus,
--                tmnxChannelPortID,
--                tnPortOpticalCompliance,
--                tnL4LoadBalancing,
--                tnLsrIpLoadBalancing,
--                tnPortLastClearedTime,
--                tnPortDDMEventSuppression,
--                tnPortSFPStatus,
--                tnPortReasonDownFlags,
--                tnPortSSMRxQualityLevel,
--                tnPortDwdmLaserChannel,
--                tnPortOtuCapable,
--                tnPortHoldTimeUnits,
--                tnPortLinkLengthInfo,
--                tnPortSFPNumLanes,
--                tnPortPhysStateChangeCount,
--                tnSonetSuppressLoOrderAlarm
--            }
--    STATUS        current
--    DESCRIPTION
--        "The group of objects supporting management of physical port
--         capabilities for revision 7.0 on Nokia 7x50 SR series systems."
--    ::= { tnPortGroups 64 }

-- tnPortNotifyObjsGroupV7v0     OBJECT-GROUP
--    OBJECTS {   tnPortNotifyDescription
--            }
--    STATUS        current
--    DESCRIPTION
--        "The group of objects supporting physical port notifications
--         for revision 7.0 on Nokia 7xxx series systems."
--    ::= { tnPortGroups 65 }

-- tnPortNotificationGroupV7v0 NOTIFICATION-GROUP
--    NOTIFICATIONS   {   tnEqPortSonetAlarm,
--                        tnEqPortSonetAlarmClear,
--                        tnEqPortSonetPathAlarm,
--                        tnEqPortSonetPathAlarmClear,
--                        tnEqPortSFPInserted,
--                        tnEqPortSFPRemoved,
--                        tnEqPortError,
--                        tnEqPortDS3Alarm,
--                        tnEqPortDS3AlarmClear,
--                        tnEqPortDS1Alarm,
--                        tnEqPortDS1AlarmClear,
--                        tnEqPortBndlYellowDiffExceeded,
--                        tnEqPortBndlRedDiffExceeded,
--                        tnEqPortBndlBadEndPtDiscr,
--                        tnEqPortEtherAlarm,
--                        tnEqPortEtherAlarmClear,
--                        tnDS1E1LoopbackStarted,
--                        tnDS1E1LoopbackStopped,
--                        tnDS3E3LoopbackStarted,
--                        tnDS3E3LoopbackStopped,
--                        tnSonetSDHLoopbackStarted,
--                        tnSonetSDHLoopbackStopped,
--                        tnEqPortEtherLoopDetected,
--                        tnEqPortEtherLoopCleared,
--                        tnEqPortSpeedCfgNotCompatible,
--                        tnEqPortDuplexCfgNotCompatible,
--                        tnEqPortIngressRateCfgNotCompatible,
--                        tnEqDigitalDiagMonitorFailure,
--                        tnEqPortSFPStatusFailure,
--                        tmnxDSXClockSyncStateChange,
--                        tnPortUnsupportedFunction,
--                        tnBundleMemberMlfrLoopback
--            }
--    STATUS        current
--    DESCRIPTION
--        "The group of notifications supporting the management of physical
--         ports for revision 7.0 on Nokia 7xxx series systems."
--    ::= { tnPortGroups 66 }

-- tnPortEtherObsoleteV7v0Group  OBJECT-GROUP
--    OBJECTS {   tnPortEtherReasonDownFlags
--            }
--    STATUS      current
--    DESCRIPTION
--        "The objects which were obsoleted for revision 7.0 on Nokia 7xxx
--         series systems."
--    ::= { tnPortGroups 67 }

-- tnPortTDMGroupV7v0    OBJECT-GROUP
--    OBJECTS {   tnDS3ChannelAcctPolicyId,
--                tnDS3ChannelCollectStats,
--                tnDS3Buildout,
--                tnDS3Type,
--                tnDS3LastChangeTime,
--                tnDS3ChannelRowStatus,
--                tnDS3ChannelType,
--                tnDS3ChannelFraming,
--                tnDS3ChannelClockSource,
--                tnDS3ChannelChannelized,
--                tnDS3ChannelSubrateCSUMode,
--                tnDS3ChannelSubrate,
--                tnDS3ChannelIdleCycleFlags,
--                tnDS3ChannelLoopback,
--                tnDS3ChannelBitErrorInsertionRate,
--                tnDS3ChannelBERTPattern,
--                tnDS3ChannelBERTDuration,
--                tnDS3ChannelMDLEicString,
--                tnDS3ChannelMDLLicString,
--                tnDS3ChannelMDLFicString,
--                tnDS3ChannelMDLUnitString,
--                tnDS3ChannelMDLPfiString,
--                tnDS3ChannelMDLPortString,
--                tnDS3ChannelMDLGenString,
--                tnDS3ChannelMDLMessageType,
--                tnDS3ChannelFEACLoopRespond,
--                tnDS3ChannelCRC,
--                tnDS3ChannelMTU,
--                tnDS3ChannelOperMTU,
--                tnDS3ChannelReportAlarm,
--                tnDS3ChannelReportAlarmStatus,
--                tnDS3ChannelLastChangeTime,
--                tnDS3ChannelInFEACLoop,
--                tnDS3ChannelMDLMonPortString,
--                tnDS3ChannelMDLMonGenString,
--                tnDS3ChannelBERTOperStatus,
--                tnDS3ChannelBERTSynched,
--                tnDS3ChannelBERTErrors,
--                tnDS3ChannelBERTTotalBits,
--                tnDS3ChannelScramble,
--                tnDS1RowStatus,
--                tnDS1Type,
--                tnDS1Framing,
--                tnDS1Loopback,
--                tnDS1InvertData,
--                tnDS1BitErrorInsertionRate,
--                tnDS1BERTPattern,
--                tnDS1BERTDuration,
--                tnDS1ReportAlarm,
--                tnDS1ReportAlarmStatus,
--                tnDS1LastChangeTime,
--                tnDS1ClockSource,
--                tnDS1BERTOperStatus,
--                tnDS1BERTSynched,
--                tnDS1BERTErrors,
--                tnDS1BERTTotalBits,
--                tnDS1RemoteLoopRespond,
--                tnDS1InRemoteLoop,
--                tnDS1BerSdThreshold,
--                tnDS1BerSfThreshold,
--                tnDS0ChanGroupRowStatus,
--                tnDS0ChanGroupTimeSlots,
--                tnDS0ChanGroupSpeed,
--                tnDS0ChanGroupCRC,
--                tnDS0ChanGroupMTU,
--                tnDS0ChanGroupOperMTU,
--                tnDS0ChanGroupLastChangeTime,
--                tnDS0ChanGroupIdleCycleFlags,
--                tnDS0ChanGroupScramble,
--                tnDS0ChanGroupBerSfLinkDown
--            }
--    STATUS      current
--    DESCRIPTION
--        "The group of objects supporting management of TDM type ports
--         for version 6.0 on the Nokia 7x50 SR series systems."
--    ::= { tnPortGroups 68 }

-- tnPortTDME1GroupV6v1    OBJECT-GROUP
--    OBJECTS {  tnDS1NationalUseBits
--            }
--    STATUS      current
--    DESCRIPTION
--        "The group of objects supporting management of TDM E1 type ports
--         for version 6.1 on the Nokia 7x50 SR series systems."
--    ::= { tnPortGroups 69 }

-- tnPortGroupV8v0                OBJECT-GROUP
--    OBJECTS {
--                tnPortHybridIngAccessWeight,
--                tnPortHybridIngNetworkWeight,
--                tnPortHybridEgrAccessWeight,
--                tnPortHybridEgrNetworkWeight,
--                tnPortInterfaceGroupHandlerIdx,
--                tnPortEtherSSMCodeType,
--                tnPortEtherSSMTxDus,
--                tnSonetTxDus,
--                tnPortAccIngQOverMBSBytes,
--                tnPortAccEgrQOverMBSBytes,
--                tnPortNetEgrQOverMBSBytes,
--                tnPortNetEgrQOverAdminPIRPercent,
--                tnPortNetEgrQOverAdminCIRPercent,
--                tnPortNetEgrQOverRateType,
--                tnPortAccEgrQOverAdminPIRPercent,
--                tnPortAccEgrQOverAdminCIRPercent,
--                tnPortAccEgrQOverRateType,
--                tnPortAccEgrQGrpHMTableLastChgd,
--                tnPortAccEgrQGrpHMRowStatus,
--                tnPortAccEgrQGrpHMLastChgd,
--                tnPortHoldTimeUnits,
--                tPortEgrVPortHMRowStatus,
--                tPortEgrVPortHMLastChgd,
--                tnSonetTxS1Byte,
--                tnPortEtherSSMRxEsmc,
--                tnPortEtherSSMTxQualityLevel
--            }
--    STATUS      current
--    DESCRIPTION
--        "The group of objects added in revision 8.0 Nokia SROS series
--         systems for port management."
--    ::= { tnPortGroups 72 }

--tmnxPortATMGroupV7v0     OBJECT-GROUP
--    OBJECTS {
--                tmnxATMIntfCellFormat,
--                tmnxATMIntfMinVpValue,
--                tmnxATMIntfMapping,
--                tmnxATMIntfCustomBufferMode,
--                tmnxATMIntfBufferPool,
--                tmnxATMIntfVcThreshold
--            }
--    STATUS      current
--    DESCRIPTION
--        "The group of objects supporting management of ATM interfaces
--         for version 7.0 on Nokia 7x50 SR series systems."
--    ::= { tmnxPortGroups 74 }
--
--tmnxMlpppBundleGroupV7v0    OBJECT-GROUP
--    OBJECTS {
--                tmnxBundleMlpppStatelessApsSwo
--            }
--    STATUS      current
--    DESCRIPTION
--        "The group of additional objects supporting management of MLPPP Bundles
--         for revision 7.0 on Nokia 7x50 SR series systems."
--    ::= { tmnxPortGroups 81 }

END
