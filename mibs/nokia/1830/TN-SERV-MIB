TN-SERV-MIB DEFINITIONS ::= BEGIN

-- (c) Copyright 2023 Nokia Networks.  All rights reserved.
-- This software is the confidential and proprietary property of
-- Nokia and may only be used in accordance with the terms of the
-- license agreement provided with this software.

IMPORTS
    MODULE-IDENTITY, OBJECT-TYPE,
    Integer32, Unsigned32, IpAddress,
    TimeTicks, Counter32                        FROM SNMPv2-SMI

    InterfaceIndexOrZero                        FROM IF-MIB

    TEXTUAL-CONVENTION, DisplayString,
    RowStatus, MacAddress, TimeStamp,
    TruthValue                                  FROM SNMPv2-TC

    InetAddressType, InetAddress
                                                FROM INET-ADDRESS-MIB

    ServiceAdminStatus, ServiceOperStatus,
    TmnxPortID, TmnxEncapVal,
    TmnxServId, TmnxCustId, TNamedItem,
    TmnxVRtrIDOrZero,
    TNamedItemOrEmpty,
    TmnxEnabledDisabled,
    ServObjDesc, SdpBindId, TmnxActionType
                                                FROM TN-TC-MIB

    tnSRMIBModules, tnSRObjs,
    tnSRNotifyPrefix                            FROM TROPIC-GLOBAL-REG

    tnSysSwitchId                               FROM TROPIC-SYSTEM-MIB
    ;

tnServicesMIBModule   MODULE-IDENTITY
    LAST-UPDATED    "201909130000Z"
    ORGANIZATION    "Nokia"
    CONTACT-INFO
        "Nokia 7x50 Support
         Web: http://www.nokia.com/comps/pages/carrier_support.jhtml"
    DESCRIPTION
        "This  document  is the SNMP MIB module to manage and provision
        the various services of the Nokia 7x50 SR system.

        This   SNMP   MIB  module  (Specification)  embodies  Nokia's
        proprietary  intellectual  property.  Nokia retains all title
        and ownership in the Specification, including any revisions.

        Nokia  grants  all interested parties a non-exclusive license
        to  use and distribute an unmodified copy of this Specification
        in  connection with management of Nokia products, and without
        fee,  provided  this copyright notice and license appear on all
        copies.

        This  Specification  is  supplied `as is', and Nokia makes no
        warranty,  either express or implied, as to the use, operation,
        condition, or performance of the Specification."

--
--  Revision History
--

    REVISION        "201909130000Z"
    DESCRIPTION     "Added the following to tnSvcBaseInfoTable:
                     tnSvcAlmProfName."

    REVISION        "201809210000Z"
    DESCRIPTION     "Added the following to tnSvcTlsInfoTable:
                     tnSvcTlsMfibTableNumEntries."

    REVISION        "201807200000Z"
    DESCRIPTION     "Added the following textual convention:
                     PWTemplateId."

    REVISION        "201707070000Z"
    DESCRIPTION     "Added etree(16) to ServType."

    REVISION        "201603150000Z"
    DESCRIPTION     "Added the following to tnSvcBaseInfoTable:
                        tnsvcEpipeAllowIpIfBinding."

    REVISION        "201511020000Z"
    DESCRIPTION     "Added the following MIB table:
                     tnSvcEndPointTable."

    REVISION        "201212130000Z"
    DESCRIPTION     "1) Added the following to tnSvcBaseInfoTable:
                        tnSvcName.
                     2) Added the following to tnSvcTlsInfoTable:
                        tnsvcTlsAllowIpIfBinding."

    REVISION        "201212050000Z"
    DESCRIPTION     "Commented out unsupported MIB tables and
                     attributes for 1830."

    REVISION        "201209010000Z"
    DESCRIPTION     "Changed the following indexes from read-only to
                     not-accessible:
                     tnCustId
                     tnCustMultSvcSiteName
                     tnSvcId
                     tnTlsFdbMacAddr
                     tnIesIfIndex."

    REVISION        "200902280000Z"
    DESCRIPTION     "Rev 7.0                28 Feb 2009 00:00
                     7.0 release of the TIMETRA-SERV-MIB."

    REVISION        "200807010000Z"
    DESCRIPTION     "Rev 6.1                01 Jul 2008 00:00
                     6.1 release of the TIMETRA-SERV-MIB."

    REVISION        "200801010000Z"
    DESCRIPTION     "Rev 6.0                01 Jan 2008 00:00
                     6.0 release of the TIMETRA-SERV-MIB."

    REVISION        "200701010000Z"
    DESCRIPTION     "Rev 5.0                01 Jan 2007 00:00
                     5.0 release of the TIMETRA-SERV-MIB."

    REVISION        "200602280000Z"
    DESCRIPTION     "Rev 4.0                28 Feb 2006 00:00
                     4.0 release of the TIMETRA-SERV-MIB."

    REVISION        "200508310000Z"
    DESCRIPTION     "Rev 3.0                31 Aug 2005 00:00
                     3.0 release of the TIMETRA-SERV-MIB."

    REVISION        "200501240000Z"
    DESCRIPTION     "Rev 2.1                24 Jan 2005 00:00
                     2.1 release of the TIMETRA-SERV-MIB."

    REVISION        "200401150000Z"
    DESCRIPTION     "Rev 2.0                15 Jan 2004 00:00
                     2.0 release of the TIMETRA-SERV-MIB."

    REVISION        "200308150000Z"
    DESCRIPTION     "Rev 1.2                15 Aug 2003 00:00
                     1.2 release of the TIMETRA-SERV-MIB."

    REVISION        "200301200000Z"
    DESCRIPTION     "Rev 1.0                20 Jan 2003 00:00
                     1.0 Release of the TIMETRA-SERV-MIB."

    REVISION        "200008140000Z"
    DESCRIPTION     "Rev 0.1                14 Aug 2000 00:00
                     Initial version of the TIMETRA-SERV-MIB."

    ::= { tnSRMIBModules 4 }

-- --------------------------------------------------------------------
--      TIMETRA-SERV-MIB organisation
-- --------------------------------------------------------------------
tnServObjs            OBJECT IDENTIFIER ::= { tnSRObjs 4 }
  tnCustObjs            OBJECT IDENTIFIER ::= { tnServObjs 1 }
  tnSvcObjs             OBJECT IDENTIFIER ::= { tnServObjs 2 }
-- tnTstpNotifyObjs     OBJECT IDENTIFIER ::= { tnServObjs 5 }
--   tnSvcNotifyObjs      OBJECT IDENTIFIER ::= { tnServObjs 6 }

-- tnServConformance    OBJECT IDENTIFIER ::= { tnSRConfs 4 }
--   tnCustConformance    OBJECT IDENTIFIER ::= { tnServConformance 1 }
--   tnSvcConformance     OBJECT IDENTIFIER ::= { tnServConformance 2 }
--   tnTstpConformance    OBJECT IDENTIFIER ::= { tnServConformance 5 }

tnServNotifications   OBJECT IDENTIFIER ::= { tnSRNotifyPrefix 4 }
  tnCustTrapsPrefix     OBJECT IDENTIFIER ::= { tnServNotifications 1 }
    tnCustTraps           OBJECT IDENTIFIER ::= { tnCustTrapsPrefix 0 }
  tnSvcTrapsPrefix      OBJECT IDENTIFIER ::= { tnServNotifications 2 }
    tnSvcTraps            OBJECT IDENTIFIER ::= { tnSvcTrapsPrefix 0 }
  tnTstpTrapsPrefix     OBJECT IDENTIFIER ::= { tnServNotifications 5 }
    tnTstpTraps           OBJECT IDENTIFIER ::= { tnTstpTrapsPrefix 0 }

-- --------------------------------------------------------------------
--      TIMETRA-SERV-MIB Textual Conventions
-- --------------------------------------------------------------------
ServObjName ::= TEXTUAL-CONVENTION
    STATUS          current
    DESCRIPTION     "ASCII string used to name various service
                     objects."
    SYNTAX          DisplayString (SIZE (0..32))

-- ServObjDesc ::= TEXTUAL-CONVENTION
--     STATUS          current
--     DESCRIPTION     "ASCII string used to describe various service
--                      objects."
--     SYNTAX          DisplayString (SIZE (0..80))

ServObjLongDesc ::= TEXTUAL-CONVENTION
    STATUS          current
    DESCRIPTION     "Long ASCII string used to describe various service
                     objects."
    SYNTAX          DisplayString (SIZE (0..160))

ServType ::= TEXTUAL-CONVENTION
    STATUS          current
    DESCRIPTION     "This textual convention is used to specify the
                     type of a given service."
    SYNTAX          INTEGER {
                        unknown (0), -- Unknown service type
                        epipe   (1), -- Ethernet pipe
                        p3pipe  (2), -- POS pipe
                        tls     (3), -- Virtual private LAN service
                        vprn    (4), -- Virtual private routed network
                        ies     (5), -- Internet enhanced service
                        mirror  (6), -- Mirror service
                        apipe   (7), -- ATM pipe service
                        fpipe   (8), -- FR pipe service
                        ipipe   (9), -- IP interworking pipe service
                        cpipe   (10), -- Circuit Emulation pipe service
                        etree   (16)  -- ETree service
                    }

VpnId ::= TEXTUAL-CONVENTION
    STATUS          current
    DESCRIPTION     "A number used to identify a VPN. In general
                     each service corresponds to a single VPN, but
                     under some circumstances a VPN may be composed
                     of multiple services."
    SYNTAX          Unsigned32 (0|1..2147483647)

SdpId ::= TEXTUAL-CONVENTION
    STATUS          current
    DESCRIPTION     "A 16-bit number used to identify a Service
                     Distribution Point. This ID must be unique only
                     within the ESR where it is defined. The value 0
                     is used as the null ID."
    SYNTAX          Unsigned32 (0|1..17407)

-- SdpTemplateId ::= TEXTUAL-CONVENTION
--     STATUS          current
--     DESCRIPTION     "A number used to uniquely identify a template
--                      for the creation of a Service Distribution Point.
--                      The value 0 is used as the null ID."
--     SYNTAX          Unsigned32 (0|1..2147483647)

PWTemplateId ::= TEXTUAL-CONVENTION
    STATUS          current
    DESCRIPTION     "A number used to uniquely identify an pseudowire (PW)
                     template for the creation of a Service Distribution
                     Point. The value 0 is used as the null ID."
    SYNTAX          Unsigned32 (0|1..2147483647)

TlsBpduTranslation ::= TEXTUAL-CONVENTION
    STATUS          current
    DESCRIPTION     "This textual convention is used to specify whether
                     received L2 Protocol Tunnel pdu's are translated
                     before being sent out on a port or sap."
    SYNTAX          INTEGER {
                        auto     (1),
                        disabled (2),
                        pvst     (3),
                        stp      (4),
                        pvst-rw  (5),
                        auto-rw  (6)
                    }

TlsLimitMacMoveLevel ::= TEXTUAL-CONVENTION
    STATUS          current
    DESCRIPTION     "This textual convention is used to specify the hierarchy
                     in which spoke-SDPs are blocked when a MAC-move limit is
                     exceeded. When a MAC is moving among multiple SAPs or
                     spoke-SDPs, the SAP bind or spoke-SDP bind with the
                     lower level is blocked first. (tertiary is the lowest)"
    SYNTAX          INTEGER {
                        primary   (1),
                        secondary (2),
                        tertiary  (3)
                    }

TlsLimitMacMove  ::= TEXTUAL-CONVENTION
    STATUS          current
    DESCRIPTION     "This textual convention is used to specify the behavior
                     when the re-learn rate specified by tnSvcTlsMacMoveMaxRate
                     is exceeded.

                     A value of 'blockable' specifies that the agent will
                     monitor the MAC relearn rate on a SAP or SDP Bind and
                     it will block it when the re-learn rate specified by
                     tnSvcTlsMacMoveMaxRate is exceeded. A value of 'nonBlockable'
                     specifies that the  SAP or SDP Bind will not be blocked,
                     and another blockable SAP or SDP Bind will be blocked
                     instead."
    SYNTAX          INTEGER {
                        blockable    (1),
                        nonBlockable (2)
                    }

SdpBindVcType  ::= TEXTUAL-CONVENTION
    STATUS          current
    DESCRIPTION     "This textual convention is used to specify the type of
                     virtual circuit (VC) associated with the SDP binding.
                     The value 'vpls' is no longer supported."
    SYNTAX          INTEGER {
                        undef      (1),
                        ether      (2),
                        --vpls     (3) obsolete
                        vlan       (4),
                        mirror     (5),
                        atmSdu     (6),
                        atmCell    (7),
                        atmVcc     (8),
                        atmVpc     (9),
                        frDlci     (10),
                        ipipe      (11),
                        satopE1    (12),
                        satopT1    (13),
                        satopE3    (14),
                        satopT3    (15),
                        cesopsn    (16),
                        cesopsnCas (17)
                    }

StpExceptionCondition ::= TEXTUAL-CONVENTION
    STATUS          current
    DESCRIPTION     "This textual convention is used to specify an
                     STP exception condition encountered on an
                     interface
                     - none : no exception condition found.
                     - oneWayCommuniation : The neighbor RSTP peer on this link
                                            is not able to detect our presence.
                     - downstreamLoopDetected : A loop is detected on this
                       link."
    SYNTAX          INTEGER {
                        none                   (1),
                        oneWayCommuniation     (2),
                        downstreamLoopDetected (3)
                    }

LspIdList ::= TEXTUAL-CONVENTION
    STATUS          current
    DESCRIPTION     "Each group of four octets in this string specify
                     a 32-bit LSP ID, which corresponds to the
                     vRtrMplsLspIndex of the given MPLS LSP. The LSP
                     IDs are stored in network byte order; i.e. octet
                     N corresponds to the most significant 8 bits of
                     the LSP ID, and octet N+3 correspond to the least
                     significant 8 bits. The list is terminated by the
                     null LSP ID. The LSP IDs in this list are not
                     required to be sorted in any specific order. The
                     list is large enough to hold up to 16 LSP IDs,
                     plus the null terminator."
    SYNTAX          OCTET STRING (SIZE (0..68))

BridgeId ::= TEXTUAL-CONVENTION
    STATUS          current
    DESCRIPTION     "The Bridge-Identifier used by the Spanning Tree
                     Protocol to uniquely identify a bridge. The first
                     two octets represent the bridge priority (in big
                     endian format) while the remaining six octets
                     represent the main MAC address of the bridge."
    SYNTAX          OCTET STRING (SIZE (8))

TSapIngQueueId ::= TEXTUAL-CONVENTION
    STATUS          current
    DESCRIPTION     "The value used to uniquely identify a SAP ingress queue.
                     The actual valid values are those defined in the given
                     SAP ingress QoS policy."
    SYNTAX          Unsigned32 (1..32)

-- TSapEgrQueueId ::= TEXTUAL-CONVENTION
--     STATUS          current
--     DESCRIPTION     "The value used to uniquely identify a SAP egress queue.
--                      The actual valid values are those defined in the given
--                      SAP egress QoS policy."
--     SYNTAX          Unsigned32 (1..8)

TStpPortState ::= TEXTUAL-CONVENTION
    STATUS          current
    DESCRIPTION     "The value used to specify the port state as defined
                     by application of the Spanning Tree Protocol. This
                     state controls what action a port takes on reception
                     of a frame."
    SYNTAX          INTEGER {
                        disabled   (1),
                        blocking   (2),
                        listening  (3),
                        learning   (4),
                        forwarding (5),
                        broken     (6),
                        discarding (7)
                    }

StpPortRole ::= TEXTUAL-CONVENTION
    STATUS          current
    DESCRIPTION     "the stp portrole defined by the Rapid Spanning Tree
                     Protocol."

    SYNTAX          INTEGER {
                        master     (0),
                        root       (1),
                        designated (2),
                        alternate  (3),
                        backup     (4),
                        disabled   (5)
                    }

StpProtocol ::= TEXTUAL-CONVENTION
    STATUS          current
    DESCRIPTION     "indicates all possible version of the stp protocol."
    SYNTAX          INTEGER {
                        notApplicable (0),
                        stp           (1),
                        rstp          (2),
                        mstp          (3)
                    }

MfibLocation ::= TEXTUAL-CONVENTION
    STATUS          current
    DESCRIPTION     "MfibLocation represents the type of local 'interface':
                     -'sap': sap interface
                     -'sdp': mesh-sdp or spoke-sdp interface."
    SYNTAX          INTEGER {
                        sap (1),
                        sdp (2)
                    }

MfibGrpSrcFwdOrBlk ::= TEXTUAL-CONVENTION
    STATUS          current
    DESCRIPTION     "MfibGrpSrcFwdOrBlk describes whether traffic for the
                     related source-group is to be forwarded or blocked."
    SYNTAX          INTEGER {
                        forward (1),
                        block   (2)
                    }

MvplsPruneState ::= TEXTUAL-CONVENTION
    STATUS          current
    DESCRIPTION     "Managed VPLS (mVPLS): state of a SAP or spoke-SDP in a
                     user VPLS (uVPLS).
                     - notApplicable :
                       the SAP or spoke SDP of a uVPLS is not managed by a SAP
                       or spoke SDP of a mVPLS.
                     - notPruned:
                       the SAP or spoke SDP of a uVPLS is managed by a mVPLS,
                       but the link is not pruned.
                     -pruned
                       the SAP or spoke SDP of a uVPLS is managed by a mVPLS,
                       but the link is pruned as a result of an STP decision
                       taken in the STP instance running in the mVPLS."
    SYNTAX          INTEGER {
                        notApplicable (1),
                        notPruned     (2),
                        pruned        (3)
                    }

-- TQosQueueAttribute ::= TEXTUAL-CONVENTION
--     STATUS          current
--     DESCRIPTION     "Indicates attributes of a QoS queue"
--     SYNTAX          BITS {
--                         cbs          (0),
--                         cir          (1),
--                         cirAdaptRule (2),
--                         mbs          (3),
--                         pir          (4),
--                         pirAdaptRule (5),
--                         hiPrioOnly   (6),
--                         avgOverhead  (7) egress only
--                     }

-- TVirtSchedAttribute ::= TEXTUAL-CONVENTION
--     STATUS          current
--     DESCRIPTION     "Indicates attributes of a virtual scheduler"
--     SYNTAX          BITS {
--                         cir       (0),
--                         pir       (1),
--                         summedCir (2)
--                     }

MstiInstanceId ::= TEXTUAL-CONVENTION
    STATUS          current
    DESCRIPTION     "indicates all possible multiple spanning tree instances,
                     not including the CIST."
    SYNTAX          Unsigned32 (1..4094)

MstiInstanceIdOrZero ::= TEXTUAL-CONVENTION
    STATUS          current
    DESCRIPTION     "indicates all possible multiple spanning tree instances,
                     including the CIST (for which case the value '0' is
                     reserved)."
    SYNTAX          Unsigned32 (0..4094)

DhcpLseStateInfoOrigin ::= TEXTUAL-CONVENTION
    STATUS          current
    DESCRIPTION     "Indicates the originator of the provided information."
    SYNTAX          INTEGER {
                        none            (0),
                        dhcp            (1),
                        radius          (2),
                        retailerRadius  (3),
                        retailerDhcp    (4),
                        default         (5) -- The default subId, specified in
                                            -- sapSubMgmtDefSubIdent, is used.
                    }

IAIDType ::= TEXTUAL-CONVENTION
    STATUS          current
    DESCRIPTION     "Indicates the type of the addresses that are associated
                     with the Identity Association ID (IAID)"
    SYNTAX          INTEGER {
                        undefined     (0),
                        temporary     (1), -- IAID for temporary addresses,
                                           -- as defined in RFC 3041
                        non-temporary (2), -- IAID for non-temporary addresses
                        prefix        (3)  -- IAID for prefixes
                    }

TdmOptionsSigPkts ::= TEXTUAL-CONVENTION
    STATUS          current
    DESCRIPTION     "Encodes support for the cpipe circuit emulation (CE)
                     application signaling packets:
                     - 'noSigPkts' :
                       for a cpipe that does not use signalling packets.
                     - 'dataPkts' :
                       for a cpipe carrying TDM data packets and expecting CE
                       application signalling packets in a separate cpipe.
                     - 'sigPkts' :
                       for a cpipe carrying CE application signalling packets
                       with the data packets in a separate cpipe.
                     - 'dataAndSigPkts' :
                       for a cpipe carrying TDM data and CE application
                       signalling on the same cpipe."

    SYNTAX          INTEGER {
                        noSigPkts      (0),
                        dataPkts       (1),
                        sigPkts        (2),
                        dataAndSigPkts (3)
                    }

TdmOptionsCasTrunkFraming ::= TEXTUAL-CONVENTION
    STATUS          current
    DESCRIPTION     "Encodes the CEM SAPs CAS trunk framing type:
                     - 'noCas' :
                       for all CEM SAPs except 'nxDS0WithCas'.
                     - 'e1Trunk' :
                       for a 'nxDS0WithCas' SAP with E1 trunk.
                     - 't1EsfTrunk' :
                       for a 'nxDS0WithCas' SAP with T1 ESF trunk.
                     - 't1SfTrunk' :
                       for a 'nxDS0WithCas' SAP with T1 SF trunk."
    SYNTAX          INTEGER {
                        noCas      (0),
                        e1Trunk    (1),
                        t1EsfTrunk (2),
                        t1SfTrunk  (3)
                    }

-- CemSapReportAlarm ::= TEXTUAL-CONVENTION
--     STATUS      current
--     DESCRIPTION
--         "The CemSapReportAlarm data type indicates the type of CEM SAP alarm:
--          strayPkts     - receiving stray packets.
--          malformedPkts - detecting malformed packets.
--          pktLoss       - experiencing packet loss.
--          bfrOverrun    - experiencing jitter buffer overrun.
--          bfrUnderrun   - experiencing jitter buffer underrun.
--          rmtPktLoss    - remote packet loss indication.
--          rmtFault      - remote TDM fault indication.
--          rmtRdi        - remote RDI indication."
--     SYNTAX          BITS {
--                         notUsed       (0),
--                         strayPkts     (1),
--                         malformedPkts (2),
--                         pktLoss       (3),
--                         bfrOverrun    (4),
--                         bfrUnderrun   (5),
--                         rmtPktLoss    (6),
--                         rmtFault      (7),
--                         rmtRdi        (8)
--                     }

-- CemSapEcid ::= TEXTUAL-CONVENTION
--     STATUS          current
--     DESCRIPTION     "The Emulated Circuit Identifier (ECID) is a 20 bit
--                      unsigned binary field containing an identifier for the
--                      circuit being emulated.  ECIDs have local significance
--                      only and are associated with a specific MAC address.
--                      Therefore the SAP can have a different ECID for each
--                      direction."
--     SYNTAX          Unsigned32 (0..1048575)

-- SdpBFHundredthsOfPercent ::= TEXTUAL-CONVENTION
--     STATUS      current
--     DESCRIPTION
--         "The percentage of total SDP bandwidth reserved for SDP bindings
--          with two decimal places accuracy."
--     SYNTAX      Integer32 (1..10000)

SdpBindBandwidth ::= TEXTUAL-CONVENTION
    STATUS       current
    DESCRIPTION
        "The required SDP binding bandwidth, in kbps."
    SYNTAX       Unsigned32 (0..100000000)


L2ptProtocols ::= TEXTUAL-CONVENTION
    STATUS      current
    DESCRIPTION
        "The L2ptProtocols indicates which L2 protocols should have their tunnels
         terminated when 'L2ptTermination' is enabled.
         stp           - spanning tree protocols stp/mstp/pvst/rstp
         cdp           - cisco discovery protocol
         vtp           - virtual trunk protocol
         dtp           - dynamic trunking protocol
         pagp          - port aggregation protocol
         udld          - unidirectional link detection"

    SYNTAX          BITS {
                        stp       (0),
                        cdp       (1),
                        vtp       (2),
                        dtp       (3),
                        pagp      (4),
                        udld      (5)
                    }

SvcISID ::= TEXTUAL-CONVENTION
    STATUS      current
    DESCRIPTION
        "The SvcISID specifies a 24 bit (0..16777215) service instance
        identifier for the service. As part of the Provider Backbone Bridging
        frames, it is used at the destination PE as a demultiplexor field.

        The value of -1 is used to indicate the value of this object is
        un-specified."
    SYNTAX          Integer32 (-1 | 0..16777215)

L2RouteOrigin ::= TEXTUAL-CONVENTION
    STATUS      current
    DESCRIPTION
        "The L2RouteOrigin indicates the source from which an L2 route
         was learned."
    SYNTAX          INTEGER {
                        manual    (1),
                        bgp-l2vpn (2),
                        radius    (3)
                    }

ConfigStatus ::= TEXTUAL-CONVENTION
    STATUS      current
    DESCRIPTION
        "The ConfigStatus indicates the status of the configuration for
         the purpose of notifications."
    SYNTAX          INTEGER {
                        created  (1),
                        modified (2),
                        deleted  (3)
                    }

ServAccessLocation ::= TEXTUAL-CONVENTION
    STATUS          current
    DESCRIPTION
            "ServAccessLocation represents the type of local 'access point':
                     -'sap'  : sap
                     -'spoke': spoke-sdp ."
    SYNTAX          INTEGER {
                        sap (1),
                        spoke (2)
                    }

ServShcvOperState ::= TEXTUAL-CONVENTION
    STATUS          current
    DESCRIPTION
            "ServShcvOperState represents the operational state
              of the subscriber host connectivity verification."
    SYNTAX          INTEGER {
                        disabled  (1),
                        undefined (2),
                        down      (3),
                        up        (4)
                    }

-- --------------------------------------------------------------------
-- Objects in the TIMETRA-SERV-MIB
-- --------------------------------------------------------------------
-- --------------------------------------------------------------------
-- Customer related objects
-- --------------------------------------------------------------------
   tnCustNumEntries OBJECT-TYPE
       SYNTAX          Integer32
       MAX-ACCESS      read-only
       STATUS          current
       DESCRIPTION     "The value of the object tnCustNumEntries indicates the
                        current number of tnCustomer records configured in this
                        device.

                        This is currently not used and always returns 0."
       ::= { tnCustObjs 1 }

   tnCustNextFreeId OBJECT-TYPE
       SYNTAX          TmnxCustId
       MAX-ACCESS      read-only
       STATUS          current
       DESCRIPTION     "The value of the object tnCustNextFreeId indicates the next
                        available value for tnCustId, the index for the
                        tnCustInfoTable.

                        This is currently not used and always returns 0."
       ::= { tnCustObjs 2 }

-- ------------------------------------
-- Customer Table
-- ------------------------------------
tnCustInfoTable OBJECT-TYPE
    SYNTAX          SEQUENCE OF TnCustInfoEntry
    MAX-ACCESS      not-accessible
    STATUS          current
    DESCRIPTION     "A table that contains tnCustomer information. There
                     is an entry in this table corresponding to the
                     default tnCustomer. This entry cannot be edited or
                     deleted, and it is used as the default tnCustomer
                     for newly created services."
    ::= { tnCustObjs 3 }

tnCustInfoEntry OBJECT-TYPE
    SYNTAX          TnCustInfoEntry
    MAX-ACCESS      not-accessible
    STATUS          current
    DESCRIPTION     "Information about a specific tnCustomer."
    INDEX           { tnSysSwitchId, tnCustId }
    ::= { tnCustInfoTable 1 }

TnCustInfoEntry ::=
    SEQUENCE {
        tnCustId              TmnxCustId,
        tnCustRowStatus       RowStatus,
        tnCustDescription     ServObjDesc,
        tnCustContact         ServObjDesc,
        tnCustPhone           ServObjDesc,
        tnCustLastMgmtChange  TimeStamp
    }

tnCustId OBJECT-TYPE
    SYNTAX          TmnxCustId
    MAX-ACCESS      not-accessible
    STATUS          current
    DESCRIPTION     "Customer identifier. This ID must be unique
                     within a service domain."
    ::= { tnCustInfoEntry 1 }

tnCustRowStatus OBJECT-TYPE
    SYNTAX          RowStatus
    MAX-ACCESS      read-create
    STATUS          current
    DESCRIPTION     "The value of the object  tnCustRowStatus specifies the
                     status of this row."
    ::= { tnCustInfoEntry 2 }

tnCustDescription OBJECT-TYPE
    SYNTAX          ServObjDesc
    MAX-ACCESS      read-create
    STATUS          current
    DESCRIPTION     "The value of the object tnCustDescription specifies
                     optional, generic information about this tnCustomer
                     in a displayable format."
    DEFVAL          { "" }
    ::= { tnCustInfoEntry 3 }

tnCustContact OBJECT-TYPE
    SYNTAX          ServObjDesc
    MAX-ACCESS      read-create
    STATUS          current
    DESCRIPTION     "The value of the object tnCustContact specifies the name of
                     the primary contact person for this tnCustomer."
    DEFVAL          { "" }
    ::= { tnCustInfoEntry 4 }

tnCustPhone OBJECT-TYPE
    SYNTAX          ServObjDesc
    MAX-ACCESS      read-create
    STATUS          current
    DESCRIPTION     "The value of the object tnCustPhone specifies the
                     phone/pager number used to reach the primary contact
                     person."
    DEFVAL          { "" }
    ::= { tnCustInfoEntry 5 }

tnCustLastMgmtChange OBJECT-TYPE
    SYNTAX          TimeStamp
    MAX-ACCESS      read-only
    STATUS          current
    DESCRIPTION     "The value of the object tnCustLastMgmtChange indicates the
                     value of the object sysUpTime at the time of the
                     most recent management-initiated change to
                     this tnCustomer."
    ::= { tnCustInfoEntry 6 }

-- ------------------------------------
-- Customer Multi-Service Site Table
-- ------------------------------------
-- tnCustMultiServiceSiteTable OBJECT-TYPE
--     SYNTAX          SEQUENCE OF TnCustMultiServiceSiteEntry
--     MAX-ACCESS      not-accessible
--     STATUS          current
--     DESCRIPTION     "."
--     ::= { tnCustObjs 4 }
--
-- tnCustMultiServiceSiteEntry OBJECT-TYPE
--     SYNTAX          TnCustMultiServiceSiteEntry
--     MAX-ACCESS      not-accessible
--     STATUS          current
--     DESCRIPTION     "Information about a specific tnCustomer's
--                      multi-service site."
--     INDEX           { tnSysSwitchId, tnCustId, IMPLIED tnCustMultSvcSiteName }
--     ::= { tnCustMultiServiceSiteTable 1 }
--
-- TnCustMultiServiceSiteEntry ::=
--     SEQUENCE {
--         tnCustMultSvcSiteName                     TNamedItem,
--         tnCustMultSvcSiteRowStatus                RowStatus,
--         tnCustMultSvcSiteDescription              ServObjDesc,
--         tnCustMultSvcSiteScope                    INTEGER,
--         tnCustMultSvcSiteAssignment               Unsigned32,
--         tnCustMultSvcSiteIngressSchedulerPolicy   ServObjName,
--         tnCustMultSvcSiteEgressSchedulerPolicy    ServObjName,
--         tnCustMultSvcSiteLastMgmtChange           TimeStamp,
--         tnCustMultSvcSiteTodSuite                 TNamedItemOrEmpty,
--         tnCustMultSvcSiteCurrentIngrSchedPlcy     ServObjName,
--         tnCustMultSvcSiteCurrentEgrSchedPlcy      ServObjName,
--         tnCustMultSvcSiteEgressAggRateLimit       TPortSchedulerPIR,
--         tnCustMultSvcSiteIntendedIngrSchedPlcy    ServObjName,
--         tnCustMultSvcSiteIntendedEgrSchedPlcy     ServObjName,
--         tnCustMultSvcSiteFrameBasedAccnt          TruthValue
--     }
--
-- tnCustMultSvcSiteName OBJECT-TYPE
--     SYNTAX          TNamedItem
--     MAX-ACCESS      not-accessible
--     STATUS          current
--     DESCRIPTION     "."
--     ::= { tnCustMultiServiceSiteEntry 1 }
--
-- tnCustMultSvcSiteRowStatus OBJECT-TYPE
--     SYNTAX          RowStatus
--     MAX-ACCESS      read-create
--     STATUS          current
--     DESCRIPTION     "The value of the object  tnCustMultSvcSiteRowStatus
--                      specifies the status of this row."
--     ::= { tnCustMultiServiceSiteEntry 2 }
--
-- tnCustMultSvcSiteDescription OBJECT-TYPE
--     SYNTAX          ServObjDesc
--     MAX-ACCESS      read-create
--     STATUS          current
--     DESCRIPTION     "The value of the object tnCustMultSvcSiteDescription
--                      specifies option, generic information about this
--                      tnCustomer's Multi-Service Site."
--     DEFVAL          { "" }
--     ::= { tnCustMultiServiceSiteEntry 3 }
--
-- tnCustMultSvcSiteScope OBJECT-TYPE
--     SYNTAX          INTEGER {
--                         port (1),
--                         card (2)
--                     }
--     MAX-ACCESS      read-create
--     STATUS          current
--     DESCRIPTION     "The value of the object tnCustMultSvcSiteScope specifies
--                      the scope of the ingress and egress QoS scheduler policies
--                      assigned to this Multi-Service Site. When the value is
--                     'port' all the SAPs that are members of this
--                      Multi-Service Site must be defined on the same port.
--                      Similarly for the case of'card'."
--     DEFVAL          { port }
--     ::= { tnCustMultiServiceSiteEntry 4 }
--
-- tnCustMultSvcSiteAssignment OBJECT-TYPE
--     SYNTAX          Unsigned32
--     MAX-ACCESS      read-create
--     STATUS          current
--     DESCRIPTION     "The value of the object tnCustMultSvcSiteAssignment
--                      specifies the port ID, MDA, or card number, where
--                      the SAPs that are members of this Multi-
--                      Service Site are defined."
--     DEFVAL          { 0 }
--     ::= { tnCustMultiServiceSiteEntry 5 }
--
-- tnCustMultSvcSiteIngressSchedulerPolicy OBJECT-TYPE
--     SYNTAX          ServObjName
--     MAX-ACCESS      read-create
--     STATUS          current
--     DESCRIPTION     "The value of the object
--                      tnCustMultSvcSiteIngressSchedulerPolicy specifies the
--                      ingress QoS scheduler policy assigned to this
--                      Multi-Service Site."
--     DEFVAL          { "" }
--     ::= { tnCustMultiServiceSiteEntry 6 }
--
-- tnCustMultSvcSiteEgressSchedulerPolicy OBJECT-TYPE
--     SYNTAX          ServObjName
--     MAX-ACCESS      read-create
--     STATUS          current
--     DESCRIPTION     "The value of the object
--                      tnCustMultSvcSiteEgressSchedulerPolicy specifies the egress
--                      QoS scheduler policy assigned to this Multi-Service Site."
--     DEFVAL          { "" }
--     ::= { tnCustMultiServiceSiteEntry 7 }
--
-- tnCustMultSvcSiteLastMgmtChange OBJECT-TYPE
--     SYNTAX          TimeStamp
--     MAX-ACCESS      read-only
--     STATUS          current
--     DESCRIPTION     "The value of the object tnCustMultSvcSiteLastMgmtChange
--                      indicates the value of sysUpTime at the time of the
--                      most recent management-initiated change to
--                      this multi-service site."
--     ::= { tnCustMultiServiceSiteEntry 8 }
--
-- tnCustMultSvcSiteTodSuite OBJECT-TYPE
--     SYNTAX          TNamedItemOrEmpty
--     MAX-ACCESS      read-create
--     STATUS          current
--     DESCRIPTION     "The value of the object tnCustMultSvcSiteTodSuite specifies
--                      the Time of Day (ToD) suite to be applied on this
--                      multi-service site. An empty string indicates that no ToD
--                      suite is applied on this multi-service Site.
--                      A set request will only be allowed, if the indicated suite
--                      is defined is TIMETRA-SCHEDULER-MIB::tmnxTodSuiteTable.
--                      Using a suite the values of
--                      tnCustMultSvcSiteIngressSchedulerPolicy and
--                      tnCustMultSvcSiteEgressSchedulerPolicy can be time based
--                      manipulated."
--     DEFVAL          { ''H }
--     ::= { tnCustMultiServiceSiteEntry 9 }
--
-- tnCustMultSvcSiteCurrentIngrSchedPlcy OBJECT-TYPE
--     SYNTAX          ServObjName
--     MAX-ACCESS      read-only
--     STATUS          current
--     DESCRIPTION     "The value of the object
--                      tnCustMultSvcSiteCurrentIngrSchedPlcy indicates the Ingress
--                      QoS scheduler on this multi-service Site, or zero if none
--                      is currently active.
--                      The active policy may deviate from
--                      tnCustMultSvcSiteIngressSchedulerPolicy
--                      in case it is overruled by a ToD-suite policy defined on
--                      this multi-service site."
--     ::= { tnCustMultiServiceSiteEntry 10 }
--
-- tnCustMultSvcSiteCurrentEgrSchedPlcy OBJECT-TYPE
--     SYNTAX          ServObjName
--     MAX-ACCESS      read-only
--     STATUS          current
--     DESCRIPTION     "The value of the object tnCustMultSvcSiteCurrentEgrSchedPlcy
--                      indicates the Egress QoS scheduler on this SAP, or zero if
--                      none is currently active.
--                      The active policy may deviate from the
--                      sapEgressQosSchedulerPolicy in case it is overruled by a
--                      ToD-suite policy defined on this multi-service site."
--     ::= { tnCustMultiServiceSiteEntry 11 }
--
-- tnCustMultSvcSiteEgressAggRateLimit       OBJECT-TYPE
--     SYNTAX          TPortSchedulerPIR
--     UNITS           "kbps"
--     MAX-ACCESS      read-create
--     STATUS          current
--     DESCRIPTION     "The value of the object tnCustMultSvcSiteEgressAggRateLimit
--                      specifies the maximum total rate of all egress queues for
--                      this multi-service site. The value '-1' means that there
--                      is no limit."
--     DEFVAL          { -1 }
--     ::= { tnCustMultiServiceSiteEntry 12 }
--
-- tnCustMultSvcSiteIntendedIngrSchedPlcy OBJECT-TYPE
--     SYNTAX          ServObjName
--     MAX-ACCESS      read-only
--     STATUS          current
--     DESCRIPTION     "The value of the object tnCustMultSvcSiteIntendedIngrSchedPlcy
--                      indicates  indicates the Ingress QoS scheduler on this
--                      multi-service Site that should be applied.
--                      If it deviates from tnCustMultSvcSiteCurrentIngrSchedPlcy,
--                      this  means that there was a problem when trying to
--                      activate this filter. It can only deviate when using
--                      tod-suites for the SAP. When the tod-suites decides that
--                      a new filter must be applied, it will try to do this.
--                      If it fails, the current and intended field are
--                      not equal."
--     ::= { tnCustMultiServiceSiteEntry 13 }
--
-- tnCustMultSvcSiteIntendedEgrSchedPlcy OBJECT-TYPE
--     SYNTAX          ServObjName
--     MAX-ACCESS      read-only
--     STATUS          current
--     DESCRIPTION     "The value of the object tnCustMultSvcSiteIntendedEgrSchedPlcy
--                      indicates  indicates the Egress QoS scheduler on this
--                      multi-service Site that should be applied.
--                      If it deviates from tnCustMultSvcSiteCurrentEgrSchedPlcy,
--                      this  means that there was a problem when trying to
--                      activate this filter. It can only deviate when using
--                      tod-suites for the SAP. When the tod-suites decides that
--                      a new filter must be applied, it will try to do this.
--                      If it fails, the current and intended field are
--                      not equal."
--     ::= { tnCustMultiServiceSiteEntry 14 }
--
-- tnCustMultSvcSiteFrameBasedAccnt OBJECT-TYPE
--     SYNTAX       TruthValue
--     MAX-ACCESS   read-create
--     STATUS       current
--     DESCRIPTION
--         "The value of tnCustMultSvcSiteFrameBasedAccnt specifies whether
--          to use frame-based accounting when evaluating
--          tnCustMultSvcSiteEgressAggRateLimit for the egress queues for
--          this multi-service site.
--
--          If the value is 'false', the default packet-based accounting
--          method will be used."
--     DEFVAL { false }
--     ::= { tnCustMultiServiceSiteEntry 15 }

-- ----------------------------------------------------
-- Customer Multi-Service Site Ingress Statistics Table
-- ----------------------------------------------------
-- tnCustMultiSvcSiteIngQosSchedStatsTable OBJECT-TYPE
--     SYNTAX          SEQUENCE OF TnCustMultiSvcSiteIngQosSchedStatsEntry
--     MAX-ACCESS      not-accessible
--     STATUS          current
--     DESCRIPTION     "A table that contains ingress QoS scheduler
--                      statistics for the tnCustomer multi service site."
--     ::= { tnCustObjs 5 }
--
-- tnCustMultiSvcSiteIngQosSchedStatsEntry OBJECT-TYPE
--     SYNTAX          TnCustMultiSvcSiteIngQosSchedStatsEntry
--     MAX-ACCESS      not-accessible
--     STATUS          current
--     DESCRIPTION     "Ingress statistics about a specific tnCustomer
--                      multi service site ingress scheduler."
--     INDEX           { tnSysSwitchId, tnCustId, tnCustMultSvcSiteName,
--                       IMPLIED tnCustIngQosSchedName}
--     ::= { tnCustMultiSvcSiteIngQosSchedStatsTable 1 }
--
-- TnCustMultiSvcSiteIngQosSchedStatsEntry ::=
--     SEQUENCE {
--         tnCustIngQosSchedName                     TNamedItem,
--         tnCustIngQosSchedStatsForwardedPackets    Counter64,
--         tnCustIngQosSchedStatsForwardedOctets     Counter64
--     }
--
-- tnCustIngQosSchedName OBJECT-TYPE
--     SYNTAX          TNamedItem
--     MAX-ACCESS      not-accessible
--     STATUS          current
--     DESCRIPTION     "The index of the ingress QoS scheduler of
--                      this tnCustomer multi service site."
--     ::= { tnCustMultiSvcSiteIngQosSchedStatsEntry 1 }
--
-- tnCustIngQosSchedStatsForwardedPackets OBJECT-TYPE
--     SYNTAX          Counter64
--     MAX-ACCESS      read-only
--     STATUS          current
--     DESCRIPTION     "The value of the object
--                      tnCustIngQosSchedStatsForwardedPackets indicates the number
--                      of forwarded packets, as determined by the tnCustomer
--                      multi service site ingress scheduler policy."
--     ::= { tnCustMultiSvcSiteIngQosSchedStatsEntry 2 }
--
-- tnCustIngQosSchedStatsForwardedOctets OBJECT-TYPE
--     SYNTAX          Counter64
--     MAX-ACCESS      read-only
--     STATUS          current
--     DESCRIPTION     "The value of the object
--                      tnCustIngQosSchedStatsForwardedOctets indicates the number
--                      of forwarded octets, as determined by the tnCustomer
--                      multi service site ingress scheduler policy."
--     ::= { tnCustMultiSvcSiteIngQosSchedStatsEntry 3 }

-- -----------------------------------------------------
-- Customer Multi-Service Site Egress Statistics Table
-- -----------------------------------------------------
-- tnCustMultiSvcSiteEgrQosSchedStatsTable OBJECT-TYPE
--     SYNTAX          SEQUENCE OF TnCustMultiSvcSiteEgrQosSchedStatsEntry
--     MAX-ACCESS      not-accessible
--     STATUS          current
--     DESCRIPTION     "A table that contains egress QoS scheduler
--                      statistics for the tnCustomer multi service site."
--     ::= { tnCustObjs 6 }
--
-- tnCustMultiSvcSiteEgrQosSchedStatsEntry OBJECT-TYPE
--     SYNTAX          TnCustMultiSvcSiteEgrQosSchedStatsEntry
--     MAX-ACCESS      not-accessible
--     STATUS          current
--     DESCRIPTION     "Egress statistics about a specific tnCustomer
--                      multi service site egress scheduler."
--     INDEX           { tnSysSwitchId, tnCustId, tnCustMultSvcSiteName,
--                       IMPLIED tnCustEgrQosSchedName}
--     ::= { tnCustMultiSvcSiteEgrQosSchedStatsTable 1 }
--
-- TnCustMultiSvcSiteEgrQosSchedStatsEntry ::=
--     SEQUENCE {
--         tnCustEgrQosSchedName                     TNamedItem,
--         tnCustEgrQosSchedStatsForwardedPackets    Counter64,
--         tnCustEgrQosSchedStatsForwardedOctets     Counter64
--     }
--
-- tnCustEgrQosSchedName OBJECT-TYPE
--     SYNTAX          TNamedItem
--     MAX-ACCESS      not-accessible
--     STATUS          current
--     DESCRIPTION     "The index of the egress QoS scheduler of
--                      this tnCustomer multi service site."
--     ::= { tnCustMultiSvcSiteEgrQosSchedStatsEntry 1 }
--
-- tnCustEgrQosSchedStatsForwardedPackets OBJECT-TYPE
--     SYNTAX          Counter64
--     MAX-ACCESS      read-only
--     STATUS          current
--     DESCRIPTION     "The value of the object
--                      tnCustEgrQosSchedStatsForwardedPackets indicates number of
--                      forwarded packets, as determined by the tnCustomer
--                      multi service site egress scheduler policy."
--     ::= { tnCustMultiSvcSiteEgrQosSchedStatsEntry 2 }
--
-- tnCustEgrQosSchedStatsForwardedOctets OBJECT-TYPE
--     SYNTAX          Counter64
--     MAX-ACCESS      read-only
--     STATUS          current
--     DESCRIPTION     "The value of the object
--                      tnCustEgrQosSchedStatsForwardedOctets indicates the number
--                      of forwarded octets, as determined by the tnCustomer
--                      multi service site egress scheduler policy."
--     ::= { tnCustMultiSvcSiteEgrQosSchedStatsEntry 3 }

-- ----------------------------------------------------
-- Customer Multi-Service Site Ingress Statistics Table
-- with specific portId
-- ----------------------------------------------------
-- tnCustIngQosPortIdSchedStatsTable OBJECT-TYPE
--     SYNTAX          SEQUENCE OF TnCustIngQosPortIdSchedStatsEntry
--     MAX-ACCESS      not-accessible
--     STATUS          current
--     DESCRIPTION
--         "The tnCustIngQosPortIdSchedStatsTable contains ingress QoS scheduler
--          statistics for the tnCustomer multi service site."
--     ::= { tnCustObjs 7 }
--
-- tnCustIngQosPortIdSchedStatsEntry OBJECT-TYPE
--     SYNTAX          TnCustIngQosPortIdSchedStatsEntry
--     MAX-ACCESS      not-accessible
--     STATUS          current
--     DESCRIPTION
--         "Each entry represents the ingress statistics about a specific tnCustomer
--          multi service site ingress scheduler. Entries are created when
--          a scheduler policy is applied to an MSS."
--     INDEX           { tnSysSwitchId, tnCustId, tnCustMultSvcSiteName,
--                       tnCustIngQosPortIdSchedName, tnCustIngQosAssignmentPortId }
--     ::= { tnCustIngQosPortIdSchedStatsTable 1 }
--
-- TnCustIngQosPortIdSchedStatsEntry ::=
--     SEQUENCE {
--         tnCustIngQosPortIdSchedName                     TNamedItem,
--         tnCustIngQosAssignmentPortId                    TmnxPortID,
--         tnCustIngQosPortSchedFwdPkts                    Counter64,
--         tnCustIngQosPortSchedFwdOctets                  Counter64
--     }
--
-- tnCustIngQosPortIdSchedName OBJECT-TYPE
--     SYNTAX          TNamedItem
--     MAX-ACCESS      not-accessible
--     STATUS          current
--     DESCRIPTION
--         "The value of tnCustIngQosPortIdSchedName is used as an index
--          of the ingress QoS scheduler of this tnCustomer multi service site."
--     ::= { tnCustIngQosPortIdSchedStatsEntry 1 }
--
-- tnCustIngQosAssignmentPortId OBJECT-TYPE
--     SYNTAX          TmnxPortID
--     MAX-ACCESS      not-accessible
--     STATUS          current
--     DESCRIPTION
--         "The value of tnCustIngQosAssignmentPortId is used as an index
--          of the ingress QoS scheduler of this tnCustomer multi service site.
--          When an MSS assignment is an aps/ccag/lag in 'link' mode, each
--          member-port of the aps/ccag/lag has its own scheduler. This object
--          refers to the TmnxPortID of these member-ports."
--     ::= {tnCustIngQosPortIdSchedStatsEntry 2}
--
-- tnCustIngQosPortSchedFwdPkts OBJECT-TYPE
--     SYNTAX          Counter64
--     MAX-ACCESS      read-only
--     STATUS          current
--     DESCRIPTION
--         "The value of tnCustIngQosPortSchedFwdPkts indicates the
--          number of forwarded packets, as determined by the tnCustomer
--          multi service site ingress scheduler policy."
--     ::= { tnCustIngQosPortIdSchedStatsEntry 3 }
--
-- tnCustIngQosPortSchedFwdOctets OBJECT-TYPE
--     SYNTAX          Counter64
--     MAX-ACCESS      read-only
--     STATUS          current
--     DESCRIPTION
--         "The value of tnCustIngQosPortSchedFwdOctets indicates the
--          number of forwarded octets, as determined by the tnCustomer
--          multi service site ingress scheduler policy."
--     ::= { tnCustIngQosPortIdSchedStatsEntry 4 }

-- --------------------------------------------------------
-- Customer Multi-Service Site Egress Statistics Table
-- with specific portId
-- --------------------------------------------------------
-- tnCustEgrQosPortIdSchedStatsTable OBJECT-TYPE
--     SYNTAX          SEQUENCE OF TnCustEgrQosPortIdSchedStatsEntry
--     MAX-ACCESS      not-accessible
--     STATUS          current
--     DESCRIPTION
--         "The tnCustEgrQosPortIdSchedStatsTable contains egress QoS scheduler
--          statistics for the tnCustomer multi service site."
--     ::= { tnCustObjs 8 }
--
-- tnCustEgrQosPortIdSchedStatsEntry OBJECT-TYPE
--     SYNTAX          TnCustEgrQosPortIdSchedStatsEntry
--     MAX-ACCESS      not-accessible
--     STATUS          current
--     DESCRIPTION
--         "Each row entry represents the egress statistics for a tnCustomer
--          multi-service-site egress scheduler. Entries are created when
--          a scheduler policy is applied to an MSS."
--     INDEX           { tnSysSwitchId, tnCustId, tnCustMultSvcSiteName,
--                       tnCustEgrQosPortIdSchedName, tnCustEgrQosAssignmentPortId }
--     ::= { tnCustEgrQosPortIdSchedStatsTable 1 }
--
-- TnCustEgrQosPortIdSchedStatsEntry ::=
--     SEQUENCE {
--         tnCustEgrQosPortIdSchedName       TNamedItem,
--         tnCustEgrQosAssignmentPortId      TmnxPortID,
--         tnCustEgrQosPortSchedFwdPkts      Counter64,
--         tnCustEgrQosPortSchedFwdOctets    Counter64
--     }
--
-- tnCustEgrQosPortIdSchedName OBJECT-TYPE
--     SYNTAX          TNamedItem
--     MAX-ACCESS      not-accessible
--     STATUS          current
--     DESCRIPTION
--         "The value of tnCustEgrQosPortIdSchedName is used as an index
--          of the egress QoS scheduler of this tnCustomer multi service site."
--     ::= { tnCustEgrQosPortIdSchedStatsEntry 1}
--
-- tnCustEgrQosAssignmentPortId OBJECT-TYPE
--     SYNTAX          TmnxPortID
--     MAX-ACCESS      not-accessible
--     STATUS          current
--     DESCRIPTION
--         "The value of tnCustEgrQosAssignmentPortId is used as an index
--          of the egress QoS scheduler of this tnCustomer multi service site.
--          When an MSS assignment is an aps/ccag/lag in 'link' mode, each
--          member-port of the aps/ccag/lag has its own scheduler. This object
--          refers to the TmnxPortID of these member-ports."
--     ::= { tnCustEgrQosPortIdSchedStatsEntry 2}
--
-- tnCustEgrQosPortSchedFwdPkts OBJECT-TYPE
--     SYNTAX          Counter64
--     MAX-ACCESS      read-only
--     STATUS          current
--     DESCRIPTION
--         "The value of tnCustEgrQosPortSchedFwdPkts indicates the
--          number of forwarded packets, as determined by the tnCustomer
--          multi service site egress scheduler policy."
--     ::= { tnCustEgrQosPortIdSchedStatsEntry 3 }
--
-- tnCustEgrQosPortSchedFwdOctets OBJECT-TYPE
--     SYNTAX          Counter64
--     MAX-ACCESS      read-only
--     STATUS          current
--     DESCRIPTION
--         "The value of tnCustEgrQosPortSchedFwdOctets indicates the
--          number of forwarded octets, as determined by the tnCustomer
--          multi service site egress scheduler policy."
--     ::= { tnCustEgrQosPortIdSchedStatsEntry 4 }

-- --------------------------------------------------------
-- Customer Multi-Service Site Ingress QoS Scheduler Table
-- --------------------------------------------------------
-- tnCustMssIngQosSchedInfoTable OBJECT-TYPE
--     SYNTAX          SEQUENCE OF TnCustMssIngQosSchedInfoEntry
--     MAX-ACCESS      not-accessible
--     STATUS          current
--     DESCRIPTION     "A table that contains ingress QoS scheduler
--                      statistics for the tnCustomer multi service site."
--     ::= { tnCustObjs 9 }
--
-- tnCustMssIngQosSchedInfoEntry OBJECT-TYPE
--     SYNTAX          TnCustMssIngQosSchedInfoEntry
--     MAX-ACCESS      not-accessible
--     STATUS          current
--     DESCRIPTION     "Ingress statistics about a specific tnCustomer
--                      multi service site ingress scheduler."
--     INDEX           { tnSysSwitchId, tnCustId,
--                       tnCustMultSvcSiteName,
--                       IMPLIED tnCustMssIngQosSName }
--     ::= { tnCustMssIngQosSchedInfoTable 1 }
--
-- TnCustMssIngQosSchedInfoEntry ::=
--     SEQUENCE {
--         tnCustMssIngQosSName              TNamedItem,
--         tnCustMssIngQosSRowStatus         RowStatus,
--         tnCustMssIngQosSLastMgmtChange    TimeStamp,
--         tnCustMssIngQosSOverrideFlags     TVirtSchedAttribute,
--         tnCustMssIngQosSPIR               TPIRRate,
--         tnCustMssIngQosSCIR               TCIRRate,
--         tnCustMssIngQosSSummedCIR         TruthValue
--     }
--
-- tnCustMssIngQosSName OBJECT-TYPE
--     SYNTAX          TNamedItem
--     MAX-ACCESS      not-accessible
--     STATUS          current
--     DESCRIPTION     "The value of tnCustMssIngQosSName indicates the name of
--                      the virtual scheduler whose parameters are to be
--                      overridden."
--     ::= { tnCustMssIngQosSchedInfoEntry 1 }
--
-- tnCustMssIngQosSRowStatus OBJECT-TYPE
--     SYNTAX          RowStatus
--     MAX-ACCESS      read-create
--     STATUS          current
--     DESCRIPTION     "The value of tnCustMssIngQosSRowStatus controls the
--                      creation and deletion of rows in this table."
--     ::= { tnCustMssIngQosSchedInfoEntry 2 }
--
-- tnCustMssIngQosSLastMgmtChange OBJECT-TYPE
--     SYNTAX          TimeStamp
--     MAX-ACCESS      read-only
--     STATUS          current
--     DESCRIPTION     "The value of tnCustMssIngQosSLastMgmtChange indicates the
--                      value of sysUpTime at the time of the last management
--                      change of any writable object of this row."
--     ::= { tnCustMssIngQosSchedInfoEntry 3 }
--
-- tnCustMssIngQosSOverrideFlags OBJECT-TYPE
--     SYNTAX          TVirtSchedAttribute
--     MAX-ACCESS      read-create
--     STATUS          current
--     DESCRIPTION     "The value of tnCustMssIngQosSOverrideFlags specifies the
--                      set of attributes whose values have been overridden
--                      via management on this virtual scheduler. Clearing a
--                      given flag will return the corresponding overridden
--                      attribute to the value defined on the SAP's ingress
--                      scheduler policy."
--     ::= { tnCustMssIngQosSchedInfoEntry 4 }
--
-- tnCustMssIngQosSPIR OBJECT-TYPE
--     SYNTAX          TPIRRate
--     UNITS           "kilo bits per second"
--     MAX-ACCESS      read-create
--     STATUS          current
--     DESCRIPTION     "The value of tnCustMssIngQosSPIR specifies the desired
--                      PIR value for this virtual scheduler."
--     DEFVAL { -1 }
--     ::= { tnCustMssIngQosSchedInfoEntry 5 }
--
-- tnCustMssIngQosSCIR OBJECT-TYPE
--     SYNTAX          TCIRRate
--     UNITS           "kilo bits per second"
--     MAX-ACCESS      read-create
--     STATUS          current
--     DESCRIPTION     "The value of tnCustMssIngQosSCIR specifies the desired
--                      CIR value for this virtual scheduler."
--     DEFVAL { 0 }
--     ::= { tnCustMssIngQosSchedInfoEntry 6 }
--
-- tnCustMssIngQosSSummedCIR OBJECT-TYPE
--     SYNTAX          TruthValue
--     MAX-ACCESS      read-create
--     STATUS          current
--     DESCRIPTION     "The value of tnCustMssIngQosSSummedCIR specifies if the CIR
--                      should be used as the summed CIR values of the children
--                      schedulers or queues. If set to 'true', the applicable
--                      scheduler CIR (tnCustMssIngQosSCIR) loses its meaning."
--     DEFVAL { true }
--     ::= { tnCustMssIngQosSchedInfoEntry 7 }

-- --------------------------------------------------------
-- Customer Multi-Service Site Egrress QoS Scheduler Table
-- --------------------------------------------------------
-- tnCustMssEgrQosSchedInfoTable OBJECT-TYPE
--     SYNTAX          SEQUENCE OF TnCustMssEgrQosSchedInfoEntry
--     MAX-ACCESS      not-accessible
--     STATUS          current
--     DESCRIPTION     "A table that contains egress QoS scheduler
--                      statistics for the tnCustomer multi service site."
--     ::= { tnCustObjs 10 }
--
-- tnCustMssEgrQosSchedInfoEntry OBJECT-TYPE
--     SYNTAX          TnCustMssEgrQosSchedInfoEntry
--     MAX-ACCESS      not-accessible
--     STATUS          current
--     DESCRIPTION     "Egrress statistics about a specific tnCustomer
--                      multi service site egress scheduler."
--     INDEX           { tnSysSwitchId,  tnCustId,
--                       tnCustMultSvcSiteName,
--                       IMPLIED tnCustMssEgrQosSName }
--     ::= { tnCustMssEgrQosSchedInfoTable 1 }
--
-- TnCustMssEgrQosSchedInfoEntry ::=
--     SEQUENCE {
--         tnCustMssEgrQosSName              TNamedItem,
--         tnCustMssEgrQosSRowStatus         RowStatus,
--         tnCustMssEgrQosSLastMgmtChange    TimeStamp,
--         tnCustMssEgrQosSOverrideFlags     TVirtSchedAttribute,
--         tnCustMssEgrQosSPIR               TPIRRate,
--         tnCustMssEgrQosSCIR               TCIRRate,
--         tnCustMssEgrQosSSummedCIR         TruthValue
--     }
--
-- tnCustMssEgrQosSName OBJECT-TYPE
--     SYNTAX          TNamedItem
--     MAX-ACCESS      not-accessible
--     STATUS          current
--     DESCRIPTION     "The value of tnCustMssEgrQosSName indicates the name of
--                      the virtual scheduler whose parameters are to be
--                      overridden."
--     ::= { tnCustMssEgrQosSchedInfoEntry 1 }
--
-- tnCustMssEgrQosSRowStatus OBJECT-TYPE
--     SYNTAX          RowStatus
--     MAX-ACCESS      read-create
--     STATUS          current
--     DESCRIPTION     "The value of tnCustMssEgrQosSRowStatus controls the
--                      creation and deletion of rows in this table."
--     ::= { tnCustMssEgrQosSchedInfoEntry 2 }
--
-- tnCustMssEgrQosSLastMgmtChange OBJECT-TYPE
--     SYNTAX          TimeStamp
--     MAX-ACCESS      read-only
--     STATUS          current
--     DESCRIPTION     "The value of tnCustMssEgrQosSLastMgmtChange indicates the
--                      value of sysUpTime at the time of the last management
--                      change of any writable object of this row."
--     ::= { tnCustMssEgrQosSchedInfoEntry 3 }
--
-- tnCustMssEgrQosSOverrideFlags OBJECT-TYPE
--     SYNTAX          TVirtSchedAttribute
--     MAX-ACCESS      read-create
--     STATUS          current
--     DESCRIPTION     "The value of tnCustMssEgrQosSOverrideFlags specifies the
--                      set of attributes whose values have been overridden
--                      via management on this virtual scheduler. Clearing a
--                      given flag will return the corresponding overridden
--                      attribute to the value defined on the SAP's ingress
--                      scheduler policy."
--     ::= { tnCustMssEgrQosSchedInfoEntry 4 }
--
-- tnCustMssEgrQosSPIR OBJECT-TYPE
--     SYNTAX          TPIRRate
--     UNITS           "kilo bits per second"
--     MAX-ACCESS      read-create
--     STATUS          current
--     DESCRIPTION     "The value of tnCustMssEgrQosSPIR specifies the desired
--                      PIR value for this virtual scheduler."
--     DEFVAL { -1 }
--     ::= { tnCustMssEgrQosSchedInfoEntry 5 }
--
-- tnCustMssEgrQosSCIR OBJECT-TYPE
--     SYNTAX          TCIRRate
--     UNITS           "kilo bits per second"
--     MAX-ACCESS      read-create
--     STATUS          current
--     DESCRIPTION     "The value of tnCustMssEgrQosSCIR specifies the desired
--                      CIR value for this virtual scheduler."
--     DEFVAL { 0 }
--     ::= { tnCustMssEgrQosSchedInfoEntry 6 }
--
-- tnCustMssEgrQosSSummedCIR OBJECT-TYPE
--     SYNTAX          TruthValue
--     MAX-ACCESS      read-create
--     STATUS          current
--     DESCRIPTION     "The value of tnCustMssEgrQosSSummedCIR specifies if the CIR
--                      should be used as the summed CIR values of the children
--                      schedulers or queues. If set to 'true', the applicable
--                      scheduler CIR (tnCustMssEgrQosSCIR) loses its meaning."
--     DEFVAL { true }
--     ::= { tnCustMssEgrQosSchedInfoEntry 7 }

-- --------------------------------------------------------
-- Customer Multi-Service Site Ingress Per-Policy
-- Statistics Table
-- --------------------------------------------------------
-- tnCustMultiSvcSiteIngSchedPlcyStatsTable OBJECT-TYPE
--     SYNTAX          SEQUENCE OF TnCustMultiSvcSiteIngSchedPlcyStatsEntry
--     MAX-ACCESS      not-accessible
--     STATUS          current
--     DESCRIPTION     "A table that contains ingress QoS scheduler
--                      statistics for the tnCustomer multi service site, organized
--                      by scheduler policy."
--     ::= { tnCustObjs 11 }
--
-- tnCustMultiSvcSiteIngSchedPlcyStatsEntry OBJECT-TYPE
--     SYNTAX          TnCustMultiSvcSiteIngSchedPlcyStatsEntry
--     MAX-ACCESS      not-accessible
--     STATUS          current
--     DESCRIPTION     "Ingress statistics about a specific tnCustomer
--                      multi service site egress scheduler. Entries are created
--                      when a scheduler policy of a MSS is replaced with another
--                      one due to Time-Of-Day policies."
--     INDEX           { tnSysSwitchId,  tnCustId, tnCustMultSvcSiteName,
--                       tnSchedulerPolicyName, IMPLIED tnVirtualSchedulerName}
--     ::= { tnCustMultiSvcSiteIngSchedPlcyStatsTable 1 }
--
-- TnCustMultiSvcSiteIngSchedPlcyStatsEntry ::=
--     SEQUENCE {
--         tnCustIngSchedPlcyStatsFwdPkt    Counter64,
--         tnCustIngSchedPlcyStatsFwdOct     Counter64
--     }
--
-- tnCustIngSchedPlcyStatsFwdPkt OBJECT-TYPE
--     SYNTAX          Counter64
--     MAX-ACCESS      read-only
--     STATUS          current
--     DESCRIPTION     "The value of the object
--                      tnCustIngSchedPlcyStatsFwdPkt indicates
--                      the number of forwarded packets, as determined by the
--                      tnCustomer multi service site ingress scheduler policy."
--     ::= { tnCustMultiSvcSiteIngSchedPlcyStatsEntry 1 }
--
-- tnCustIngSchedPlcyStatsFwdOct OBJECT-TYPE
--     SYNTAX          Counter64
--     MAX-ACCESS      read-only
--     STATUS          current
--     DESCRIPTION     "The value of the object
--                      tnCustIngSchedPlcyStatsFwdOct indicates
--                      the number of forwarded octets, as determined by the
--                      tnCustomer multi service site ingress scheduler policy."
--     ::= { tnCustMultiSvcSiteIngSchedPlcyStatsEntry 2 }

-- --------------------------------------------------------
-- Customer Multi-Service Site Egress Per-Policy
-- Statistics Table
-- --------------------------------------------------------
-- tnCustMultiSvcSiteEgrSchedPlcyStatsTable OBJECT-TYPE
--     SYNTAX          SEQUENCE OF TnCustMultiSvcSiteEgrSchedPlcyStatsEntry
--     MAX-ACCESS      not-accessible
--     STATUS          current
--     DESCRIPTION     "A table that contains egress QoS scheduler
--                      statistics for the tnCustomer multi service site, organized
--                      by scheduler policy."
--     ::= { tnCustObjs 12 }
--
-- tnCustMultiSvcSiteEgrSchedPlcyStatsEntry OBJECT-TYPE
--     SYNTAX          TnCustMultiSvcSiteEgrSchedPlcyStatsEntry
--     MAX-ACCESS      not-accessible
--     STATUS          current
--     DESCRIPTION     "Egress statistics about a specific tnCustomer
--                      multi service site egress scheduler. Entries are created
--                      when a scheduler policy of a MSS is replaced with another
--                      one due to Time-Of-Day policies."
--     INDEX           { tnSysSwitchId,  tnCustId, tnCustMultSvcSiteName,
--                       tnSchedulerPolicyName, IMPLIED tnVirtualSchedulerName}
--     ::= { tnCustMultiSvcSiteEgrSchedPlcyStatsTable 1 }
--
-- TnCustMultiSvcSiteEgrSchedPlcyStatsEntry ::=
--     SEQUENCE {
--         tnCustEgrSchedPlcyStatsFwdPkt    Counter64,
--         tnCustEgrSchedPlcyStatsFwdOct    Counter64
--     }
--
-- tnCustEgrSchedPlcyStatsFwdPkt OBJECT-TYPE
--     SYNTAX          Counter64
--     MAX-ACCESS      read-only
--     STATUS          current
--     DESCRIPTION     "The value of the object
--                      tnCustEgrSchedPlcyStatsFwdPkt indicates
--                      the number of forwarded packets, as determined by
--                      the tnCustomer multi service site egress scheduler policy."
--     ::= { tnCustMultiSvcSiteEgrSchedPlcyStatsEntry 1 }
--
-- tnCustEgrSchedPlcyStatsFwdOct OBJECT-TYPE
--     SYNTAX          Counter64
--     MAX-ACCESS      read-only
--     STATUS          current
--     DESCRIPTION     "The value of the object
--                      tnCustEgrSchedPlcyStatsFwdOct indicates
--                      the number of forwarded octets, as determined by
--                      the tnCustomer multi service site egress scheduler policy."
--     ::= { tnCustMultiSvcSiteEgrSchedPlcyStatsEntry 2 }

-- --------------------------------------------------------
-- Customer Multi-Service Site Ingress Per-Policy Statistics
-- Table with specific portId
-- --------------------------------------------------------
-- tnCustMultiSvcSiteIngSchedPlcyPortStatsTable OBJECT-TYPE
--     SYNTAX          SEQUENCE OF TnCustMultiSvcSiteIngSchedPlcyPortStatsEntry
--     MAX-ACCESS      not-accessible
--     STATUS          current
--     DESCRIPTION
--         "The tnCustMultiSvcSiteIngSchedPlcyPortStatsTable contains
--          ingress QoS scheduler statistics for the tnCustomer multi service site,
--          organized by scheduler policy."
--     ::= { tnCustObjs 13 }
--
-- tnCustMultiSvcSiteIngSchedPlcyPortStatsEntry OBJECT-TYPE
--     SYNTAX          TnCustMultiSvcSiteIngSchedPlcyPortStatsEntry
--     MAX-ACCESS      not-accessible
--     STATUS          current
--     DESCRIPTION
--         "Each entry represents the ingress statistics about a specific tnCustomer
--          multi service site ingress scheduler. Entries are created when
--          a scheduler policy of a MSS is replaced with another one due
--          to Time-Of-Day policies."
--     INDEX           { tnSysSwitchId,  tnCustId, tnCustMultSvcSiteName, tnSchedulerPolicyName,
--                       tnVirtualSchedulerName,
--                       tnCustIngSchedPlcyPortStatsPort }
--     ::= { tnCustMultiSvcSiteIngSchedPlcyPortStatsTable 1 }
--
-- TnCustMultiSvcSiteIngSchedPlcyPortStatsEntry ::=
--     SEQUENCE {
--         tnCustIngSchedPlcyPortStatsPort           TmnxPortID,
--         tnCustIngSchedPlcyPortStatsFwdPkt         Counter64,
--         tnCustIngSchedPlcyPortStatsFwdOct         Counter64
--     }
--
-- tnCustIngSchedPlcyPortStatsPort OBJECT-TYPE
--     SYNTAX          TmnxPortID
--     MAX-ACCESS      not-accessible
--     STATUS          current
--     DESCRIPTION
--         "The value of tnCustIngSchedPlcyPortStatsPort is used as
--          an index of the ingress QoS scheduler of this tnCustomer multi service
--          site.
--          When an MSS assignment is an aps/ccag/lag in 'link' mode, each
--          member-port of the aps/ccag/lag has its own scheduler. This object
--          refers to the TmnxPortID of these member-ports."
--     ::= { tnCustMultiSvcSiteIngSchedPlcyPortStatsEntry 1}
--
-- tnCustIngSchedPlcyPortStatsFwdPkt OBJECT-TYPE
--     SYNTAX          Counter64
--     MAX-ACCESS      read-only
--     STATUS          current
--     DESCRIPTION
--         "The value of tnCustIngSchedPlcyPortStatsFwdPkt indicates the
--          number of forwarded packets, as determined by the tnCustomer
--          multi service site ingress scheduler policy."
--     ::= { tnCustMultiSvcSiteIngSchedPlcyPortStatsEntry 2 }
--
-- tnCustIngSchedPlcyPortStatsFwdOct OBJECT-TYPE
--     SYNTAX          Counter64
--     MAX-ACCESS      read-only
--     STATUS          current
--     DESCRIPTION
--         "The value of tnCustIngSchedPlcyPortStatsFwdOct indicates the
--          number of forwarded octets, as determined by the tnCustomer
--          multi service site ingress scheduler policy."
--     ::= { tnCustMultiSvcSiteIngSchedPlcyPortStatsEntry 3 }

-- --------------------------------------------------------
-- Customer Multi-Service Site Egress Per-Policy Statistics
-- Table with specific portId
-- --------------------------------------------------------
-- tnCustMultiSvcSiteEgrSchedPlcyPortStatsTable OBJECT-TYPE
--     SYNTAX          SEQUENCE OF TnCustMultiSvcSiteEgrSchedPlcyPortStatsEntry
--     MAX-ACCESS      not-accessible
--     STATUS          current
--     DESCRIPTION
--         "The tnCustMultiSvcSiteEgrSchedPlcyPortStatsTable contains
--          egress QoS scheduler statistics for the tnCustomer multi service site,
--          organized by scheduler policy."
--     ::= { tnCustObjs 14 }
--
-- tnCustMultiSvcSiteEgrSchedPlcyPortStatsEntry OBJECT-TYPE
--     SYNTAX          TnCustMultiSvcSiteEgrSchedPlcyPortStatsEntry
--     MAX-ACCESS      not-accessible
--     STATUS          current
--     DESCRIPTION
--         "Each entry represents the egress statistics about a specific tnCustomer
--          multi service site egress scheduler. Entries are created when
--          a scheduler policy of a MSS is replaced with another one due
--          to Time-Of-Day policies."
--     INDEX           { tnSysSwitchId,  tnCustId, tnCustMultSvcSiteName, tnSchedulerPolicyName,
--                       tnVirtualSchedulerName,
--                       tnCustEgrSchedPlcyPortStatsPort }
--     ::= { tnCustMultiSvcSiteEgrSchedPlcyPortStatsTable 1 }
--
-- TnCustMultiSvcSiteEgrSchedPlcyPortStatsEntry ::=
--     SEQUENCE {
--         tnCustEgrSchedPlcyPortStatsPort      TmnxPortID,
--         tnCustEgrSchedPlcyPortStatsFwdPkt    Counter64,
--         tnCustEgrSchedPlcyPortStatsFwdOct    Counter64
--     }
--
-- tnCustEgrSchedPlcyPortStatsPort OBJECT-TYPE
--     SYNTAX          TmnxPortID
--     MAX-ACCESS      not-accessible
--     STATUS          current
--     DESCRIPTION
--         "The value of tnCustEgrSchedPlcyPortStatsPort is used as
--          an index of the egress QoS scheduler of this tnCustomer multi service
--          site.
--          When an MSS assignment is an aps/ccag/lag in 'link' mode, each
--          member-port of the aps/ccag/lag has its own scheduler. This object
--          refers to the TmnxPortID of these member-ports."
--     ::= { tnCustMultiSvcSiteEgrSchedPlcyPortStatsEntry 1}
--
-- tnCustEgrSchedPlcyPortStatsFwdPkt OBJECT-TYPE
--     SYNTAX          Counter64
--     MAX-ACCESS      read-only
--     STATUS          current
--     DESCRIPTION
--         "The value of tnCustEgrSchedPlcyPortStatsFwdPkt indicates the
--          number of forwarded packets, as determined by the tnCustomer
--          multi service site egress scheduler policy."
--     ::= { tnCustMultiSvcSiteEgrSchedPlcyPortStatsEntry 2 }
--
-- tnCustEgrSchedPlcyPortStatsFwdOct OBJECT-TYPE
--     SYNTAX          Counter64
--     MAX-ACCESS      read-only
--     STATUS          current
--     DESCRIPTION
--         "The value of tnCustEgrSchedPlcyPortStatsFwdOct indicates the
--          number of forwarded octets, as determined by the tnCustomer
--          multi service site egress scheduler policy."
--     ::= { tnCustMultiSvcSiteEgrSchedPlcyPortStatsEntry 3 }

-- ------------------------------------
-- Customer traps
-- ------------------------------------
-- tnCustCreated NOTIFICATION-TYPE
--     OBJECTS {
--         tnCustId
--     }
--     STATUS          obsolete
--     DESCRIPTION     "The trap tnCustCreated is sent when a new row is created
--                      in the tnCustInfoTable."
--     ::= { tnCustTraps 1 }
--
-- tnCustDeleted NOTIFICATION-TYPE
--     OBJECTS {
--         tnCustId
--     }
--     STATUS          obsolete
--     DESCRIPTION     "The trap tnCustDeleted is sent when an existing row is
--                      deleted from the tnCustInfoTable."
--     ::= { tnCustTraps 2 }
--
-- tnCustMultSvcSiteCreated NOTIFICATION-TYPE
--     OBJECTS {
--         tnCustId,
--         tnCustMultSvcSiteName
--     }
--     STATUS          obsolete
--     DESCRIPTION     "The trap tnCustMultSvcSiteCreated is sent when a new row is
--                      created in the tnCustMultiServiceSiteTable."
--     ::= { tnCustTraps 3 }
--
-- tnCustMultSvcSiteDeleted NOTIFICATION-TYPE
--     OBJECTS {
--         tnCustId,
--         tnCustMultSvcSiteName
--     }
--     STATUS          obsolete
--     DESCRIPTION     "The trap tnCustMultSvcSiteDeleted is sent when an existing
--                      row is deleted from the tnCustMultiServiceSiteTable."
--     ::= { tnCustTraps 4 }

-- --------------------------------------------------------------------
-- Service related objects
-- --------------------------------------------------------------------
-- ------------------------------
-- tnSvcObjs group
-- ------------------------------
   tnSvcNumEntries OBJECT-TYPE
       SYNTAX          Integer32
       MAX-ACCESS      read-only
       STATUS          current
       DESCRIPTION     "The current number of services configured on this node.

                        This is currently not used and always returns 0."
       ::= { tnSvcObjs 1 }

-- --------------------------------
-- Base Service Table
-- --------------------------------
tnSvcBaseInfoTable OBJECT-TYPE
    SYNTAX          SEQUENCE OF TnSvcBaseInfoEntry
    MAX-ACCESS      not-accessible
    STATUS          current
    DESCRIPTION     "A table that contains basic service information."
    ::= { tnSvcObjs 2 }

tnSvcBaseInfoEntry OBJECT-TYPE
    SYNTAX          TnSvcBaseInfoEntry
    MAX-ACCESS      not-accessible
    STATUS          current
    DESCRIPTION     "Basic information about a specific service."
    INDEX           { tnSysSwitchId, tnSvcId }
    ::= { tnSvcBaseInfoTable 1 }

TnSvcBaseInfoEntry ::=
    SEQUENCE {
        tnSvcId                          TmnxServId,
        tnSvcRowStatus                   RowStatus,
        tnSvcType                        ServType,
        tnSvcCustId                      TmnxCustId,
        tnSvcIpRouting                   TmnxEnabledDisabled,
        tnSvcDescription                 ServObjDesc,
        tnSvcMtu                         INTEGER,
        tnSvcAdminStatus                 ServiceAdminStatus,
        tnSvcOperStatus                  ServiceOperStatus,
        tnSvcNumSaps                     Integer32,
        tnSvcNumSdps                     Integer32,
        tnSvcLastMgmtChange              TimeStamp,
        tnSvcDefMeshVcId                 Unsigned32,
        tnSvcVpnId                       VpnId,
        tnSvcVRouterId                   TmnxVRtrIDOrZero,
        tnSvcAutoBind                    INTEGER,
        tnSvcLastStatusChange            TimeStamp,
        tnSvcVllType                     INTEGER,
        tnSvcMgmtVpls                    TruthValue,
        tnSvcRadiusDiscovery             TruthValue,
        tnSvcRadiusUserNameType          INTEGER,
        tnSvcRadiusUserName              DisplayString,
        tnSvcVcSwitching                 TruthValue,
        tnSvcRadiusPEDiscPolicy          TNamedItemOrEmpty,
        tnSvcRadiusDiscoveryShutdown     ServiceAdminStatus,
        tnSvcVplsType                    INTEGER,
        tnSvcNumMcStandbySaps            Integer32,
        tnSvcName                        TNamedItemOrEmpty,
        tnsvcEpipeAllowIpIfBinding       TruthValue,
        tnSvcAlmProfName                 OCTET STRING
    }

tnSvcId OBJECT-TYPE
    SYNTAX          TmnxServId
    MAX-ACCESS      not-accessible
    STATUS          current
    DESCRIPTION     "The value of the object tnSvcId specifies the
                     Service identifier. This value should be unique within the
                     service domain."
    ::= { tnSvcBaseInfoEntry 1 }

tnSvcRowStatus OBJECT-TYPE
    SYNTAX          RowStatus
    MAX-ACCESS      read-create
    STATUS          current
    DESCRIPTION     "This value of the object  tnSvcRowStatus specifies the
                     status of this row.

                     To delete an entry from this table, the corresponding
                     service must be administratively down, have no SAP's
                     defined on it, and have no SDP bindings.

                     For tnSvcType 'vprn', the service can be associated
                     with a routing instance by specifying tnSvcVRouterId
                     during the creation of the service.

                     The value of the object tnSvcVplsType specifies the VPLS
                     service type. The value of this object must be specified
                     when the row is created and cannot be changed while the
                     tnSvcRowStatus is 'active'."

    ::= { tnSvcBaseInfoEntry 2 }

tnSvcType OBJECT-TYPE
    SYNTAX          ServType
    MAX-ACCESS      read-create
    STATUS          current
    DESCRIPTION     "The value of the object tnSvcType specifies the service
                     type: e.g. epipe, tls, etc. The value of this object
                     must be specified when the row is created and cannot be
                     changed while the row status is 'active'."
    ::= { tnSvcBaseInfoEntry 3 }

tnSvcCustId OBJECT-TYPE
    SYNTAX          TmnxCustId
    MAX-ACCESS      read-create
    STATUS          current
    DESCRIPTION     "The value of the object tnSvcCustId specifies the ID of the
                     tnCustomer who owns this service.
                     The value of this object must be specified when the row is
                     created and cannot be changed while the row status is
                     'active'."
    ::= { tnSvcBaseInfoEntry 4 }

tnSvcIpRouting OBJECT-TYPE
    SYNTAX          TmnxEnabledDisabled
    MAX-ACCESS      read-create
    STATUS          current
    DESCRIPTION     "The value of the object tnSvcIpRouting specifies, for a
                     'tls' service, whether IP routing is enabled.
                     For 'epipe', 'p3pipe', 'apipe', 'fpipe', 'ipipe'
                     and 'cpipe' services, this object cannot be set and has
                     the value 'disabled', whereas for 'vprn' and 'ies'
                     services the value is 'enabled' and cannot be set either.
                     For 'tls' services the value of this object must be
                     specified when the row is created and cannot be changed
                     while the row status is 'active'."
    ::= { tnSvcBaseInfoEntry 5 }

tnSvcDescription OBJECT-TYPE
    SYNTAX          ServObjDesc
    MAX-ACCESS      read-create
    STATUS          current
    DESCRIPTION     "The value of the object tnSvcDescription specifiers an
                     optional, generic information about this service."
    DEFVAL          { "" }
    ::= { tnSvcBaseInfoEntry 6 }

tnSvcMtu OBJECT-TYPE
    SYNTAX          Integer32 (0..9194)
    MAX-ACCESS      read-create
    STATUS          current
    DESCRIPTION     "The value of the object tnSvcMtu specifies the largest frame
                     size (in octets) that this service can handle.

                     Setting svcMtu to a value of zero (0), causes the agent
                     to recalculate the default MTU size.

                     The default value of this object depends on the service
                     type:
                     1514 octets for epipe, p3pipe and tls, 1508 for apipe
                     and fpipe, and 1500 octets for vprn, ipipe and ies, 1514
                     octets for cpipe."
    ::= { tnSvcBaseInfoEntry 7 }

tnSvcAdminStatus OBJECT-TYPE
    SYNTAX          ServiceAdminStatus
    MAX-ACCESS      read-create
    STATUS          current
    DESCRIPTION     "The value of the object tnSvcAdminStatus specifies the
                     desired state of this service."
    DEFVAL          { down }
    ::= { tnSvcBaseInfoEntry 8 }

tnSvcOperStatus OBJECT-TYPE
    SYNTAX          ServiceOperStatus
    MAX-ACCESS      read-only
    STATUS          current
    DESCRIPTION     "The value of the object tnSvcOperStatus indicates the
                     operating state of this service. The requirements for a
                     service to be operationally up depend on the service type:

                     epipe, p3pipe, apipe, fpipe, ipipe and cpipe services are
                     'up' when the service is administratively up and either
                     both SAP's or a SAP and a spoke SDP Bind are operationally
                     up.

                     tls services are 'up' when the service is
                     administratively up and either at least two SAP's or
                     spoke SDP Bind's, or one SAP or spoke SDP Bind and
                     at least one mesh SDP Bind are operationally up.

                     vprn and ies services are 'up' when the service is
                     administratively up and at least one interface is
                     operationally up."
    ::= { tnSvcBaseInfoEntry 9 }

tnSvcNumSaps OBJECT-TYPE
    SYNTAX          Integer32
    MAX-ACCESS      read-only
    STATUS          current
    DESCRIPTION     "The value of the object tnSvcNumSaps indicates the number of
                     SAPs defined on this service."
    ::= { tnSvcBaseInfoEntry 10 }

tnSvcNumSdps OBJECT-TYPE
    SYNTAX          Integer32
    MAX-ACCESS      read-only
    STATUS          current
    DESCRIPTION     "The value of the object tnSvcNumSdps indicates the number of
                     SDPs bound to this service."
    ::= { tnSvcBaseInfoEntry 11 }

tnSvcLastMgmtChange OBJECT-TYPE
    SYNTAX          TimeStamp
    MAX-ACCESS      read-only
    STATUS          current
    DESCRIPTION     "The value of of the object tnSvcLastMgmtChange indicates
                     the value of sysUpTime at the time of the most recent
                     management-initiated change to this service."
    ::= { tnSvcBaseInfoEntry 12 }

tnSvcDefMeshVcId OBJECT-TYPE
    SYNTAX          Unsigned32
    MAX-ACCESS      read-create
    STATUS          current
    DESCRIPTION     "The value of the object tnSvcDefMeshVcId specifies, only in
                     services that accept mesh SDP bindings, the VC ID portion
                     of the sdpBindId index of each mesh SDP binding defined in
                     the service. The default value of this object is equal to
                     the service ID."
    ::= { tnSvcBaseInfoEntry 13 }

tnSvcVpnId OBJECT-TYPE
    SYNTAX          VpnId
    MAX-ACCESS      read-create
    STATUS          current
    DESCRIPTION     "The value of the object  tnSvcVpnId specifies the VPN ID
                     assigned to this service.  The value of this object can
                     be specified only when the row is created. If the value is
                     not specified, it defaults to the service ID."
    DEFVAL          { 0 }
    ::= { tnSvcBaseInfoEntry 14 }

tnSvcVRouterId OBJECT-TYPE
    SYNTAX          TmnxVRtrIDOrZero
    MAX-ACCESS      read-create
    STATUS          current
    DESCRIPTION     "The value of the object tnSvcVRouterId specifies, for a IES
                     or VPRN service the associated virtual router instance
                     where its interfaces are defined.

                     This object has a special significance for the VPRN
                     service as it can be used to associate the service to a
                     specific virtual router instance.

                     If no routing instance is specified or a value of zero (0)
                     is specified, the agent will assign the vRtrID index value
                     that would have been returned by the vRtrNextVRtrID object
                     in the TIMETRA-VRTR-MIB. The agent supports an SNMP SET
                     operation to the tnSvcVRouterId object only during
                     row creation."
    DEFVAL { 0 }
    ::= { tnSvcBaseInfoEntry 15 }

tnSvcAutoBind OBJECT-TYPE
    SYNTAX          INTEGER {
                        none     (1),
                        gre      (2),
                        ldp      (3),
                        rsvp-te  (4),
                        mpls     (5)
                    }
    MAX-ACCESS      read-create
    STATUS          current
    DESCRIPTION     "The value of the object tnSvcAutoBind specifies, for a VPRN
                     service, the type of lookup to be used by the routing
                     instance if no SDP to the destination exists."
    DEFVAL          { none }
    ::= { tnSvcBaseInfoEntry 16 }

tnSvcLastStatusChange OBJECT-TYPE
    SYNTAX          TimeStamp
    MAX-ACCESS      read-only
    STATUS          current
    DESCRIPTION     "The value of the object tnSvcLastStatusChange indicates the
                     value of sysUpTime at the time of the most recent
                     operating status change to his service."
    ::= { tnSvcBaseInfoEntry 17 }

tnSvcVllType OBJECT-TYPE
    SYNTAX          INTEGER {
                        undef     (1),
                        atmSdu    (6),
                        atmCell   (7),
                        atmVcc    (8),
                        atmVpc    (9),
                        frDlci    (10),
                        satopE1   (12),
                        satopT1   (13),
                        satopE3   (14),
                        satopT3   (15),
                        cesopsn   (16),
                        cesopsnCas(17)
                    }
    MAX-ACCESS      read-create
    STATUS          current
    DESCRIPTION     "The value of the object tnSvcVllType specifies, for a apipe,
                     fpipe or cpipe service, the type of pseudo-wire to be
                     signalled for the service.  The default for this object
                     depends on the service type:
                     'atmSdu' for apipes, 'frDlci' for fpipes, satopE1 for
                     cpipes, and 'undef' for all other service types."
    ::= { tnSvcBaseInfoEntry 18 }

tnSvcMgmtVpls OBJECT-TYPE
    SYNTAX          TruthValue
    MAX-ACCESS      read-create
    STATUS          current
    DESCRIPTION    "The value of the object tnSvcMgmtVpls specifies, only if
                    tnSvcType = 'tls' whether or not the service is a management
                    vpls.
                    If set to false the service is acting as a regular VPLS
                    service. If set to true, the service is  acting  as  a
                    management  VPLS  service. This implies that RSTP will
                    always be enabled, and that the  conclusions of this RSTP
                    can be associated to different (regular) VPLSs.
                    The value of this object cannot be changed after creation."
    DEFVAL          { false }
    ::= { tnSvcBaseInfoEntry 19 }

tnSvcRadiusDiscovery OBJECT-TYPE
    SYNTAX           TruthValue
    MAX-ACCESS       read-create
    STATUS           current
    DESCRIPTION
        "The value of the object tnSvcRadiusDiscovery specifies whether RADIUS
         auto-discovery is enabled on this service."
    DEFVAL          { false }
    ::= { tnSvcBaseInfoEntry 20 }


tnSvcRadiusUserNameType OBJECT-TYPE
    SYNTAX           INTEGER {
                     none                 (0),
                     vpn-id               (1),
                     router-distinguisher (2)
                     }
    MAX-ACCESS       read-create
    STATUS           current
    DESCRIPTION
        "The value of the object tnSvcRadiusUserNameType specifies whether RADIUS
         user name is vpn-id or router-distinguisher.  By default, the
         value of this object is 'none'.

         tnSvcRadiusUserNameType and tnSvcRadiusUserName, which indicates the
         RADIUS username, must be set together in the same SNMP request
         PDU if tnSvcRadiusUserNameType is vpn-id or router-distinguisher or
         else the set request will fail with an inconsistentValue error."
    DEFVAL          { none }
    ::= { tnSvcBaseInfoEntry 21 }

tnSvcRadiusUserName OBJECT-TYPE
    SYNTAX           DisplayString (SIZE (0..64))
    MAX-ACCESS       read-create
    STATUS           current
    DESCRIPTION
        "The value of the object tnSvcRadiusUserName specifies the  RADIUS
         user name.  tnSvcRadiusUserNameType specifies the type of the
         username and has to be set along with tnSvcRadiusUserName when
         tnSvcRadiusUserName can either be a vpn-id or a router-distinguisher."
    DEFVAL          { "" }
    ::= { tnSvcBaseInfoEntry 22 }

tnSvcVcSwitching OBJECT-TYPE
    SYNTAX           TruthValue
    MAX-ACCESS       read-create
    STATUS           current
    DESCRIPTION
        "The value of the object tnSvcVcSwitching specifies if the PW
         switching signalling is used for the Spokes configured under the
         service.
         This object can only be specified when the row is created."
    DEFVAL     { false }
    ::= { tnSvcBaseInfoEntry 23 }

tnSvcRadiusPEDiscPolicy OBJECT-TYPE
    SYNTAX           TNamedItemOrEmpty
    MAX-ACCESS       read-create
    STATUS           current
    DESCRIPTION
        "The value of the object tnSvcRadiusPEDiscPolicy specifies the
         RADIUS PE Discovery Policy name. "
    DEFVAL     { "" }
    ::= { tnSvcBaseInfoEntry 24 }

tnSvcRadiusDiscoveryShutdown OBJECT-TYPE
    SYNTAX     ServiceAdminStatus
    MAX-ACCESS read-create
    STATUS     current
    DESCRIPTION
      "The value of tnSvcRadiusDiscoveryShutdown specifies the desired
       administrative state for the RADIUS auto-discovery server. When
       the server is 'down' the operational state of the server is
       disabled.

       By default, state of the RADIUS auto-discovery server is 'down'."
    DEFVAL { down }
    ::= { tnSvcBaseInfoEntry 25 }

tnSvcVplsType OBJECT-TYPE
    SYNTAX          INTEGER {
                        none  (1),
                        bVpls (2),
                        iVpls (3)
                    }
    MAX-ACCESS      read-create
    STATUS          current
    DESCRIPTION     "Backbone VPLS ('bVpls') refers to the B-Component instance
                     of the Provider Backbone Bridging (PBB/IEEE 802.1ah)
                     feature. It represents the Multi-point tunneling component
                     that multiplexes multiple Customer VPNs (ISIDs) together.
                     It is similar to a regular VPLS instance that operates
                     on the Backbone MAC addresses.

                     ISID VPLS ('iVpls') or I-VPLS refers to the I-Component
                     instance of the Provider Backbone Bridging (PBB/IEEE
                     802.1ah) feature. It identifies the specific VPN entity
                     associated to a tnCustomer Multipoint (ELAN) service. It is
                     similar to a regular VPLS instance that operates on the
                     Customer MAC addresses.

                     The value of the object tnSvcVplsType specifies the VPLS
                     service type. The value of this object must be specified
                     when the row is created and cannot be changed while the
                     tnSvcRowStatus is 'active'."
    DEFVAL     { none }
    ::= { tnSvcBaseInfoEntry 26 }

tnSvcNumMcStandbySaps OBJECT-TYPE
    SYNTAX          Integer32
    MAX-ACCESS      read-only
    STATUS          current
    DESCRIPTION     "The value of the object tnSvcNumMcStandbySaps indicates the
                     number of SAPs defined on this service on a port which is
                     in multi-chassis standby mode."
    ::= { tnSvcBaseInfoEntry 27 }

tnSvcName OBJECT-TYPE
    SYNTAX          TNamedItemOrEmpty
    MAX-ACCESS      read-create
    STATUS          current
    DESCRIPTION     "The value of the svcName specifies the name of the service.
                     This value should be unique within the service domain."
    DEFVAL { ''H }
    ::= { tnSvcBaseInfoEntry 28 }

tnsvcEpipeAllowIpIfBinding  OBJECT-TYPE
    SYNTAX          TruthValue
    MAX-ACCESS      read-write
    STATUS          current
    DESCRIPTION     "The value of the object tnsvcEpipesAllowIpIfBinding indicates,
                     whether to allow IP interface binding on this EPIPE service."
    DEFVAL          { false }
    ::= { tnSvcBaseInfoEntry 29 }

tnSvcAlmProfName OBJECT-TYPE
    SYNTAX         OCTET STRING (SIZE(1..40))
    MAX-ACCESS     read-create
    STATUS         current
    DESCRIPTION    "."
    ::= { tnSvcBaseInfoEntry 30 }

-- ------------------------------------
-- TLS Service Table
-- ------------------------------------
tnSvcTlsInfoTable OBJECT-TYPE
    SYNTAX          SEQUENCE OF TnSvcTlsInfoEntry
    MAX-ACCESS      not-accessible
    STATUS          current
    DESCRIPTION     "A table that contains TLS service information."
    ::= { tnSvcObjs 3 }

tnSvcTlsInfoEntry OBJECT-TYPE
    SYNTAX          TnSvcTlsInfoEntry
    MAX-ACCESS      not-accessible
    STATUS          current
    DESCRIPTION     "TLS specific information about a service."
    INDEX           { tnSysSwitchId, tnSvcId }
    ::= { tnSvcTlsInfoTable 1 }

TnSvcTlsInfoEntry ::=
    SEQUENCE {
        tnSvcTlsMacLearning                   TmnxEnabledDisabled,
        tnSvcTlsDiscardUnknownDest            TmnxEnabledDisabled,
        tnSvcTlsFdbTableSize                  Integer32,
        tnSvcTlsFdbNumEntries                 Integer32,
        tnSvcTlsFdbNumStaticEntries           Integer32,
        tnSvcTlsFdbLocalAgeTime               Integer32,
        tnSvcTlsFdbRemoteAgeTime              Integer32,
        tnSvcTlsStpAdminStatus                TmnxEnabledDisabled,
        tnSvcTlsStpPriority                   Integer32,
        tnSvcTlsStpBridgeAddress              MacAddress,
        tnSvcTlsStpTimeSinceTopologyChange    TimeTicks,
        tnSvcTlsStpTopologyChanges            Integer32,
        tnSvcTlsStpDesignatedRoot             BridgeId,
        tnSvcTlsStpRootCost                   Integer32,
        tnSvcTlsStpRootPort                   Integer32,
        tnSvcTlsStpMaxAge                     Integer32,
        tnSvcTlsStpHelloTime                  Integer32,
--        tnSvcTlsStpHoldTime                   Integer32,
        tnSvcTlsStpForwardDelay               Integer32,
        tnSvcTlsStpBridgeMaxAge               Integer32,
        tnSvcTlsStpBridgeHelloTime            Integer32,
        tnSvcTlsStpBridgeForwardDelay         Integer32,
        tnSvcTlsStpOperStatus                 INTEGER,
        tnSvcTlsStpVirtualRootBridgeStatus    INTEGER,
        tnSvcTlsMacAgeing                     TmnxEnabledDisabled,
        tnSvcTlsStpTopologyChangeActive       TruthValue,
        tnSvcTlsFdbTableFullHighWatermark     Integer32,
        tnSvcTlsFdbTableFullLowWatermark      Integer32,
        tnSvcTlsVpnId                         VpnId,
        tnSvcTlsCustId                        TmnxCustId,
        tnSvcTlsStpVersion                    INTEGER,
        tnSvcTlsStpHoldCount                  Integer32,
        tnSvcTlsStpPrimaryBridge              BridgeId,
        tnSvcTlsStpBridgeInstanceId           Integer32,
        tnSvcTlsStpVcpOperProtocol            StpProtocol,
        tnSvcTlsMacMoveMaxRate                Unsigned32,
        tnSvcTlsMacMoveRetryTimeout           Unsigned32,
        tnSvcTlsMacMoveAdminStatus            TmnxEnabledDisabled,
        tnSvcTlsMacRelearnOnly                TruthValue,
        tnSvcTlsMfibTableSize                 Integer32,
        tnSvcTlsMfibTableFullHighWatermark    Integer32,
        tnSvcTlsMfibTableFullLowWatermark     Integer32,
        tnSvcTlsMacFlushOnFail                TmnxEnabledDisabled,
        tnSvcTlsStpRegionName                 DisplayString,
        tnSvcTlsStpRegionRevision             Integer32,
        tnSvcTlsStpBridgeMaxHops              Integer32,
        tnSvcTlsStpCistRegionalRoot           BridgeId,
        tnSvcTlsStpCistIntRootCost            Integer32,
        tnSvcTlsStpCistRemainingHopCount      Integer32,
        tnSvcTlsStpCistRegionalRootPort       Integer32,
        tnSvcTlsFdbNumLearnedEntries          Integer32,
        tnSvcTlsFdbNumOamEntries              Integer32,
        tnSvcTlsFdbNumDhcpEntries             Integer32,
        tnSvcTlsFdbNumHostEntries             Integer32,
        tnSvcTlsShcvAction                    INTEGER,
        tnSvcTlsShcvSrcIp                     IpAddress,
        tnSvcTlsShcvSrcMac                    MacAddress,
        tnSvcTlsShcvInterval                  Unsigned32,
        tnSvcTlsPriPortsCumulativeFactor      Unsigned32,
        tnSvcTlsSecPortsCumulativeFactor      Unsigned32,
        tnSvcTlsL2ptTermEnabled               TruthValue,
        tnSvcTlsPropagateMacFlush             TruthValue,
        tnSvcTlsMrpAdminStatus                TmnxEnabledDisabled,
        tnSvcTlsMrpMaxAttributes              Unsigned32,
        tnSvcTlsMrpAttributeCount             Unsigned32,
        tnSvcTlsMrpFailedRegisterCount        Unsigned32,
        tnSvcTlsMcPathMgmtPlcyName            TNamedItem,
        tnSvcTlsMrpFloodTime                  Unsigned32,
        tnSvcTlsMrpAttrTblHighWatermark       Integer32,
        tnSvcTlsMrpAttrTblLowWatermark        Integer32,
        tnSvcTlsMacMoveNumRetries             Unsigned32,
        tnSvcTlsMacSubNetLen                  Integer32,
        tnSvcTlsSendFlushOnBVplsFail          TruthValue,
        tnSvcTlsPropMacFlushFromBVpls         TruthValue,
        tnSvcTlsMacNotifInterval              Unsigned32,
        tnSvcTlsMacNotifCount                 Unsigned32,
        tnSvcTlsMacNotifAdminState            TmnxEnabledDisabled,
        tnSvcTlsShcvRetryTimeout              Unsigned32,
        tnSvcTlsShcvRetryCount                Unsigned32,
        tnsvcTlsAllowIpIfBinding              TruthValue,
        tnSvcTlsMfibTableNumEntries           Integer32
     }

tnSvcTlsMacLearning OBJECT-TYPE
    SYNTAX          TmnxEnabledDisabled
    MAX-ACCESS      read-write
    STATUS          current
    DESCRIPTION     "The value of the object tnSvcTlsMacLearning specifies
                     whether the MAC learning process is enabled in this TLS."
    DEFVAL          { enabled }
    ::= { tnSvcTlsInfoEntry 1 }

tnSvcTlsDiscardUnknownDest OBJECT-TYPE
    SYNTAX          TmnxEnabledDisabled
    MAX-ACCESS      read-write
    STATUS          current
    DESCRIPTION     "The value of the object tnSvcTlsDiscardUnknownDest
                     specifies whether frames received with an unknown
                     destination MAC are discarded in this TLS."
    DEFVAL          { disabled }
    ::= { tnSvcTlsInfoEntry 2 }

tnSvcTlsFdbTableSize OBJECT-TYPE
    SYNTAX          Integer32 (1..511999)
    MAX-ACCESS      read-write
    STATUS          current
    DESCRIPTION     "The value of the object tnSvcTlsFdbTableSize specifies the
                     maximum number of learned and static entries allowed in
                     the FDB of this service.

                     The maximum value of tnSvcTlsFdbTableSize is '511999', when
                     the the value of TIMETRA-CHASSIS-MIB::tmnxChassisOperMode
                     is 'd'.

                     The maximum value of tnSvcTlsFdbTableSize is '196607', when
                     the the value of TIMETRA-CHASSIS-MIB::tmnxChassisOperMode
                     is 'c'.

                     In other cases, the maximum value of tnSvcTlsFdbTableSize is
                     '131071'."
    DEFVAL          { 250 }
    ::= { tnSvcTlsInfoEntry 3 }

tnSvcTlsFdbNumEntries OBJECT-TYPE
    SYNTAX          Integer32
    MAX-ACCESS      read-only
    STATUS          current
    DESCRIPTION     "The value of the object tnSvcTlsFdbNumEntries indicates the
                     current number of entries in the FDB of this service."
    ::= { tnSvcTlsInfoEntry 4 }

tnSvcTlsFdbNumStaticEntries OBJECT-TYPE
    SYNTAX          Integer32
    MAX-ACCESS      read-only
    STATUS          current
    DESCRIPTION     "The value of the object tnSvcTlsFdbNumStaticEntries
                     indicates the current number of static entries in the FDB
                     of this service."
    ::= { tnSvcTlsInfoEntry 5 }

tnSvcTlsFdbLocalAgeTime OBJECT-TYPE
    SYNTAX          Integer32 (60..86400)
    MAX-ACCESS      read-write
    STATUS          current
    DESCRIPTION     "The value of the object tnSvcTlsFdbLocalAgeTime specifies
                     the number of seconds used to age out TLS FDB entries
                     learned on local SAPs."
    DEFVAL          { 300 }
    ::= { tnSvcTlsInfoEntry 6 }

tnSvcTlsFdbRemoteAgeTime OBJECT-TYPE
    SYNTAX          Integer32 (60..86400)
    MAX-ACCESS      read-write
    STATUS          current
    DESCRIPTION     "The value of the object tnSvcTlsFdbRemoteAgeTime specifies
                     the number of seconds used to age out TLS FDB entries
                     learned on an SDP. These entries correspond to MAC
                     addresses learned on remote SAPs."
    DEFVAL          { 900 }
    ::= { tnSvcTlsInfoEntry 7 }

tnSvcTlsStpAdminStatus OBJECT-TYPE
    SYNTAX          TmnxEnabledDisabled
    MAX-ACCESS      read-write
    STATUS          current
    DESCRIPTION     "The value of the object tnSvcTlsStpAdminStatus specifies the
                     administrative state of the Spanning Tree Protocol
                     instance associated with this service."
    DEFVAL          { disabled }
    ::= { tnSvcTlsInfoEntry 8 }

tnSvcTlsStpPriority OBJECT-TYPE
    SYNTAX          Integer32 (0..65535)
    MAX-ACCESS      read-write
    STATUS          current
    DESCRIPTION     "The value of the object  tnSvcTlsStpPriority specifies
                     the priority of the Spanning Tree Protocol instance
                     associated with this service.
                     It is used as the highest 4 bits of the Bridge ID
                     included in the Configuration BPDU's generated by
                     this bridge.
                     The tnSvcTlsStpPriority can only take-on values which
                     multiples of 4096 (4k). If a value is specified which
                     is not a multiple of 4K, then this value will be
                     replaced by the closest multiple of 4K which is lower
                     then the value entered."
    DEFVAL          { 32768 }
    ::= { tnSvcTlsInfoEntry 9 }

tnSvcTlsStpBridgeAddress OBJECT-TYPE
    SYNTAX          MacAddress
    MAX-ACCESS      read-only
    STATUS          current
    DESCRIPTION     "The value of the  object tnSvcTlsStpBridgeAddress indicates
                     the MAC address used to identify this bridge in the
                     network. It is used as the last six octets of the
                     Bridge ID included in the Configuration BPDU's generated
                     by this bridge. The most significant 38 bits of the bridge
                     address are taken from the base MAC address of the
                     device, while the least significant 10 bits are
                     based on the corresponding TLS instance ID."
    ::= { tnSvcTlsInfoEntry 10 }

tnSvcTlsStpTimeSinceTopologyChange OBJECT-TYPE
    SYNTAX          TimeTicks
    MAX-ACCESS      read-only
    STATUS          current
    DESCRIPTION     "The value of the object tnSvcTlsStpTimeSinceTopologyChange
                     indicates the time (in hundredths of a second) since the
                     last time a topology change was detected by the Spanning
                     Tree Protocol instance associated with this service."
    ::= { tnSvcTlsInfoEntry 11 }

tnSvcTlsStpTopologyChanges OBJECT-TYPE
    SYNTAX          Integer32
    MAX-ACCESS      read-only
    STATUS          current
    DESCRIPTION     "The value of the object tnSvcTlsStpTopologyChanges indicates
                     the total number of topology changes detected by the
                     Spanning Tree Protocol instance associated with this
                     service since the management entity was last reset or
                     initialized."
    ::= { tnSvcTlsInfoEntry 12 }

tnSvcTlsStpDesignatedRoot OBJECT-TYPE
    SYNTAX          BridgeId
    MAX-ACCESS      read-only
    STATUS          current
    DESCRIPTION     "The value of the object tnSvcTlsStpDesignatedRoot indicates
                     the bridge identifier of the root of the spanning tree as
                     determined by the Spanning Tree Protocol instance
                     associated with this service. This value is used as the
                     Root Identifier parameter in all Configuration BPDUs
                     originated by this node."
    ::= { tnSvcTlsInfoEntry 13 }

tnSvcTlsStpRootCost OBJECT-TYPE
    SYNTAX          Integer32
    MAX-ACCESS      read-only
    STATUS          current
    DESCRIPTION     "The value of the object tnSvcTlsStpRootCost indicates the
                     cost of the path to the root bridge as seen from this
                     bridge."
    ::= { tnSvcTlsInfoEntry 14 }

tnSvcTlsStpRootPort OBJECT-TYPE
    SYNTAX          Integer32
    MAX-ACCESS      read-only
    STATUS          current
    DESCRIPTION     "The value of the object tnSvcTlsStpRootPort indicates the
                     port number of the port which offers the lowest cost path
                     from this bridge to the root bridge."
    ::= { tnSvcTlsInfoEntry 15 }

tnSvcTlsStpMaxAge OBJECT-TYPE
    SYNTAX          Integer32
    MAX-ACCESS      read-only
    STATUS          current
    DESCRIPTION     "The value of the object tnSvcTlsStpMaxAge indicates the
                     maximum age of Spanning Tree Protocol information learned
                     from the network on any port before it is discarded. This
                     is the actual value that this bridge is currently using."
    ::= { tnSvcTlsInfoEntry 16 }

tnSvcTlsStpHelloTime OBJECT-TYPE
    SYNTAX          Integer32
    MAX-ACCESS      read-only
    STATUS          current
    DESCRIPTION     "The value of the object tnSvcTlsStpHelloTime indicates the
                     amount of time between the transmission of Configuration
                     BPDUs. This is the actual value that this bridge is
                     currently using."
    ::= { tnSvcTlsInfoEntry 17 }

-- tnSvcTlsStpHoldTime OBJECT-TYPE
--     SYNTAX          Integer32
--     MAX-ACCESS      read-only
--     STATUS          obsolete
--     DESCRIPTION     "The value of the object tnSvcTlsStpHoldTime indicates the
--                      interval length during which no more than two
--                      Configuration BPDUs shall be transmitted by this bridge.
--                      This object is no longer used. It is replaced by the
--                      object tnSvcTlsStpHoldCount.
--                      This object was made obsolete in the 3.0 release."
--     ::= { tnSvcTlsInfoEntry 18 }

tnSvcTlsStpForwardDelay OBJECT-TYPE
    SYNTAX          Integer32
    MAX-ACCESS      read-only
    STATUS          current
    DESCRIPTION     "The value of the object tnSvcTlsStpForwardDelay indicates
                     how fast a port changes its state when moving towards the
                     Forwarding state. The value determines how long the port
                     stays in each of the Listening and Learning states, which
                     precede the Forwarding state. This value is also used to
                     age all dynamic entries in the Forwarding Database when a
                     topology change has been detected and is underway. This is
                     the actual value that this bridge is currently using."
    ::= { tnSvcTlsInfoEntry 19 }

tnSvcTlsStpBridgeMaxAge OBJECT-TYPE
    SYNTAX          Integer32 (6..40)
    MAX-ACCESS      read-write
    STATUS          current
    DESCRIPTION     "The value of the object tnSvcTlsStpBridgeMaxAge specifies
                     the value that all bridges should use for 'MaxAge' when this
                     bridge is acting as the root bridge."
    ::= { tnSvcTlsInfoEntry 20 }

tnSvcTlsStpBridgeHelloTime OBJECT-TYPE
    SYNTAX          Integer32 (1..10)
    MAX-ACCESS      read-write
    STATUS          current
    DESCRIPTION     "The value of the object tnSvcTlsStpBridgeHelloTime specifies
                     the value that all bridges should use for 'HelloTime' when
                     this bridge is acting as the root bridge."
    ::= { tnSvcTlsInfoEntry 21 }

tnSvcTlsStpBridgeForwardDelay OBJECT-TYPE
    SYNTAX          Integer32 (4..30)
    MAX-ACCESS      read-write
    STATUS          current
    DESCRIPTION     "The value of the object tnSvcTlsStpBridgeForwardDelay
                     specifies the value that all bridges should use for
                     'ForwardDelay' when this bridge is acting as the root
                     bridge."
    ::= { tnSvcTlsInfoEntry 22 }

tnSvcTlsStpOperStatus OBJECT-TYPE
    SYNTAX          INTEGER {
                        up   (1),
                        down (2)
                    }
    MAX-ACCESS      read-only
    STATUS          current
    DESCRIPTION     "The value of the object  tnSvcTlsStpOperStatus indicates the
                     operating status of the Spanning Tree Protocol instance
                     associated with this service."
    ::= { tnSvcTlsInfoEntry 30 }

tnSvcTlsStpVirtualRootBridgeStatus OBJECT-TYPE
    SYNTAX          INTEGER {
                        up   (1),
                        down (2)
                    }
    MAX-ACCESS      read-only
    STATUS          current
    DESCRIPTION     "The value of the object  tnSvcTlsStpVirtualRootBridgeStatus
                     indicates the operating status of the  Virtual Root Bridge
                     of the Spanning Tree Protocol instance associated with
                     this service. The status of the Virtual Root Bridge is
                    'up' when there is connectivity to the core: i.e. one or
                     more SDP's in this service are operationally up."
    ::= { tnSvcTlsInfoEntry 31 }

tnSvcTlsMacAgeing OBJECT-TYPE
    SYNTAX          TmnxEnabledDisabled
    MAX-ACCESS      read-write
    STATUS          current
    DESCRIPTION     "The value of the object tnSvcTlsMacAgeing specifies whether
                     the MAC aging process is enabled in this TLS."
    DEFVAL          { enabled }
    ::= { tnSvcTlsInfoEntry 32 }

tnSvcTlsStpTopologyChangeActive OBJECT-TYPE
    SYNTAX          TruthValue
    MAX-ACCESS      read-only
    STATUS          current
    DESCRIPTION     "The value of the object tnSvcTlsStpTopologyChangeActive
                     indicates, when set to 'true', that a topology change is
                     currently in progress."
    ::= { tnSvcTlsInfoEntry 33 }

tnSvcTlsFdbTableFullHighWatermark OBJECT-TYPE
    SYNTAX          Integer32 (0..100)
    MAX-ACCESS      read-write
    STATUS          current
    DESCRIPTION     "The value of the object tnSvcTlsFdbTableFullHighWatermark
                     specifies the utilization of the FDB table of this TLS
                     service at which a table full alarm will be raised
                     by the agent."
    DEFVAL          { 95 }
    ::= { tnSvcTlsInfoEntry 34 }

tnSvcTlsFdbTableFullLowWatermark OBJECT-TYPE
    SYNTAX          Integer32 (0..100)
    MAX-ACCESS      read-write
    STATUS          current
    DESCRIPTION     "The value of the object tnSvcTlsFdbTableFullLowWatermark
                     specifies the utilization of the FDB table of this TLS
                     service at which a table full alarm will be raised
                     by the agent."
    DEFVAL          { 90 }
    ::= { tnSvcTlsInfoEntry 35 }

tnSvcTlsVpnId OBJECT-TYPE
    SYNTAX          VpnId
    MAX-ACCESS      read-only
    STATUS          current
    DESCRIPTION     "The value of the object tnSvcTlsVpnId indicates the VPN ID
                     of the associated TLS service."
    ::= { tnSvcTlsInfoEntry 36 }

tnSvcTlsCustId OBJECT-TYPE
    SYNTAX          TmnxCustId
    MAX-ACCESS      read-only
    STATUS          current
    DESCRIPTION     "The vakue of the object tnSvcTlsCustId indicates the
                     Customer ID of the associated TLS service."
    ::= { tnSvcTlsInfoEntry 37 }

tnSvcTlsStpVersion OBJECT-TYPE
    SYNTAX          INTEGER {
                        rstp         (2),
                        compDot1w    (3),
                        dot1w        (4),
                        mstp         (5),
                        pmstp        (6)
                    }
    MAX-ACCESS      read-write
    STATUS          current
    DESCRIPTION     "The value of the object tnSvcTlsStpVersion specifies the
                     version of Spanning Tree Protocol the bridge is currently
                     running.

                     The value 'rstp' corresponds to  the Rapid Spanning
                     Tree Protocol specified in IEEE 802.1D/D4-2003.

                     The value 'compDot1w' corresponds to the mode where the
                     Rapid Spanning Tree is backward compatible with IEEE
                     802.1w.

                     The value 'dot1w' corresponds to  the Rapid Spanning
                     Tree Protocol fully conformant to IEEE 802.1w.

                     The value 'mstp' corresponds to the Multiple Spanning
                     Tree Protocol specified in IEEE 802.1Q-REV/D3.0-04/2005.

                     The value 'pmstp' corresponds to Provider MSTP protocol
                     compliant with IEEE-802.1ad-2005.

                     New values may be defined as future versions of the
                     protocol become available."
    DEFVAL          { rstp }
    ::= { tnSvcTlsInfoEntry 38 }

tnSvcTlsStpHoldCount OBJECT-TYPE
    SYNTAX          Integer32 (1..10)
    MAX-ACCESS      read-write
    STATUS          current
    DESCRIPTION     "The value of the object tnSvcTlsStpHoldCount specifies the
                     maximum number of BPDUs that are transmitted in any
                     'HelloTime' interval.
                     The value used by the bridge to limit the maximum
                     transmission rate of BPDUs."
    REFERENCE
                    "IEEE 802.1w clause 17.16.6"
    DEFVAL          { 6 }
    ::= { tnSvcTlsInfoEntry 39 }

tnSvcTlsStpPrimaryBridge OBJECT-TYPE
    SYNTAX          BridgeId
    MAX-ACCESS      read-only
    STATUS          current
    DESCRIPTION     "The value of the object tnSvcTlsStpPrimaryBridge indicates
                     the BridgeId of the bridge that acts as the primary bridge,
                     being the gateway from the core mesh towards the root
                     bridge."
    ::= { tnSvcTlsInfoEntry 40 }

tnSvcTlsStpBridgeInstanceId OBJECT-TYPE
    SYNTAX          Integer32 (0 ..4095)
    MAX-ACCESS      read-only
    STATUS          current
    DESCRIPTION     "The value of the object tnSvcTlsStpBridgeInstanceId
                     indicates a 12 bit value chosen by the the system. It is
                     part of the STP bridge Id, which consists of 8 octets:
                     - 4 highest bits of octet 1:
                         the bridge priority (ref tnSvcTlsStpPriority)
                     - 12 bits (4 lowest bits of octet 1 + 8 bits of octet 2):
                         bridge instance Id (this object!).
                     - 6 octets: bridge MAC addess
                         ref tnSvcTlsStpBridgeAddress
                     The value is set to 0 if tnSvcTlsStpOperStatus is not 'up'."
    ::= { tnSvcTlsInfoEntry 41 }

tnSvcTlsStpVcpOperProtocol OBJECT-TYPE
    SYNTAX          StpProtocol
    MAX-ACCESS      read-only
    STATUS          current
    DESCRIPTION     "The value of the object tnSvcTlsStpVcpOperProtocol indicates
                     whether stp, rstp or mstp is running on this VCP.
                     If the protocol is not enabled on this VCP, the value
                     notApplicable is returned."
    ::= { tnSvcTlsInfoEntry 42 }

tnSvcTlsMacMoveMaxRate OBJECT-TYPE
    SYNTAX          Unsigned32 (1..10)
    MAX-ACCESS      read-write
    STATUS          current
    DESCRIPTION     "The value of the object tnSvcTlsMacMoveMaxRate specifies the
                     maximum rate at which MAC's can be re-learned in this TLS
                     service, before the SAP where the moving MAC was last seen
                     is automatically disabled in order to protect the system
                     against undetected loops or duplicate MAC's.
                     The rate is computed as the maximum number of re-learns
                     allowed in a 5 second interval: e.g. the default rate
                     of 2 re-learns per second corresponds to 10 re-learns
                     in a 5 second period."
    DEFVAL          { 2 }
    ::= { tnSvcTlsInfoEntry 43 }

tnSvcTlsMacMoveRetryTimeout OBJECT-TYPE
    SYNTAX          Unsigned32 (0..600)
    MAX-ACCESS      read-write
    STATUS          current
    DESCRIPTION     "The value of the object  tnSvcTlsMacMoveRetryTimeout
                     specifies the time in seconds to wait before a SAP that
                     has been disabled after exceeding the maximum re-learn
                     rate is re-enabled.

                     A value of zero indicates that the SAP will not be
                     automatically re-enabled after being disabled. If after
                     the SAP is re-enabled it is disabled again, the effective
                     retry timeout is doubled in order to avoid thrashing.

                     An inconsistentValue error is returned if the value of this
                     object is set to less than fie times the value of
                     tnSvcTlsSecPortsCumulativeFactor."
    DEFVAL          { 10 }
    ::= { tnSvcTlsInfoEntry 44 }

tnSvcTlsMacMoveAdminStatus OBJECT-TYPE
    SYNTAX          TmnxEnabledDisabled
    MAX-ACCESS      read-write
    STATUS          current
    DESCRIPTION     "The value of the object tnSvcTlsMacMoveAdminStatus
                     specifies the administrative state of the
                     MAC movement feature associated with this service."
    DEFVAL          { disabled }
    ::= { tnSvcTlsInfoEntry 45 }

tnSvcTlsMacRelearnOnly OBJECT-TYPE
    SYNTAX          TruthValue
    MAX-ACCESS      read-only
    STATUS          current
    DESCRIPTION     "The value of the object tnSvcTlsMacRelearnOnly indicates
                     when set to 'true' that either the FDB table of this TLS
                     service is full, or that the maximum system-wide number of
                     MAC's supported by the agent has been reached, and thus
                     MAC learning is temporary disabled, and only MAC re-learns
                     can take place."
    ::= { tnSvcTlsInfoEntry 46 }

tnSvcTlsMfibTableSize OBJECT-TYPE
    SYNTAX          Integer32 (0..16383)
    MAX-ACCESS      read-write
    STATUS          current
    DESCRIPTION     "The value of the object  tnSvcTlsMfibTableSize specifies the
                     maximum number of entries allowed in the MFIB table of
                     this service. If the value is 0, then there is no limit."
    DEFVAL          { 0 }
    ::= { tnSvcTlsInfoEntry 47 }

tnSvcTlsMfibTableFullHighWatermark OBJECT-TYPE
    SYNTAX          Integer32 (0..100)
    MAX-ACCESS      read-write
    STATUS          current
    DESCRIPTION     "The value of the object tnSvcTlsMfibTableFullHighWatermark
                     specifies the utilization of the MFIB table of this TLS
                     service at which a table full alarm will be raised by the
                     agent."
    DEFVAL          { 95 }
    ::= { tnSvcTlsInfoEntry 48 }

tnSvcTlsMfibTableFullLowWatermark OBJECT-TYPE
    SYNTAX          Integer32 (0..100)
    MAX-ACCESS      read-write
    STATUS          current
    DESCRIPTION     "The value of the object tnSvcTlsMfibTableFullLowWatermark
                     specifies utilization of the MFIB table of this TLS
                     service at which a table full alarm will be cleared by the
                     agent."
    DEFVAL          { 90 }
    ::= { tnSvcTlsInfoEntry 49 }

tnSvcTlsMacFlushOnFail OBJECT-TYPE
    SYNTAX          TmnxEnabledDisabled
    MAX-ACCESS      read-write
    STATUS          current
    DESCRIPTION     "The value of the object tnSvcTlsMacFlushOnFail specifies
                     whether a special mac-flush is sent when a
                     port or sap becomes operational down."
    DEFVAL          { disabled }
    ::= { tnSvcTlsInfoEntry 50 }

tnSvcTlsStpRegionName OBJECT-TYPE
    SYNTAX          DisplayString (SIZE (0..32))
    MAX-ACCESS      read-write
    STATUS          current
    DESCRIPTION     "The value of the object tnSvcTlsStpRegionName specifies
                     the MSTP region name. Together with region revision and
                     VLAN-to-instance assignment it defines the MSTP region."
    DEFVAL          { "" }
    ::= { tnSvcTlsInfoEntry 51 }

tnSvcTlsStpRegionRevision OBJECT-TYPE
    SYNTAX          Integer32 (0..65535)
    MAX-ACCESS      read-write
    STATUS          current
    DESCRIPTION     "The value of the object tnSvcTlsStpRegionRevision specifies
                     the MSTP region revision number. Together with region
                     name and VLAN-to-instance assignment it defines the MSTP
                     region."
    DEFVAL          { 0 }
    ::= { tnSvcTlsInfoEntry 52 }

tnSvcTlsStpBridgeMaxHops OBJECT-TYPE
    SYNTAX          Integer32 (1..40)
    MAX-ACCESS      read-write
    STATUS          current
    DESCRIPTION     "The value of the object tnSvcTlsStpBridgeMaxHops specifies
                     the maximum number of hops (known as 'MaxHops' in 802.1Q)."
    DEFVAL          { 20 }
    ::= { tnSvcTlsInfoEntry 53 }

tnSvcTlsStpCistRegionalRoot OBJECT-TYPE
    SYNTAX          BridgeId
    MAX-ACCESS      read-only
    STATUS          current
    DESCRIPTION     "The value of the object tnSvcTlsStpCistRegionalRoot
                     indicates the bridge identifier of the regional root of
                     the CIST spanning tree as determined by the Spanning Tree
                     Protocol instance associated with this service. This value
                     is used as the CIST Regional Root Identifier parameter in
                     all MSTP BPDUs originated by this node."
    ::= { tnSvcTlsInfoEntry 54 }

tnSvcTlsStpCistIntRootCost OBJECT-TYPE
    SYNTAX          Integer32
    MAX-ACCESS      read-only
    STATUS          current
    DESCRIPTION     "The value of the object tnSvcTlsStpCistIntRootCost indicates
                     the cost of the path to the CIST regional root bridge
                     as seen from this bridge."
    ::= { tnSvcTlsInfoEntry 55 }

tnSvcTlsStpCistRemainingHopCount OBJECT-TYPE
    SYNTAX          Integer32
    MAX-ACCESS      read-only
    STATUS          current
    DESCRIPTION     "The value of the object tnSvcTlsStpCistRemainingHopCount
                     specifies the remaining number of hops."
    ::= { tnSvcTlsInfoEntry 56 }

tnSvcTlsStpCistRegionalRootPort OBJECT-TYPE
    SYNTAX          Integer32
    MAX-ACCESS      read-only
    STATUS          current
    DESCRIPTION     "The value of the object tnSvcTlsStpCistRegionalRootPort
                     indicates the port number of the port which offers the
                     lowest cost path from this bridge to the regional root
                     bridge."
    ::= { tnSvcTlsInfoEntry 57 }

tnSvcTlsFdbNumLearnedEntries OBJECT-TYPE
    SYNTAX          Integer32
    MAX-ACCESS      read-only
    STATUS          current
    DESCRIPTION     "The value of the object tnSvcTlsFdbNumLearnedEntries
                     indicates the current number of learned entries in the FDB
                     of this service."
    ::= { tnSvcTlsInfoEntry 58 }

tnSvcTlsFdbNumOamEntries OBJECT-TYPE
    SYNTAX          Integer32
    MAX-ACCESS      read-only
    STATUS          current
    DESCRIPTION     "The value of the object tnSvcTlsFdbNumOamEntries
                     indicates the current number of OAM entries in the FDB
                     of this service."
    ::= { tnSvcTlsInfoEntry 59 }

tnSvcTlsFdbNumDhcpEntries OBJECT-TYPE
    SYNTAX          Integer32
    MAX-ACCESS      read-only
    STATUS          current
    DESCRIPTION     "The value of the object tnSvcTlsFdbNumDhcpEntries
                     indicates the current number of dhcp-learned entries in the
                     FDB of this service."
    ::= { tnSvcTlsInfoEntry 60 }

tnSvcTlsFdbNumHostEntries OBJECT-TYPE
    SYNTAX          Integer32
    MAX-ACCESS      read-only
    STATUS          current
    DESCRIPTION     "The value of the object tnSvcTlsFdbNumHostEntries
                     indicates the current number of host-learned entries in the
                     FDB of this service."
    ::= { tnSvcTlsInfoEntry 61 }

tnSvcTlsShcvAction OBJECT-TYPE
    SYNTAX          INTEGER {
                         alarm  (1),
                         remove (2)
                    }
    MAX-ACCESS      read-write
    STATUS          current
    DESCRIPTION     "The value of the object tnSvcTlsShcvAction
                     indicates whether any action should be triggered when
                     the connectivity check fails."
    DEFVAL          { alarm }
    ::= { tnSvcTlsInfoEntry 62 }


tnSvcTlsShcvSrcIp OBJECT-TYPE
    SYNTAX          IpAddress
    MAX-ACCESS      read-write
    STATUS          current
    DESCRIPTION     "The value of the object tnSvcTlsShcvSrcIp
                     specifies the source IP address used when doing the
                     connectivity check. The value 0.0.0.0 indicates that
                     no host IP address is specified."
    ::= { tnSvcTlsInfoEntry 63 }

tnSvcTlsShcvSrcMac OBJECT-TYPE
    SYNTAX          MacAddress
    MAX-ACCESS      read-write
    STATUS          current
    DESCRIPTION     "The value of the object tnSvcTlsShcvSrcMac
                     specifies the MAC address used when doing the connectivity
                     check. The value 0:0:0:0:0:0 indicates that no host MAC
                     address is specified."
    ::= { tnSvcTlsInfoEntry 64 }

tnSvcTlsShcvInterval OBJECT-TYPE
    SYNTAX          Unsigned32 (0..6000)
    UNITS           "minutes"
    MAX-ACCESS      read-write
    STATUS          current
    DESCRIPTION     "The value of the object tnSvcTlsShcvInterval specifies
                     the interval in minutes between connectivity checks.
                     Zero means no connectivity checking."
    DEFVAL          { 0 }
    ::= { tnSvcTlsInfoEntry 65 }

tnSvcTlsPriPortsCumulativeFactor OBJECT-TYPE
    SYNTAX          Unsigned32 (3..10)
    MAX-ACCESS      read-write
    STATUS          current
    DESCRIPTION     "The value of the object tnSvcTlsPriPortsCumulativeFactor
                     specifies a factor for the primary ports defining how
                     many MAC-relearn periods should be used to measure the
                     MAC-relearn rate, tnSvcTlsMacMoveMaxRate. This rate must
                     be exceeded during consecutive periods before the
                     corresponding ports (SAP and/or spoke-SDP) are blocked by
                     the MAC-move feature.

                     An inconsistentValue error is returned if an attempt is
                     made to set the value of tnSvcTlsPriPortsCumulativeFactor to
                     a value lower than or equal to
                     tnSvcTlsSecPortsCumulativeFactor."
    DEFVAL          { 3 }
    ::= { tnSvcTlsInfoEntry 66 }

tnSvcTlsSecPortsCumulativeFactor OBJECT-TYPE
    SYNTAX          Unsigned32 (2..9)
    MAX-ACCESS      read-write
    STATUS          current
    DESCRIPTION     "The value of the object tnSvcTlsSecPortsCumulativeFactor
                     specifies a factor for the secondary ports defining how
                     many MAC-relearn periods should be used to measure the
                     MAC-relearn rate, tnSvcTlsMacMoveMaxRate. This rate must
                     be exceeded during consecutive periods before the
                     corresponding ports (SAP and/or spoke-SDP) are blocked by
                     the MAC-move feature.

                     An inconsistentValue error is returned if an attempt is
                     made to set the value of tnSvcTlsSecPortsCumulativeFactor to
                     a value greater than or equal to
                     tnSvcTlsPriPortsCumulativeFactor."
    DEFVAL          { 2 }
    ::= { tnSvcTlsInfoEntry 67 }

tnSvcTlsL2ptTermEnabled OBJECT-TYPE
    SYNTAX          TruthValue
    MAX-ACCESS      read-only
    STATUS          current
    DESCRIPTION     "The value of the object tnSvcTlsL2ptTermEnabled
                     indicates if 'L2PT-termination' and/or 'Bpdu-translation'
                     is in use in this service by at least one SAP or
                     spoke SDP Bind. If the value is 'true', it means that
                     at least one of 'L2PT-termination' or 'Bpdu-translation'
                     is enabled.

                     When enabled it is not possible to enable
                     stp on this service."
    ::= { tnSvcTlsInfoEntry 68 }

tnSvcTlsPropagateMacFlush OBJECT-TYPE
    SYNTAX          TruthValue
    MAX-ACCESS      read-write
    STATUS          current
    DESCRIPTION     "The value of tnSvcTlsPropagateMacFlush specifies whether
                     'MAC flush' messages received from the given LDP are
                     propagated to all spoke-SDPs and mesh-SDPs within the
                     context of this VPLS service. The propagation will follow
                     the 'split-horizon' principle and any data-path blocking in
                     order to avoid the looping of these messages.

                     The value of 'true' enables the propagation."
    DEFVAL         { false }
    ::= { tnSvcTlsInfoEntry 69 }

tnSvcTlsMrpAdminStatus OBJECT-TYPE
    SYNTAX          TmnxEnabledDisabled
    MAX-ACCESS      read-write
    STATUS          current
    DESCRIPTION     "The value of the object tnSvcTlsMrpAdminStatus specifies
                     whether the Multiple Registration Protocol (MRP) is
                     enabled in this TLS."
    DEFVAL          { disabled }
    ::= { tnSvcTlsInfoEntry 70 }

tnSvcTlsMrpMaxAttributes OBJECT-TYPE
    SYNTAX          Unsigned32 (1..2048)
    MAX-ACCESS      read-write
    STATUS          current
    DESCRIPTION     "The value of the object tnSvcTlsMrpMaxAttributes indicates
                     maximum number of MRP attributes supported in this TLS.

                     In most cases the default value is 2048 MRP attributes.
                     For some platform and chassis types, especially single slot
                     chassises, the default value will be lower due to resource
                     constraints.

                     An inconsistentValue error is returned if an attempt is
                     made to set this object to a value the platform cannot
                     support."
    ::= { tnSvcTlsInfoEntry 71 }

tnSvcTlsMrpAttributeCount OBJECT-TYPE
    SYNTAX          Unsigned32
    MAX-ACCESS      read-only
    STATUS          current
    DESCRIPTION     "The value of the object tnSvcTlsMrpAttributeCount indicates
                     the number of MRP attributes currently associated to the
                     TLS by either being registered or declared.

                     Note that an 'iVpls' service (with tnSvcVplsType set to
                     'iVpls') holds a declaration in the 'bVpls' service (with
                     tnSvcVplsType set to 'bVpls') regardless of the state of the
                     'iVpls' service, although that declaration will not be
                     propagated in the 'bVpls' service unless the tnSvcOperStatus
                     of 'iVpls' service is 'up'."
    ::= { tnSvcTlsInfoEntry 72 }

tnSvcTlsMrpFailedRegisterCount OBJECT-TYPE
    SYNTAX          Unsigned32
    MAX-ACCESS      read-only
    STATUS          current
    DESCRIPTION     "The value of the object tnSvcTlsMrpFailedRegisterCount
                     indicates number of failed MRP attribute registrations in
                     this TLS."
    ::= { tnSvcTlsInfoEntry 73 }

tnSvcTlsMcPathMgmtPlcyName OBJECT-TYPE
    SYNTAX          TNamedItem
    MAX-ACCESS      read-write
    STATUS          current
    DESCRIPTION     "The value of tnSvcTlsMcPathMgmtPlcyName specifies the
                     multicast policy name configured on this service."
    DEFVAL          { "default" }
    ::= { tnSvcTlsInfoEntry 74 }

tnSvcTlsMrpFloodTime OBJECT-TYPE
    SYNTAX          Unsigned32 (0|3..600)
    UNITS           "seconds"
    MAX-ACCESS      read-write
    STATUS          current
    DESCRIPTION     "The value of the object tnSvcTlsMrpFloodTime specifies
                     the amount of time in seconds after a status change in the
                     TLS during which traffic is flooded.  Once that time
                     expires, traffic will be delivered according to the MRP
                     registrations which exist in the TLS.

                     The value of 0 indicates that no flooding will occur on
                     state changes in the TLS."
    DEFVAL          { 0 }
    ::= { tnSvcTlsInfoEntry 75 }

tnSvcTlsMrpAttrTblHighWatermark OBJECT-TYPE
    SYNTAX          Integer32 (0..100)
    MAX-ACCESS      read-write
    STATUS          current
    DESCRIPTION     "The value of the object tnSvcTlsMrpAttrTblHighWatermark
                     specifies the utilization of the MRP attribute table of
                     this TLS service at which a table full alarm will be raised
                     by the agent."
    DEFVAL          { 95 }
    ::= { tnSvcTlsInfoEntry 76 }

tnSvcTlsMrpAttrTblLowWatermark OBJECT-TYPE
    SYNTAX          Integer32 (0..100)
    MAX-ACCESS      read-write
    STATUS          current
    DESCRIPTION     "The value of the object tnSvcTlsMrpAttrTblLowWatermark
                     specifies utilization of the MRP attribute table of this
                     TLS service at which a table full alarm will be cleared by
                     the agent."
    DEFVAL          { 90 }
    ::= { tnSvcTlsInfoEntry 77 }

tnSvcTlsMacMoveNumRetries OBJECT-TYPE
    SYNTAX          Unsigned32 (0..255)
    MAX-ACCESS      read-write
    STATUS          current
    DESCRIPTION     "The value of the object  tnSvcTlsMacMoveNumRetries
                     specifies the number of times retries are performed for
                     reenabling the SAP/SDP.

                     A value of zero indicates unlimited number of retries."

    DEFVAL          { 3 }
    ::= { tnSvcTlsInfoEntry 78 }

tnSvcTlsMacSubNetLen OBJECT-TYPE
    SYNTAX          Integer32 (24..48)
    MAX-ACCESS      read-write
    STATUS          current
    DESCRIPTION     "The value of the object tnSvcTlsMacSubNetLen specifies
                     the number of bits to be considered when performing
                     MAC-Learning or MAC-Switching."
    DEFVAL          { 48 }
    ::= { tnSvcTlsInfoEntry 79 }


tnSvcTlsSendFlushOnBVplsFail OBJECT-TYPE
    SYNTAX          TruthValue
    MAX-ACCESS      read-write
    STATUS          current
    DESCRIPTION     "The value of the object tnSvcTlsSendFlushOnBVplsFail
                     specifies whether a special 'MAC flush' is sent in the
                     local 'iVpls' following a failure of SAP/Endpoint/SDP in
                     the 'bVpls'."
    DEFVAL          { false }
    ::= { tnSvcTlsInfoEntry 80 }

tnSvcTlsPropMacFlushFromBVpls OBJECT-TYPE
    SYNTAX          TruthValue
    MAX-ACCESS      read-write
    STATUS          current
    DESCRIPTION     "The value of the object tnSvcTlsPropMacFlushFromBVpls
                     specifies whether to propagate any 'MAC flush' from 'bVpls'
                     into the local 'iVpls'."
    DEFVAL          { false }
    ::= { tnSvcTlsInfoEntry 81 }

tnSvcTlsMacNotifInterval OBJECT-TYPE
    SYNTAX          Unsigned32 (0..100)
    UNITS           "deci-seconds"
    MAX-ACCESS      read-write
    STATUS          current
    DESCRIPTION     "The value of tnSvcTlsMacNotifInterval specifies time-interval
                     between subsequent MAC notification messages.  The default
                     value for this object indicates that the value is inherited
                     from tnSvcMacNotifInterval."
    REFERENCE       "ITU-T Y.1731 specification"
    DEFVAL          { 0 }
    ::= { tnSvcTlsInfoEntry 82 }

tnSvcTlsMacNotifCount OBJECT-TYPE
    SYNTAX          Unsigned32 (0..10)
    MAX-ACCESS      read-write
    STATUS          current
    DESCRIPTION     "The value of tnSvcTlsMacNotifCount specifies number of
                     MAC notification messages to be sent. The default value
                     for this object indicates that the value is inherited from
                     tnSvcMacNotifCount."
    REFERENCE       "ITU-T Y.1731 specification"
    DEFVAL          { 0 }
    ::= { tnSvcTlsInfoEntry 83 }

tnSvcTlsMacNotifAdminState OBJECT-TYPE
    SYNTAX          TmnxEnabledDisabled
    MAX-ACCESS      read-write
    STATUS          current
    DESCRIPTION     "The value of tnSvcTlsMacNotifAdminState specifies whether
                     MAC notification messages should be sent."
    DEFVAL { disabled }
    ::= { tnSvcTlsInfoEntry 84 }

tnSvcTlsShcvRetryTimeout OBJECT-TYPE
    SYNTAX          Unsigned32 (10..60)
    UNITS           "seconds"
    MAX-ACCESS      read-write
    STATUS          current
    DESCRIPTION     "The value of the object tnSvcTlsShcvRetryTimeout specifies
                     the timeout in seconds before a connectivity check
                     retransmission."
    DEFVAL          { 10 }
    ::= { tnSvcTlsInfoEntry 87 }

tnSvcTlsShcvRetryCount OBJECT-TYPE
    SYNTAX          Unsigned32 (2..29)
    MAX-ACCESS      read-write
    STATUS          current
    DESCRIPTION     "The value of the object tnSvcTlsShcvRetryCount specifies
                     the number of connectivity check retransmissions.

                     Setting the value to n specifies that, for any given host,
                     at most (n+1) probes are done each interval,
                     and (n+1) missed replies are considered as a connectivity
                     failure."
    DEFVAL          { 2 }
    ::= { tnSvcTlsInfoEntry 88 }

tnsvcTlsAllowIpIfBinding  OBJECT-TYPE
    SYNTAX          TruthValue
    MAX-ACCESS      read-write
    STATUS          current
    DESCRIPTION     "The value of the object tnsvcTlsAllowIpIfBinding indicates,
                     whether to allow IP interface binding on this service."
    DEFVAL          { false }
    ::= { tnSvcTlsInfoEntry 89 }

tnSvcTlsMfibTableNumEntries  OBJECT-TYPE
    SYNTAX          Integer32
    MAX-ACCESS      read-only
    STATUS          current
    DESCRIPTION     "The value of the object tnSvcTlsMfibTableNumEntries indicates
                     the number of MFIB entries on this service."
    ::= { tnSvcTlsInfoEntry 90 }

-- ------------------------------------
-- TLS FDB Table
-- ------------------------------------
tnTlsFdbInfoTable OBJECT-TYPE
    SYNTAX          SEQUENCE OF TnTlsFdbInfoEntry
    MAX-ACCESS      not-accessible
    STATUS          current
    DESCRIPTION     "A table that contains TLS FDB information."
    ::= { tnSvcObjs 4 }

tnTlsFdbInfoEntry OBJECT-TYPE
    SYNTAX          TnTlsFdbInfoEntry
    MAX-ACCESS      not-accessible
    STATUS          current
    DESCRIPTION     "Information about a specific TLS FDB."
    INDEX           { tnSysSwitchId, tnSvcId, tnTlsFdbMacAddr }
    ::= { tnTlsFdbInfoTable 1 }

TnTlsFdbInfoEntry ::=
    SEQUENCE {
        tnTlsFdbMacAddr           MacAddress,
        tnTlsFdbRowStatus         RowStatus,
        tnTlsFdbType              INTEGER,
        tnTlsFdbLocale            INTEGER,
        tnTlsFdbPortId            TmnxPortID,
        tnTlsFdbEncapValue        TmnxEncapVal,
        tnTlsFdbSdpId             SdpId,
        tnTlsFdbVcId              Unsigned32,
        tnTlsFdbVpnId             VpnId,
        tnTlsFdbCustId            TmnxCustId,
        tnTlsFdbLastStateChange   TimeStamp,
        tnTlsFdbProtected         TruthValue,
        tnTlsFdbBackboneDstMac    MacAddress,
        tnTlsFdbNumIVplsMac       Unsigned32,
        tnTlsFdbEndPointName      TNamedItemOrEmpty,
        tnTlsFdbEPMacOperSdpId    SdpId,
        tnTlsFdbEPMacOperVcId     Unsigned32,
        tnTlsFdbPbbNumEpipes      Unsigned32
    }

tnTlsFdbMacAddr OBJECT-TYPE
    SYNTAX          MacAddress
    MAX-ACCESS      not-accessible
    STATUS          current
    DESCRIPTION     "The value of the object tnTlsFdbMacAddr specifies the
                     48-bit IEEE 802.3 MAC address."
    ::= { tnTlsFdbInfoEntry 1 }

tnTlsFdbRowStatus OBJECT-TYPE
    SYNTAX          RowStatus
    MAX-ACCESS      read-create
    STATUS          current
    DESCRIPTION     "The value of the object tnTlsFdbRowStatus specifies the
                     status of this row. The only values supported during a set
                     operation are 'createAndGo' and 'destroy'."
    ::= { tnTlsFdbInfoEntry 2 }

tnTlsFdbType OBJECT-TYPE
    SYNTAX          INTEGER {
                        static  (1),
                        learned (2),
                        oam     (3),
                        dhcp    (4),
                        host    (5)
                    }
    MAX-ACCESS      read-create
    STATUS          current
    DESCRIPTION     " The value of the object tnTlsFdbType specifies:
                     - 'static':  Static TLS FDB entries created via management
                     - 'learned': dynamic entries created via the learning
                                  process
                     - 'oam':     entries created via the OAM process
                     - 'dhcp':    learned  addresses can be temporarily frozen
                                  by the DHCP snooping application for the
                                  duration of a DHCP lease
                     - 'host':    entry added by the system for a static
                                  configured subscriber host."
    ::= { tnTlsFdbInfoEntry 3 }

tnTlsFdbLocale OBJECT-TYPE
    SYNTAX          INTEGER {
                        sap      (1),
                        sdp      (2),
                        cpm      (3),
                        endpoint (4)
                    }
    MAX-ACCESS      read-create
    STATUS          current
    DESCRIPTION     "The value of the object tnTlsFdbLocale specifies for TLS
                     FDB entries defined on a local SAP the value 'sap',
                     remote entries defined on an SDP have the value 'sdp',
                     entries associated with the Control Processor have the
                     value 'cpm' and entries associated with the explicit
                     endpoint have the value 'endpoint'.

                     The value of this object must be specified when
                     the row is created and cannot be changed while
                     the row status is 'active'."
    ::= { tnTlsFdbInfoEntry 4 }

tnTlsFdbPortId OBJECT-TYPE
    SYNTAX          TmnxPortID
    MAX-ACCESS      read-create
    STATUS          current
    DESCRIPTION     "When the value of tnTlsFdbLocale is 'sap', this
                     object, along with tnTlsFdbEncapValue, specifies
                     the SAP associated with the MAC address defined
                     by tnTlsFdbMacAddr. This object is otherwise
                     insignificant and should contain a value of 0."
    ::= { tnTlsFdbInfoEntry 5 }

tnTlsFdbEncapValue OBJECT-TYPE
    SYNTAX          TmnxEncapVal
    MAX-ACCESS      read-create
    STATUS          current
    DESCRIPTION     "The value of the object tnTlsFdbEncapValue specifies, when
                     the value of tnTlsFdbLocale is 'sap', along with
                     tnTlsFdbPortId, SAP associated with the MAC address defined
                     by tnTlsFdbMacAddr. This object is otherwise insignificant
                     and should contain a value of 0."
    ::= { tnTlsFdbInfoEntry 6 }

tnTlsFdbSdpId OBJECT-TYPE
    SYNTAX          SdpId
    MAX-ACCESS      read-create
    STATUS          current
    DESCRIPTION     "The value of the object tnTlsFdbSdpId specifies, when the
                     value of tnTlsFdbLocale is 'sdp', along with tnTlsFdbVcId,the
                     SDP Binding associated with the MAC address
                     defined by tnTlsFdbMacAddr. This object is other-
                     wise insignificant and should contain a value of 0."
    ::= { tnTlsFdbInfoEntry 7 }

tnTlsFdbVcId OBJECT-TYPE
    SYNTAX          Unsigned32
    MAX-ACCESS      read-create
    STATUS          current
    DESCRIPTION     "The value of the object tnTlsFdbVcId specifies, when the
                     value of tnTlsFdbLocale is 'sdp', along with tnTlsFdbSdpId,
                     the SDP Binding associated with the MAC address defined by
                     tnTlsFdbMacAddr. This object is other-wise insignificant and
                     should contain a value of 0."
    ::= { tnTlsFdbInfoEntry 8 }

tnTlsFdbVpnId OBJECT-TYPE
    SYNTAX          VpnId
    MAX-ACCESS      read-only
    STATUS          current
    DESCRIPTION     "The value of the object tnTlsFdbVpnId indicates the VPN ID
                     of the associated TLS."
    ::= { tnTlsFdbInfoEntry 9 }

tnTlsFdbCustId OBJECT-TYPE
    SYNTAX          TmnxCustId
    MAX-ACCESS      read-only
    STATUS          current
    DESCRIPTION     "The value of the object tnTlsFdbCustId indicates the
                     Customer ID of the associated TLS."
    ::= { tnTlsFdbInfoEntry 10 }

tnTlsFdbLastStateChange OBJECT-TYPE
    SYNTAX          TimeStamp
    MAX-ACCESS      read-only
    STATUS          current
    DESCRIPTION     "The value of the object tnTlsFdbLastStateChange indicates
                     the value of sysUpTime at the time of the most recent
                     state change of this entry. A state change is defined as a
                     change in the value of: tnTlsFdbRowStatus, tnTlsFdbType,
                     tnTlsFdbLocale, tnTlsFdbPortId, tnTlsFdbEncapValue,
                     tnTlsFdbSdpId or tnTlsFdbVcId."
    ::= { tnTlsFdbInfoEntry 11 }

tnTlsFdbProtected OBJECT-TYPE
    SYNTAX          TruthValue
    MAX-ACCESS      read-only
    STATUS          current
    DESCRIPTION     "The value of the object tnTlsFdbProtected indicates
                     whether or not this MAC is protected. When the value
                     of this object is 'true' the agent will protect
                     the MAC from being learned or re-learned on a SAP
                     that has restricted learning enabled."
    ::= { tnTlsFdbInfoEntry 12 }

tnTlsFdbBackboneDstMac OBJECT-TYPE
    SYNTAX          MacAddress
    MAX-ACCESS      read-only
    STATUS          current
    DESCRIPTION     "The value of the object tnTlsFdbBackboneDstMac indicates the
                     Backbone VPLS service MAC address used as destination MAC
                     address in the Provider Backbone Bridging frames for this
                     tnTlsFdbMacAddr.

                     This object is insignificant for services with tnSvcVplsType
                     not set to 'iVpls' and should contain a value of
                     0:0:0:0:0:0."
    ::= { tnTlsFdbInfoEntry 13 }

tnTlsFdbNumIVplsMac OBJECT-TYPE
    SYNTAX          Unsigned32
    MAX-ACCESS      read-only
    STATUS          current
    DESCRIPTION     "The value of the object tnTlsFdbNumIVplsMac indicates the
                     number of ISID VPLS service MAC addressess which are using
                     this Backbone MAC address defined by tnTlsFdbMacAddr.

                     This object is insignificant for services with tnSvcVplsType
                     not set to 'bVpls' and should contain a value of 0."
    ::= { tnTlsFdbInfoEntry 14 }

tnTlsFdbEndPointName         OBJECT-TYPE
    SYNTAX      TNamedItemOrEmpty
    MAX-ACCESS  read-create
    STATUS      current
    DESCRIPTION
        "The value of tnTlsFdbEndPointName specifies the name of the service
        endpoint associated with the MAC Address."
    DEFVAL     { "" }
    ::= { tnTlsFdbInfoEntry 15 }

tnTlsFdbEPMacOperSdpId OBJECT-TYPE
    SYNTAX          SdpId
    MAX-ACCESS      read-only
    STATUS          current
    DESCRIPTION
        "The value of the object tnTlsFdbEPMacOperSdpId along with
        tnTlsFdbEPMacOperVcId indicates the SDP binding associated with this
        static MAC address for this endpoint.

        This object is valid when tnTlsFdbLocale is 'endpoint', otherwise
        it should contain a value of 0."
    ::= { tnTlsFdbInfoEntry 16 }

tnTlsFdbEPMacOperVcId OBJECT-TYPE
    SYNTAX          Unsigned32
    MAX-ACCESS      read-only
    STATUS          current
    DESCRIPTION
        "The value of the object tnTlsFdbEPMacOperVcId along with
        tnTlsFdbEPMacOperSdpId indicates the SDP binding associated with this
        static MAC address for this endpoint.

        This object is valid when tnTlsFdbLocale is 'endpoint', otherwise
        it should contain a value of 0."
    ::= { tnTlsFdbInfoEntry 17 }

tnTlsFdbPbbNumEpipes OBJECT-TYPE
    SYNTAX          Unsigned32
    MAX-ACCESS      read-only
    STATUS          current
    DESCRIPTION
        "The value of the object tnTlsFdbPbbNumEpipes indicates number of E-Pipes
        that resolve to this MAC Address.

        This object is valid for service with tnSvcVplsType set to 'bVpls',
        otherwise it should contain a value of 0."
    ::= { tnTlsFdbInfoEntry 18 }

-- ------------------------------------
-- IES Interface Table
-- ------------------------------------
-- tnIesIfTable OBJECT-TYPE
--     SYNTAX          SEQUENCE OF IesIfEntry
--     MAX-ACCESS      not-accessible
--     STATUS          current
--     DESCRIPTION     "A table that contains IES interface information."
--     ::= { tnSvcObjs 5 }
--
-- tnIesIfEntry OBJECT-TYPE
--     SYNTAX          IesIfEntry
--     MAX-ACCESS      not-accessible
--     STATUS          current
--     DESCRIPTION     "Information about a specific IES interface."
--     INDEX           { tnSysSwitchId,  tnSvcId, tnIesIfIndex }
--     ::= { tnIesIfTable 1 }
--
-- IesIfEntry ::=
--     SEQUENCE {
--         tnIesIfIndex                 InterfaceIndex,
--         tnIesIfRowStatus             RowStatus,
--         tnIesIfName                  TNamedItem,
--         tnIesIfDescription           ServObjLongDesc,
--         tnIesIfAdminStatus           ServiceAdminStatus,
--         tnIesIfOperStatus            ServiceOperStatus,
--         tnIesIfLastMgmtChange        TimeStamp,
--         tnIesIfVpnId                 VpnId,
--         tnIesIfCustId                TmnxCustId,
--         tnIesIfLoopback              TruthValue,
--         tnIesIfLastStatusChange      TimeStamp,
--         tnIesIfType                  INTEGER,
--         tnIesIfParentIf              InterfaceIndexOrZero,
--         tnIesIfShcvSource            INTEGER,
--         tnIesIfShcvAction            INTEGER,
--         tnIesIfShcvInterval          Unsigned32,
--         tnIesIfFwdServId             TmnxServId,
--         tnIesIfFwdSubIf              InterfaceIndexOrZero,
--         tnIesIfPrivateRetailSubnets  TruthValue,
--         tnIesIfShcvRetryTimeout      Unsigned32,
--         tnIesIfShcvRetryCount        Unsigned32
--     }
--
-- tnIesIfIndex OBJECT-TYPE
--     SYNTAX          InterfaceIndex
--     MAX-ACCESS      not-accessible
--     STATUS          current
--     DESCRIPTION     "The secondary index of the row in the vRtrIfTable
--                      corresponding to this IES interface. The primary
--                      index is 1; i.e. all IES interfaces are defined in
--                      the Base virtual router context."
--     ::= { tnIesIfEntry 1 }
--
-- tnIesIfRowStatus OBJECT-TYPE
--     SYNTAX          RowStatus
--     MAX-ACCESS      read-create
--     STATUS          current
--     DESCRIPTION     "The value of the object tnIesIfRowStatus specifies the
--                      status of this row.
--                      The only values supported during a set operation are
--                      'createAndGo' and 'destroy'."
--     ::= { tnIesIfEntry 2 }
--
-- tnIesIfName OBJECT-TYPE
--     SYNTAX          TNamedItem
--     MAX-ACCESS      read-create
--     STATUS          current
--     DESCRIPTION     "The value of the object tnIesIfName specifies the name used
--                      to refer to this IES interface. This  name must be unique
--                      within the Base virtual router context.
--                      This object must be specified when the row is created, and
--                      cannot be changed while the rowstatus is 'active'."
--     ::= { tnIesIfEntry 3 }
--
-- tnIesIfDescription OBJECT-TYPE
--     SYNTAX          ServObjLongDesc
--     MAX-ACCESS      read-create
--     STATUS          current
--     DESCRIPTION     "The value of the object tnIesIfDescription specifies
--                      generic information about this IES interface."
--     DEFVAL          { "" }
--     ::= { tnIesIfEntry 4 }
--
-- tnIesIfAdminStatus OBJECT-TYPE
--     SYNTAX          ServiceAdminStatus
--     MAX-ACCESS      read-create
--     STATUS          current
--     DESCRIPTION     "The value of the object tnIesIfAdminStatus specifies the
--                      desired state of this IES interface."
--     DEFVAL          { up }
--     ::= { tnIesIfEntry 5 }
--
-- tnIesIfOperStatus OBJECT-TYPE
--     SYNTAX          ServiceOperStatus
--     MAX-ACCESS      read-only
--     STATUS          current
--     DESCRIPTION     "The value of the object tnIesIfOperStatus indicates the
--                      operating state of this IES interface."
--     ::= { tnIesIfEntry 6 }
--
-- tnIesIfLastMgmtChange OBJECT-TYPE
--     SYNTAX          TimeStamp
--     MAX-ACCESS      read-only
--     STATUS          current
--     DESCRIPTION     "The value of the object tnIesIfLastMgmtChange indicates the
--                      value of sysUpTime at the time of the most recent
--                      management-initiated change to this IES interface."
--     ::= { tnIesIfEntry 7 }
--
-- tnIesIfVpnId OBJECT-TYPE
--     SYNTAX          VpnId
--     MAX-ACCESS      read-only
--     STATUS          current
--     DESCRIPTION     "The value of the object tnIesIfVpnId indicates the VPN ID of
--                      the associated IES service."
--     ::= { tnIesIfEntry 8 }
--
-- tnIesIfCustId OBJECT-TYPE
--     SYNTAX          TmnxCustId
--     MAX-ACCESS      read-only
--     STATUS          current
--     DESCRIPTION     "The value of the object tnIesIfCustId indicates the Customer
--                      ID of the associated IES service."
--     ::= { tnIesIfEntry 9 }
--
-- tnIesIfLoopback OBJECT-TYPE
--     SYNTAX          TruthValue
--     MAX-ACCESS      read-create
--     STATUS          current
--     DESCRIPTION     "When the value of tnIesIfLoopback is set to 'true',
--                      loopback is enabled on the  IES interface represented
--                      by this row entry.  When the value is 'false',
--                      loopback is disabled."
--     ::= { tnIesIfEntry 10 }
--
-- tnIesIfLastStatusChange OBJECT-TYPE
--     SYNTAX          TimeStamp
--     MAX-ACCESS      read-only
--     STATUS          current
--     DESCRIPTION     "The value of the object tnIesIfLastStatusChange indicates
--                      the value of sysUpTime at the time of the most recent
--                      operating status change to his interface."
--     ::= { tnIesIfEntry 11 }
--
-- tnIesIfType  OBJECT-TYPE
--     SYNTAX          INTEGER {
--                         service    (1),
--                         subscriber (2),
--                         group      (3),
--                         redundant  (4),
--                         cem        (5),
--                         ipsec      (6),
--                         ipMirror   (7),
--                         video      (8)
--                     }
--     MAX-ACCESS      read-create
--     STATUS          current
--     DESCRIPTION     "The value of tnIesIfType specifies the type
--                      of this IES interface. This object can only be set at
--                      row creation time.
--                      'service'     - This is a normal IES interface.
--                      'subscriber'  - This is a subscriber interface,
--                                      under which multiple group interfaces
--                                      can be configured.
--                      'group'       - This is a group interface, belonging
--                                      to a parent subscriber interface.
--                      'redundant'   - This is a redundant interface, used
--                                      for dual homing.
--                      'cem'         - This is a CEM interface, used for
--                                      IP/UDP encapsulated CEM IES interface.
--                      'ipsec'       - This is an IPsec interface, used for
--                                      IPsec tunneling.
--                      'ipMirror'    - This is an IP interface, used for
--                                      IP Mirroring.
--                      'video'       - This is a video IP interface."
--     DEFVAL          { service }
--     ::= { tnIesIfEntry 12 }
--
-- tnIesIfParentIf   OBJECT-TYPE
--     SYNTAX          InterfaceIndexOrZero
--     MAX-ACCESS      read-create
--     STATUS          current
--     DESCRIPTION     "The value of tnIesIfParentIf specifies the ifIndex of
--                      this interface's parent. This value can only be set at
--                      row creation time, and is only valid when
--                      tnIesIfType is 'group'. The interface pointed to by
--                      tnIesIfParentIf must be of type 'subscriber'."
--     DEFVAL          { 0 }
--     ::= { tnIesIfEntry 13 }
--
-- tnIesIfShcvSource    OBJECT-TYPE
--     SYNTAX          INTEGER {
--                         interface (1),
--                         vrrp      (2)
--                     }
--     MAX-ACCESS      read-create
--     STATUS          current
--     DESCRIPTION     "The value of tnIesIfShcvSource specifies the source used
--                      for subscriber host connectivity checking"
--     DEFVAL          { interface }
--     ::= { tnIesIfEntry 14 }
--
-- tnIesIfShcvAction    OBJECT-TYPE
--     SYNTAX          INTEGER {
--                         alarm  (1),
--                         remove (2)
--                     }
--     MAX-ACCESS      read-create
--     STATUS          current
--     DESCRIPTION     "The value of tnIesIfShcvAction specifies the action to be
--                      taken for hosts on this interface whose host connectivity
--                      checking fails"
--     DEFVAL          { alarm }
--     ::= { tnIesIfEntry 15 }
--
-- tnIesIfShcvInterval   OBJECT-TYPE
--     SYNTAX          Unsigned32 (0..6000)
--     UNITS           "minutes"
--     MAX-ACCESS      read-create
--     STATUS          current
--     DESCRIPTION     "The value of the object tnIesIfShcvInterval specifies
--                      the interval in minutes between connectivity checks.
--                      Zero means no in host-connection-verify"
--     DEFVAL          { 0 }
--     ::= { tnIesIfEntry 16 }
--
-- tnIesIfFwdServId       OBJECT-TYPE
--     SYNTAX           TmnxServId
--     MAX-ACCESS       read-create
--     STATUS           current
--     DESCRIPTION      "The value of tnIesIfFwdServId specifies the forwarding
--                       service ID for a subscriber interface in a retailer
--                       context. This value can only be set at row creation time
--                       along with tnIesIfFwdSubIf, and it is only valid when
--                       tnIesIfType is 'subscriber'. The tnIesIfFwdServId MUST
--                       correspond to a service of type 'vprn'."
--     DEFVAL           { 0 }
--     ::= { tnIesIfEntry 17 }
--
-- tnIesIfFwdSubIf        OBJECT-TYPE
--     SYNTAX           InterfaceIndexOrZero
--     MAX-ACCESS       read-create
--     STATUS           current
--     DESCRIPTION      "The value of tnIesIfFwdSubIf specifies the forwarding
--                       subscriber interface for a subscriber interface in a
--                       retailer context. This value can only be set at row
--                       creation time along with tnIesIfFwdServId, and it is only
--                       valid when tnIesIfType is 'subscriber'. The interface
--                       pointed to by tnIesIfFwdSubIf MUST be of type 'subscriber'
--                       in the the service context defined by tnIesIfFwdServId."
--     DEFVAL           { 0 }
--     ::= { tnIesIfEntry 18 }
--
-- tnIesIfPrivateRetailSubnets  OBJECT-TYPE
--     SYNTAX           TruthValue
--     MAX-ACCESS       read-create
--     STATUS           current
--     DESCRIPTION      "The value of tnIesIfPrivateRetailSubnets specifies
--                       whether or not overlapping Ip address may exist between
--                       different retailers referring to this interface."
--     ::= { tnIesIfEntry 19 }
--
-- tnIesIfShcvRetryTimeout OBJECT-TYPE
--     SYNTAX          Unsigned32 (10..60)
--     UNITS           "seconds"
--     MAX-ACCESS      read-create
--     STATUS          current
--     DESCRIPTION     "The value of the object tnIesIfShcvRetryTimeout specifies
--                      the timeout in seconds before a connectivity check
--                      retransmission."
--     DEFVAL          { 10 }
--     ::= { tnIesIfEntry 25 }
--
-- tnIesIfShcvRetryCount OBJECT-TYPE
--     SYNTAX          Unsigned32 (2..29)
--     MAX-ACCESS      read-create
--     STATUS          current
--     DESCRIPTION     "The value of the object tnIesIfShcvRetryCount specifies
--                      the number of connectivity check retransmissions.
--
--                      Setting the value to n specifies that, for any given host,
--                      at most (n+1) probes are done each interval,
--                      and (n+1) missed replies are considered as a connectivity
--                      failure."
--     DEFVAL          { 2 }
--     ::= { tnIesIfEntry 26 }

-- ------------------------------------
-- TLS Split-Horizon Group Table
-- ------------------------------------
tnTlsShgInfoTable OBJECT-TYPE
    SYNTAX          SEQUENCE OF TnTlsShgInfoEntry
    MAX-ACCESS      not-accessible
    STATUS          current
    DESCRIPTION     "A table that contains TLS service split-horizon group
                     information. A maximum of 30 split-horizon groups can
                     be created in a given TLS service. Maximum is set to 15
                     for a TLS service with tnSvcVplsType set to 'bVpls', or
                     'iVpls'."
    ::= { tnSvcObjs 6 }

tnTlsShgInfoEntry OBJECT-TYPE
    SYNTAX          TnTlsShgInfoEntry
    MAX-ACCESS      not-accessible
    STATUS          current
    DESCRIPTION     "Split-horizon group information about a TLS service."
    INDEX           { tnSysSwitchId,  tnSvcId, IMPLIED tnTlsShgName }
    ::= { tnTlsShgInfoTable 1 }

TnTlsShgInfoEntry ::=
    SEQUENCE {
        tnTlsShgName                  TNamedItem,
        tnTlsShgRowStatus             RowStatus,
        tnTlsShgCustId                TmnxCustId,
        tnTlsShgInstanceId            Unsigned32,
        tnTlsShgDescription           ServObjDesc,
        tnTlsShgLastMgmtChange        TimeStamp,
        tnTlsShgResidential           TruthValue,
        tnTlsShgRestProtSrcMac        TruthValue,
        tnTlsShgRestUnprotDstMac      TruthValue,
        tnTlsShgRestProtSrcMacAction  INTEGER,
        tnTlsShgCreationOrigin        L2RouteOrigin
    }

tnTlsShgName OBJECT-TYPE
    SYNTAX          TNamedItem
    MAX-ACCESS      not-accessible
    STATUS          current
    DESCRIPTION     "The value of the object tnTlsShgName specifies the name of
                     the split-horizon group. The name must be unique within
                     a TLS, however the same name can appear in different
                     TLS services, in which case they denote different
                     split-horizon groups."
    ::= { tnTlsShgInfoEntry 1 }

tnTlsShgRowStatus OBJECT-TYPE
    SYNTAX          RowStatus
    MAX-ACCESS      read-create
    STATUS          current
    DESCRIPTION     "The value of the object  tnTlsShgRowStatus specifies the
                     status of this row.
                     The only values supported during a set operation are
                     'createAndGo' and 'destroy'. To delete an entry
                     from this table, there should be no TLS SAP's or
                     TLS spoke SDP Bindings refering to it."
    ::= { tnTlsShgInfoEntry 2 }

tnTlsShgCustId OBJECT-TYPE
    SYNTAX          TmnxCustId
    MAX-ACCESS      read-only
    STATUS          current
    DESCRIPTION     "The value of the object tnTlsShgCustId indicates the
                     Customer ID of the associated TLS service."
    ::= { tnTlsShgInfoEntry 3 }

tnTlsShgInstanceId OBJECT-TYPE
    SYNTAX          Unsigned32
    MAX-ACCESS      read-only
    STATUS          current
    DESCRIPTION     "The value of the object tnTlsShgInstanceId indicates the
                     instance identifier for the split horizon group."
    ::= { tnTlsShgInfoEntry 4 }

tnTlsShgDescription OBJECT-TYPE
    SYNTAX          ServObjDesc
    MAX-ACCESS      read-create
    STATUS          current
    DESCRIPTION     "The value of the object tnTlsShgDescription specifies
                     generic information about this split-horizon group."
    DEFVAL { "" }
    ::= { tnTlsShgInfoEntry 5 }

tnTlsShgLastMgmtChange OBJECT-TYPE
    SYNTAX          TimeStamp
    MAX-ACCESS      read-only
    STATUS          current
    DESCRIPTION     "The value of the object tnTlsShgLastMgmtChange indicates the
                     value of sysUpTime at the time of the most recent
                     management-initiated change to this split-horizon group."
    ::= { tnTlsShgInfoEntry 6 }

tnTlsShgResidential OBJECT-TYPE
    SYNTAX          TruthValue
    MAX-ACCESS      read-create
    STATUS          current
    DESCRIPTION     "The value of the object tnTlsShgResidential  specifies
                     whether  or not the split-horizon-group is residential.In
                     a Residential Split Horizon Group (RSHG) there is no
                     downstream broadcast, and all saps in the group will share
                     the default ingress queue. The value can be specified
                     during  row-creation, cannot be changed later on."
    DEFVAL { false }
    ::= { tnTlsShgInfoEntry 7 }

tnTlsShgRestProtSrcMac OBJECT-TYPE
    SYNTAX          TruthValue
    MAX-ACCESS      read-create
    STATUS          current
    DESCRIPTION     "The value of the object tnTlsShgRestProtSrcMac indicates
                     how the agent will handle relearn requests for protected
                     MAC addresses received on SAP's belonging to this SHG.
                     When the value of this object is 'true' requests to
                     relearn a protected MAC address will be ignored.
                     In addition, if the value of tnTlsShgRestProtSrcMacAction
                     is 'disable', then the SAP where the protected source
                     MAC was seen will be brought operationally down."
    DEFVAL          { false }
    ::= { tnTlsShgInfoEntry 8 }

tnTlsShgRestUnprotDstMac OBJECT-TYPE
    SYNTAX          TruthValue
    MAX-ACCESS      read-create
    STATUS          current
    DESCRIPTION     "The value of the object tnTlsShgRestUnprotDstMac indicates
                     how the system will forward packets destined to an
                     unprotected MAC address. When the value of this object is
                     'true' packets destined to an unprotected MAC address
                     will be dropped."
    DEFVAL          { false }
    ::= { tnTlsShgInfoEntry 9 }

tnTlsShgRestProtSrcMacAction OBJECT-TYPE
    SYNTAX          INTEGER {
                        disable    (1),
                        alarm-only (2)
                    }
    MAX-ACCESS      read-create
    STATUS          current
    DESCRIPTION     "The value of the object tnTlsShgRestProtSrcMacAction
                     indicates the action to take whenever a relearn request
                     for a protected MAC is received on a restricted SAP
                     belonging to this SHG.
                     When the value of this object is 'disable' the SAP
                     will be placed in the operational down state, with the
                     operating flag 'recProtSrcMac' set. When the value of
                     this object is 'alarm-only', the SAP will be left up
                     and only a notification, sapReceivedProtSrcMac,  will be
                     generated."
    DEFVAL          { disable }
    ::= { tnTlsShgInfoEntry 10 }

tnTlsShgCreationOrigin  OBJECT-TYPE
    SYNTAX          L2RouteOrigin
    MAX-ACCESS      read-only
    STATUS          current
    DESCRIPTION     "The value of tnTlsShgCreationOrigin indicates the protocol or
                     mechanism which created this SHG."
    ::= { tnTlsShgInfoEntry 11 }

-- ------------------------------------
-- APIPE Service Table
-- ------------------------------------
-- tnSvcApipeInfoTable OBJECT-TYPE
--     SYNTAX          SEQUENCE OF TnSvcApipeInfoEntry
--     MAX-ACCESS      not-accessible
--     STATUS          current
--     DESCRIPTION     "A table that contains APIPE service information."
--     ::= { tnSvcObjs 7 }
--
-- tnSvcApipeInfoEntry OBJECT-TYPE
--     SYNTAX          TnSvcApipeInfoEntry
--     MAX-ACCESS      not-accessible
--     STATUS          current
--     DESCRIPTION     "APIPE specific information about a service."
--     INDEX           { tnSysSwitchId,  tnSvcId }
--     ::= { tnSvcApipeInfoTable 1 }
--
-- TnSvcApipeInfoEntry ::=
--     SEQUENCE {
--         tnSvcApipeInterworking                   INTEGER
--     }
--
-- tnSvcApipeInterworking OBJECT-TYPE
--     SYNTAX          INTEGER {
--                         none              (1),
--                         frf-5             (2),
--                         frf-8-2-translate (3)
--                     }
--     MAX-ACCESS      read-write
--     STATUS          current
--     DESCRIPTION     "The value of the object tnSvcApipeInterworking specifies the
--                      interworking function that should be applied for packets
--                      that ingress/egress SAPs that are part of a APIPE
--                      service."
--     DEFVAL          { none }
--     ::= { tnSvcApipeInfoEntry 1 }

-- ------------------------------------
-- TLS MFIB Information Table
-- ------------------------------------
-- tnTlsMFibInfoTable OBJECT-TYPE
--     SYNTAX          SEQUENCE OF TlsMFibInfoEntry
--     MAX-ACCESS      not-accessible
--     STATUS          obsolete
--     DESCRIPTION     "tnTlsMFibInfoTable contains the IPv4 Multicast FIB for
--                      this Tls.
--
--                      This table was made obsolete in the 6.0 release.
--                      It is replaced by tnTlsMFibTable."
--     ::= { tnSvcObjs 8 }
--
-- tnTlsMFibInfoEntry OBJECT-TYPE
--     SYNTAX          TlsMFibInfoEntry
--     MAX-ACCESS      not-accessible
--     STATUS          obsolete
--     DESCRIPTION     "An  entry in the tnTlsMFibInfoTable. Each entry indicates
--                      whether  traffic from a certain source to a certain
--                      multicast destination (group) needs to be forwarded or
--                      blocked on the indicated SAP/SDP."
--     INDEX           { tnSysSwitchId,  tnSvcId,
--                       tnTlsMFibInfoGrpAddr,
--                       tnTlsMFibInfoSrcAddr,
--                       tnTlsMFibInfoLocale,
--                       tnTlsMFibInfoPortId,
--                       tnTlsMFibInfoEncapValue,
--                       tnTlsMFibInfoSdpId,
--                       tnTlsMFibInfoVcId }
--
--     ::= { tnTlsMFibInfoTable 1 }
--
-- TlsMFibInfoEntry ::=
--     SEQUENCE {
--         tnTlsMFibInfoGrpAddr      IpAddress,
--         tnTlsMFibInfoSrcAddr      IpAddress,
--         tnTlsMFibInfoLocale       MfibLocation,
--         tnTlsMFibInfoPortId       TmnxPortID,
--         tnTlsMFibInfoEncapValue   TmnxEncapVal,
--         tnTlsMFibInfoSdpId        SdpId,
--         tnTlsMFibInfoVcId         Unsigned32,
--         tnTlsMFibInfoFwdOrBlk     MfibGrpSrcFwdOrBlk,
--         tnTlsMFibInfoSvcId        TmnxServId
--     }
--
-- tnTlsMFibInfoGrpAddr OBJECT-TYPE
--     SYNTAX          IpAddress
--     MAX-ACCESS      not-accessible
--     STATUS          obsolete
--     DESCRIPTION     "The value of the object tnTlsMFibInfoGrpAddr indicates the
--                      IPv4 multicast destination address for which this table
--                      entry contains information."
--     ::= { tnTlsMFibInfoEntry 1 }
--
-- tnTlsMFibInfoSrcAddr OBJECT-TYPE
--     SYNTAX          IpAddress
--     MAX-ACCESS      not-accessible
--     STATUS          obsolete
--     DESCRIPTION     "tnTlsMFibInfoSrcAddr indicates the IPv4 unicast source
--                      address for which this table entry contains information."
--     ::= { tnTlsMFibInfoEntry 2 }
--
-- tnTlsMFibInfoLocale OBJECT-TYPE
--     SYNTAX          MfibLocation
--     MAX-ACCESS      not-accessible
--     STATUS          obsolete
--     DESCRIPTION     "tnTlsMFibInfoLocale indicates if the information in
--                      this entry pertains to a 'sap' or to an 'sdp'."
--     ::= { tnTlsMFibInfoEntry 3 }
--
-- tnTlsMFibInfoPortId OBJECT-TYPE
--     SYNTAX          TmnxPortID
--     MAX-ACCESS      not-accessible
--     STATUS          obsolete
--     DESCRIPTION     "When the value of tnTlsMFibInfoLocale is 'sap', the object
--                      tnTlsMFibInfoPortId along with the object
--                      tnTlsMFibInfoEncapValue, indicates the SAP for which this
--                      entry contains information. This object is otherwise
--                      insignificant and contains the value 0."
--     ::= { tnTlsMFibInfoEntry 4 }
--
-- tnTlsMFibInfoEncapValue OBJECT-TYPE
--     SYNTAX          TmnxEncapVal
--     MAX-ACCESS      not-accessible
--     STATUS          obsolete
--     DESCRIPTION     "When the value of tnTlsMFibInfoLocale is 'sap', the object
--                      tnTlsMFibInfoEncapValue, along with the object
--                      tnTlsMFibInfoPortId, indicates the SAP for which this entry
--                      contains information. This object is otherwise
--                      insignificant and contains the value 0."
--     ::= { tnTlsMFibInfoEntry 5 }
--
-- tnTlsMFibInfoSdpId OBJECT-TYPE
--     SYNTAX          SdpId
--     MAX-ACCESS      not-accessible
--     STATUS          obsolete
--     DESCRIPTION     "When the value of tnTlsMFibInfoLocale is 'sdp', the object
--                      tnTlsMFibInfoSdpId, along with tnTlsMFibInfoVcId, indicates
--                      the SDP Binding for which this entry contains information.
--                      This object is otherwise insignificant and contains the
--                      value 0."
--     ::= { tnTlsMFibInfoEntry 6 }
--
-- tnTlsMFibInfoVcId OBJECT-TYPE
--     SYNTAX          Unsigned32
--     MAX-ACCESS      not-accessible
--     STATUS          obsolete
--     DESCRIPTION     "When the value of tnTlsMFibInfoLocale is 'sdp', the object
--                      tnTlsMFibInfoVcId, along with tnTlsMFibInfoSdpId, indicates
--                      the SDP Binding for which this entry contains information.
--                      This object is otherwise insignificant and contains the
--                      value 0."
--     ::= { tnTlsMFibInfoEntry 7 }
--
-- tnTlsMFibInfoFwdOrBlk OBJECT-TYPE
--     SYNTAX          MfibGrpSrcFwdOrBlk
--     MAX-ACCESS      read-only
--     STATUS          obsolete
--     DESCRIPTION     "tnTlsMFibInfoFwdOrBlk indicates if traffic for the
--                      indicated (S,G) pair will be blocked or forwarded on the
--                      indicated SAP or SDP."
--     ::= { tnTlsMFibInfoEntry 8 }
--
-- tnTlsMFibInfoSvcId OBJECT-TYPE
--     SYNTAX          TmnxServId
--     MAX-ACCESS      read-only
--     STATUS          obsolete
--     DESCRIPTION     "tnTlsMFibInfoSvcId indicates the TLS service to which
--                      the indicated SAP or SDP belongs."
--     ::= { tnTlsMFibInfoEntry 9 }

-- ----------------------------------------
-- TLS MFIB Group Source Statistics Table
-- ----------------------------------------
-- tnTlsMFibGrpSrcStatsTable OBJECT-TYPE
--     SYNTAX          SEQUENCE OF TlsMFibGrpSrcStatsEntry
--     MAX-ACCESS      not-accessible
--     STATUS          obsolete
--     DESCRIPTION     "tnTlsMFibGrpSrcStatsTable contains statistics for the
--                      entries in the IPv4 Multicast FIB for this Tls. These
--                      statistics are collected by the forwarding engine.
--
--                      This table was made obsolete in the 6.0 release.
--                      It is replaced by tnTlsMFibStatsTable."
--     ::= { tnSvcObjs 9 }
--
-- tnTlsMFibGrpSrcStatsEntry OBJECT-TYPE
--     SYNTAX          TlsMFibGrpSrcStatsEntry
--     MAX-ACCESS      not-accessible
--     STATUS          obsolete
--     DESCRIPTION     "An entry in the tnTlsMFibGrpSrcStatsTable."
--     INDEX           { tnSysSwitchId,  tnSvcId,
--                       tnTlsMFibGrpSrcStatsGrpAddr,
--                       tnTlsMFibGrpSrcStatsSrcAddr }
--     ::= { tnTlsMFibGrpSrcStatsTable 1 }
--
-- TlsMFibGrpSrcStatsEntry ::=
--     SEQUENCE {
--         tnTlsMFibGrpSrcStatsGrpAddr          IpAddress,
--         tnTlsMFibGrpSrcStatsSrcAddr          IpAddress,
--         tnTlsMFibGrpSrcStatsForwardedPkts    Counter64,
--         tnTlsMFibGrpSrcStatsForwardedOctets  Counter64
--     }
--
-- tnTlsMFibGrpSrcStatsGrpAddr OBJECT-TYPE
--     SYNTAX          IpAddress
--     MAX-ACCESS      not-accessible
--     STATUS          obsolete
--     DESCRIPTION     "tnTlsMFibGrpSrcStatsGrpAddr indicates the IPv4 multicast
--                      destination address for which this table entry contains
--                      information."
--     ::= { tnTlsMFibGrpSrcStatsEntry 1 }
--
-- tnTlsMFibGrpSrcStatsSrcAddr OBJECT-TYPE
--     SYNTAX          IpAddress
--     MAX-ACCESS      not-accessible
--     STATUS          obsolete
--     DESCRIPTION     "tnTlsMFibGrpSrcStatsSrcAddr indicates the IPv4 unicast
--                      source address for which this table entry contains
--                      information."
--     ::= { tnTlsMFibGrpSrcStatsEntry 2 }
--
-- tnTlsMFibGrpSrcStatsForwardedPkts OBJECT-TYPE
--     SYNTAX          Counter64
--     MAX-ACCESS      read-only
--     STATUS          obsolete
--     DESCRIPTION     "tnTlsMFibGrpSrcStatsForwardedPkts indicates the number of
--                      IPv4 multicast packets that were forwarded to the SAPs
--                      and SDPs listed in the tnTlsMFibInfoTable."
--     ::= { tnTlsMFibGrpSrcStatsEntry 3 }
--
-- tnTlsMFibGrpSrcStatsForwardedOctets OBJECT-TYPE
--     SYNTAX          Counter64
--     MAX-ACCESS      read-only
--     STATUS          obsolete
--     DESCRIPTION     "tnTlsMFibGrpSrcStatsForwardedOctets indicates the number
--                      of octets that were forwarded to the SAPs and SDPs
--                      listed in the tnTlsMFibInfoTable."
--     ::= { tnTlsMFibGrpSrcStatsEntry 4 }

-- --------------------------------
-- Redundant Group Table
-- --------------------------------
-- tnTlsRdntGrpTable OBJECT-TYPE
--     SYNTAX          SEQUENCE OF TlsRdntGrpEntry
--     MAX-ACCESS      not-accessible
--     STATUS          current
--     DESCRIPTION     "A table that contains TLS service Redundant Group
--                      information.  There is no limit on the number of
--                      Redundant Groups that can be created globally or
--                      within a service."
--     ::= {tnSvcObjs 10}
--
-- tnTlsRdntGrpEntry OBJECT-TYPE
--     SYNTAX          TlsRdntGrpEntry
--     MAX-ACCESS      not-accessible
--     STATUS          current
--     DESCRIPTION     "Redundant Group information"
--     INDEX           { tnSysSwitchId,  tnSvcId, IMPLIED tnTlsRdntGrpName }
--     ::= { tnTlsRdntGrpTable 1 }
--
-- TlsRdntGrpEntry ::=
--     SEQUENCE {
--         tnTlsRdntGrpName           TNamedItem,
--         tnTlsRdntGrpRowStatus      RowStatus,
--         tnTlsRdntGrpDescription    ServObjDesc,
--         tnTlsRdntGrpLastMgmtChange TimeStamp
--     }
--
-- tnTlsRdntGrpName OBJECT-TYPE
--     SYNTAX          TNamedItem
--     MAX-ACCESS      not-accessible
--     STATUS          current
--     DESCRIPTION     "The value of the object tnTlsRdntGrpName specifies the
--                      name of the redundant group.
--                      The name must be unique within a TLS, however the same
--                      name can appear in different TLS services, in which
--                      case they denote different redundant groups."
--     ::= { tnTlsRdntGrpEntry 1 }
--
-- tnTlsRdntGrpRowStatus OBJECT-TYPE
--     SYNTAX          RowStatus
--     MAX-ACCESS      read-create
--     STATUS          current
--     DESCRIPTION     "The value of the object tnTlsRdntGrpRowStatus specifies
--                      the status of this row. The only values supported are
--                      'active', 'createAndGo' and 'destroy'."
--     ::= { tnTlsRdntGrpEntry 2 }
--
-- tnTlsRdntGrpDescription OBJECT-TYPE
--     SYNTAX          ServObjDesc
--     MAX-ACCESS      read-create
--     STATUS          current
--     DESCRIPTION     "The value of the object tnTlsRdntGrpDescription specifies
--                      generic information about this redundant group."
--     DEFVAL          { ''H }
--     ::= { tnTlsRdntGrpEntry 3 }
--
-- tnTlsRdntGrpLastMgmtChange OBJECT-TYPE
--     SYNTAX          TimeStamp
--     MAX-ACCESS      read-only
--     STATUS          current
--     DESCRIPTION     "The value of the object tnTlsRdntGrpLastMgmtChange
--                      indicates the sysUpTime at the time of the most
--                      recent management-initiated change to this redundant
--                      group."
--     ::= { tnTlsRdntGrpEntry 4 }

-- ---------------------------------
-- Redundant Group Member Table
-- ---------------------------------
-- tnTlsRdntGrpMemberTable OBJECT-TYPE
--     SYNTAX          SEQUENCE OF TlsRdntGrpMemberEntry
--     MAX-ACCESS      not-accessible
--     STATUS          current
--     DESCRIPTION     "A table that holds information about the members of
--                      TLS redundant groups."
--     ::= { tnSvcObjs 11 }
--
-- tnTlsRdntGrpMemberEntry OBJECT-TYPE
--     SYNTAX          TlsRdntGrpMemberEntry
--     MAX-ACCESS      not-accessible
--     STATUS          current
--     DESCRIPTION     "Redundant Group Member information."
--     INDEX           { tnSysSwitchId,  tnTlsRdntGrpName,
--                       tnTlsRdntGrpMemberRemoteNodeAddrTp,
--                       tnTlsRdntGrpMemberRemoteNodeAddr,
--                       tnTlsRdntGrpMemberIsSap,
--                       tnTlsRdntGrpMemberPort,
--                       tnTlsRdntGrpMemberEncap
--                     }
--     ::= { tnTlsRdntGrpMemberTable 1 }
--
-- TlsRdntGrpMemberEntry ::=
--     SEQUENCE {
--         tnTlsRdntGrpMemberRemoteNodeAddrTp InetAddressType,
--         tnTlsRdntGrpMemberRemoteNodeAddr   InetAddress,
--         tnTlsRdntGrpMemberIsSap            TruthValue,
--         tnTlsRdntGrpMemberPort             TmnxPortID,
--         tnTlsRdntGrpMemberEncap            TmnxEncapVal,
--         tnTlsRdntGrpMemberRowStatus        RowStatus,
--         tnTlsRdntGrpMemberLastMgmtChange   TimeStamp
--     }
--
-- tnTlsRdntGrpMemberRemoteNodeAddrTp OBJECT-TYPE
--     SYNTAX          InetAddressType
--     MAX-ACCESS      not-accessible
--     STATUS          current
--     DESCRIPTION     "The value of the object tnTlsRdntGrpMemberRemoteNodeAddrTp
--                      specifies the addresstype of the remote ldp peer."
--     ::= { tnTlsRdntGrpMemberEntry 1}
--
-- tnTlsRdntGrpMemberRemoteNodeAddr OBJECT-TYPE
--     SYNTAX          InetAddress
--     MAX-ACCESS      not-accessible
--     STATUS          current
--     DESCRIPTION     "The value of the object tnTlsRdntGrpMemberRemoteNodeAddr
--                      specifies the ip address of the remote ldp peer."
--     ::= { tnTlsRdntGrpMemberEntry 2}
--
-- tnTlsRdntGrpMemberIsSap OBJECT-TYPE
--     SYNTAX          TruthValue
--     MAX-ACCESS      not-accessible
--     STATUS          current
--     DESCRIPTION     "The value of the object tnTlsRdntGrpMemberIsSap
--                      specifies whether the Port ID and Encap describe a sap
--                      or a port (in which case Encap has no meaning)."
--     ::= { tnTlsRdntGrpMemberEntry 3}
--
-- tnTlsRdntGrpMemberPort OBJECT-TYPE
--     SYNTAX          TmnxPortID
--     MAX-ACCESS      not-accessible
--     STATUS          current
--     DESCRIPTION     "When the value of tnTlsRdntGrpMemberIsSap is 'sap',
--                      the value of the object  tnTlsRdntGrpMemberPort, along
--                      with tnTlsRdntGrpMemberEncap, specifies
--                      a SAP, otherwise a port (in which case
--                      tnTlsRdntGrpMemberEncap is insignificant)."
--     ::= { tnTlsRdntGrpMemberEntry 4}
--
-- tnTlsRdntGrpMemberEncap OBJECT-TYPE
--     SYNTAX          TmnxEncapVal
--     MAX-ACCESS      not-accessible
--     STATUS          current
--     DESCRIPTION     "When the value of tnTlsRdntGrpMemberIsSap is 'sap',
--                      the value of the object  tnTlsRdntGrpMemberEncap, along
--                      with tnTlsRdntGrpMemberPort, specifies a SAP. This object
--                      is otherwise insignificant and  should contain a
--                      value of 0."
--     ::= { tnTlsRdntGrpMemberEntry 5}
--
-- tnTlsRdntGrpMemberRowStatus OBJECT-TYPE
--     SYNTAX          RowStatus
--     MAX-ACCESS      read-create
--     STATUS          current
--     DESCRIPTION     "The value of the object tnTlsRdntGrpMemberRowStatus
--                      specifies the status of this row. The
--                      only values supported are 'active', 'createAndGo'
--                      and 'destroy'."
--     ::= { tnTlsRdntGrpMemberEntry 6 }
--
-- tnTlsRdntGrpMemberLastMgmtChange OBJECT-TYPE
--     SYNTAX          TimeStamp
--     MAX-ACCESS      read-only
--     STATUS          current
--     DESCRIPTION     "The value of the object tnTlsRdntGrpMemberLastMgmtChange
--                      indicates the time of the most recent management-initiated
--                      change to this redundant group member."
--     ::= { tnTlsRdntGrpMemberEntry 7}

-- -----------------------------------------
-- TLS MSTI Table
-- -----------------------------------------
-- tnTlsMstiTable OBJECT-TYPE
--     SYNTAX          SEQUENCE OF TnTlsMstiEntry
--     MAX-ACCESS      not-accessible
--     STATUS          current
--     DESCRIPTION     "A table that contains Multiple Spanning Tree Instance
--                      (MSTI) information. Each management VPLS running MSTP can
--                      have upto 15 MSTI, not including the CIST."
--     ::= { tnSvcObjs 12 }
--
-- tnTlsMstiEntry OBJECT-TYPE
--     SYNTAX          TnTlsMstiEntry
--     MAX-ACCESS      not-accessible
--     STATUS          current
--     DESCRIPTION     "Information about a specific MSTI."
--     INDEX           { tnSysSwitchId,  tnSvcId, tnTlsMstiInstanceId}
--     ::= { tnTlsMstiTable 1 }
--
-- TnTlsMstiEntry ::=
--     SEQUENCE {
--         tnTlsMstiInstanceId        MstiInstanceId,
--         tnTlsMstiRowStatus         RowStatus,
--         tnTlsMstiPriority          Integer32,
--         tnTlsMstiLastMgmtChange    TimeStamp,
--         tnTlsMstiRegionalRoot      BridgeId,
--         tnTlsMstiIntRootCost       Integer32,
--         tnTlsMstiRemainingHopCount Integer32,
--         tnTlsMstiRegionalRootPort  Integer32
--     }
--
-- tnTlsMstiInstanceId OBJECT-TYPE
--     SYNTAX          MstiInstanceId
--     MAX-ACCESS      not-accessible
--     STATUS          current
--     DESCRIPTION     "The value of the object tnTlsMstiInstanceId specifies the
--                      Multiple Spanning Tree Instance."
--     ::= { tnTlsMstiEntry 1 }
--
--
-- tnTlsMstiRowStatus OBJECT-TYPE
--     SYNTAX          RowStatus
--     MAX-ACCESS      read-create
--     STATUS          current
--     DESCRIPTION     "The value of the object tnTlsMstiRowStatus specifies the
--                      status of this row.
--                      The only values supported during a set operation are
--                      'active', 'createAndGo' and 'destroy'."
--     ::= { tnTlsMstiEntry 2 }
--
-- tnTlsMstiPriority OBJECT-TYPE
--     SYNTAX          Integer32 (0..65535)
--     MAX-ACCESS      read-create
--     STATUS          current
--     DESCRIPTION     "The value of the object tnTlsMstiPriority specifies the
--                      priority of this spcecific Multiple Spanning Tree
--                      Instance for this service.
--                      It is used as the highest 4 bits of the Bridge ID
--                      included in the MSTP BPDU's generated by
--                      this bridge.
--                      The tnTlsMstiPriority can only take-on values which
--                      multiples of 4096 (4k). If a value is specified which
--                      is not a multiple of 4K, then this value will be
--                      replaced by the closest multiple of 4K which is lower
--                      then the value entered."
--     DEFVAL          { 32768 }
--     ::= { tnTlsMstiEntry 3 }
--
-- tnTlsMstiLastMgmtChange OBJECT-TYPE
--     SYNTAX          TimeStamp
--     MAX-ACCESS      read-only
--     STATUS          current
--     DESCRIPTION     "The value of the object tnTlsMstiLastMgmtChange indicates
--                      the value of sysUpTime at the time of the most recent
--                      management-initiated change to this MSTI."
--     ::= { tnTlsMstiEntry 4 }
--
-- tnTlsMstiRegionalRoot OBJECT-TYPE
--     SYNTAX          BridgeId
--     MAX-ACCESS      read-only
--     STATUS          current
--     DESCRIPTION     "The value of the object tnTlsMstiRegionalRoot
--                      indicates the bridge identifier of the regional root of
--                      the MSTI spanning tree as determined by the Spanning Tree
--                      Protocol instance associated with this service. This value
--                      is used as the CIST Regional Root Identifier parameter in
--                      all MSTP BPDUs originated by this node."
--     ::= { tnTlsMstiEntry 5 }
--
-- tnTlsMstiIntRootCost OBJECT-TYPE
--     SYNTAX          Integer32
--     MAX-ACCESS      read-only
--     STATUS          current
--     DESCRIPTION     "The value of the object tnTlsMstiIntRootCost indicates the
--                      cost of the path to the regional root bridge as seen from
--                      this bridge."
--     ::= { tnTlsMstiEntry 6 }
--
-- tnTlsMstiRemainingHopCount OBJECT-TYPE
--     SYNTAX          Integer32
--     MAX-ACCESS      read-only
--     STATUS          current
--     DESCRIPTION     "The value of the object tnTlsMstiRemainingHopCount
--                      specifies the remaining number of hops."
--     ::= { tnTlsMstiEntry 7 }
--
-- tnTlsMstiRegionalRootPort OBJECT-TYPE
--     SYNTAX          Integer32
--     MAX-ACCESS      read-only
--     STATUS          current
--     DESCRIPTION     "The value of the object tnTlsMstiRegionalRootPort indicates
--                      the port number of the port which offers the lowest cost
--                      path from this bridge to the regional root bridge."
--     ::= { tnTlsMstiEntry 8 }

-- -----------------------------------------
-- TLS MSTI Managed VLAN List Table
-- -----------------------------------------
-- tnTlsMstiManagedVlanListTable OBJECT-TYPE
--     SYNTAX          SEQUENCE OF TnTlsMstiManagedVlanListEntry
--     MAX-ACCESS      not-accessible
--     STATUS          current
--     DESCRIPTION     "This table is used only for a management VPLS when MSTP
--                      is running. It indicates for each multiple spanning tree
--                      instance the ranges of associated VLANs that will be
--                      affected when a certain SAP changes state."
--     ::= { tnSvcObjs 13 }
--
-- tnTlsMstiManagedVlanListEntry OBJECT-TYPE
--     SYNTAX          TnTlsMstiManagedVlanListEntry
--     MAX-ACCESS      not-accessible
--     STATUS          current
--     DESCRIPTION     "Each row specifies a range of VLANS associated
--                      with a SAP of a MVPLS. Ranges may contains overlapping
--                      sections only for Mvpls SAPs that belong to the same
--                      service."
--     INDEX           { tnSysSwitchId,  tnSvcId,
--                       tnTlsMstiInstanceId,
--                       tnTlsMstiMvplsMinVlanTag,
--                       tnTlsMstiMvplsMaxVlanTag }
--     ::= { tnTlsMstiManagedVlanListTable 1 }
--
-- TnTlsMstiManagedVlanListEntry ::=
--     SEQUENCE {
--         tnTlsMstiMvplsMinVlanTag  QTag, == integer(1 .. 4094)
--         tnTlsMstiMvplsMaxVlanTag  QTag,
--         tnTlsMstiMvplsRowStatus   RowStatus
--     }
--
-- tnTlsMstiMvplsMinVlanTag OBJECT-TYPE
--     SYNTAX          QTag
--     MAX-ACCESS      not-accessible
--     STATUS          current
--     DESCRIPTION     "The value of tnTlsMstiMvplsMinVlanTag specifies
--                      the left bound (i.e. min. value) of a range of VLANs
--                      that are associated with the Mvpls SAP.
--                      tnTlsMstiMvplsMinVlanTag must be smaller than (or equal
--                      to) tnTlsMstiMvplsMaxVlanTag."
--     ::= { tnTlsMstiManagedVlanListEntry 1 }
--
-- tnTlsMstiMvplsMaxVlanTag OBJECT-TYPE
--     SYNTAX          QTag
--     MAX-ACCESS      not-accessible
--     STATUS          current
--     DESCRIPTION     "The value of tnTlsMstiMvplsMaxVlanTag specifies the
--                      right bound (i.e. max. value) of a range of VLANs that
--                      are associated with the Mvpls SAP."
--     ::= { tnTlsMstiManagedVlanListEntry 2 }
--
-- tnTlsMstiMvplsRowStatus OBJECT-TYPE
--     SYNTAX           RowStatus
--     MAX-ACCESS       read-create
--     STATUS           current
--     DESCRIPTION      "The value of tnTlsMstiMvplsRowStatus specifies
--                       the status of this row. The only values supported
--                       during a set operation are 'active', 'createAndGo' and
--                       'destroy'."
--     ::= { tnTlsMstiManagedVlanListEntry 3 }

-- -----------------------------------------
-- TLS Egress Multicast Group Table
-- -----------------------------------------
-- tnTlsEgressMulticastGroupTable OBJECT-TYPE
--     SYNTAX          SEQUENCE OF TnTlsEgressMulticastGroupEntry
--     MAX-ACCESS      not-accessible
--     STATUS          current
--     DESCRIPTION     "This table is used to manage VPLS Egress Multicast
--                      Groups. These groups are used to group together VPLS
--                      SAP's in order to improve the efficiency of the egress
--                      multicast replication process."
--     ::= { tnSvcObjs 14 }
--
-- tnTlsEgressMulticastGroupEntry OBJECT-TYPE
--     SYNTAX          TnTlsEgressMulticastGroupEntry
--     MAX-ACCESS      not-accessible
--     STATUS          current
--     DESCRIPTION     "An entry containing management information applicable
--                      to a particular VPLS Egress Multicast Group."
--     INDEX           { tnSysSwitchId,  IMPLIED tnTlsEgrMcGrpName }
--     ::= { tnTlsEgressMulticastGroupTable 1 }
--
-- TnTlsEgressMulticastGroupEntry ::=
--     SEQUENCE {
--         tnTlsEgrMcGrpName                 TNamedItem,
--         tnTlsEgrMcGrpRowStatus            RowStatus,
--         tnTlsEgrMcGrpLastMgmtChange       TimeStamp,
--         tnTlsEgrMcGrpDescription          ServObjDesc,
--         tnTlsEgrMcGrpChainLimit           Unsigned32,
--         tnTlsEgrMcGrpEncapType            INTEGER,
--         tnTlsEgrMcGrpDot1qEtherType       Unsigned32,
--         tnTlsEgrMcGrpMacFilterId          TFilterID,
--         tnTlsEgrMcGrpIpFilterId           TFilterID,
--         tnTlsEgrMcGrpIpv6FilterId         TFilterID,
--         tnTlsEgrMcGrpQinqEtherType        Unsigned32,
--         tnTlsEgrMcGrpQinqFixedTagPosition INTEGER,
--         tnTlsEgrMcGrpAdminQinqFixedTagVal Unsigned32,
--         tnTlsEgrMcGrpOperQinqFixedTagVal  Unsigned32
--     }
--
-- tnTlsEgrMcGrpName OBJECT-TYPE
--     SYNTAX          TNamedItem
--     MAX-ACCESS      not-accessible
--     STATUS          current
--     DESCRIPTION     "The value of tnTlsEgrMcGrpName indicates the name of
--                      the Egress Multicast Group."
--     ::= { tnTlsEgressMulticastGroupEntry 1 }
--
-- tnTlsEgrMcGrpRowStatus OBJECT-TYPE
--     SYNTAX          RowStatus
--     MAX-ACCESS      read-create
--     STATUS          current
--     DESCRIPTION     "The value of tnTlsEgrMcGrpRowStatus controls the creation
--                      and deletion of rows in this table."
--     ::= { tnTlsEgressMulticastGroupEntry 2 }
--
-- tnTlsEgrMcGrpLastMgmtChange OBJECT-TYPE
--     SYNTAX          TimeStamp
--     MAX-ACCESS      read-only
--     STATUS          current
--     DESCRIPTION     "The value of tnTlsEgrMcGrpLastMgmtChange indicates the
--                      value of sysUpTime at the time of the last management
--                      change of any writable object of this row."
--     ::= { tnTlsEgressMulticastGroupEntry 3 }
--
-- tnTlsEgrMcGrpDescription OBJECT-TYPE
--     SYNTAX          ServObjDesc
--     MAX-ACCESS      read-create
--     STATUS          current
--     DESCRIPTION     "Generic information about this Egress Multicast Group."
--     DEFVAL          { "" }
--     ::= { tnTlsEgressMulticastGroupEntry 4 }
--
-- tnTlsEgrMcGrpChainLimit OBJECT-TYPE
--     SYNTAX          Unsigned32 (1..30)
--     MAX-ACCESS      read-create
--     STATUS          current
--     DESCRIPTION     "The value of tnTlsEgrMcGrpChainLimit specifies the maximum
--                      number of SAP's that can be placed together in a single
--                      chain on this Egress Multicast Group."
--     DEFVAL          { 16 }
--     ::= { tnTlsEgressMulticastGroupEntry 5 }
--
-- tnTlsEgrMcGrpEncapType OBJECT-TYPE
--     SYNTAX          INTEGER {
--                         unknown   (0),
--                         nullEncap (1),
--                         qEncap    (2),
--                         qinqEncap (10)
--                     }
--     MAX-ACCESS      read-create
--     STATUS          current
--     DESCRIPTION     "The value of tnTlsEgrMcGrpEncapType specifies the common
--                      service encapsulation type used by all the SAP's on this
--                      Egress Multicast Group."
--     DEFVAL          { nullEncap }
--     ::= { tnTlsEgressMulticastGroupEntry 6 }
--
-- tnTlsEgrMcGrpDot1qEtherType OBJECT-TYPE
--     SYNTAX          Unsigned32 ('600'H..'ffff'H)
--     MAX-ACCESS      read-create
--     STATUS          current
--     DESCRIPTION     "The value of tnTlsEgrMcGrpDot1qEtherType specifies the
--                      common ethertype value used by all the 802.1Q SAP's on
--                      this Egress Multicast Group."
--     DEFVAL          { '8100'H }
--     ::= { tnTlsEgressMulticastGroupEntry 7 }
--
-- tnTlsEgrMcGrpMacFilterId OBJECT-TYPE
--     SYNTAX          TFilterID
--     MAX-ACCESS      read-create
--     STATUS          current
--     DESCRIPTION     "The value of tnTlsEgrMcGrpMacFilterId specifies the common
--                      egress MAC filter ID used by all the SAP's on this
--                      Egress Multicast Group."
--     DEFVAL          { 0 }
--     ::= { tnTlsEgressMulticastGroupEntry 8 }
--
-- tnTlsEgrMcGrpIpFilterId OBJECT-TYPE
--     SYNTAX          TFilterID
--     MAX-ACCESS      read-create
--     STATUS          current
--     DESCRIPTION     "The value of tnTlsEgrMcGrpIpFilterId specifies the common
--                      egress IP filter ID used by all the SAP's on this
--                      Egress Multicast Group."
--     DEFVAL          { 0 }
--     ::= { tnTlsEgressMulticastGroupEntry 9 }
--
-- tnTlsEgrMcGrpIpv6FilterId OBJECT-TYPE
--     SYNTAX          TFilterID
--     MAX-ACCESS      read-create
--     STATUS          current
--     DESCRIPTION     "The value of tnTlsEgrMcGrpIpv6FilterId specifies the common
--                      egress IPv6 filter ID used by all the SAP's on this
--                      Egress Multicast Group."
--     DEFVAL          { 0 }
--     ::= { tnTlsEgressMulticastGroupEntry 10 }
--
-- tnTlsEgrMcGrpQinqEtherType OBJECT-TYPE
--     SYNTAX          Unsigned32 ('600'H..'ffff'H)
--     MAX-ACCESS      read-create
--     STATUS          current
--     DESCRIPTION     "The value of tnTlsEgrMcGrpQinqEtherType specifies the
--                      common ethertype value used by all the 'QinQ' SAP's in
--                      this Egress Multicast Group."
--     DEFVAL          { '8100'H }
--     ::= { tnTlsEgressMulticastGroupEntry 11 }
--
-- tnTlsEgrMcGrpQinqFixedTagPosition OBJECT-TYPE
--     SYNTAX          INTEGER {
--                         topTag    (2),   == top (outter) tag is fixed
--                         bottomTag (3)    == bottom (inner) tag is fixed
--                     }
--     MAX-ACCESS      read-create
--     STATUS          current
--     DESCRIPTION     "The value of tnTlsEgrMcGrpQinqFixedTagPosition specifies
--                      the common position of the fixed 802.1Q tag of all the
--                      'QinQ' SAP's in this Egress Multicast Group. This object
--                      has no meaning when the value of tnTlsEgrMcGrpEncapType
--                      is not 'qinqEncap'."
--     DEFVAL          { bottomTag }
--     ::= { tnTlsEgressMulticastGroupEntry 12 }
--
-- tnTlsEgrMcGrpAdminQinqFixedTagVal OBJECT-TYPE
--     SYNTAX          Unsigned32 (0|1..4094)
--     MAX-ACCESS      read-create
--     STATUS          current
--     DESCRIPTION     "The value of tnTlsEgrMcGrpAdminQinqFixedTagVal
--                      specifies the provisioned common value of the fixed
--                      802.1Q tag of all the 'QinQ' SAP's in this Egress
--                      Multicast Group.
--
--                      The value 0 is used to indicate that the actual value
--                      of the fixed tag will be defined implicitly by the
--                      corresponding tag of the first SAP added to this Egress
--                      Multicast Group."
--     DEFVAL          { 0 }
--     ::= { tnTlsEgressMulticastGroupEntry 13 }
--
-- tnTlsEgrMcGrpOperQinqFixedTagVal OBJECT-TYPE
--     SYNTAX          Unsigned32
--     MAX-ACCESS      read-only
--     STATUS          current
--     DESCRIPTION     "The value of tnTlsEgrMcGrpOperQinqFixedTagVal
--                      specifies the operating common value of the fixed
--                      802.1Q tag of all the 'QinQ' SAP's in this Egress
--                      Multicast Group."
--     ::= { tnTlsEgressMulticastGroupEntry 14 }

-- ----------------------------------------
-- DHCP Lease State Table
-- ----------------------------------------
-- tnSvcDhcpLeaseStateTable OBJECT-TYPE
--     SYNTAX          SEQUENCE OF TnSvcDhcpLeaseStateEntry
--     MAX-ACCESS      not-accessible
--     STATUS          current
--     DESCRIPTION     "A table that contains DHCP lease states."
--     ::= { tnSvcObjs 16 }
--
-- tnSvcDhcpLeaseStateEntry OBJECT-TYPE
--     SYNTAX          TnSvcDhcpLeaseStateEntry
--     MAX-ACCESS      not-accessible
--     STATUS          current
--     DESCRIPTION     "Information about a specific DHCP lease state."
--     INDEX           { tnSysSwitchId,  tnSvcId,
--                       tnSvcDhcpLseStateCiAddrType,
--                       tnSvcDhcpLseStateCiAddr }
--     ::= { tnSvcDhcpLeaseStateTable 1 }
--
-- TnSvcDhcpLeaseStateEntry ::=
--     SEQUENCE {
--         tnSvcDhcpLseStateCiAddrType           InetAddressType,
--         tnSvcDhcpLseStateCiAddr               InetAddress,
--         tnSvcDhcpLseStateLocale               INTEGER,
--         tnSvcDhcpLseStatePortId               TmnxPortID,
--         tnSvcDhcpLseStateEncapValue           TmnxEncapVal,
--         tnSvcDhcpLseStateSdpId                SdpId,
--         tnSvcDhcpLseStateVcId                 Unsigned32,
--         tnSvcDhcpLseStateChAddr               MacAddress,
--         tnSvcDhcpLseStateRemainLseTime        Unsigned32,
--         tnSvcDhcpLseStateOption82             OCTET STRING,
--         tnSvcDhcpLseStatePersistKey           Unsigned32,
--         tnSvcDhcpLseStateSubscrIdent          DisplayString,
--         tnSvcDhcpLseStateSubProfString        DisplayString,
--         tnSvcDhcpLseStateSlaProfString        DisplayString,
--         tnSvcDhcpLseStateShcvOperState        INTEGER,
--         tnSvcDhcpLseStateShcvChecks           Unsigned32,
--         tnSvcDhcpLseStateShcvReplies          Unsigned32,
--         tnSvcDhcpLseStateShcvReplyTime        TimeStamp,
--         tnSvcDhcpLseStateClientId             OCTET STRING,
--         tnSvcDhcpLseStateIAID                 Unsigned32,
--         tnSvcDhcpLseStateIAIDType             IAIDType,
--         tnSvcDhcpLseStateCiAddrMaskLen        Unsigned32,
--         tnSvcDhcpLseStateRetailerSvcId        TmnxServId,
--         tnSvcDhcpLseStateRetailerIf           InterfaceIndexOrZero,
--         tnSvcDhcpLseStateAncpString           DisplayString,
--         tnSvcDhcpLseStateFramedIpNetMaskTp    InetAddressType,
--         tnSvcDhcpLseStateFramedIpNetMask      InetAddress,
--         tnSvcDhcpLseStateBCastIpAddrType      InetAddressType,
--         tnSvcDhcpLseStateBCastIpAddr          InetAddress,
--         tnSvcDhcpLseStateDefaultRouterTp      InetAddressType,
--         tnSvcDhcpLseStateDefaultRouter        InetAddress,
--         tnSvcDhcpLseStatePrimaryDnsType       InetAddressType,
--         tnSvcDhcpLseStatePrimaryDns           InetAddress,
--         tnSvcDhcpLseStateSecondaryDnsType     InetAddressType,
--         tnSvcDhcpLseStateSecondaryDns         InetAddress,
--         tnSvcDhcpLseStateSessionTimeout       Unsigned32,
--         tnSvcDhcpLseStateServerLeaseStart     DateAndTime,
--         tnSvcDhcpLseStateServerLastRenew      DateAndTime,
--         tnSvcDhcpLseStateServerLeaseEnd       DateAndTime,
--         tnSvcDhcpLseStateDhcpServerAddrType   InetAddressType,
--         tnSvcDhcpLseStateDhcpServerAddr       InetAddress,
--         tnSvcDhcpLseStateOriginSubscrId       DhcpLseStateInfoOrigin,
--         tnSvcDhcpLseStateOriginStrings        DhcpLseStateInfoOrigin,
--         tnSvcDhcpLseStateOriginLeaseInfo      DhcpLseStateInfoOrigin,
--         tnSvcDhcpLseStateDhcpClientAddrType   InetAddressType,
--         tnSvcDhcpLseStateDhcpClientAddr       InetAddress,
--         tnSvcDhcpLseStateLeaseSplitActive     TruthValue,
--         tnSvcDhcpLseStateInterDestId          DisplayString,
--         tnSvcDhcpLseStatePrimaryNbnsType      InetAddressType,
--         tnSvcDhcpLseStatePrimaryNbns          InetAddress,
--         tnSvcDhcpLseStateSecondaryNbnsType    InetAddressType,
--         tnSvcDhcpLseStateSecondaryNbns        InetAddress,
--         tnSvcDhcpLseStateAppProfString        DisplayString,
--         tnSvcDhcpLseStateNextHopMacAddr       MacAddress,
--         tnSvcDhcpLseStateCategoryMapName      TNamedItemOrEmpty,
--         tnSvcDhcpLseStateNakNextRenew         TruthValue,
--         tnSvcDhcpLseStateRadiusClassAttr      OCTET STRING,
--         tnSvcDhcpLseStateRadiusUserName       DisplayString
--     }
--
-- tnSvcDhcpLseStateCiAddrType OBJECT-TYPE
--     SYNTAX          InetAddressType
--     MAX-ACCESS      not-accessible
--     STATUS          current
--     DESCRIPTION     "The value of tnSvcDhcpLseStateCiAddrType indicates the
--                      address type of tnSvcDhcpLseStateCiAddr."
--     ::= { tnSvcDhcpLeaseStateEntry 1 }
--
-- tnSvcDhcpLseStateCiAddr OBJECT-TYPE
--     SYNTAX          InetAddress
--     MAX-ACCESS      not-accessible
--     STATUS          current
--     DESCRIPTION     "The value of tnSvcDhcpLseStateCiAddr indicates the IP
--                      address of the DHCP lease state."
--     ::= { tnSvcDhcpLeaseStateEntry 2 }
--
-- tnSvcDhcpLseStateLocale OBJECT-TYPE
--     SYNTAX          INTEGER {
--                         sap (1),
--                         sdp (2)
--                     }
--     MAX-ACCESS      read-only
--     STATUS          current
--     DESCRIPTION     "The value of tnSvcDhcpLseStateLocale specifies if the DHCP
--                      lease state is learned via a SAP or SDP."
--     ::= { tnSvcDhcpLeaseStateEntry 3 }
--
-- tnSvcDhcpLseStatePortId OBJECT-TYPE
--     SYNTAX          TmnxPortID
--     MAX-ACCESS      read-only
--     STATUS          current
--     DESCRIPTION     "When the value of tnSvcDhcpLseStateLocale is 'sap', the
--                      object tnSvcDhcpLseStatePortId along with the object
--                      tnSvcDhcpLseStateEncapValue, indicates the SAP for which
--                      this entry contains information. This object is otherwise
--                      insignificant and contains the value 0."
--     ::= { tnSvcDhcpLeaseStateEntry 4 }
--
-- tnSvcDhcpLseStateEncapValue OBJECT-TYPE
--     SYNTAX          TmnxEncapVal
--     MAX-ACCESS      read-only
--     STATUS          current
--     DESCRIPTION     "When the value of tnSvcDhcpLseStateLocale is 'sap', the
--                      object tnSvcDhcpLseStatePortId along with the object
--                      tnSvcDhcpLseStateEncapValue, indicates the SAP for which
--                      this entry contains information. This object is otherwise
--                      insignificant and contains the value 0."
--     ::= { tnSvcDhcpLeaseStateEntry 5 }
--
-- tnSvcDhcpLseStateSdpId OBJECT-TYPE
--     SYNTAX          SdpId
--     MAX-ACCESS      read-only
--     STATUS          current
--     DESCRIPTION     "When the value of tnSvcDhcpLseStateLocale is 'sdp', the
--                      object tnSvcDhcpLseStateSdpId, along with the object
--                      tnSvcDhcpLseStateVcId, indicates the SDP Binding for which
--                      this entry contains information. This object is otherwise
--                      insignificant and contains the value 0."
--     ::= { tnSvcDhcpLeaseStateEntry 6 }
--
-- tnSvcDhcpLseStateVcId OBJECT-TYPE
--     SYNTAX          Unsigned32
--     MAX-ACCESS      read-only
--     STATUS          current
--     DESCRIPTION     "When the value of tnSvcDhcpLseStateLocale is 'sdp', the
--                      object tnSvcDhcpLseStateSdpId, along with the object
--                      tnSvcDhcpLseStateVcId, indicates the SDP Binding for which
--                      this entry contains information. This object is otherwise
--                      insignificant and contains the value 0."
--     ::= { tnSvcDhcpLeaseStateEntry 7 }
--
-- tnSvcDhcpLseStateChAddr OBJECT-TYPE
--     SYNTAX          MacAddress
--     MAX-ACCESS      read-only
--     STATUS          current
--     DESCRIPTION     "The value of tnSvcDhcpLseStateChAddr indicates the MAC
--                      address of the DHCP lease state."
--     ::= { tnSvcDhcpLeaseStateEntry 8 }
--
-- tnSvcDhcpLseStateRemainLseTime OBJECT-TYPE
--     SYNTAX          Unsigned32
--     UNITS           "seconds"
--     MAX-ACCESS      read-only
--     STATUS          current
--     DESCRIPTION     "The value of tnSvcDhcpLseStateRemainLseTime indicates the
--                      remaining lease time of the DHCP lease state."
--     ::= { tnSvcDhcpLeaseStateEntry 9 }
--
-- tnSvcDhcpLseStateOption82 OBJECT-TYPE
--     SYNTAX          OCTET STRING
--     MAX-ACCESS      read-only
--     STATUS          current
--     DESCRIPTION     "The value of tnSvcDhcpLseStateOption82 indicates the content
--                      of option 82 for this DHCP lease state."
--     ::= { tnSvcDhcpLeaseStateEntry 10 }
--
-- tnSvcDhcpLseStatePersistKey OBJECT-TYPE
--     SYNTAX          Unsigned32
--     MAX-ACCESS      read-only
--     STATUS          current
--     DESCRIPTION     "The value of tnSvcDhcpLseStatePersistKey indicates a key
--                      value that can be used to track this lease state in the
--                      persistence file."
--     ::= { tnSvcDhcpLeaseStateEntry 11 }
--
-- tnSvcDhcpLseStateSubscrIdent OBJECT-TYPE
--     SYNTAX          DisplayString
--     MAX-ACCESS      read-only
--     STATUS          current
--     DESCRIPTION     "The value of tnSvcDhcpLseStateSubscrIdent indicates the
--                      id of the parent subscriber of this DHCP lease state.
--
--                      The value of tnSvcDhcpLseStateOriginSubscrId indicates
--                      whether this subscriber identification was received from
--                      the DHCP or from the Radius server."
--     ::= { tnSvcDhcpLeaseStateEntry 12 }
--
-- tnSvcDhcpLseStateSubProfString OBJECT-TYPE
--     SYNTAX          DisplayString
--     MAX-ACCESS      read-only
--     STATUS          current
--     DESCRIPTION     "The value of tnSvcDhcpLseStateSubProfString indicates the
--                      subscriber profile string applicable for this DHCP lease
--                      state.
--
--                      The value of tnSvcDhcpLseStateOriginStrings indicates
--                      whether this subscriber profile string was received from
--                      the DHCP or from the Radius server."
--     ::= { tnSvcDhcpLeaseStateEntry 13 }
--
-- tnSvcDhcpLseStateSlaProfString OBJECT-TYPE
--     SYNTAX          DisplayString
--     MAX-ACCESS      read-only
--     STATUS          current
--     DESCRIPTION     "The value of tnSvcDhcpLseStateSlaProfString indicates the
--                      SLA profile string applicable for this DHCP lease state.
--
--                      The value of tnSvcDhcpLseStateOriginStrings indicates
--                      whether this SLA profile string was received from
--                      the DHCP or from the Radius server."
--     ::= { tnSvcDhcpLeaseStateEntry 14 }
--
-- tnSvcDhcpLseStateShcvOperState OBJECT-TYPE
--     SYNTAX          INTEGER{
--                         disabled  (1),
--                         undefined (2),
--                         down      (3),
--                         up        (4)
--                     }
--     MAX-ACCESS      read-only
--     STATUS          current
--     DESCRIPTION     "The value of tnSvcDhcpLseStateShcvOperState indicates the
--                      state of the subscriber host connectivity check for
--                      this DHCP lease state."
--     ::= { tnSvcDhcpLeaseStateEntry 15 }
--
-- tnSvcDhcpLseStateShcvChecks OBJECT-TYPE
--     SYNTAX          Unsigned32
--     MAX-ACCESS      read-only
--     STATUS          current
--     DESCRIPTION     "The value of tnSvcDhcpLseStateShcvChecks indicates the
--                      number of host connectivity check requests for
--                      this DHCP lease state."
--     ::= { tnSvcDhcpLeaseStateEntry 16 }
--
-- tnSvcDhcpLseStateShcvReplies OBJECT-TYPE
--     SYNTAX          Unsigned32
--     MAX-ACCESS      read-only
--     STATUS          current
--     DESCRIPTION     "The value of tnSvcDhcpLseStateShcvReplies indicates the
--                      number of host connectivity replies for
--                      this DHCP lease state."
--     ::= { tnSvcDhcpLeaseStateEntry 17 }
--
-- tnSvcDhcpLseStateShcvReplyTime OBJECT-TYPE
--     SYNTAX          TimeStamp
--     MAX-ACCESS      read-only
--     STATUS          current
--     DESCRIPTION     "The value of tnSvcDhcpLseStateShcvReplyTime indicates the
--                      time of the last successful host connectivity check for
--                      this DHCP lease state."
--     ::= { tnSvcDhcpLeaseStateEntry 18 }
--
-- tnSvcDhcpLseStateClientId OBJECT-TYPE
--     SYNTAX          OCTET STRING
--     MAX-ACCESS      read-only
--     STATUS          current
--     DESCRIPTION     "The value of tnSvcDhcpLseStateClientId indicates the
--                      DHCPv6 clients unique identifier (DUID) as generated
--                      by the client."
--     ::= { tnSvcDhcpLeaseStateEntry 19 }
--
-- tnSvcDhcpLseStateIAID OBJECT-TYPE
--     SYNTAX          Unsigned32
--     MAX-ACCESS      read-only
--     STATUS          current
--     DESCRIPTION     "The value of tnSvcDhcpLseStateIAID indicates the
--                      Identity Association ID (IAID)
--                      the address or prefix defined by
--                      tnSvcDhcpLseStateCiAddr/tnSvcDhcpLseStateCiAddrMaskLen
--                      has been assigned to.
--
--                      This object is only meaningful for DHCPv6 leases."
--     REFERENCE
--                     "RFC 3315 section 10"
--     ::= { tnSvcDhcpLeaseStateEntry 20 }
--
-- tnSvcDhcpLseStateIAIDType OBJECT-TYPE
--     SYNTAX          IAIDType
--     MAX-ACCESS      read-only
--     STATUS          current
--     DESCRIPTION     "The value of tnSvcDhcpLseStateIAIDType indicates the
--                      type of tnSvcDhcpLseStateIAID.
--
--                      This object is only meaningful for DHCPv6 leases."
--     REFERENCE
--                     "RFC 3315"
--     ::= { tnSvcDhcpLeaseStateEntry 21 }
--
-- tnSvcDhcpLseStateCiAddrMaskLen OBJECT-TYPE
--     SYNTAX          Unsigned32 (0..128)
--     MAX-ACCESS      read-only
--     STATUS          current
--     DESCRIPTION     "The value of tnSvcDhcpLseStateCiAddrMaskLen indicates the
--                      prefix length of the tnSvcDhcpLseStateCiAddr for a DHCPv6
--                      lease."
--     ::= { tnSvcDhcpLeaseStateEntry 22 }
--
-- tnSvcDhcpLseStateRetailerSvcId OBJECT-TYPE
--     SYNTAX          TmnxServId
--     MAX-ACCESS      read-only
--     STATUS          current
--     DESCRIPTION     "The value of tnSvcDhcpLseStateRetailerSvcId indicates the
--                      service ID of the retailer VPRN service to which this
--                      DHCP lease belongs. When this object is non zero, the
--                      DHCP lease belongs to a retailer VPRN."
--     ::= { tnSvcDhcpLeaseStateEntry 23 }
--
-- tnSvcDhcpLseStateRetailerIf OBJECT-TYPE
--      SYNTAX         InterfaceIndexOrZero
--      MAX-ACCESS      read-only
--      STATUS          current
--      DESCRIPTION     "The value of tnSvcDhcpLseStateRetailerIf indicates the
--                       interface index of the retailer VPRN interface to
--                       which this DHCP lease belongs. When this object is
--                       non zero, the DHCP lease belongs to a retailer VPRN."
--      ::= { tnSvcDhcpLeaseStateEntry 24 }
--
-- tnSvcDhcpLseStateAncpString OBJECT-TYPE
--     SYNTAX          DisplayString (SIZE (1..63))
--     MAX-ACCESS      read-only
--     STATUS          current
--     DESCRIPTION     "The object tnSvcDhcpLseStateAncpString indicates the
--                      value of the ancp-string received from either the DHCP
--                      or the Radius server as indicated by the value of
--                      tnSvcDhcpLseStateOriginStrings."
--     ::= { tnSvcDhcpLeaseStateEntry 25 }
--
-- tnSvcDhcpLseStateFramedIpNetMaskTp OBJECT-TYPE
--     SYNTAX          InetAddressType
--     MAX-ACCESS      read-only
--     STATUS          current
--     DESCRIPTION     "The value of tnSvcDhcpLseStateFramedIpNetMaskTp indicates the
--                      address type of tnSvcDhcpLseStateFramedIpNetMask."
--     ::= { tnSvcDhcpLeaseStateEntry 26 }
--
-- tnSvcDhcpLseStateFramedIpNetMask OBJECT-TYPE
--     SYNTAX          InetAddress
--     MAX-ACCESS      read-only
--     STATUS          current
--     DESCRIPTION     "The value of tnSvcDhcpLseStateFramedIpNetMask indicates the
--                      framed IP netmask received from either the DHCP or the
--                      Radius server as indicated by the value of
--                      tnSvcDhcpLseStateOriginLeaseInfo.
--
--                      The value of this object is ''H when not applicable."
--     ::= { tnSvcDhcpLeaseStateEntry 27 }
--
-- tnSvcDhcpLseStateBCastIpAddrType OBJECT-TYPE
--     SYNTAX          InetAddressType
--     MAX-ACCESS      read-only
--     STATUS          current
--     DESCRIPTION     "The value of tnSvcDhcpLseStateBCastIpAddrType indicates the
--                      address type of tnSvcDhcpLseStateBCastIpAddr."
--     ::= { tnSvcDhcpLeaseStateEntry 28 }
--
-- tnSvcDhcpLseStateBCastIpAddr OBJECT-TYPE
--     SYNTAX          InetAddress
--     MAX-ACCESS      read-only
--     STATUS          current
--     DESCRIPTION     "The value of tnSvcDhcpLseStateBCastIpAddr indicates the
--                      broadcast IP address received from either the DHCP or the
--                      Radius server as indicated by the value of
--                      tnSvcDhcpLseStateOriginLeaseInfo.
--
--                      The value of this object is ''H when not applicable."
--     ::= { tnSvcDhcpLeaseStateEntry 29 }
--
-- tnSvcDhcpLseStateDefaultRouterTp OBJECT-TYPE
--     SYNTAX          InetAddressType
--     MAX-ACCESS      read-only
--     STATUS          current
--     DESCRIPTION     "The value of tnSvcDhcpLseStateDefaultRouterTp indicates the
--                      address type of tnSvcDhcpLseStateDefaultRouter."
--     ::= { tnSvcDhcpLeaseStateEntry 30 }
--
-- tnSvcDhcpLseStateDefaultRouter OBJECT-TYPE
--     SYNTAX          InetAddress
--     MAX-ACCESS      read-only
--     STATUS          current
--     DESCRIPTION     "The value of tnSvcDhcpLseStateDefaultRouter indicates the
--                      default router received from either the DHCP or the
--                      Radius server as indicated by the value of
--                      tnSvcDhcpLseStateOriginLeaseInfo.
--
--                      The value of this object is ''H when not applicable."
--     ::= { tnSvcDhcpLeaseStateEntry 31 }
--
-- tnSvcDhcpLseStatePrimaryDnsType OBJECT-TYPE
--     SYNTAX          InetAddressType
--     MAX-ACCESS      read-only
--     STATUS          current
--     DESCRIPTION     "The value of tnSvcDhcpLseStatePrimaryDnsType indicates the
--                      address type of tnSvcDhcpLseStatePrimaryDns."
--     ::= { tnSvcDhcpLeaseStateEntry 32 }
--
-- tnSvcDhcpLseStatePrimaryDns OBJECT-TYPE
--     SYNTAX          InetAddress
--     MAX-ACCESS      read-only
--     STATUS          current
--     DESCRIPTION     "The value of tnSvcDhcpLseStatePrimaryDns indicates the
--                      primary DNS server received from either the DHCP or the
--                      Radius server as indicated by the value of
--                      tnSvcDhcpLseStateOriginLeaseInfo.
--
--                      The value of this object is ''H when not applicable."
--     ::= { tnSvcDhcpLeaseStateEntry 33 }
--
-- tnSvcDhcpLseStateSecondaryDnsType OBJECT-TYPE
--     SYNTAX          InetAddressType
--     MAX-ACCESS      read-only
--     STATUS          current
--     DESCRIPTION     "The value of tnSvcDhcpLseStateSecondaryDnsType indicates the
--                      address type of tnSvcDhcpLseStateSecondaryDns."
--     ::= { tnSvcDhcpLeaseStateEntry 34 }
--
-- tnSvcDhcpLseStateSecondaryDns OBJECT-TYPE
--     SYNTAX          InetAddress
--     MAX-ACCESS      read-only
--     STATUS          current
--     DESCRIPTION     "The value of tnSvcDhcpLseStateSecondaryDns indicates the
--                      secondary DNS server received from either the DHCP or the
--                      Radius server as indicated by the value of
--                      tnSvcDhcpLseStateOriginLeaseInfo.
--
--                      The value of this object is ''H when not applicable."
--     ::= { tnSvcDhcpLeaseStateEntry 35 }
--
-- tnSvcDhcpLseStateSessionTimeout OBJECT-TYPE
--     SYNTAX          Unsigned32 (0..65535)
--     UNITS           "seconds"
--     MAX-ACCESS      read-only
--     STATUS          current
--     DESCRIPTION     "The value of tnSvcDhcpLseStateSessionTimeout indicates the
--                      session timeout received from either the DHCP or the
--                      Radius server as indicated by the value of
--                      tnSvcDhcpLseStateOriginLeaseInfo."
--     ::= { tnSvcDhcpLeaseStateEntry 36 }
--
-- tnSvcDhcpLseStateServerLeaseStart OBJECT-TYPE
--     SYNTAX          DateAndTime
--     MAX-ACCESS      read-only
--     STATUS          current
--     DESCRIPTION     "The value of tnSvcDhcpLseStateServerLeaseStart indicates
--                      when this lease was created."
--     ::= { tnSvcDhcpLeaseStateEntry 37 }
--
-- tnSvcDhcpLseStateServerLastRenew OBJECT-TYPE
--     SYNTAX          DateAndTime
--     MAX-ACCESS      read-only
--     STATUS          current
--     DESCRIPTION     "The value of tnSvcDhcpLseStateServerLastRenew indicates
--                      when we last received a renewal from either the DHCP or the
--                      Radius server."
--     ::= { tnSvcDhcpLeaseStateEntry 38 }
--
-- tnSvcDhcpLseStateServerLeaseEnd OBJECT-TYPE
--     SYNTAX          DateAndTime
--     MAX-ACCESS      read-only
--     STATUS          current
--     DESCRIPTION     "The value of tnSvcDhcpLseStateServerLeaseEnd indicates
--                      when the server will consider the lease as being
--                      expired."
--     ::= { tnSvcDhcpLeaseStateEntry 39 }
--
-- tnSvcDhcpLseStateDhcpServerAddrType OBJECT-TYPE
--     SYNTAX          InetAddressType
--     MAX-ACCESS      read-only
--     STATUS          current
--     DESCRIPTION     "The value of tnSvcDhcpLseStateDhcpServerAddrType indicates
--                      the address type of tnSvcDhcpLseStateDhcpServerAddr."
--     ::= { tnSvcDhcpLeaseStateEntry 40 }
--
-- tnSvcDhcpLseStateDhcpServerAddr OBJECT-TYPE
--     SYNTAX          InetAddress
--     MAX-ACCESS      read-only
--     STATUS          current
--     DESCRIPTION     "The value of tnSvcDhcpLseStateDhcpServerAddr indicates the
--                      IP address of the DHCP server received from either the
--                      DHCP or the Radius server as indicated by the value of
--                      tnSvcDhcpLseStateOriginLeaseInfo.
--
--                      The value of this object is ''H when not applicable."
--     ::= { tnSvcDhcpLeaseStateEntry 41 }
--
-- tnSvcDhcpLseStateOriginSubscrId OBJECT-TYPE
--     SYNTAX          DhcpLseStateInfoOrigin
--     MAX-ACCESS      read-only
--     STATUS          current
--     DESCRIPTION     "The value of tnSvcDhcpLseStateOriginSubscrId indicates
--                      which source provided the subscriber-id."
--     ::= { tnSvcDhcpLeaseStateEntry 42 }
--
-- tnSvcDhcpLseStateOriginStrings OBJECT-TYPE
--     SYNTAX          DhcpLseStateInfoOrigin
--     MAX-ACCESS      read-only
--     STATUS          current
--     DESCRIPTION     "The value of tnSvcDhcpLseStateOriginStrings indicates
--                      which server provided the Sub-profile, SLA profile,
--                      Ancp string and Intermediate Destination Id."
--     ::= { tnSvcDhcpLeaseStateEntry 43 }
--
-- tnSvcDhcpLseStateOriginLeaseInfo OBJECT-TYPE
--     SYNTAX          DhcpLseStateInfoOrigin
--     MAX-ACCESS      read-only
--     STATUS          current
--     DESCRIPTION     "The value of tnSvcDhcpLseStateOriginLeaseInfo indicates
--                      which server provided the lease state information."
--     ::= { tnSvcDhcpLeaseStateEntry 44 }
--
-- tnSvcDhcpLseStateDhcpClientAddrType OBJECT-TYPE
--     SYNTAX          InetAddressType
--     MAX-ACCESS      read-only
--     STATUS          current
--     DESCRIPTION     "The value of tnSvcDhcpLseStateDhcpClientAddrType indicates
--                      the address type of tnSvcDhcpLseStateDhcpClientAddr."
--     ::= { tnSvcDhcpLeaseStateEntry 45 }
--
-- tnSvcDhcpLseStateDhcpClientAddr OBJECT-TYPE
--     SYNTAX          InetAddress
--     MAX-ACCESS      read-only
--     STATUS          current
--     DESCRIPTION     "The value of tnSvcDhcpLseStateDhcpClientAddr indicates the
--                      IP address of the DHCP Client that owns the lease info.
--
--                      In some cases this address can be different from the
--                      address specified in tnSvcDhcpLseStateCiAddr, e.g. in case of
--                      DHCPv6 prefix delegation."
--     ::= { tnSvcDhcpLeaseStateEntry 46 }
--
-- tnSvcDhcpLseStateLeaseSplitActive OBJECT-TYPE
--     SYNTAX          TruthValue
--     MAX-ACCESS      read-only
--     STATUS          current
--     DESCRIPTION     "The value of tnSvcDhcpLseStateLeaseSplitActive indicates
--                      whether or not the current lease time resulted from a
--                      lease split.
--                      If tnSvcDhcpLseStateLeaseSplitActive is 'true',
--                      the lease time passed to the client is determined by the
--                      value of the object sapTlsDhcpProxyLeaseTime for VPLS SAPs,
--                      or by the value of the object vRtrIfDHCPProxyLeaseTime
--                      for Layer 3 interfaces."
--     ::= { tnSvcDhcpLeaseStateEntry 47 }
--
-- tnSvcDhcpLseStateInterDestId OBJECT-TYPE
--     SYNTAX          DisplayString (SIZE (0..32))
--     MAX-ACCESS      read-only
--     STATUS          current
--     DESCRIPTION     "The object tnSvcDhcpLseStateInterDestId indicates the
--                      intermediate destination identifier received from either
--                      the DHCP or the Radius server or the local user database
--                      as indicated by the value of tnSvcDhcpLseStateOriginStrings."
--     ::= { tnSvcDhcpLeaseStateEntry 48 }
--
-- tnSvcDhcpLseStatePrimaryNbnsType OBJECT-TYPE
--     SYNTAX          InetAddressType
--     MAX-ACCESS      read-only
--     STATUS          current
--     DESCRIPTION     "The value of tnSvcDhcpLseStatePrimaryNbnsType indicates the
--                      address type of tnSvcDhcpLseStatePrimaryNbns."
--     ::= { tnSvcDhcpLeaseStateEntry 49 }
--
-- tnSvcDhcpLseStatePrimaryNbns OBJECT-TYPE
--     SYNTAX          InetAddress
--     MAX-ACCESS      read-only
--     STATUS          current
--     DESCRIPTION     "The value of tnSvcDhcpLseStatePrimaryNbns indicates the
--                      primary NBNS server received from either the DHCP or the
--                      Radius server as indicated by the value of
--                      tnSvcDhcpLseStateOriginLeaseInfo.
--
--                      The value of this object is ''H when not applicable."
--     ::= { tnSvcDhcpLeaseStateEntry 50 }
--
-- tnSvcDhcpLseStateSecondaryNbnsType OBJECT-TYPE
--     SYNTAX          InetAddressType
--     MAX-ACCESS      read-only
--     STATUS          current
--     DESCRIPTION     "The value of tnSvcDhcpLseStateSecondaryNbnsType indicates
--                      the address type of tnSvcDhcpLseStateSecondaryNbns."
--     ::= { tnSvcDhcpLeaseStateEntry 51 }
--
-- tnSvcDhcpLseStateSecondaryNbns OBJECT-TYPE
--     SYNTAX          InetAddress
--     MAX-ACCESS      read-only
--     STATUS          current
--     DESCRIPTION     "The value of tnSvcDhcpLseStateSecondaryNbns indicates the
--                      secondary NBNS server received from either the DHCP or the
--                      Radius server as indicated by the value of
--                      tnSvcDhcpLseStateOriginLeaseInfo.
--
--                      The value of this object is ''H when not applicable."
--     ::= { tnSvcDhcpLeaseStateEntry 52 }
--
-- tnSvcDhcpLseStateAppProfString OBJECT-TYPE
--     SYNTAX          DisplayString
--     MAX-ACCESS      read-only
--     STATUS          current
--     DESCRIPTION     "The value of tnSvcDhcpLseStateAppProfString indicates the
--                      application profile string applicable for this DHCP lease
--                      state.
--
--                      The value of tnSvcDhcpLseStateOriginStrings indicates
--                      whether this application profile string was received from
--                      DHCP or from the Radius server."
--     ::= { tnSvcDhcpLeaseStateEntry 53 }
--
-- tnSvcDhcpLseStateNextHopMacAddr OBJECT-TYPE
--     SYNTAX          MacAddress
--     MAX-ACCESS      read-only
--     STATUS          current
--     DESCRIPTION     "The value of tnSvcDhcpLseStateNextHopMacAddr indicates the
--                      MAC address of the next hop of this DHCP lease state.
--
--                      Normally, the next hop MAC address equals the value of
--                      tnSvcDhcpLseStateChAddr. If the value of the object
--                      TIMETRA-VRTR-MIB::vRtrIfDHCPLayer2Header is set to 'true',
--                      a routing device can be present between this node and
--                      the DHCP client. In that case, the value of the next hop
--                      MAC address contains the MAC address of this routing
--                      device."
--     ::= { tnSvcDhcpLeaseStateEntry 54 }
--
-- tnSvcDhcpLseStateCategoryMapName OBJECT-TYPE
--     SYNTAX          TNamedItemOrEmpty
--     MAX-ACCESS      read-only
--     STATUS          current
--     DESCRIPTION     "The object tnSvcDhcpLseStateCategoryMapName indicates the
--                      value of the category map name received from either the
--                      DHCP or the Radius server as indicated by the value of
--                      tnSvcDhcpLseStateOriginStrings."
--     ::= { tnSvcDhcpLeaseStateEntry 55 }
--
-- tnSvcDhcpLseStateNakNextRenew OBJECT-TYPE
--     SYNTAX          TruthValue
--     MAX-ACCESS      read-only
--     STATUS          current
--     DESCRIPTION     "The value of tnSvcDhcpLseStateNakNextRenew indicates
--                      that the system will reply with a DHCP-NAK when the client
--                      sends the next DHCP-REQUEST, whereafter the lease-state
--                      will be deleted.
--
--                      This state is entered upon reception of a
--                      FORCE-NAK COA (Change Of Authority) request from RADIUS
--                      for this lease state, which at the same time also
--                      triggered the system to send a FORCE-RENEW DHCP message
--                      to the client."
--     ::= { tnSvcDhcpLeaseStateEntry 56 }
--
-- tnSvcDhcpLseStateRadiusClassAttr OBJECT-TYPE
--     SYNTAX          OCTET STRING (SIZE (0..64))
--     MAX-ACCESS      read-only
--     STATUS          current
--     DESCRIPTION     "The value of tnSvcDhcpLseStateRadiusClassAttr indicates the
--                      Class attribute returned by the RADIUS server in an
--                      Access-Accept message.
--
--                      If no RADIUS authentication is performed for this lease
--                      state, or RADIUS did not return this attribute, the value
--                      of this object is empty."
--     ::= { tnSvcDhcpLeaseStateEntry 57 }
--
-- tnSvcDhcpLseStateRadiusUserName OBJECT-TYPE
--     SYNTAX          DisplayString (SIZE (0..128))
--     MAX-ACCESS      read-only
--     STATUS          current
--     DESCRIPTION     "The value of tnSvcDhcpLseStateRadiusUserName indicates the
--                      User-Name attribute returned by the RADIUS server in an
--                      Access-Accept message.
--
--                      If RADIUS did not return this attribute, the value of this
--                      object is equal to the User-Name attribute sent in the
--                      original Access-Request message.
--
--                      If no RADIUS authentication is performed for this session,
--                      the value of this object is empty."
--     ::= { tnSvcDhcpLeaseStateEntry 58 }

-- -----------------------------------------
-- TLS Protected MAC Address Table
-- -----------------------------------------
-- tnTlsProtectedMacTable OBJECT-TYPE
--     SYNTAX          SEQUENCE OF TlsProtectedMacEntry
--     MAX-ACCESS      not-accessible
--     STATUS          current
--     DESCRIPTION     "This table is used to manage protected MAC addresses
--                      within a VPLS's FDB."
--     ::= { tnSvcObjs 17 }
--
-- tnTlsProtectedMacEntry OBJECT-TYPE
--     SYNTAX          TlsProtectedMacEntry
--     MAX-ACCESS      not-accessible
--     STATUS          current
--     DESCRIPTION     "An entry containing management information applicable
--                      to a particular protected MAC address."
--     INDEX           { tnSysSwitchId,  tnSvcId, tnTlsProtMacAddress }
--     ::= { tnTlsProtectedMacTable 1 }
--
-- TlsProtectedMacEntry ::=
--     SEQUENCE {
--         tnTlsProtMacAddress           MacAddress,
--         tnTlsProtMacRowStatus         RowStatus,
--         tnTlsProtMacLastMgmtChange    TimeStamp
--     }
--
-- tnTlsProtMacAddress OBJECT-TYPE
--     SYNTAX          MacAddress
--     MAX-ACCESS      not-accessible
--     STATUS          current
--     DESCRIPTION     "The value of tnTlsProtMacAddress indicates the address
--                      of the protected MAC."
--     ::= { tnTlsProtectedMacEntry 1 }
--
-- tnTlsProtMacRowStatus OBJECT-TYPE
--     SYNTAX          RowStatus
--     MAX-ACCESS      read-create
--     STATUS          current
--     DESCRIPTION     "The value of tnTlsProtMacRowStatus controls the creation
--                      and deletion of rows in this table."
--     ::= { tnTlsProtectedMacEntry 2 }
--
-- tnTlsProtMacLastMgmtChange OBJECT-TYPE
--     SYNTAX          TimeStamp
--     MAX-ACCESS      read-only
--     STATUS          current
--     DESCRIPTION     "The value of tnTlsProtMacLastMgmtChange indicates the
--                      value of sysUpTime at the time of the last management
--                      change of any writable object of this row."
--     ::= { tnTlsProtectedMacEntry 3 }

-- ----------------------------------------
-- tnSvcDhcpLeaseStateModifyTable
-- ----------------------------------------
-- tnSvcDhcpLeaseStateModifyTable OBJECT-TYPE
--     SYNTAX          SEQUENCE OF TnSvcDhcpLeaseStateModifyEntry
--     MAX-ACCESS      not-accessible
--     STATUS          current
--     DESCRIPTION     "The tnSvcDhcpLeaseStateModifyTable augments the
--                      tnSvcDhcpLeaseStateTable.
--                      The table allows the operator to modify attributes of the
--                      lease state."
--     ::= { tnSvcObjs 18 }
--
-- tnSvcDhcpLeaseStateModifyEntry OBJECT-TYPE
--     SYNTAX          TnSvcDhcpLeaseStateModifyEntry
--     MAX-ACCESS      not-accessible
--     STATUS          current
--     DESCRIPTION     "Each row entry contains parameters that allow to modify a
--                      lease-state's  attributes."
--     AUGMENTS        { tnSvcDhcpLeaseStateEntry }
--     ::= { tnSvcDhcpLeaseStateModifyTable 1 }
--
-- TnSvcDhcpLeaseStateModifyEntry ::=
--     SEQUENCE {
--         tnSvcDhcpLseStateModifySubIndent   DisplayString,
--         tnSvcDhcpLseStateModifySubProfile  DisplayString,
--         tnSvcDhcpLseStateModifySlaProfile  DisplayString,
--         tnSvcDhcpLseStateEvaluateState     TruthValue,
--         tnSvcDhcpLseStateModInterDestId    DisplayString,
--         tnSvcDhcpLseStateModifyAncpString  TmnxAncpStringOrZero,
--         tnSvcDhcpLseStateModifyAppProfile  DisplayString
--     }
--
-- tnSvcDhcpLseStateModifySubIndent OBJECT-TYPE
--     SYNTAX          DisplayString (SIZE (0..32))
--     MAX-ACCESS      read-write
--     STATUS          current
--     DESCRIPTION     "The value of tnSvcDhcpLseStateModifySubIndent allows to
--                      specify a new subscriber name for this lease state.
--
--                      When a SET of this object is done with a non empty string, the
--                      system will attempt to assign a new subscriber name.
--
--                      A SET with an empty string has no effect on the system.
--                      (NOOP).
--
--                      GETs and GETNEXTs on this variable return an empty string."
--     DEFVAL           { ''H }   == the empty string
--     ::= { tnSvcDhcpLeaseStateModifyEntry 1 }
--
-- tnSvcDhcpLseStateModifySubProfile OBJECT-TYPE
--     SYNTAX          DisplayString (SIZE (0..16))
--     MAX-ACCESS      read-write
--     STATUS          current
--     DESCRIPTION     "The value of tnSvcDhcpLseStateModifySubProfile allows to
--                      specify a new subscriber profile string for this lease
--                      state.
--
--                      When a SET of this object is done with a non empty string,
--                      the system will attempt to assign a new subscriber profile.
--
--                      A SET with an empty string has no effect on the system.
--                      (NOOP).
--
--                      GETs and GETNEXTs on this variable return an empty string."
--     DEFVAL           { ''H }   == the empty string
--     ::= { tnSvcDhcpLeaseStateModifyEntry 2 }
--
-- tnSvcDhcpLseStateModifySlaProfile OBJECT-TYPE
--     SYNTAX          DisplayString (SIZE (0..16))
--     MAX-ACCESS      read-write
--     STATUS          current
--     DESCRIPTION     "The value of tnSvcDhcpLseStateModifySlaProfile allows to
--                      specify a new SLA profile string for this lease state.
--
--                      When a SET of this object is done with a non empty string,
--                      the system will attempt to assign a new SLA profile.
--
--                      A SET with an empty string has no effect on the system.
--                      (NOOP).
--
--                      GETs and GETNEXTs on this variable return an empty string."
--     DEFVAL           { ''H }   == the empty string
--     ::= { tnSvcDhcpLeaseStateModifyEntry 3 }
--
-- tnSvcDhcpLseStateEvaluateState OBJECT-TYPE
--     SYNTAX          TruthValue
--     MAX-ACCESS      read-write
--     STATUS          current
--     DESCRIPTION     "The value of tnSvcDhcpLseStateEvaluateState allows to
--                      cause a re-evaluation of the specified lease state.
--
--                      When this object is set to 'true', the system will perform
--                      a re-evaluation of the lease state.
--
--                      GETs and GETNEXTs on this variable return false.
--
--                      It is not possible to simultaneously request for a
--                      lease-state re-evaluation, and modify any of the
--                      tnSvcDhcpLseStateModifySubIndent,
--                      tnSvcDhcpLseStateModifySubProfile or
--                      tnSvcDhcpLseStateModifySlaProfile values."
--     DEFVAL          { false }
--     ::= { tnSvcDhcpLeaseStateModifyEntry 4 }
--
-- tnSvcDhcpLseStateModInterDestId OBJECT-TYPE
--     SYNTAX          DisplayString (SIZE (0..32))
--     MAX-ACCESS      read-write
--     STATUS          current
--     DESCRIPTION     "The value of tnSvcDhcpLseStateModInterDestId allows to
--                      specify a new intermediate destination id for this lease
--                      state.
--
--                      When a SET of this object is done with a non empty string,
--                      the system will attempt to assign a new intermediate
--                      destination id.
--
--                      A SET with an empty string has no effect on the system.
--                      (NOOP).
--
--                      GETs and GETNEXTs on this variable return an empty string."
--     DEFVAL           { ''H }
--     ::= { tnSvcDhcpLeaseStateModifyEntry 5 }
--
-- tnSvcDhcpLseStateModifyAncpString OBJECT-TYPE
--     SYNTAX          TmnxAncpStringOrZero
--     MAX-ACCESS      read-write
--     STATUS          current
--     DESCRIPTION     "The value of tnSvcDhcpLseStateModifyAncpString allows to
--                      specify a new ANCP-string for this lease state.
--
--                      When a SET of this object is done with a non empty string,
--                      the system will attempt to assign a new ANCP-string.
--
--                      A SET with an empty string has no effect on the system.
--                      (NOOP).
--
--                      GETs and GETNEXTs on this variable return an empty string."
--     DEFVAL           { ''H }   == the empty string
--     ::= { tnSvcDhcpLeaseStateModifyEntry 6 }
--
-- tnSvcDhcpLseStateModifyAppProfile OBJECT-TYPE
--     SYNTAX          DisplayString (SIZE (0..16))
--     MAX-ACCESS      read-write
--     STATUS          current
--     DESCRIPTION     "The value of tnSvcDhcpLseStateModifyAppProfile specifies
--                      a new application profile string for this lease state.
--
--                      When a SET of this object is done with a non empty string,
--                      the system assigns a new application profile.
--
--                      A SET with an empty string has no effect on the system.
--                      (NOOP).
--
--                      GETs and GETNEXTs on this variable return an empty
--                      string."
--     DEFVAL           { ''H }   == the empty string
--     ::= { tnSvcDhcpLeaseStateModifyEntry 7 }

-- ----------------------------------------
-- tnSvcEndPointTable
-- ----------------------------------------
 tnSvcEndPointTable        OBJECT-TYPE
     SYNTAX      SEQUENCE OF TnSvcEndPointEntry
     MAX-ACCESS  not-accessible
     STATUS      current
     DESCRIPTION "The tnSvcEndPointTable has an entry for each service endpoint
                  configured on this system."
     ::= { tnSvcObjs 19 }

 tnSvcEndPointEntry        OBJECT-TYPE
     SYNTAX      TnSvcEndPointEntry
     MAX-ACCESS  not-accessible
     STATUS      current
     DESCRIPTION "Each row entry represents a particular service endpoint.
                  Entries are created/deleted by the user."
     INDEX       { tnSysSwitchId, tnSvcId, tnSvcEndPointName }
     ::= { tnSvcEndPointTable 1 }

 TnSvcEndPointEntry ::=
     SEQUENCE {
         tnSvcEndPointName                 TNamedItem,
         tnSvcEndPointRowStatus            RowStatus,
         tnSvcEndPointDescription          ServObjDesc,
         tnSvcEndPointRevertTime           Integer32,
         tnSvcEndPointTxActiveType         INTEGER,
         tnSvcEndPointTxActivePortId       InterfaceIndexOrZero,
         tnSvcEndPointTxActiveEncap        TmnxEncapVal,
         tnSvcEndPointTxActiveSdpId        SdpBindId,
         tnSvcEndPointForceSwitchOver      TmnxActionType,
         tnSvcEndPointForceSwitchOverSdpId SdpBindId,
         tnSvcEndPointActiveHoldDelay      Unsigned32,
         tnSvcEndPointIgnoreStandbySig     TruthValue,
         tnSvcEndPointMacPinning           TmnxEnabledDisabled,
         tnSvcEndPointMacLimit             Integer32,
         tnSvcEndPointSuppressStandbySig   TruthValue,
         tnSvcEndPointRevertTimeCountDn    Integer32,
         tnSvcEndPointTxActiveChangeCount  Counter32,
         tnSvcEndPointTxActiveLastChange   TimeStamp,
         tnSvcEndPointTxActiveUpTime       TimeTicks,
         tnSvcEndPointMCEPId               Unsigned32,
         tnSvcEndPointMCEPPeerAddrType     InetAddressType,
         tnSvcEndPointMCEPPeerAddr         InetAddress,
         tnSvcEndPointMCEPPeerName         TNamedItemOrEmpty,
         tnSvcEndPointBlockOnMeshFail      TruthValue,
         tnSvcEndPointMCEPPsvModeActive    TruthValue,
         tnSvcEndPointStandbySigMaster     TruthValue
     }

 tnSvcEndPointName         OBJECT-TYPE
     SYNTAX      TNamedItem
     MAX-ACCESS  not-accessible
     STATUS      current
     DESCRIPTION "The value of tnSvcEndPointName specifies the name of the service
                  endpoint."
     ::= { tnSvcEndPointEntry 1 }

 tnSvcEndPointRowStatus    OBJECT-TYPE
     SYNTAX      RowStatus
     MAX-ACCESS  read-create
     STATUS      current
     DESCRIPTION "The value of tnSvcEndPointRowStatus is used for the creation and
                  deletion of service endpoints."
     ::= { tnSvcEndPointEntry 2 }

 tnSvcEndPointDescription  OBJECT-TYPE
     SYNTAX      ServObjDesc
     MAX-ACCESS  read-create
     STATUS      current
     DESCRIPTION "The value of tnSvcEndPointDescription specifies the textual
                  description of this service endpoint."
     DEFVAL      { "" }
     ::= { tnSvcEndPointEntry 3 }

 tnSvcEndPointRevertTime  OBJECT-TYPE
     SYNTAX      Integer32 (-1 | 0..600)
     UNITS       "seconds"
     MAX-ACCESS  read-create
     STATUS      current
     DESCRIPTION "The value of tnSvcEndPointRevertTime specifies the time to wait
                  before reverting back to the primary spoke-sdp defined on this
                  service endpoint, after having failed over to a backup
                  spoke-sdp. When the value is '-1', the spoke-sdp will never
                  revert back."
     DEFVAL      { 0 }
     ::= { tnSvcEndPointEntry 4 }

 tnSvcEndPointTxActiveType OBJECT-TYPE
     SYNTAX      INTEGER {
                     none    (0), -- No end-point objects are active
                     sap     (1), -- A SAP is Tx active
                     sdpBind (2)  -- An SDP bind is Tx Active
                 }
     MAX-ACCESS  read-only
     STATUS      current
     DESCRIPTION "The value of tnSvcEndPointTxActiveType indicates the type of
                  end-point object that is current transmit active. "
     ::= { tnSvcEndPointEntry 5 }

 tnSvcEndPointTxActivePortId       OBJECT-TYPE
     SYNTAX      InterfaceIndexOrZero
     MAX-ACCESS  read-only
     STATUS      current
     DESCRIPTION "The value of tnSvcEndPointTxActivePortId indicates the Port ID
                  of the SAP that is transmit active. This object is only valid
                  when tnSvcEndPointTxActiveType is 'sap'."
     ::= { tnSvcEndPointEntry 6 }

 tnSvcEndPointTxActiveEncap       OBJECT-TYPE
     SYNTAX      TmnxEncapVal
     MAX-ACCESS  read-only
     STATUS      current
     DESCRIPTION "The value of tnSvcEndPointTxActiveEncap indicates the
                  encapsulation value of the SAP that is transmit active. This
                  object is only valid when tnSvcEndPointTxActiveType is 'sap'."
     ::= { tnSvcEndPointEntry 7 }

 tnSvcEndPointTxActiveSdpId       OBJECT-TYPE
     SYNTAX      SdpBindId
     MAX-ACCESS  read-only
     STATUS      current
     DESCRIPTION "The value of tnSvcEndPointTxActiveSdpId indicates the SDP bind
                  ID of the SDP bind that is transmit active. This object is only
                  valid when tnSvcEndPointTxActiveType is 'sdpBind'."
     ::= { tnSvcEndPointEntry 8 }

 tnSvcEndPointForceSwitchOver      OBJECT-TYPE
     SYNTAX      TmnxActionType
     MAX-ACCESS  read-create
     STATUS      current
     DESCRIPTION "The value of tnSvcEndPointForceSwitchOver specifies whether to
                  force a switchover of the active SDP bind. When it is set to
                  'doAction', the SDP bind specified by
                  tnSvcEndPointForceSwitchOverSdpId will become active."
     DEFVAL      { notApplicable }
     ::= { tnSvcEndPointEntry 9 }

 tnSvcEndPointForceSwitchOverSdpId   OBJECT-TYPE
     SYNTAX      SdpBindId
     MAX-ACCESS  read-create
     STATUS      current
     DESCRIPTION "The value of tnSvcEndPointForceSwitchOverSdpId specifies the SDP
                  bind to switch over to when tnSvcEndPointForceSwitchOver is set
                  to 'doAction'. If the value of this object is non default, it
                  indicates that a forced switchover has taken place. Setting
                  this object to the default value clears any previous forced
                  switchover. "
     DEFVAL      { '0000000000000000'H }
     ::= { tnSvcEndPointEntry 10 }

 tnSvcEndPointActiveHoldDelay     OBJECT-TYPE
     SYNTAX      Unsigned32 (0..60)
     UNITS       "deci-seconds"
     MAX-ACCESS  read-create
     STATUS      current
     DESCRIPTION "The value of tnSvcEndPointActiveHoldDelay specifies the amount
                  of time in deci-seconds to hold the active state before going
                  into the standby state when a local MC-LAG SAP goes down."
     DEFVAL      { 0 }
     ::= { tnSvcEndPointEntry 11 }

 tnSvcEndPointIgnoreStandbySig     OBJECT-TYPE
     SYNTAX      TruthValue
     MAX-ACCESS  read-create
     STATUS      current
     DESCRIPTION "The value of tnSvcEndPointIgnoreStandbySig specifies whether the
                  local internal tasks will take into account the 'pseudo-wire
                  forwarding standby' bit received from the LDP peer which is
                  normally ignored.

                  When set to 'true', this bit is not considered in the internal
                  tasks.

                  A similar object sdpBindTlsIgnoreStandbySig is present at the
                  SDP level. The value of sdpBindTlsIgnoreStandbySig is set to
                  the value of tnSvcEndPointIgnoreStandbySig for the spoke-SDP
                  associated with this endpoint."
     DEFVAL      { false }
     ::= { tnSvcEndPointEntry 12 }

 tnSvcEndPointMacPinning OBJECT-TYPE
     SYNTAX      TmnxEnabledDisabled
     MAX-ACCESS  read-create
     STATUS      current
     DESCRIPTION "The value of tnSvcEndPointMacPinning specifies whether or not
                  MAC address pinning is active on this end-point."
     DEFVAL { disabled }
     ::= { tnSvcEndPointEntry 13 }

 tnSvcEndPointMacLimit OBJECT-TYPE
     SYNTAX      Integer32(0..511999)
     MAX-ACCESS  read-create
     STATUS      current
     DESCRIPTION "The value of the object tnSvcEndPointMacLimit specifies the
                  maximum number of learned and static entries allowed for this
                  end-point.

                  The value 0 means: no limit for this end-point.

                  When the value of TIMETRA-CHASSIS-MIB::tmnxChassisOperMode is
                  'a' or 'b', the maximum value of this object is '131071'.

                  When the value of TIMETRA-CHASSIS-MIB::tmnxChassisOperMode is
                  'c', the maximum value of this object is '196607'.

                  When the value of TIMETRA-CHASSIS-MIB::tmnxChassisOperMode is
                  'd', the maximum value of this object is '511999'."
     DEFVAL          { 0 }
     ::= { tnSvcEndPointEntry 14 }

 tnSvcEndPointSuppressStandbySig     OBJECT-TYPE
     SYNTAX      TruthValue
     MAX-ACCESS  read-create
     STATUS      current
     DESCRIPTION "The value of the object tnSvcEndPointSuppressStandbySig specifies
                  whether the 'pseudo wire forwarding standby' bit will be sent
                  to the LDP peer whenever the spoke SDP
                  'tnSvcEndPointTxActiveSdpId' is selected as standby.

                  When set to 'true', this bit will not be sent."
     DEFVAL      { true }
     ::= { tnSvcEndPointEntry 15 }

 tnSvcEndPointRevertTimeCountDn  OBJECT-TYPE
     SYNTAX      Integer32 (-1 | 0..600)
     UNITS       "seconds"
     MAX-ACCESS  read-only
     STATUS      current
     DESCRIPTION "The value of tnSvcEndPointRevertTimeCountDn indicates the timer
                  count down before reverting back to the primary spoke-sdp
                  defined on this service endpoint, after having failed over to
                  a backup spoke-sdp.

                  This timer count down begins after primary Spoke SDP becomes
                  operational.

                  The value of -1 indicates when revert is not-applicable."
     ::= { tnSvcEndPointEntry 16 }

 tnSvcEndPointTxActiveChangeCount  OBJECT-TYPE
     SYNTAX      Counter32
     MAX-ACCESS  read-only
     STATUS      current
     DESCRIPTION "The value of tnSvcEndPointTxActiveChangeCount indicates the
                  number of times active transmit change has taken place in this
                  endpoint."
     ::= { tnSvcEndPointEntry 17 }

 tnSvcEndPointTxActiveLastChange  OBJECT-TYPE
     SYNTAX      TimeStamp
     MAX-ACCESS  read-only
     STATUS      current
     DESCRIPTION "The value of tnSvcEndPointTxActiveLastChange indicates the
                  value of sysUpTime at the time of the last active transmit
                  change in this endpoint."
     ::= { tnSvcEndPointEntry 18 }

 tnSvcEndPointTxActiveUpTime OBJECT-TYPE
     SYNTAX      TimeTicks
     MAX-ACCESS  read-only
     STATUS      current
     DESCRIPTION "The value of tnSvcEndPointTxActiveUpTime indicates the active
                 'up' time (in hundredths of a second) of the end-point object
                 that is current transmit active."
     ::= { tnSvcEndPointEntry 19 }

 tnSvcEndPointMCEPId         OBJECT-TYPE
     SYNTAX      Unsigned32
     MAX-ACCESS  read-create
     STATUS      current
     DESCRIPTION "The value of tnSvcEndPointMCEPId specifies the multi-chassis
                  end-point identifier assigned to this endpoint."
     DEFVAL { 0 }
     ::= { tnSvcEndPointEntry 20 }

 tnSvcEndPointMCEPPeerAddrType OBJECT-TYPE
     SYNTAX      InetAddressType
     MAX-ACCESS  read-create
     STATUS      current
     DESCRIPTION "The value of tnSvcEndPointMCEPPeerAddrType specifies the
                  address type of tnSvcEndPointMCEPPeerAddr object.

                  An 'inconsistentValue' error is returned if this object is
                  set to non-default value when tnSvcEndPointMCEPId is set to
                  its default value.

                  An 'inconsistentValue' error is returned if this object is
                  set to non-default value when tnSvcEndPointMCEPPeerName is set
                  to its non-default value."
     DEFVAL { unknown }
     ::= { tnSvcEndPointEntry 21 }

 tnSvcEndPointMCEPPeerAddr OBJECT-TYPE
     SYNTAX      InetAddress
     MAX-ACCESS  read-create
     STATUS      current
     DESCRIPTION "The value of tnSvcEndPointMCEPPeerAddr specifies the
                  IP address of multi-chassis end-point peer.

                  An 'inconsistentValue' error is returned if this object is
                  set to non-default value when tnSvcEndPointMCEPId is set to
                  its default value.

                  An 'inconsistentValue' error is returned if this object is
                  set to non-default value when tnSvcEndPointMCEPPeerName is set
                  to its non-default value."
     DEFVAL { ''H }
     ::= { tnSvcEndPointEntry 22 }

 tnSvcEndPointMCEPPeerName OBJECT-TYPE
     SYNTAX      TNamedItemOrEmpty
     MAX-ACCESS  read-create
     STATUS      current
     DESCRIPTION "The value of tnSvcEndPointMCEPPeerName specifies the name of
                  multi-chassis end-point peer
                  TIMETRA-MC-REDUNDANCY-MIB::tmnxMcPeerName.

                  An 'inconsistentValue' error is returned if this object is
                  set to non-default value when tnSvcEndPointMCEPId is set to
                  its default value.

                  An 'inconsistentValue' error is returned if this object is
                  set to non-default value when tnSvcEndPointMCEPPeerAddrType and
                  tnSvcEndPointMCEPPeerAddr are set to their non-default values."
     DEFVAL { ''H }
     ::= { tnSvcEndPointEntry 23 }

 tnSvcEndPointBlockOnMeshFail     OBJECT-TYPE
     SYNTAX      TruthValue
     MAX-ACCESS  read-create
     STATUS      current
     DESCRIPTION "The value of tnSvcEndPointBlockOnMeshFail specifies that the
                  operational status of spoke-SDPs in the endpoint will be
                  affected by the operational status of associated mesh SDPs in
                  this service.

                 If there are no mesh SDPs in the service, value of this
                  object is ignored.

                  When this object is set to 'true', then the operational
                  status of the spoke-SDPs in the endpoint will be 'down' until
                  the operational status of at least one mesh SDP in this service
                  is 'up'.

                  When set to 'false', the operational status of the spoke-SDPs
                  in the endpoint will not be affected by the operational status
                  of any mesh SDPs in the service."
     DEFVAL      { false }
     ::= { tnSvcEndPointEntry 24 }

 tnSvcEndPointMCEPPsvModeActive        OBJECT-TYPE
     SYNTAX      TruthValue
     MAX-ACCESS  read-only
     STATUS      current
     DESCRIPTION
         "The value of tnSvcEndPointMCEPPsvModeActive indicates whether
         passive-mode behavior is currently active on this multi-chassis
         end-point."
     ::= { tnSvcEndPointEntry 25 }

 tnSvcEndPointStandbySigMaster OBJECT-TYPE
     SYNTAX      TruthValue
     MAX-ACCESS  read-create
     STATUS      current
     DESCRIPTION
         "The value of tnSvcEndPointStandbySigMaster specifies whether
          PW standby bit will be sent to T-LDP peer whenever spoke-SDPs
          of this endpoint are selected as standby."
     DEFVAL { false }
     ::= { tnSvcEndPointEntry 26 }

------------------------------------------
-- tnIesGrpIfTable
-- ----------------------------------------
-- tnIesGrpIfTable   OBJECT-TYPE
--     SYNTAX      SEQUENCE OF IesGrpIfEntry
--     MAX-ACCESS  not-accessible
--     STATUS      current
--     DESCRIPTION "The tnIesGrpIfTable has entry for each group interface
--                  configured on this system."
--     ::= { tnSvcObjs 21 }
--
-- tnIesGrpIfEntry   OBJECT-TYPE
--     SYNTAX      IesGrpIfEntry
--     MAX-ACCESS  not-accessible
--     STATUS      current
--     DESCRIPTION "Each row entry represents the attributes of a group interface.
--                  Entries are create/destroyed when entries in tnIesIfEntry with
--                  tnIesIfType 'group' are created/destroyed."
--     INDEX       { tnSysSwitchId, tnSvcId, tnIesIfIndex }
--     ::= { tnIesGrpIfTable 1 }
--
-- IesGrpIfEntry   ::=
--     SEQUENCE {
--         tnIesGrpIfRedInterface     InterfaceIndexOrZero,
--         tnIesGrpIfOperUpWhileEmpty TruthValue
--    }
--
-- tnIesGrpIfRedInterface    OBJECT-TYPE
--     SYNTAX      InterfaceIndexOrZero
--     MAX-ACCESS  read-write
--     STATUS      current
--     DESCRIPTION "The value of tnIesGrpIfRedInterface specifies the ifIndex
--                  of the redundant interface this group interface is tied to.
--                  The interface pointed to by this object must be of
--                  type 'redundant'."
--     DEFVAL      { 0 }
--     ::= { tnIesGrpIfEntry 1 }
--
-- tnIesGrpIfOperUpWhileEmpty    OBJECT-TYPE
--     SYNTAX      TruthValue
--     MAX-ACCESS  read-write
--     STATUS      current
--     DESCRIPTION "The value of tnIesGrpIfOperUpWhileEmpty specifies the
--                  whether that operational status of the the IES group
--                  interface, as indicated by tnIesIfOperStatus, should have
--                  a value of 'up' even when there are no SAPs on the
--                  group interface.
--
--                  If the value of tnIesGrpIfOperUpWhileEmpty is 'true', the
--                  value of tnIesIfOperStatus for the IES group interface will
--                  be 'up' when there are no SAPs on the group interface. When
--                  the value of tnIesGrpIfOperUpWhileEmpty is 'false', the value
--                  of tnIesIfOperStatus will depend on the operational state of
--                  the SAPs on the group interface. The value of
--                  tnIesGrpIfOperUpWhileEmpty will be ignored when there are
--                  SAPs on the IES group interface."
--     DEFVAL      { false }
--     ::= { tnIesGrpIfEntry 2 }

-- ----------------------------------------
-- tnSvcPEDiscoveryPolicyTable
-- ----------------------------------------
-- tnSvcPEDiscoveryPolicyTable  OBJECT-TYPE
--     SYNTAX        SEQUENCE OF TnSvcPEDiscoveryPolicyEntry
--     MAX-ACCESS    not-accessible
--     STATUS        current
--     DESCRIPTION   "The tnSvcPEDiscoveryPolicyTable has an entry for each PE policy."
--     ::= { tnSvcObjs 22 }
--
-- tnSvcPEDiscoveryPolicyEntry  OBJECT-TYPE
--     SYNTAX      TnSvcPEDiscoveryPolicyEntry
--     MAX-ACCESS  not-accessible
--     STATUS      current
--     DESCRIPTION
--         "tnSvcPEDiscoveryPolicyEntry is an entry (conceptual row) in the
--          tnSvcPEDiscoveryPolicyTable. Each entry represents the configuration
--          of a PE Discovery Policy.
--
--          Entries in this table can be created and deleted via SNMP SET
--          operations to tnSvcPEDiscoveryPolicyRowStatus."
--     INDEX {tnSysSwitchId, IMPLIED tnSvcPEDiscoveryPolicyName}
--     ::= { tnSvcPEDiscoveryPolicyTable 1 }
--
-- TnSvcPEDiscoveryPolicyEntry ::= SEQUENCE {
--             tnSvcPEDiscoveryPolicyName          TNamedItem,
--             tnSvcPEDiscoveryPolicyRowStatus     RowStatus,
--             tnSvcPEDiscoveryPolicyPassword      OCTET STRING,
--             tnSvcPEDiscoveryPolicyInterval      Unsigned32,
--             tnSvcPEDiscoveryPolicyTimeout       Unsigned32
-- }
--
-- tnSvcPEDiscoveryPolicyName       OBJECT-TYPE
--     SYNTAX           TNamedItem
--     MAX-ACCESS       not-accessible
--     STATUS           current
--     DESCRIPTION
--         "The value of the object tnSvcPEDiscoveryPolicyName specifies the
--          RADIUS PE Discovery Policy name."
--     ::= { tnSvcPEDiscoveryPolicyEntry 1 }
--
-- tnSvcPEDiscoveryPolicyRowStatus OBJECT-TYPE
--     SYNTAX      RowStatus
--     MAX-ACCESS  read-create
--     STATUS      current
--     DESCRIPTION
--         "tnSvcPEDiscoveryPolicyRowStatus controls the creation and deletion
--          of rows in the table.
--
--          To create a row in the tnSvcPEDiscoveryPolicyTable,
--          set tnSvcPEDiscoveryPolicyRowStatus to 'createAndGo'. All objects will take
--          on default values and the agent will change tnSvcPEDiscoveryPolicyRowStatus
--          to 'active'.
--
--          To delete a row in the tnSvcPEDiscoveryPolicyTable, set
--          tnSvcPEDiscoveryPolicyRowStatus to 'delete'."
--     ::= { tnSvcPEDiscoveryPolicyEntry 2 }
--
-- tnSvcPEDiscoveryPolicyPassword  OBJECT-TYPE
--     SYNTAX      OCTET STRING (SIZE(0..32))
--     MAX-ACCESS  read-create
--     STATUS      current
--     DESCRIPTION
--         "The value of tnSvcPEDiscoveryPolicyPassword specifies the password that is
--          used when contacting the RADIUS server for VPLS auto-discovery.
--
--
--          The value of tnSvcPEDiscPolServerSecret cannot be set to an empty
--          string.  GETs and GETNEXTs on this variable return an empty string."
--     DEFVAL { ''H }
--     ::= { tnSvcPEDiscoveryPolicyEntry 3 }
--
-- tnSvcPEDiscoveryPolicyInterval  OBJECT-TYPE
--     SYNTAX      Unsigned32 (1..30)
--     UNITS       "minutes"
--     MAX-ACCESS  read-create
--     STATUS      current
--     DESCRIPTION
--         "The value of tnSvcPEDiscoveryPolicyInterval specifies the polling
--          interval for Radius PE discovery in minutes."
--     DEFVAL { 5 }
--     ::= { tnSvcPEDiscoveryPolicyEntry 4 }
--
-- tnSvcPEDiscoveryPolicyTimeout  OBJECT-TYPE
--     SYNTAX      Unsigned32 (1..90)
--     UNITS       "seconds"
--     MAX-ACCESS  read-create
--     STATUS      current
--     DESCRIPTION
--         "The value of tnSvcPEDiscoveryPolicyTimeout specifies the number of
--          seconds to wait before timing out a RADIUS server."
--     DEFVAL { 3 }
--     ::= { tnSvcPEDiscoveryPolicyEntry 5 }

-- ----------------------------------------
-- tnSvcPEDiscoveryPolicyServerTable
-- ----------------------------------------
-- tnSvcPEDiscPolServerTable OBJECT-TYPE
--     SYNTAX      SEQUENCE OF TnSvcPEDiscPolServerEntry
--     MAX-ACCESS  not-accessible
--     STATUS      current
--     DESCRIPTION
--         "The tnSvcPEDiscPolServerTable has an entry for each RADIUS server.
--          The table can have up to a maximum of 5 entries."
-- ::= { tnSvcObjs 23 }
--
-- tnSvcPEDiscPolServerEntry OBJECT-TYPE
--     SYNTAX      TnSvcPEDiscPolServerEntry
--     MAX-ACCESS  not-accessible
--     STATUS      current
--     DESCRIPTION
--         "tnSvcPEDiscPolServerEntry is an entry (conceptual row) in the
--          tnSvcPEDiscPolServerTable. Each entry represents the configuration
--          for a RADIUS server.
--
--          Entries in this table can be created and deleted via SNMP SET
--          operations to tnSvcPEDiscPolServerRowStatus."
--     INDEX {tnSysSwitchId, tnSvcPEDiscPolServerIndex,
--              IMPLIED tnSvcPEDiscoveryPolicyName }
--     ::= { tnSvcPEDiscPolServerTable 1 }
--
-- TnSvcPEDiscPolServerEntry ::= SEQUENCE {
--     tnSvcPEDiscPolServerIndex           Unsigned32,
--     tnSvcPEDiscPolServerRowStatus       RowStatus,
--     tnSvcPEDiscPolServerAddressType     InetAddressType,
--     tnSvcPEDiscPolServerAddress         InetAddress,
--     tnSvcPEDiscPolServerSecret          OCTET STRING,
--     tnSvcPEDiscPolServerOperStatus      ServiceOperStatus,
--     tnSvcPEDiscPolServerPort            Unsigned32
-- }
--
-- tnSvcPEDiscPolServerIndex OBJECT-TYPE
--     SYNTAX      Unsigned32 (1..5)
--     MAX-ACCESS  not-accessible
--     STATUS      current
--     DESCRIPTION
--         "The tnSvcPEDiscPolServerIndex indicates the unique value which
--          identifies a specific radius server."
--     ::= { tnSvcPEDiscPolServerEntry 1 }
--
-- tnSvcPEDiscPolServerRowStatus OBJECT-TYPE
--     SYNTAX      RowStatus
--     MAX-ACCESS  read-create
--     STATUS      current
--     DESCRIPTION
--         "tnSvcPEDiscPolServerRowStatus controls the creation and deletion
--          of rows in the table.
--
--          To create a row in the tnSvcPEDiscPolServerTable,
--          set tnSvcPEDiscPolServerRowStatus to 'createAndGo'. All objects
--          except tnSvcPEDiscPolServerSecret will take
--          on default values and the agent will change tnSvcPEDiscPolServerRowStatus
--          to 'active'.  A value for tnSvcPEDiscPolServerSecret must be always specified
--          or else the row creation will fail.
--
--          To delete a row in the tnSvcPEDiscPolServerTable, set
--          tmnxRadiusServerRowStatus to 'delete'."
--     ::= { tnSvcPEDiscPolServerEntry 2 }
--
-- tnSvcPEDiscPolServerAddressType OBJECT-TYPE
--     SYNTAX      InetAddressType
--     MAX-ACCESS  read-create
--     STATUS      current
--     DESCRIPTION
--         "The value of tnSvcPEDiscPolServerAddressType is used to configure
--          the address type of tnSvcPEDiscPolServerAddress address."
--     DEFVAL { unknown }
--     ::= { tnSvcPEDiscPolServerEntry 3 }
--
-- tnSvcPEDiscPolServerAddress OBJECT-TYPE
--     SYNTAX      InetAddress
--     MAX-ACCESS  read-create
--     STATUS      current
--     DESCRIPTION
--         "The value of tnSvcPEDiscPolServerAddress is used to configure the
--          IP address of the RADIUS server."
--     DEFVAL { ''H }
--     ::= { tnSvcPEDiscPolServerEntry 4 }
--
-- tnSvcPEDiscPolServerSecret OBJECT-TYPE
--     SYNTAX      OCTET STRING (SIZE(0..20))
--     MAX-ACCESS  read-create
--     STATUS      current
--     DESCRIPTION
--         "The tnSvcPEDiscPolServerSecret is used to configure the secret key
--          associated with the RADIUS server.
--
--          The value of tnSvcPEDiscPolServerSecret cannot be set to an empty
--          string.  GETs and GETNEXTs on this variable return an empty string."
--     ::= { tnSvcPEDiscPolServerEntry 5 }
--
-- tnSvcPEDiscPolServerOperStatus OBJECT-TYPE
--     SYNTAX      ServiceOperStatus
--     MAX-ACCESS  read-only
--     STATUS      current
--     DESCRIPTION
--         "The tnSvcPEDiscPolServerOperStatus indicates the current status
--          of the RADIUS server."
--     ::= { tnSvcPEDiscPolServerEntry 6 }
--
-- tnSvcPEDiscPolServerPort  OBJECT-TYPE
--     SYNTAX      Unsigned32 (1..65535)
--     MAX-ACCESS  read-create
--     STATUS      current
--     DESCRIPTION
--         "The tnSvcPEDiscPolServerPort is used to configure the UDP port
--          number on which to contact the RADIUS server."
--      DEFVAL { 1812 }
--     ::= { tnSvcPEDiscPolServerEntry 7 }

-- ------------------------------
-- Service Whole saler table
-- ------------------------------
-- tnSvcWholesalerInfoTable OBJECT-TYPE
--     SYNTAX      SEQUENCE OF TnSvcWholesalerInfoEntry
--     MAX-ACCESS  not-accessible
--     STATUS      current
--     DESCRIPTION
--         "The tnSvcWholesalerInfoTable has an entry for each wholesaler service
--          associated with a retailer service on this system."
--     ::= { tnSvcObjs 24 }
--
-- tnSvcWholesalerInfoEntry    OBJECT-TYPE
--     SYNTAX      TnSvcWholesalerInfoEntry
--     MAX-ACCESS  not-accessible
--     STATUS      current
--     DESCRIPTION
--         "Each row entry represents the attributes of a wholesaler-retailer
--          pairing. Entries are created/destroyed when forwarding interfaces
--          are defined."
--     INDEX { tnSysSwitchId, tnSvcId, tnSvcWholesalerID }
--     ::= { tnSvcWholesalerInfoTable 1}
--
-- TnSvcWholesalerInfoEntry ::= SEQUENCE
--     {
--         tnSvcWholesalerID                 TmnxServId,
--         tnSvcWholesalerNumStaticHosts     Unsigned32,
--         tnSvcWholesalerNumDynamicHosts    Unsigned32,
--         tnSvcWholesalerNumDhcpLeaseStates Unsigned32,
--         tnSvcWholesalerNumPppoeSessions   Unsigned32,
--         tnSvcWholesalerNumArpHosts        Unsigned32
--     }
--
-- tnSvcWholesalerID        OBJECT-TYPE
--     SYNTAX      TmnxServId
--     MAX-ACCESS  not-accessible
--     STATUS      current
--     DESCRIPTION
--         "The value of tnSvcWholesalerID is used to specify the service ID of the
--          wholesaler."
--     ::= { tnSvcWholesalerInfoEntry 1 }
--
-- tnSvcWholesalerNumStaticHosts        OBJECT-TYPE
--     SYNTAX      Unsigned32
--     MAX-ACCESS  read-only
--     STATUS      current
--     DESCRIPTION
--         "The value of tnSvcWholesalerNumStaticHosts indicates the number of
--          static hosts in the wholesaler indicated by tnSvcWholesalerID that
--          belong to subnets of the retailer service."
--     ::= { tnSvcWholesalerInfoEntry 2 }
--
-- tnSvcWholesalerNumDynamicHosts        OBJECT-TYPE
--     SYNTAX      Unsigned32
--     MAX-ACCESS  read-only
--     STATUS      current
--     DESCRIPTION
--         "The value of tnSvcWholesalerNumDynamicHosts indicates the number of
--          dynamic hosts in the wholesaler indicated by tnSvcWholesalerID that
--          belong to subnets of the retailer service."
--     ::= { tnSvcWholesalerInfoEntry 3 }
--
-- tnSvcWholesalerNumDhcpLeaseStates     OBJECT-TYPE
--     SYNTAX      Unsigned32
--     MAX-ACCESS  read-only
--     STATUS      current
--     DESCRIPTION
--         "The value of tnSvcWholesalerNumDhcpLeaseStates indicates the number of
--          DHCP lease states in the wholesaler indicated by tnSvcWholesalerID that
--          belong to subnets of the retailer service."
--     ::= { tnSvcWholesalerInfoEntry 4 }
--
-- tnSvcWholesalerNumPppoeSessions       OBJECT-TYPE
--     SYNTAX      Unsigned32
--     MAX-ACCESS  read-only
--     STATUS      current
--     DESCRIPTION
--         "The value of tnSvcWholesalerNumPppoeSessions indicates the number of
--          PPPoE sessions in the wholesaler indicated by tnSvcWholesalerID that
--          belong to subnets of the retailer service."
--     ::= { tnSvcWholesalerInfoEntry 5 }
--
-- tnSvcWholesalerNumArpHosts            OBJECT-TYPE
--     SYNTAX      Unsigned32
--     MAX-ACCESS  read-only
--     STATUS      current
--     DESCRIPTION
--         "The value of tnSvcWholesalerNumArpHosts indicates the number of
--          ARP hosts in the wholesaler indicated by tnSvcWholesalerID that
--          belong to subnets of the retailer service."
--     ::= { tnSvcWholesalerInfoEntry 6 }

-- ----------------------------------------
-- tnSvcDhcpLeaseStateActionTable
-- ----------------------------------------
-- tnSvcDhcpLeaseStateActionTable OBJECT-TYPE
--     SYNTAX          SEQUENCE OF TnSvcDhcpLeaseStateActionEntry
--     MAX-ACCESS      not-accessible
--     STATUS          current
--     DESCRIPTION     "The tnSvcDhcpLeaseStateActionTable augments the
--                      tnSvcDhcpLeaseStateTable.
--                      The table allows the operator to perform actions on the
--                      lease state."
--     ::= { tnSvcObjs 25 }
--
-- tnSvcDhcpLeaseStateActionEntry OBJECT-TYPE
--     SYNTAX          TnSvcDhcpLeaseStateActionEntry
--     MAX-ACCESS      not-accessible
--     STATUS          current
--     DESCRIPTION     "Each row entry contains parameters that allow to perform
--                      an action on the corresponding lease-state."
--     AUGMENTS        { tnSvcDhcpLeaseStateEntry }
--     ::= { tnSvcDhcpLeaseStateActionTable 1 }
--
-- TnSvcDhcpLeaseStateActionEntry ::=
--     SEQUENCE {
--         tnSvcDhcpLseStateForceRenew        TruthValue
--     }
--
-- tnSvcDhcpLseStateForceRenew OBJECT-TYPE
--     SYNTAX          TruthValue
--     MAX-ACCESS      read-write
--     STATUS          current
--     DESCRIPTION     "The value of tnSvcDhcpLseStateForceRenew allows to force the
--                      DHCP client to renew its lease.
--
--                      When the value of this object is set to 'true', the system
--                      will send a forcerenew DHCP message to the client.
--
--                      GETs and GETNEXTs on this variable return false."
--     DEFVAL          { false }
--     ::= { tnSvcDhcpLeaseStateActionEntry 1 }

-- ----------------------------------------
--  Nokia 7x50 SR series Service Itf DHCP6 msg type Stats Table
-- ----------------------------------------
-- tnSvcIfDHCP6MsgStatTable OBJECT-TYPE
--     SYNTAX  SEQUENCE OF TnSvcIfDHCP6MsgStatEntry
--     MAX-ACCESS  not-accessible
--     STATUS      current
--     DESCRIPTION
--         "The vRtrDHCP6MsgStatTable has an entry for each interface defined
--          in a service for which DHCP6 can be enabled."
--     ::= { tnSvcObjs 26 }
--
-- tnSvcIfDHCP6MsgStatEntry  OBJECT-TYPE
--     SYNTAX      TnSvcIfDHCP6MsgStatEntry
--     MAX-ACCESS  not-accessible
--     STATUS      current
--     DESCRIPTION
--         "Each row entry represents a collection of counters for each DHCP6
--          message type for an interface in a service.
--
--         Entries cannot be created and deleted via SNMP SET operations."
--     INDEX { tnSysSwitchId, tnSvcId,
--             tnIesIfIndex }
--     ::= { tnSvcIfDHCP6MsgStatTable 1 }
--
-- TnSvcIfDHCP6MsgStatEntry ::=
--      SEQUENCE {
--          tnSvcIfDHCP6MsgStatsLstClrd  TimeStamp,
--          tnSvcIfDHCP6MsgStatsRcvd     Gauge32,
--          tnSvcIfDHCP6MsgStatsSent     Gauge32,
--          tnSvcIfDHCP6MsgStatsDropped  Gauge32
--      }
--
-- tnSvcIfDHCP6MsgStatsLstClrd  OBJECT-TYPE
--     SYNTAX      TimeStamp
--     MAX-ACCESS  read-only
--     STATUS      current
--     DESCRIPTION
--         "The value of tnSvcIfDHCP6MsgStatsLstClrd indicates the sysUpTime
--          when the counters of this row were last reset. A value of zero for
--          this object indicates that the counters have not been reset since the
--          system has last been initialized."
--     ::= { tnSvcIfDHCP6MsgStatEntry 1 }
--
-- tnSvcIfDHCP6MsgStatsRcvd  OBJECT-TYPE
--     SYNTAX      Gauge32
--     MAX-ACCESS  read-only
--     STATUS      current
--     DESCRIPTION
--         "The value of tnSvcIfDHCP6MsgStatsRcvd indicates the number of
--          DHCP6 packets were received on this service interface."
--     ::= { tnSvcIfDHCP6MsgStatEntry 2 }
--
-- tnSvcIfDHCP6MsgStatsSent  OBJECT-TYPE
--     SYNTAX      Gauge32
--     MAX-ACCESS  read-only
--     STATUS      current
--     DESCRIPTION
--         "The value of tnSvcIfDHCP6MsgStatsSent indicates the number of
--          DHCP6 packets were sent on this service interface."
--     ::= { tnSvcIfDHCP6MsgStatEntry 3 }
--
-- tnSvcIfDHCP6MsgStatsDropped  OBJECT-TYPE
--     SYNTAX      Gauge32
--     MAX-ACCESS  read-only
--     STATUS      current
--     DESCRIPTION
--         "The value of tnSvcIfDHCP6MsgStatsDropped indicates the number of
--          DHCP6 packets were dropped on this service interface."
--     ::= { tnSvcIfDHCP6MsgStatEntry 4 }

-- ----------------------------------------
-- TLS PBB Information Table
-- ----------------------------------------
tnSvcTlsBackboneInfoTable OBJECT-TYPE
    SYNTAX          SEQUENCE OF TnSvcTlsBackboneInfoEntry
    MAX-ACCESS      not-accessible
    STATUS          current
    DESCRIPTION     "The tnSvcTlsBackboneInfoTable augments the tnSvcTlsInfoTable.
                     The table allows the operator to modify attributes of the
                     Provider Backbone Bridging feature."
    ::= { tnSvcObjs 27 }

tnSvcTlsBackboneInfoEntry OBJECT-TYPE
    SYNTAX          TnSvcTlsBackboneInfoEntry
    MAX-ACCESS      not-accessible
    STATUS          current
    DESCRIPTION     "Each row entry contains objects that allows the
                     modification of the Provider Backbone Bridging feature
                     for a specific TLS service"
    AUGMENTS        { tnSvcTlsInfoEntry }
    ::= { tnSvcTlsBackboneInfoTable 1 }

TnSvcTlsBackboneInfoEntry ::=
    SEQUENCE {
        tnSvcTlsBackboneSrcMac             MacAddress,
        tnSvcTlsBackboneVplsSvcId          TmnxServId,
        tnSvcTlsBackboneVplsSvcISID        SvcISID,
        tnSvcTlsBackboneOperSrcMac         MacAddress,
        tnSvcTlsBackboneOperVplsSvcISID    SvcISID,
        tnSvcTlsBackboneLDPMacFlush        TruthValue,
        tnSvcTlsBackboneVplsStp            TmnxEnabledDisabled,
        tnSvcTlsBackboneLDPMacFlushNotMine TruthValue,
        tnSvcTlsBackboneUseSapBMac         TruthValue
    }

tnSvcTlsBackboneSrcMac OBJECT-TYPE
    SYNTAX          MacAddress
    MAX-ACCESS      read-write
    STATUS          current
    DESCRIPTION     "The value of tnSvcTlsBackboneSrcMac specifies the Backbone
                     Source MAC-Address for Provider Backbone Bridging packets.
                     If not provisioned, it defaults to the loopback chassis
                     MAC-Address.

                     An inconsistentValue error is returned if an attempt
                     is made to set this object when the value of
                     tnSvcVplsType is not 'bVpls'."
    DEFVAL { '000000000000'h }
    ::= { tnSvcTlsBackboneInfoEntry 1 }

tnSvcTlsBackboneVplsSvcId OBJECT-TYPE
    SYNTAX          TmnxServId
    MAX-ACCESS      read-write
    STATUS          current
    DESCRIPTION     "The value of tnSvcTlsBackboneVplsSvcId specifies the
                     Backbone-VPLS service associated with this service.

                     An inconsistentValue error is returned if an attempt
                     is made to set this object when the value of
                     tnSvcVplsType is not 'iVpls'.

                     Setting the value of this object to its default
                     value will also set the value of
                     tnSvcTlsBackboneVplsStp to its default value."
    DEFVAL          { 0 }
    ::= { tnSvcTlsBackboneInfoEntry 2 }

tnSvcTlsBackboneVplsSvcISID OBJECT-TYPE
    SYNTAX          SvcISID
    MAX-ACCESS      read-write
    STATUS          current
    DESCRIPTION     "The value of the object tnSvcTlsBackboneVplsSvcISID specifies
                     a 24 bit (0..16777215) service instance identifier for
                     this service. As part of the Provider Backbone Bridging
                     frames, it is used at the destination PE as a
                     demultiplexor field.

                     The default value of -1 is used to indicate the value of
                     this object is un-specified.

                     This object must be set along with tnSvcTlsBackboneVplsSvcId.
                     An inconsistentValue error is returned if an attempt
                     is made to set this object when the value of
                     tnSvcVplsType is not 'iVpls'."
    DEFVAL          { -1 }
    ::= { tnSvcTlsBackboneInfoEntry 3 }

tnSvcTlsBackboneOperSrcMac OBJECT-TYPE
    SYNTAX          MacAddress
    MAX-ACCESS      read-only
    STATUS          current
    DESCRIPTION     "The value of tnSvcTlsBackboneOperSrcMac indicates the
                     operational Backbone Source MAC-Address for Provider
                     Backbone Bridging packets."
    ::= { tnSvcTlsBackboneInfoEntry 4 }

tnSvcTlsBackboneOperVplsSvcISID OBJECT-TYPE
    SYNTAX          SvcISID
    MAX-ACCESS      read-only
    STATUS          current
    DESCRIPTION     "The value of tnSvcTlsBackboneOperVplsSvcISID indicates
                     operational value of service instance identifier used for
                     this service. As part of the Provider Backbone Bridging
                     frames, it is used at the destination PE as a
                     demultiplexor field."
    ::= { tnSvcTlsBackboneInfoEntry 5 }

tnSvcTlsBackboneLDPMacFlush OBJECT-TYPE
    SYNTAX          TruthValue
    MAX-ACCESS      read-write
    STATUS          current
    DESCRIPTION     "The value of tnSvcTlsBackboneLDPMacFlush specifies whether
                     'LDP MAC withdraw all from me' message received in the
                     'iVpls' domain should attempt to generate a new 'LDP MAC
                     withdraw all from me' message in the 'bVpls' domain.
                     Generation of the 'LDP MAC withdraw all from me'
                     message is still constrained by the tnSvcTlsMacFlushOnFail
                     value in the 'bVpls'.

                     An inconsistentValue error is returned if an attempt
                     is made to set this object when the value of
                     tnSvcVplsType is not 'iVpls'."
    DEFVAL          { false }
    ::= { tnSvcTlsBackboneInfoEntry 6 }

tnSvcTlsBackboneVplsStp OBJECT-TYPE
    SYNTAX          TmnxEnabledDisabled
    MAX-ACCESS      read-write
    STATUS          current
    DESCRIPTION     "The value of tnSvcTlsBackboneVplsStp specifies whether
                     STP is enabled on the Backbone VPLS specified by
                     tnSvcTlsBackboneVplsSvcId.

                     An inconsistentValue error is returned if an attempt
                     is made to set this object when the value of
                     tnSvcVplsType is not 'iVpls' or if an attempt is made
                     to set this object to enable when the value of
                     tnSvcTlsBackboneVplsSvcId is set to the default.

                     The value of this object is set to disable
                     when the value of tnSvcTlsBackboneVplsSvcId is set to
                     default."
    DEFVAL          { disabled }
    ::= { tnSvcTlsBackboneInfoEntry 7 }

tnSvcTlsBackboneLDPMacFlushNotMine OBJECT-TYPE
    SYNTAX          TruthValue
    MAX-ACCESS      read-write
    STATUS          current
    DESCRIPTION     "The value of tnSvcTlsBackboneLDPMacFlush specifies whether
                     'LDP MAC withdraw' message received in the 'iVpls' domain
                     should attempt to generate a new 'LDP MAC withdraw' message
                     in the 'bVpls' domain. Generation of the 'LDP MAC withdraw'
                     message is still constrained by the tnSvcTlsMacFlushOnFail
                     value in the 'bVpls'.

                     An inconsistentValue error is returned if an attempt
                     is made to set this object when the value of
                     tnSvcVplsType is not 'iVpls'."
    DEFVAL          { false }
    ::= { tnSvcTlsBackboneInfoEntry  8}

tnSvcTlsBackboneUseSapBMac OBJECT-TYPE
    SYNTAX          TruthValue
    MAX-ACCESS      read-write
    STATUS          current
    DESCRIPTION     "The value of tnSvcTlsBackboneUseSapBMac specifies
                     whether to enable dual-homing to use source Backbone
                     MAC-Address allocated for multi-homed SAPs (assigned
                     to an MC-LAG) in the related service with tnSvcVplsType
                     set to 'i-vpls' or with tnSvcType set to 'epipe'."
    DEFVAL { false }
    ::= { tnSvcTlsBackboneInfoEntry 9 }

-- ------------------------------------
-- TLS MFIB Table
-- ------------------------------------
tnTlsMFibTable OBJECT-TYPE
    SYNTAX          SEQUENCE OF TlsMFibEntry
    MAX-ACCESS      not-accessible
    STATUS          current
    DESCRIPTION     "tnTlsMFibTable contains the Multicast FIB for this Tls."
    ::= { tnSvcObjs 28 }

tnTlsMFibEntry OBJECT-TYPE
    SYNTAX          TlsMFibEntry
    MAX-ACCESS      not-accessible
    STATUS          current
    DESCRIPTION     "An entry in the tnTlsMFibTable. Each entry indicates
                     whether  traffic from a certain source to a certain
                     multicast destination (group) needs to be forwarded or
                     blocked on the indicated SAP/SDP."
    INDEX           { tnSysSwitchId,  tnSvcId,
                      tnTlsMFibEntryType,
                      tnTlsMFibGrpMacAddr,
                      tnTlsMFibGrpInetAddrType,
                      tnTlsMFibGrpInetAddr,
                      tnTlsMFibSrcInetAddrType,
                      tnTlsMFibSrcInetAddr,
                      tnTlsMFibLocale,
                      tnTlsMFibPortId,
                      tnTlsMFibEncapValue,
                      tnTlsMFibSdpId,
                      tnTlsMFibVcId }
    ::= { tnTlsMFibTable 1 }

TlsMFibEntry ::=
    SEQUENCE {
        tnTlsMFibEntryType            INTEGER,
        tnTlsMFibGrpMacAddr           MacAddress,
        tnTlsMFibGrpInetAddrType      InetAddressType,
        tnTlsMFibGrpInetAddr          InetAddress,
        tnTlsMFibSrcInetAddrType      InetAddressType,
        tnTlsMFibSrcInetAddr          InetAddress,
        tnTlsMFibLocale               MfibLocation,
        tnTlsMFibPortId               TmnxPortID,
        tnTlsMFibEncapValue           TmnxEncapVal,
        tnTlsMFibSdpId                SdpId,
        tnTlsMFibVcId                 Unsigned32,
        tnTlsMFibFwdOrBlk             MfibGrpSrcFwdOrBlk,
        tnTlsMFibSvcId                TmnxServId
    }

tnTlsMFibEntryType OBJECT-TYPE
    SYNTAX          INTEGER {
                        ipBased  (1),
                        macBased (2)
                    }
    MAX-ACCESS      not-accessible
    STATUS          current
    DESCRIPTION     "The value of the object tnTlsMFibEntryType indicates
                     the type of this tnTlsMFibEntry.

                     - macBased: entry used for macBased multicast, as for
                                 MLD-snooping and 802.1ak MMRP.
                     - ipBased:  entry used for ip_based multicast, as for
                                 IGMP-snooping and PIM-snooping."
    ::= { tnTlsMFibEntry 1 }

tnTlsMFibGrpMacAddr OBJECT-TYPE
    SYNTAX          MacAddress
    MAX-ACCESS      not-accessible
    STATUS          current
    DESCRIPTION     "The value of the object tnTlsMFibGrpMacAddr indicates the
                     MAC address for which this table entry contains
                     information.

                     This value is only meaningful if the value of
                     tnTlsMFibEntryType is 'macBased (2)'."
    ::= { tnTlsMFibEntry 2 }

tnTlsMFibGrpInetAddrType OBJECT-TYPE
    SYNTAX          InetAddressType
    MAX-ACCESS      not-accessible
    STATUS          current
    DESCRIPTION     "The value of the object tnTlsMFibGrpInetAddrType indicates
                     the type of tnTlsMFibGrpInetAddr."
    ::= { tnTlsMFibEntry 3 }

tnTlsMFibGrpInetAddr OBJECT-TYPE
    SYNTAX          InetAddress (SIZE(0|4|16))
    MAX-ACCESS      not-accessible
    STATUS          current
    DESCRIPTION     "The value of the object tnTlsMFibGrpInetAddr indicates
                     the multicast destination IP address for which this table
                     entry contains information."
    ::= { tnTlsMFibEntry 4 }

tnTlsMFibSrcInetAddrType OBJECT-TYPE
    SYNTAX          InetAddressType
    MAX-ACCESS      not-accessible
    STATUS          current
    DESCRIPTION     "The value of tnTlsMFibSrcInetAddrType indicates the type
                     of tnTlsMFibSrcInetAddr."
    ::= { tnTlsMFibEntry 5 }

tnTlsMFibSrcInetAddr OBJECT-TYPE
    SYNTAX          InetAddress (SIZE(0|4|16))
    MAX-ACCESS      not-accessible
    STATUS          current
    DESCRIPTION     "The value of tnTlsMFibSrcInetAddr indicates the unicast
                     source IP address for which this table entry contains
                     information."
    ::= { tnTlsMFibEntry 6 }

tnTlsMFibLocale OBJECT-TYPE
    SYNTAX          MfibLocation
    MAX-ACCESS      not-accessible
    STATUS          current
    DESCRIPTION     "The value of tnTlsMFibLocale indicates if the information in
                     this entry pertains to a 'sap' or to an 'sdp'."
    ::= { tnTlsMFibEntry 7 }

tnTlsMFibPortId OBJECT-TYPE
    SYNTAX          TmnxPortID
    MAX-ACCESS      not-accessible
    STATUS          current
    DESCRIPTION     "The value of tnTlsMFibPortId indicates, together with the
                     object tnTlsMFibEncapValue, the SAP for which this entry
                     contains information.

                     This value of this object is only meaningful when the
                     value of tnTlsMFibLocale is 'sap'. Otherwise it contains
                     the value 0."
    ::= { tnTlsMFibEntry 8 }

tnTlsMFibEncapValue OBJECT-TYPE
    SYNTAX          TmnxEncapVal
    MAX-ACCESS      not-accessible
    STATUS          current
    DESCRIPTION     "The value of tnTlsMFibEncapValue indicates, together with
                     the object tnTlsMFibPortId, the SAP for which this entry
                     contains information.

                     This value of this object is only meaningful when the
                     value of tnTlsMFibLocale is 'sap'. Otherwise it contains
                     the value 0."
    ::= { tnTlsMFibEntry 9 }

tnTlsMFibSdpId OBJECT-TYPE
    SYNTAX          SdpId
    MAX-ACCESS      not-accessible
    STATUS          current
    DESCRIPTION     "The value of tnTlsMFibSdpId indicates, together with
                     the object tnTlsMFibVcId, the SDP Binding for which this
                     entry contains information.

                     This value of this object is only meaningful when the
                     value of tnTlsMFibLocale is 'sdp'. Otherwise it contains
                     the value 0."
    ::= { tnTlsMFibEntry 10 }

tnTlsMFibVcId OBJECT-TYPE
    SYNTAX          Unsigned32
    MAX-ACCESS      not-accessible
    STATUS          current
    DESCRIPTION     " The value of tnTlsMFibVcId indicates, together with
                     the object tnTlsMFibSdpId, the SDP Binding for which this
                     entry contains information.

                     This value of this object is only meaningful when the
                     value of tnTlsMFibLocale is 'sdp'. Otherwise it contains
                     the value 0."
    ::= { tnTlsMFibEntry 11 }

tnTlsMFibFwdOrBlk OBJECT-TYPE
    SYNTAX          MfibGrpSrcFwdOrBlk
    MAX-ACCESS      read-only
    STATUS          current
    DESCRIPTION     "The value of tnTlsMFibFwdOrBlk indicates if traffic for the
                     indicated (S,G) pair will be blocked or forwarded on the
                     indicated SAP or SDP."
    ::= { tnTlsMFibEntry 12 }

tnTlsMFibSvcId OBJECT-TYPE
    SYNTAX          TmnxServId
    MAX-ACCESS      read-only
    STATUS          current
    DESCRIPTION     "The value of tnTlsMFibSvcId indicates the TLS service
                     to which the indicated SAP or SDP belongs."
    ::= { tnTlsMFibEntry 13 }

-- ----------------------------------------
-- TLS MFIB Statistics Table
-- ----------------------------------------
-- tnTlsMFibStatsTable OBJECT-TYPE
--     SYNTAX          SEQUENCE OF TlsMFibStatsEntry
--     MAX-ACCESS      not-accessible
--     STATUS          current
--     DESCRIPTION     "tnTlsMFibStatsTable contains statistics for the
--                      entries in the IPv4 Multicast FIB for this Tls. These
--                      statistics are collected by the forwarding engine."
--     ::= { tnSvcObjs 29 }
--
-- tnTlsMFibStatsEntry OBJECT-TYPE
--     SYNTAX          TlsMFibStatsEntry
--     MAX-ACCESS      not-accessible
--     STATUS          current
--     DESCRIPTION     "An entry in the tnTlsMFibStatsTable."
--     INDEX           { tnSysSwitchId,  tnSvcId,
--                       tnTlsMFibStatsEntryType,
--                       tnTlsMFibStatsGrpMacAddr,
--                       tnTlsMFibStatsGrpInetAddrType,
--                       tnTlsMFibStatsGrpInetAddr,
--                       tnTlsMFibStatsSrcInetAddrType,
--                       tnTlsMFibStatsSrcInetAddr }
--     ::= { tnTlsMFibStatsTable 1 }
--
-- TlsMFibStatsEntry ::=
--     SEQUENCE {
--         tnTlsMFibStatsEntryType        INTEGER,
--         tnTlsMFibStatsGrpMacAddr       MacAddress,
--         tnTlsMFibStatsGrpInetAddrType  InetAddressType,
--         tnTlsMFibStatsGrpInetAddr      InetAddress,
--         tnTlsMFibStatsSrcInetAddrType  InetAddressType,
--         tnTlsMFibStatsSrcInetAddr      InetAddress,
--         tnTlsMFibStatsForwardedPkts    Counter64,
--         tnTlsMFibStatsForwardedOctets  Counter64
--     }
--
-- tnTlsMFibStatsEntryType OBJECT-TYPE
--     SYNTAX          INTEGER {
--                         ipBased  (1),
--                         macBased (2)
--                     }
--     MAX-ACCESS      not-accessible
--     STATUS          current
--     DESCRIPTION     "The value of the object tnTlsMFibStatsEntryType indicates
--                      the type of this tnTlsMFibStatsEntry.
--
--                      - macBased: entry used for macBased multicast, as for
--                                  MLD-snooping and 802.1ak MMRP.
--                      - ipBased:  entry used for ip_based multicast, as for
--                                  IGMP-snooping and PIM-snooping."
--     ::= { tnTlsMFibStatsEntry 1 }
--
-- tnTlsMFibStatsGrpMacAddr OBJECT-TYPE
--     SYNTAX          MacAddress
--     MAX-ACCESS      not-accessible
--     STATUS          current
--     DESCRIPTION     "The value of tnTlsMFibStatsGrpMacAddr indicates the
--                      MAC address for which this table entry contains information.
--
--                      This value is only meaningful if the value of
--                      tnTlsMFibStatsEntryType is 'macBased (2)'."
--     ::= { tnTlsMFibStatsEntry 2 }
--
-- tnTlsMFibStatsGrpInetAddrType OBJECT-TYPE
--     SYNTAX          InetAddressType
--     MAX-ACCESS      not-accessible
--     STATUS          current
--     DESCRIPTION     "The value of tnTlsMFibStatsGrpInetAddrType indicates
--                      the type of tnTlsMFibStatsGrpInetAddr."
--     ::= { tnTlsMFibStatsEntry 3 }
--
-- tnTlsMFibStatsGrpInetAddr OBJECT-TYPE
--     SYNTAX          InetAddress (SIZE(0|4|16))
--     MAX-ACCESS      not-accessible
--     STATUS          current
--     DESCRIPTION     "The value of tnTlsMFibStatsGrpInetAddr indicates
--                      the multicast destination IP address for which this table
--                      entry contains information."
--     ::= { tnTlsMFibStatsEntry 4 }
--
-- tnTlsMFibStatsSrcInetAddrType OBJECT-TYPE
--     SYNTAX          InetAddressType
--     MAX-ACCESS      not-accessible
--     STATUS          current
--     DESCRIPTION     "The value of tnTlsMFibStatsSrcInetAddrType indicates
--                      the type of tnTlsMFibStatsSrcInetAddr."
--     ::= { tnTlsMFibStatsEntry 5 }
--
-- tnTlsMFibStatsSrcInetAddr OBJECT-TYPE
--     SYNTAX          InetAddress (SIZE(0|4|16))
--     MAX-ACCESS      not-accessible
--     STATUS          current
--     DESCRIPTION     "The value of tnTlsMFibStatsSrcInetAddr indicates the unicast
--                      source IP address for which this table entry contains
--                      information."
--     ::= { tnTlsMFibStatsEntry 6 }
--
-- tnTlsMFibStatsForwardedPkts OBJECT-TYPE
--     SYNTAX          Counter64
--     MAX-ACCESS      read-only
--     STATUS          current
--     DESCRIPTION     "The value of tnTlsMFibStatsForwardedPkts indicates
--                      the number of multicast packets that were forwarded
--                      to the SAPs and SDPs listed in the tnTlsMFibInfoTable."
--     ::= { tnTlsMFibStatsEntry 7 }
--
-- tnTlsMFibStatsForwardedOctets OBJECT-TYPE
--     SYNTAX          Counter64
--     MAX-ACCESS      read-only
--     STATUS          current
--     DESCRIPTION     "The value of tnTlsMFibStatsForwardedOctets indicates
--                      the number of octets that were forwarded to the SAPs
--                      and SDPs listed in the tnTlsMFibInfoTable."
--     ::= { tnTlsMFibStatsEntry 8 }

-- ----------------------------------------
-- TLS BGP Auto-Discovery Table
-- ----------------------------------------
tnSvcTlsBgpADTableLastChanged  OBJECT-TYPE
    SYNTAX          TimeStamp
    MAX-ACCESS      read-only
    STATUS          current
    DESCRIPTION     "The value of tnSvcTlsBgpADTableLastChanged indicates the
                     sysUpTime at the time of the last modification
                     of tnSvcTlsBgpADTable.

                     If no changes were made to the entry since the last
                     re-initialization of the local network management subsystem,
                     then this object contains a zero value.

                     This is currently not used and always returns 0."
    ::= { tnSvcObjs 30 }

-- tnSvcTlsBgpADTable OBJECT-TYPE
--     SYNTAX          SEQUENCE OF TnSvcTlsBgpADEntry
--     MAX-ACCESS      not-accessible
--     STATUS          current
--     DESCRIPTION     "tnSvcTlsBgpADTable contains entries for BGP Auto-Discovery
--                      in a VPLS service context."
--     ::= { tnSvcObjs 31 }
--
-- tnSvcTlsBgpADEntry    OBJECT-TYPE
--     SYNTAX          TnSvcTlsBgpADEntry
--     MAX-ACCESS      not-accessible
--     STATUS          current
--     DESCRIPTION     "A BGP Auto-Discovery entry in the tnSvcTlsBgpADTable."
--     INDEX           { tnSysSwitchId,  tnSvcId }
--     ::= { tnSvcTlsBgpADTable 1}
--
-- TnSvcTlsBgpADEntry ::=    SEQUENCE {
--     tnSvcTlsBgpADRowStatus           RowStatus,
--     tnSvcTlsBgpADLastChanged         TimeStamp,
--     tnSvcTlsBgpADVplsId              TmnxVPNRouteDistinguisher,
--     tnSvcTlsBgpADVsiPrefix           Unsigned32,
--     tnSvcTlsBgpADVsiRD               TmnxVPNRouteDistinguisher,
--     tnSvcTlsBgpADExportRteTarget     TNamedItemOrEmpty,
--     tnSvcTlsBgpADVsiExportPolicy1    TPolicyStatementNameOrEmpty,
--     tnSvcTlsBgpADVsiExportPolicy2    TPolicyStatementNameOrEmpty,
--     tnSvcTlsBgpADVsiExportPolicy3    TPolicyStatementNameOrEmpty,
--     tnSvcTlsBgpADVsiExportPolicy4    TPolicyStatementNameOrEmpty,
--     tnSvcTlsBgpADVsiExportPolicy5    TPolicyStatementNameOrEmpty,
--     tnSvcTlsBgpADImportRteTarget     TNamedItemOrEmpty,
--     tnSvcTlsBgpADVsiImportPolicy1    TPolicyStatementNameOrEmpty,
--     tnSvcTlsBgpADVsiImportPolicy2    TPolicyStatementNameOrEmpty,
--     tnSvcTlsBgpADVsiImportPolicy3    TPolicyStatementNameOrEmpty,
--     tnSvcTlsBgpADVsiImportPolicy4    TPolicyStatementNameOrEmpty,
--     tnSvcTlsBgpADVsiImportPolicy5    TPolicyStatementNameOrEmpty,
--     tnSvcTlsBgpADAdminStatus         TmnxEnabledDisabled
-- }
--
-- tnSvcTlsBgpADRowStatus        OBJECT-TYPE
--     SYNTAX          RowStatus
--     MAX-ACCESS      read-create
--     STATUS          current
--     DESCRIPTION     "The value of tnSvcTlsBgpADRowStatus is used for the
--                      creation and deletion of BGP Auto-Discovery
--                      context in a VPLS service."
--     ::= { tnSvcTlsBgpADEntry 1 }
--
-- tnSvcTlsBgpADLastChanged        OBJECT-TYPE
--     SYNTAX          TimeStamp
--     MAX-ACCESS      read-only
--     STATUS          current
--     DESCRIPTION     "The value of tnSvcTlsBgpADLastChanged indicates the
--                      sysUpTime at the time of the last modification of
--                      this entry.
--
--                      If no changes were made to the entry since the last
--                      re-initialization of the local network management
--                      subsystem, then this object contains a zero value."
--     ::= { tnSvcTlsBgpADEntry 2 }
--
-- tnSvcTlsBgpADVplsId        OBJECT-TYPE
--     SYNTAX          TmnxVPNRouteDistinguisher
--     MAX-ACCESS      read-create
--     STATUS          current
--     DESCRIPTION     "The value of tnSvcTlsBgpADVplsId specifies the globally
--                      unique VPLS-id for BGP Auto-Discovery in this VPLS
--                      service.
--
--                      The value of tnSvcTlsBgpADAdminStatus cannot be 'enabled'
--                      until a VPLS-id has been assigned which is not all zeros."
--     DEFVAL          { '0000000000000000'H }
--     ::= { tnSvcTlsBgpADEntry 3 }
--
-- tnSvcTlsBgpADVsiPrefix OBJECT-TYPE
--     SYNTAX          Unsigned32
--     MAX-ACCESS      read-create
--     STATUS          current
--     DESCRIPTION     "The value of tnSvcTlsBgpADVsiPrefix specifies the
--                      low-order 4 bytes used to compose the Virtual Switch
--                      Instance identifier (VSI-id) to use for NLRI in BGP
--                      Auto-Discovery in this VPLS service.
--
--                      If the value of tnSvcTlsBgpADVsiPrefix is 0, the
--                      system IP address will be used."
--     DEFVAL          { 0 }
--     ::= { tnSvcTlsBgpADEntry 4 }
--
-- tnSvcTlsBgpADVsiRD     OBJECT-TYPE
--     SYNTAX          TmnxVPNRouteDistinguisher
--     MAX-ACCESS      read-create
--     STATUS          current
--     DESCRIPTION     "The value of tnSvcTlsBgpADVsiRD specifies the high-order
--                      6 bytes used to compose the Virtual Switch Instance
--                      identifier (VSI-id) to use for NLRI in BGP Auto-Discovery
--                      in this VPLS service.
--
--                      If the value of tnSvcTlsBgpADVsiRD is 0x0000000000000000,
--                      the lower 6 bytes of the VPLS-id, as specified by
--                      tnSvcTlsBgpADVplsId, will be used."
--     DEFVAL          { '0000000000000000'H }
--     ::= { tnSvcTlsBgpADEntry 5 }
--
-- tnSvcTlsBgpADExportRteTarget       OBJECT-TYPE
--     SYNTAX          TNamedItemOrEmpty
--     MAX-ACCESS      read-create
--     STATUS          current
--     DESCRIPTION     "The value of tnSvcTlsBgpADExportRteTarget specifies the
--                      extended community name for the default export policy
--                      to use for BGP Auto-Discovery in this VPLS service.
--
--                      This object cannot be set to a non-empty if
--                      tnSvcTlsBgpADExportRteTarget has a non-empty value,
--                      otherwise an 'inconsistentValue' error will be
--                      returned."
--     DEFVAL          { "" }
--     ::= { tnSvcTlsBgpADEntry 6 }
--
-- tnSvcTlsBgpADVsiExportPolicy1  OBJECT-TYPE
--     SYNTAX          TPolicyStatementNameOrEmpty
--     MAX-ACCESS      read-create
--     STATUS          current
--     DESCRIPTION    "The value of tnSvcTlsBgpADVsiExportPolicy1 specifies the
--                     name of the first VSI export policy to be used for BGP
--                     Auto-Discovery in this VPLS service.
--
--                     If multiple policy names are specified, the policies are
--                     evaluated in the order they are specified.  The first
--                     policy that matches is applied.
--
--                     The import policy name list, tnSvcTlsBgpADVsiExportPolicy1
--                     through tnSvcTlsBgpADVsiExportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 7 }
--
-- tnSvcTlsBgpADVsiExportPolicy2  OBJECT-TYPE
--     SYNTAX          TPolicyStatementNameOrEmpty
--     MAX-ACCESS      read-create
--     STATUS          current
--     DESCRIPTION    "The value of tnSvcTlsBgpADVsiExportPolicy2 specifies the
--                     name of the second VSI export policy to be used for BGP
--                     Auto-Discovery in this VPLS service.
--
--                     If multiple policy names are specified, the policies are
--                     evaluated in the order they are specified.  The first
--                     policy that matches is applied.
--
--                     The import policy name list, tnSvcTlsBgpADVsiExportPolicy1
--                     through tnSvcTlsBgpADVsiExportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 8 }
--
-- tnSvcTlsBgpADVsiExportPolicy3  OBJECT-TYPE
--     SYNTAX          TPolicyStatementNameOrEmpty
--     MAX-ACCESS      read-create
--     STATUS          current
--     DESCRIPTION    "The value of tnSvcTlsBgpADVsiExportPolicy3 specifies the
--                     name of the third VSI export policy to be used for BGP
--                     Auto-Discovery in this VPLS service.
--
--                     If multiple policy names are specified, the policies are
--                     evaluated in the order they are specified.  The first
--                     policy that matches is applied.
--
--                     The import policy name list, tnSvcTlsBgpADVsiExportPolicy1
--                     through tnSvcTlsBgpADVsiExportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 9 }
--
-- tnSvcTlsBgpADVsiExportPolicy4  OBJECT-TYPE
--     SYNTAX          TPolicyStatementNameOrEmpty
--     MAX-ACCESS      read-create
--     STATUS          current
--     DESCRIPTION    "The value of tnSvcTlsBgpADVsiExportPolicy4 specifies the
--                     name of the forth VSI export policy to be used for BGP
--                     Auto-Discovery in this VPLS service.
--
--                     If multiple policy names are specified, the policies are
--                     evaluated in the order they are specified.  The first
--                     policy that matches is applied.
--
--                     The import policy name list, tnSvcTlsBgpADVsiExportPolicy1
--                     through tnSvcTlsBgpADVsiExportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 10 }
--
-- tnSvcTlsBgpADVsiExportPolicy5  OBJECT-TYPE
--     SYNTAX          TPolicyStatementNameOrEmpty
--     MAX-ACCESS      read-create
--     STATUS          current
--     DESCRIPTION    "The value of tnSvcTlsBgpADVsiExportPolicy5 specifies the
--                     name of the fifth VSI export policy to be used for BGP
--                     Auto-Discovery in this VPLS service.
--
--                     If multiple policy names are specified, the policies are
--                     evaluated in the order they are specified.  The first
--                     policy that matches is applied.
--
--                     The import policy name list, tnSvcTlsBgpADVsiExportPolicy1
--                     through tnSvcTlsBgpADVsiExportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 11 }
--
-- tnSvcTlsBgpADImportRteTarget       OBJECT-TYPE
--     SYNTAX          TNamedItemOrEmpty
--     MAX-ACCESS      read-create
--     STATUS          current
--     DESCRIPTION     "The value of tnSvcTlsBgpADImportRteTarget specifies the
--                      extended community name for the default import policy
--                      to use for BGP Auto-Discovery in this VPLS service.
--
--                      This object cannot be set to a non-empty if
--                      tnSvcTlsBgpADImportRteTarget has a non-empty value,
--                      otherwise an 'inconsistentValue' error will be
--                      returned."
--     DEFVAL          { "" }
--     ::= { tnSvcTlsBgpADEntry 12 }
--
-- tnSvcTlsBgpADVsiImportPolicy1  OBJECT-TYPE
--     SYNTAX          TPolicyStatementNameOrEmpty
--     MAX-ACCESS      read-create
--     STATUS          current
--     DESCRIPTION    "The value of tnSvcTlsBgpADVsiImportPolicy1 specifies the
--                     name of the first VSI export policy to be used for BGP
--                     Auto-Discovery in this VPLS service.
--
--                     If multiple policy names are specified, the policies are
--                     evaluated in the order they are specified.  The first
--                     policy that matches is applied.
--
--                     The import policy name list, tnSvcTlsBgpADVsiImportPolicy1
--                     through tnSvcTlsBgpADVsiImportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 13 }
--
-- tnSvcTlsBgpADVsiImportPolicy2  OBJECT-TYPE
--     SYNTAX          TPolicyStatementNameOrEmpty
--     MAX-ACCESS      read-create
--     STATUS          current
--     DESCRIPTION    "The value of tnSvcTlsBgpADVsiImportPolicy2 specifies the
--                     name of the second VSI export policy to be used for BGP
--                     Auto-Discovery in this VPLS service.
--
--                     If multiple policy names are specified, the policies are
--                     evaluated in the order they are specified.  The first
--                     policy that matches is applied.
--
--                     The import policy name list, tnSvcTlsBgpADVsiImportPolicy1
--                     through tnSvcTlsBgpADVsiImportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 14 }
--
-- tnSvcTlsBgpADVsiImportPolicy3  OBJECT-TYPE
--     SYNTAX          TPolicyStatementNameOrEmpty
--     MAX-ACCESS      read-create
--     STATUS          current
--     DESCRIPTION    "The value of tnSvcTlsBgpADVsiImportPolicy3 specifies the
--                     name of the third VSI export policy to be used for BGP
--                     Auto-Discovery in this VPLS service.
--
--                     If multiple policy names are specified, the policies are
--                     evaluated in the order they are specified.  The first
--                     policy that matches is applied.
--
--                     The import policy name list, tnSvcTlsBgpADVsiImportPolicy1
--                     through tnSvcTlsBgpADVsiImportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 15 }
--
-- tnSvcTlsBgpADVsiImportPolicy4  OBJECT-TYPE
--     SYNTAX          TPolicyStatementNameOrEmpty
--     MAX-ACCESS      read-create
--     STATUS          current
--     DESCRIPTION    "The value of tnSvcTlsBgpADVsiImportPolicy4 specifies the
--                     name of the forth VSI export policy to be used for BGP
--                     Auto-Discovery in this VPLS service.
--
--                     If multiple policy names are specified, the policies are
--                     evaluated in the order they are specified.  The first
--                     policy that matches is applied.
--
--                     The import policy name list, tnSvcTlsBgpADVsiImportPolicy1
--                     through tnSvcTlsBgpADVsiImportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 16 }
--
-- tnSvcTlsBgpADVsiImportPolicy5  OBJECT-TYPE
--     SYNTAX          TPolicyStatementNameOrEmpty
--     MAX-ACCESS      read-create
--     STATUS          current
--     DESCRIPTION    "The value of tnSvcTlsBgpADVsiImportPolicy5 specifies the
--                     name of the fifth VSI export policy to be used for BGP
--                     Auto-Discovery in this VPLS service.
--
--                     If multiple policy names are specified, the policies are
--                     evaluated in the order they are specified.  The first
--                     policy that matches is applied.
--
--                     The import policy name list, tnSvcTlsBgpADVsiImportPolicy1
--                     through tnSvcTlsBgpADVsiImportPolicy5, is handled by the SNMP
--                     agent as a single entity.  When an SNMP SET request is
--                     received to modify one or more of the policy names, all
--                     the policy variables are first set to the empty
--                     string, ''H, and then the new names are set into the
--                     specified policy variables within a single SNMP SET PDU."
--     DEFVAL { ''H }      == the empty string
--     ::= { tnSvcTlsBgpADEntry 17 }
--
-- tnSvcTlsBgpADAdminStatus        OBJECT-TYPE
--     SYNTAX          TmnxEnabledDisabled
--     MAX-ACCESS      read-create
--     STATUS          current
--     DESCRIPTION     "The value of tnSvcTlsBgpADAdminStatus specifies the desired
--                      administrative state for BGP Auto-Discovery in this VPLS
--                      service."
--     DEFVAL          { disabled }
--     ::= { tnSvcTlsBgpADEntry 18 }

-- ----------------------------------------
-- PIPE Service Table
-- ----------------------------------------
tnSvcEpipePbbTableLastChanged  OBJECT-TYPE
    SYNTAX          TimeStamp
    MAX-ACCESS      read-only
    STATUS          current
    DESCRIPTION     "The value of tnSvcEpipePbbTableLastChanged indicates the
                     sysUpTime at the time of the last modification of
                     tnSvcEpipePbbTable.

                     If no changes were made to the entry since the last
                     re-initialization of the local network management subsystem,
                     then this object contains a zero value.

                     This is currently not used and always returns 0."
    ::= { tnSvcObjs 36 }

-- tnSvcEpipePbbTable OBJECT-TYPE
--     SYNTAX          SEQUENCE OF TnSvcEpipePbbEntry
--     MAX-ACCESS      not-accessible
--     STATUS          current
--     DESCRIPTION     "The tnSvcEpipePbbTable contains objects related to Provider
--                      Backbone Bridging (PBB) feature as relates to 'epipe'
--                      services.
--
--                      Entries are created and destroyed using tnSvcEpipePbbRowStatus
--                      object."
--     ::= { tnSvcObjs 37 }
--
-- tnSvcEpipePbbEntry OBJECT-TYPE
--     SYNTAX          TnSvcEpipePbbEntry
--     MAX-ACCESS      not-accessible
--     STATUS          current
--     DESCRIPTION     "Each row entry contains objects that allows the
--                      modification of the PBB objects for an 'epipe' service."
--     INDEX        { tnSysSwitchId, tnSvcId }
--     ::= { tnSvcEpipePbbTable 1 }
--
-- TnSvcEpipePbbEntry ::=
--     SEQUENCE {
--         tnSvcEpipePbbRowStatus               RowStatus,
--         tnSvcEpipePbbLastChngd               TimeStamp,
--         tnSvcEpipePbbBvplsSvcId              TmnxServId,
--         tnSvcEpipePbbBvplsDstMac             MacAddress,
--         tnSvcEpipePbbSvcISID                 SvcISID,
--         tnSvcEpipePbbOperState               ServiceOperStatus,
--         tnSvcEpipePbbFlooding                TruthValue,
--         tnSvcEpipePbbLastStatusChange        TimeStamp,
--         tnSvcEpipePbbBvplsOperDstMac         MacAddress,
--         tnSvcEpipePbbBvplsDstMacName         TNamedItemOrEmpty
--     }
--
-- tnSvcEpipePbbRowStatus OBJECT-TYPE
--     SYNTAX          RowStatus
--     MAX-ACCESS      read-create
--     STATUS          current
--     DESCRIPTION     "The value of tnSvcEpipePbbRowStatus is used for the
--                      creation and deletion of Provider Backbone Bridging
--                      information in a EPIPE service.
--
--                      To create an entry in the table, tnSvcEpipePbbBvplsSvcId,
--                      tnSvcEpipePbbSvcISID objects must be set along with
--                      tnSvcEpipePbbBvplsDstMac or tnSvcEpipePbbBvplsDstMacName object
--                      set to non-default value."
--     ::= { tnSvcEpipePbbEntry 1 }
--
-- tnSvcEpipePbbLastChngd        OBJECT-TYPE
--     SYNTAX          TimeStamp
--     MAX-ACCESS      read-only
--     STATUS          current
--     DESCRIPTION     "The value of tnSvcEpipePbbLastChngd indicates the sysUpTime at
--                      the time of the last modification of this entry.
--
--                      If no changes were made to the entry since the last
--                      re-initialization of the local network management
--                      subsystem, then this object contains a zero value."
--     ::= { tnSvcEpipePbbEntry 2 }
--
-- tnSvcEpipePbbBvplsSvcId OBJECT-TYPE
--     SYNTAX          TmnxServId
--     MAX-ACCESS      read-create
--     STATUS          current
--     DESCRIPTION     "The value of tnSvcEpipePbbBvplsSvcId specifies the
--                      Backbone-VPLS service for the PBB tunnel associated with
--                      this service.
--
--                      This object must be set at the creation time and can not
--                      be modified later."
--     ::= { tnSvcEpipePbbEntry 3 }
--
-- tnSvcEpipePbbBvplsDstMac OBJECT-TYPE
--     SYNTAX          MacAddress
--     MAX-ACCESS      read-create
--     STATUS          current
--     DESCRIPTION     "The value of tnSvcEpipePbbBvplsDstMac specifies the Backbone
--                      Destination MAC-Address for Provider Backbone Bridging
--                      packets.
--
--                      An 'inconsistentValue' error is returned if
--                      tnSvcEpipePbbBvplsDstMac or tnSvcEpipePbbBvplsDstMacName object
--                      is not set to non-default value."
--     DEFVAL { '000000000000'h }
--     ::= { tnSvcEpipePbbEntry 4 }
--
-- tnSvcEpipePbbSvcISID OBJECT-TYPE
--     SYNTAX          SvcISID
--     MAX-ACCESS      read-create
--     STATUS          current
--     DESCRIPTION     "The value of the object tnSvcEpipePbbSvcISID specifies
--                      a 24 bit (0..16777215) service instance identifier for the
--                      PBB tunnel associated with this service.
--
--                      As part of the Provider Backbone Bridging frames, it is
--                      used at the destination PE as a demultiplexor field.
--
--                      This object must be set along with tnSvcEpipePbbBvplsSvcId."
--     ::= { tnSvcEpipePbbEntry 5 }
--
-- tnSvcEpipePbbOperState OBJECT-TYPE
--     SYNTAX          ServiceOperStatus
--     MAX-ACCESS      read-only
--     STATUS          current
--     DESCRIPTION     "The value of the object tnSvcEpipePbbOperState indicates the
--                      operating state of PBB tunnel associated with this service."
--     ::= { tnSvcEpipePbbEntry 6 }
--
-- tnSvcEpipePbbFlooding OBJECT-TYPE
--     SYNTAX          TruthValue
--     MAX-ACCESS      read-only
--     STATUS          current
--     DESCRIPTION     "The value of the object tnSvcEpipePbbFlooding indicates
--                      the state for traffic flowing into the Backbone-VPLS
--                      through PBB tunnel.
--
--                      If the backbone-destination MAC is found in the FDB of
--                      Backbone-VPLS then traffic will be sent to specific SAP/SDP
--                      and this object will be set to 'false' otherwise traffic
--                      will be flooded to all SAP/SDP bindings in the
--                      Backbone-VPLS and the object will be set to 'true'."
--     ::= { tnSvcEpipePbbEntry 7 }
--
-- tnSvcEpipePbbLastStatusChange OBJECT-TYPE
--     SYNTAX          TimeStamp
--     MAX-ACCESS      read-only
--     STATUS          current
--     DESCRIPTION     "The value of the object tnSvcEpipePbbLastStatusChange
--                      indicates the value of sysUpTime at the time of the most
--                      recent operating status change to this tunnel."
--     ::= { tnSvcEpipePbbEntry 8 }
--
-- tnSvcEpipePbbBvplsOperDstMac OBJECT-TYPE
--     SYNTAX          MacAddress
--     MAX-ACCESS      read-only
--     STATUS          current
--     DESCRIPTION     "The value of tnSvcEpipePbbBvplsOperDstMac indicates the
--                      operational Backbone Destination MAC-Address for Provider
--                      Backbone Bridging packets."
--     ::= { tnSvcEpipePbbEntry 9 }
--
-- tnSvcEpipePbbBvplsDstMacName OBJECT-TYPE
--     SYNTAX          TNamedItemOrEmpty
--     MAX-ACCESS      read-create
--     STATUS          current
--     DESCRIPTION     "The value of tnSvcEpipePbbBvplsDstMacName specifies the
--                      Backbone Destination MAC-Address-Name for Provider
--                      Backbone Bridging packets.
--
--                      An 'inconsistentValue' error is returned if
--                      tnSvcEpipePbbBvplsDstMac or tnSvcEpipePbbBvplsDstMacName object
--                      is not set to non-default value."
--     DEFVAL  { ''H }
--     ::= { tnSvcEpipePbbEntry 10 }

-- -------------------------------------
-- TLS PIP uplink Table
-- -------------------------------------
-- tnTlsPipInfoTable OBJECT-TYPE
--     SYNTAX          SEQUENCE OF TlsPipInfoEntry
--     MAX-ACCESS      not-accessible
--     STATUS          current
--     DESCRIPTION
--         "A table that contains TLS PIP (Provider Internal Port) uplink
--         information. PIP is the virtual link between I and B components of PBB
--         (Provider Backbone Bridging) model. I component refers to a service
--         with tnSvcVplsType set to 'iVpls (3)' and B component refers to a service
--         with tnSvcVplsType set to 'bVpls (2)'. When any form of STP is enabled in
--         the iVpls domain, the PIP uplink is modeled as a regular STP port."
--     ::= { tnSvcObjs 40 }
--
-- tnTlsPipInfoEntry OBJECT-TYPE
--     SYNTAX          TlsPipInfoEntry
--     MAX-ACCESS      not-accessible
--     STATUS          current
--     DESCRIPTION     "TLS specific information about PIP uplink."
--     INDEX           { tnSysSwitchId,  tnSvcId }
--     ::= { tnTlsPipInfoTable 1 }
--
-- TlsPipInfoEntry ::=
--     SEQUENCE {
--         tnTlsPipStpPortState              TStpPortState,
--         tnTlsPipStpPortRole               StpPortRole,
--         tnTlsPipStpDesignatedBridge       BridgeId,
--         tnTlsPipStpDesignatedPort         Integer32,
--         tnTlsPipStpException              StpExceptionCondition,
--         tnTlsPipStpForwardTransitions     Counter32,
--         tnTlsPipStpInConfigBpdus          Counter32,
--         tnTlsPipStpInTcnBpdus             Counter32,
--         tnTlsPipStpInRstBpdus             Counter32,
--         tnTlsPipStpInMstBpdus             Counter32,
--         tnTlsPipStpInBadBpdus             Counter32,
--         tnTlsPipStpOutConfigBpdus         Counter32,
--         tnTlsPipStpOutTcnBpdus            Counter32,
--         tnTlsPipStpOutRstBpdus            Counter32,
--         tnTlsPipStpOutMstBpdus            Counter32,
--         tnTlsPipStpOperStatus             ServiceOperStatus,
--         tnTlsPipStpMvplsPruneState        MvplsPruneState,
--         tnTlsPipStpOperProtocol           StpProtocol,
--         tnTlsPipStpPortNum                Unsigned32,
--         tnTlsPipStpInsideRegion           TruthValue,
--         tnTlsPipInTcBitBpdus              Counter32,
--         tnTlsPipOutTcBitBpdus             Counter32
--     }
--
-- tnTlsPipStpPortState OBJECT-TYPE
--     SYNTAX          TStpPortState
--     MAX-ACCESS      read-only
--     STATUS          current
--     DESCRIPTION
--         "The value of tnTlsPipStpPortState indicates the PIP uplink's current
--         state as defined by application of the Spanning Tree Protocol. This
--         state controls what action PIP uplink takes on reception of a frame.
--         If the bridge has detected a port that is malfunctioning it will
--         place that port into the 'broken (6)' state."
--     ::= { tnTlsPipInfoEntry 1 }
--
-- tnTlsPipStpPortRole OBJECT-TYPE
--     SYNTAX          StpPortRole
--     MAX-ACCESS      read-only
--     STATUS          current
--     DESCRIPTION
--         "The value of tnTlsPipStpPortRole indicates the current role of the PIP
--         uplink as defined by the Rapid Spanning Tree Protocol."
--     ::= { tnTlsPipInfoEntry 2 }
--
-- tnTlsPipStpDesignatedBridge OBJECT-TYPE
--     SYNTAX          BridgeId
--     MAX-ACCESS      read-only
--     STATUS          current
--     DESCRIPTION
--         "The value of tnTlsPipStpDesignatedBridge indicates the Bridge Identifier
--         of the bridge which this PIP uplink considers to be the Designated
--         Bridge for this port's segment."
--     ::= { tnTlsPipInfoEntry 3 }
--
-- tnTlsPipStpDesignatedPort OBJECT-TYPE
--     SYNTAX          Integer32
--     MAX-ACCESS      read-only
--     STATUS          current
--     DESCRIPTION
--         "The value of tnTlsPipStpDesignatedPort indicates the Port Identifier of
--         the port on the Designated Bridge for this port's segment."
--     ::= { tnTlsPipInfoEntry 4 }
--
-- tnTlsPipStpException OBJECT-TYPE
--     SYNTAX          StpExceptionCondition
--     MAX-ACCESS      read-only
--     STATUS          current
--     DESCRIPTION     "The value of the object tnTlsPipStpException indicates
--                      whether an STP exception condition is present on this
--                      Pip.
--                      - none : no exception condition found.
--                      - oneWayCommuniation : The neighbor RSTP peer on this link
--                                             is not able to detect our presence.
--                      - downstreamLoopDetected :A loop is detected on this link."
--     ::= { tnTlsPipInfoEntry 5 }
--
-- tnTlsPipStpForwardTransitions OBJECT-TYPE
--     SYNTAX          Counter32
--     MAX-ACCESS      read-only
--     STATUS          current
--     DESCRIPTION     "The value of the object tnTlsPipStpForwardTransitions
--                      indicates the number of times this port has transitioned
--                      from the Learning state to the Forwarding state."
--     ::= { tnTlsPipInfoEntry 6 }
--
-- tnTlsPipStpInConfigBpdus OBJECT-TYPE
--     SYNTAX          Counter32
--     MAX-ACCESS      read-only
--     STATUS          current
--     DESCRIPTION     "The value of the object tnTlsPipStpInConfigBpdus indicates
--                      the number of Configuration BPDUs received on this
--                      PIP uplink."
--     ::= { tnTlsPipInfoEntry 7 }
--
-- tnTlsPipStpInTcnBpdus OBJECT-TYPE
--     SYNTAX          Counter32
--     MAX-ACCESS      read-only
--     STATUS          current
--     DESCRIPTION     "The value of the object  tnTlsPipStpInTcnBpdus indicates the
--                      number of Topology Change Notification BPDUs received on
--                      this PIP uplink."
--     ::= { tnTlsPipInfoEntry 8 }
--
-- tnTlsPipStpInRstBpdus OBJECT-TYPE
--     SYNTAX          Counter32
--     MAX-ACCESS      read-only
--     STATUS          current
--     DESCRIPTION     "The value of the object  tnTlsPipStpInRstBpdus indicates
--                      the number of Rapid Spanning Tree (RST) BPDUs received on
--                      this PIP uplink."
--     ::= { tnTlsPipInfoEntry 9 }
--
-- tnTlsPipStpInMstBpdus OBJECT-TYPE
--     SYNTAX          Counter32
--     MAX-ACCESS      read-only
--     STATUS          current
--     DESCRIPTION     "The value of the object tnTlsPipStpInMstBpdus indicates
--                      the number of Multiple Spanning Tree (MST) BPDUs received
--                      on this PIP uplink."
--     ::= { tnTlsPipInfoEntry 10 }
--
-- tnTlsPipStpInBadBpdus OBJECT-TYPE
--     SYNTAX          Counter32
--     MAX-ACCESS      read-only
--     STATUS          current
--     DESCRIPTION     "This object specifies the number of bad
--                      BPDUs received on this PIP uplink."
--     ::= { tnTlsPipInfoEntry 11 }
--
-- tnTlsPipStpOutConfigBpdus OBJECT-TYPE
--     SYNTAX          Counter32
--     MAX-ACCESS      read-only
--     STATUS          current
--     DESCRIPTION     "The value of the object tnTlsPipStpOutConfigBpdus indicates
--                      the number of Configuration BPDUs sent out this PIP uplink."
--     ::= { tnTlsPipInfoEntry 12 }
--
-- tnTlsPipStpOutTcnBpdus OBJECT-TYPE
--     SYNTAX          Counter32
--     MAX-ACCESS      read-only
--     STATUS          current
--     DESCRIPTION     "This object specifies the number of Topology
--                      Change Notification BPDUs sent out this PIP uplink."
--     ::= { tnTlsPipInfoEntry 13 }
--
-- tnTlsPipStpOutRstBpdus OBJECT-TYPE
--     SYNTAX          Counter32
--     MAX-ACCESS      read-only
--     STATUS          current
--     DESCRIPTION     "The value of the  object tnTlsPipStpOutRstBpdus indicates
--                      the number of Rapid Spanning Tree (RST) BPDUs sent out on
--                      this PIP uplink."
--     ::= { tnTlsPipInfoEntry 14 }
--
-- tnTlsPipStpOutMstBpdus OBJECT-TYPE
--     SYNTAX          Counter32
--     MAX-ACCESS      read-only
--     STATUS          current
--     DESCRIPTION     "The value of the object tnTlsPipStpOutMstBpdus indicates
--                      the number of Multiple Spanning Tree (MST) BPDUs sent out
--                      on this PIP uplink."
--     ::= { tnTlsPipInfoEntry 15 }
--
-- tnTlsPipStpOperStatus OBJECT-TYPE
--     SYNTAX          ServiceOperStatus
--     MAX-ACCESS      read-only
--     STATUS          current
--     DESCRIPTION     "The value of the object tnTlsPipStpOperStatus indicates the
--                      operational status of this PIP uplink."
--     ::= { tnTlsPipInfoEntry 16 }
--
-- tnTlsPipStpMvplsPruneState OBJECT-TYPE
--     SYNTAX          MvplsPruneState
--     MAX-ACCESS      read-only
--     STATUS          current
--     DESCRIPTION     "The value of tnTlsPipStpMvplsPruneState indicates the mVPLS
--                      prune state of this PIP uplink.  The state reflects
--                      whether or not this uplink is pruned by the STP instance
--                      running in the mVPLS instance."
--     ::= { tnTlsPipInfoEntry 17 }
--
-- tnTlsPipStpOperProtocol OBJECT-TYPE
--     SYNTAX          StpProtocol
--     MAX-ACCESS      read-only
--     STATUS          current
--     DESCRIPTION     "The value of tnTlsPipStpOperProtocol indicates whether 'stp',
--                     'rstp' or 'mstp' is running on this PIP uplink. If the
--                     protocol is not enabled on this PIP uplink, the value
--                     'notApplicable' is returned."
--     ::= { tnTlsPipInfoEntry 18 }
--
-- tnTlsPipStpPortNum OBJECT-TYPE
--     SYNTAX          Unsigned32 (0..4094)
--     MAX-ACCESS      read-only
--     STATUS          current
--     DESCRIPTION     "The value of the object tnTlsPipStpPortNum specifies the
--                      value of the port number field which is contained in the
--                      least significant 12 bits of the 16-bit Port ID associated
--                      with this PIP uplink."
--     ::= { tnTlsPipInfoEntry 19 }
--
-- tnTlsPipStpInsideRegion OBJECT-TYPE
--     SYNTAX          TruthValue
--     MAX-ACCESS      read-only
--     STATUS          current
--     DESCRIPTION     "The value of the object tnTlsPipStpInsideRegion indicates
--                      whether the network connected to the PIP is in the same
--                      MST region. It corresponds to the parameter 'infoInternal'
--                      in 802.1Q."
--     ::= { tnTlsPipInfoEntry 20 }
--
--
-- tnTlsPipInTcBitBpdus OBJECT-TYPE
--     SYNTAX          Counter32
--     MAX-ACCESS      read-only
--     STATUS          current
--     DESCRIPTION     "The value of the object  tnTlsPipInTcBitBpdus indicates the
--                      number of BPDUs received on this PIP uplink
--                      with the Topology Change bit set."
--     ::= { tnTlsPipInfoEntry 21 }
--
-- tnTlsPipOutTcBitBpdus OBJECT-TYPE
--     SYNTAX          Counter32
--     MAX-ACCESS      read-only
--     STATUS          current
--     DESCRIPTION     "This object specifies the number of BPDUs sent out
--                      this PIP uplink with the Topology Change bit set."
--     ::= { tnTlsPipInfoEntry 22 }

-- -----------------------------------------
-- PIP TLS MSTI Table
-- -----------------------------------------
-- tnTlsPipMstiTable OBJECT-TYPE
--     SYNTAX          SEQUENCE OF TlsPipMstiEntry
--     MAX-ACCESS      not-accessible
--     STATUS          current
--     DESCRIPTION
--         "This table contains Multiple Spanning Tree Instance information for
--         the PIP uplink. Each management VPLS running MSTP can have upto 15
--         MSTI. An entry in this table is automatically created when a
--         tnTlsMstiEntry is created."
--     ::= { tnSvcObjs 41 }
--
-- tnTlsPipMstiEntry OBJECT-TYPE
--     SYNTAX          TlsPipMstiEntry
--     MAX-ACCESS      not-accessible
--     STATUS          current
--     DESCRIPTION     "Information about a specific MSTI for a PIP uplink."
--     INDEX           { tnSysSwitchId,  tnSvcId, tnTlsMstiInstanceId}
--     ::= { tnTlsPipMstiTable 1 }
--
-- TlsPipMstiEntry ::=
--     SEQUENCE {
--         tnTlsPipMstiPortRole          StpPortRole,
--         tnTlsPipMstiPortState         TStpPortState,
--         tnTlsPipMstiDesignatedBridge  BridgeId,
--         tnTlsPipMstiDesignatedPort    Integer32
--     }
--
-- tnTlsPipMstiPortRole OBJECT-TYPE
--     SYNTAX          StpPortRole
--     MAX-ACCESS      read-only
--     STATUS          current
--     DESCRIPTION     "tnTlsPipMstiPortRole indicates the current role of the
--                      PIP uplink in the MSTI as defined by the Spanning Tree
--                      Protocol."
--     ::= { tnTlsPipMstiEntry 1 }
--
-- tnTlsPipMstiPortState OBJECT-TYPE
--     SYNTAX          TStpPortState
--     MAX-ACCESS      read-only
--     STATUS          current
--     DESCRIPTION     "The value of the object tnTlsPipMstiPortState indicates the
--                      port's current state as defined by application of the
--                      Spanning Tree Protocol. This state controls what action a
--                      port takes on reception of a frame. If the bridge has
--                      detected a port that is malfunctioning it will
--                      place that port into the broken(6) state."
--     ::= { tnTlsPipMstiEntry 2 }
--
-- tnTlsPipMstiDesignatedBridge OBJECT-TYPE
--     SYNTAX          BridgeId
--     MAX-ACCESS      read-only
--     STATUS          current
--     DESCRIPTION     "The value of the object tnTlsPipMstiDesignatedBridge
--                      indicates  the Bridge Identifier of the bridge which this
--                      port considers to be the Designated Bridge for this port's
--                      segment for this MSTI."
--     ::= { tnTlsPipMstiEntry 3 }
--
-- tnTlsPipMstiDesignatedPort OBJECT-TYPE
--     SYNTAX          Integer32
--     MAX-ACCESS      read-only
--     STATUS          current
--     DESCRIPTION     "The value of the object tnTlsPipMstiDesignatedPort indicates
--                      the Port Identifier of the port on the Designated Bridge
--                      for this port's segment for this MSTI."
--     ::= { tnTlsPipMstiEntry 4 }

-- ----------------------
-- System service objects
-- ----------------------
tnSvcTotalFdbMimDestIdxEntries OBJECT-TYPE
    SYNTAX         Unsigned32
    MAX-ACCESS     read-only
    STATUS         current
    DESCRIPTION    "The value of the object tnSvcTotalFdbMimDestIdxEntries
                    indicates the number of system wide Backbone MAC address
                    indices in use.

                    This is currently not used and always returns 0."
    ::= { tnSvcObjs 42 }

-- ----------------------------------------
-- DHCP Managed Route Table
-- ----------------------------------------
-- tnSvcDhcpManagedRouteTable OBJECT-TYPE
--     SYNTAX          SEQUENCE OF TnSvcDhcpManagedRouteEntry
--     MAX-ACCESS      not-accessible
--     STATUS          current
--     DESCRIPTION     "A table that contains DHCP managed routes."
--     ::= { tnSvcObjs 43 }
--
-- tnSvcDhcpManagedRouteEntry OBJECT-TYPE
--     SYNTAX          TnSvcDhcpManagedRouteEntry
--     MAX-ACCESS      not-accessible
--     STATUS          current
--     DESCRIPTION     "A specific DHCP managed route."
--     INDEX           { tnSysSwitchId,  tnSvcId,
--                       tnSvcDhcpLseStateCiAddrType,
--                       tnSvcDhcpLseStateCiAddr,
--                       tnSvcDhcpManagedRouteInetAddrType,
--                       tnSvcDhcpManagedRouteInetAddr,
--                       tnSvcDhcpManagedRoutePrefixLen }
--     ::= { tnSvcDhcpManagedRouteTable 1 }
--
-- TnSvcDhcpManagedRouteEntry ::=
--     SEQUENCE {
--         tnSvcDhcpManagedRouteInetAddrType  InetAddressType,
--         tnSvcDhcpManagedRouteInetAddr      InetAddress,
--         tnSvcDhcpManagedRoutePrefixLen     InetAddressPrefixLength,
--         tnSvcDhcpManagedRouteStatus        TmnxManagedRouteStatus
--     }
--
-- tnSvcDhcpManagedRouteInetAddrType OBJECT-TYPE
--     SYNTAX          InetAddressType
--     MAX-ACCESS      not-accessible
--     STATUS          current
--     DESCRIPTION     "The value of tnSvcDhcpManagedRouteInetAddrType indicates
--                      the address type of tnSvcDhcpManagedRouteInetAddr."
--     ::= { tnSvcDhcpManagedRouteEntry 1 }
--
-- tnSvcDhcpManagedRouteInetAddr OBJECT-TYPE
--     SYNTAX          InetAddress
--     MAX-ACCESS      not-accessible
--     STATUS          current
--     DESCRIPTION     "The value of tnSvcDhcpManagedRouteInetAddr indicates
--                      the IP address of the managed route."
--     ::= { tnSvcDhcpManagedRouteEntry 2 }
--
-- tnSvcDhcpManagedRoutePrefixLen OBJECT-TYPE
--     SYNTAX          InetAddressPrefixLength (0..32)
--     MAX-ACCESS      not-accessible
--     STATUS          current
--     DESCRIPTION     "The value of tnSvcDhcpManagedRoutePrefixLen indicates
--                      the prefix length of the subnet associated with
--                      tnSvcDhcpManagedRouteInetAddr."
--     ::= { tnSvcDhcpManagedRouteEntry 3 }
--
-- tnSvcDhcpManagedRouteStatus OBJECT-TYPE
--     SYNTAX          TmnxManagedRouteStatus
--     MAX-ACCESS      read-only
--     STATUS          current
--     DESCRIPTION     "The value of tnSvcDhcpManagedRouteStatus indicates
--                      the state of this managed route."
--     ::= { tnSvcDhcpManagedRouteEntry 4 }

-- --------------------------------------------------------
--  tnSvcArpHostTable
-- --------------------------------------------------------
tnSvcArpHostTableLastChanged         OBJECT-TYPE
    SYNTAX       TimeStamp
    MAX-ACCESS   read-only
    STATUS       current
    DESCRIPTION
        "The value of tnSvcArpHostTableLastChanged indicates the
         sysUpTime at the time of the last modification of an entry in the
         tnSvcArpHostTable.

         If there were no changes in the table since the last re-initialization
         of the local network management subsystem, then this object
         contains a zero value.

         This is currently not used and always returns 0."
    ::= { tnSvcObjs 44 }

-- tnSvcArpHostTable OBJECT-TYPE
--     SYNTAX      SEQUENCE OF TnSvcArpHostEntry
--     MAX-ACCESS  not-accessible
--     STATUS      current
--     DESCRIPTION
--         "A table that contains ARP hosts."
--     ::= { tnSvcObjs 45 }
--
-- tnSvcArpHostEntry OBJECT-TYPE
--     SYNTAX      TnSvcArpHostEntry
--     MAX-ACCESS  not-accessible
--     STATUS      current
--     DESCRIPTION
--         "Information about a specific ARP host."
--     INDEX { tnSysSwitchId, tnSvcId,
--             tnSvcArpHostIpAddrType,
--             tnSvcArpHostIpAddr }
--     ::= { tnSvcArpHostTable 1 }
--
-- TnSvcArpHostEntry ::=
--     SEQUENCE {
--         tnSvcArpHostIpAddrType             InetAddressType,
--         tnSvcArpHostIpAddr                 InetAddress,
--         tnSvcArpHostLocale                 ServAccessLocation,
--         tnSvcArpHostSapPortId              TmnxPortID,
--         tnSvcArpHostSapEncapValue          TmnxEncapVal,
--         tnSvcArpHostSdpId                  SdpId,
--         tnSvcArpHostVcId                   Unsigned32,
--         tnSvcArpHostSessionTimeout         Unsigned32,
--         tnSvcArpHostStart                  DateAndTime,
--         tnSvcArpHostLastAuth               DateAndTime,
--         tnSvcArpHostRefresh                DateAndTime,
--         tnSvcArpHostRemainingTime          Unsigned32,
--         tnSvcArpHostShcvOperState          ServShcvOperState,
--         tnSvcArpHostShcvChecks             Unsigned32,
--         tnSvcArpHostShcvReplies            Unsigned32,
--         tnSvcArpHostShcvReplyTime          TimeStamp,
--         tnSvcArpHostSubscrIdent            TmnxSubIdentStringOrEmpty,
--         tnSvcArpHostSubProfString          TmnxSubProfileStringOrEmpty,
--         tnSvcArpHostSlaProfString          TmnxSlaProfileStringOrEmpty,
--         tnSvcArpHostAppProfString          TmnxAppProfileStringOrEmpty,
--         tnSvcArpHostAncpString             TmnxAncpStringOrZero,
--         tnSvcArpHostInterDestId            TmnxSubMgtIntDestIdOrEmpty,
--         tnSvcArpHostRetailerSvcId          TmnxServId,
--         tnSvcArpHostRetailerIf             InterfaceIndexOrZero,
--         tnSvcArpHostMacAddr                MacAddress,
--         tnSvcArpHostPersistKey             Unsigned32,
--         tnSvcArpHostCategoryMapName        TNamedItemOrEmpty,
--         tnSvcArpHostRadiusClassAttr        OCTET STRING,
--         tnSvcArpHostRadiusUserName         DisplayString
--     }
--
-- tnSvcArpHostIpAddrType OBJECT-TYPE
--     SYNTAX          InetAddressType
--     MAX-ACCESS      not-accessible
--     STATUS          current
--     DESCRIPTION     "The value of tnSvcArpHostIpAddrType indicates the
--                      address type of tnSvcArpHostIpAddr."
--     ::= { tnSvcArpHostEntry 1 }
--
-- tnSvcArpHostIpAddr OBJECT-TYPE
--     SYNTAX          InetAddress (SIZE(0|4))
--     MAX-ACCESS      not-accessible
--     STATUS          current
--     DESCRIPTION     "The value of tnSvcArpHostIpAddr indicates the IP
--                      address of the ARP host."
--     ::= { tnSvcArpHostEntry 2 }
--
-- tnSvcArpHostLocale OBJECT-TYPE
--     SYNTAX          ServAccessLocation
--     MAX-ACCESS      read-only
--     STATUS          current
--     DESCRIPTION     "The value of tnSvcArpHostLocale indicates if the ARP
--                      Host is learned via a SAP or spoke SDP."
--     ::= { tnSvcArpHostEntry 3 }
--
-- tnSvcArpHostSapPortId OBJECT-TYPE
--     SYNTAX          TmnxPortID
--     MAX-ACCESS      read-only
--     STATUS          current
--     DESCRIPTION     "When the value of tnSvcArpHostLocale is 'sap', the
--                      object tnSvcArpHostSapPortId along with the object
--                      tnSvcArpHostSapEncapValue, indicates the SAP where this
--                      ARP host is learned. This object is otherwise
--                      insignificant and contains the value 0."
--     ::= { tnSvcArpHostEntry 4 }
--
-- tnSvcArpHostSapEncapValue OBJECT-TYPE
--     SYNTAX          TmnxEncapVal
--     MAX-ACCESS      read-only
--     STATUS          current
--     DESCRIPTION     "When the value of tnSvcArpHostLocale is 'sap', the
--                      object tnSvcArpHostSapPortId along with the object
--                      tnSvcArpHostSapEncapValue, indicates the SAP where this
--                      ARP host is learned. This object is otherwise
--                      insignificant and contains the value 0."
--     ::= { tnSvcArpHostEntry 5 }
--
-- tnSvcArpHostSdpId OBJECT-TYPE
--     SYNTAX          SdpId
--     MAX-ACCESS      read-only
--     STATUS          current
--     DESCRIPTION     "When the value of tnSvcArpHostLocale is 'sdp', the
--                      object tnSvcArpHostSdpId, along with the object
--                      tnSvcArpHostVcId, indicates the SDP Binding where this
--                      ARP host is learned. This object is otherwise
--                      insignificant and contains the value 0."
--     ::= { tnSvcArpHostEntry 6 }
--
-- tnSvcArpHostVcId OBJECT-TYPE
--     SYNTAX          Unsigned32
--     MAX-ACCESS      read-only
--     STATUS          current
--     DESCRIPTION     "When the value of tnSvcArpHostLocale is 'sdp', the
--                      object tnSvcArpHostVcId, along with the object
--                      tnSvcArpHostSdpId, indicates the SDP Binding where this
--                      ARP host is learned. This object is otherwise
--                      insignificant and contains the value 0."
--     ::= { tnSvcArpHostEntry 7 }
--
-- tnSvcArpHostSessionTimeout OBJECT-TYPE
--     SYNTAX          Unsigned32
--     MAX-ACCESS      read-only
--     STATUS          current
--     DESCRIPTION     "The value of tnSvcArpHostSessionTimeout indicates the
--                      session timeout of this ARP host.
--
--                      The session timeout can be configured in the Radius server.
--
--                      If no session timeout is specified, its value is equal to
--                      the value of the object tnSvcArpHostDefaultSessionTimeout."
--     ::= { tnSvcArpHostEntry 8 }
--
-- tnSvcArpHostStart OBJECT-TYPE
--     SYNTAX          DateAndTime (SIZE (11))
--     MAX-ACCESS      read-only
--     STATUS          current
--     DESCRIPTION     "The value of tnSvcArpHostStart indicates the time of the
--                      creation of this entry."
--     ::= { tnSvcArpHostEntry 9 }
--
-- tnSvcArpHostLastAuth OBJECT-TYPE
--     SYNTAX          DateAndTime (SIZE (11))
--     MAX-ACCESS      read-only
--     STATUS          current
--     DESCRIPTION     "The value of tnSvcArpHostLastAuth indicates the time of the
--                      last authentication."
--     ::= { tnSvcArpHostEntry 10 }
--
-- tnSvcArpHostRefresh OBJECT-TYPE
--     SYNTAX          DateAndTime (SIZE (11))
--     MAX-ACCESS      read-only
--     STATUS          current
--     DESCRIPTION     "The value of tnSvcArpHostRefresh indicates the time of the
--                      last refresh of this ARP host.
--
--                      Note that not every refresh requires authentication."
--     ::= { tnSvcArpHostEntry 11 }
--
-- tnSvcArpHostRemainingTime OBJECT-TYPE
--     SYNTAX          Unsigned32
--     UNITS           "seconds"
--     MAX-ACCESS      read-only
--     STATUS          current
--     DESCRIPTION     "The value of tnSvcArpHostRemainingTime indicates the
--                      remaining time of this ARP host."
--     ::= { tnSvcArpHostEntry 12 }
--
-- tnSvcArpHostShcvOperState OBJECT-TYPE
--     SYNTAX          ServShcvOperState
--     MAX-ACCESS      read-only
--     STATUS          current
--     DESCRIPTION     "The value of tnSvcArpHostShcvOperState indicates the
--                      state of the subscriber host connectivity check for
--                      this ARP host."
--     ::= { tnSvcArpHostEntry 13 }
--
-- tnSvcArpHostShcvChecks OBJECT-TYPE
--     SYNTAX          Unsigned32
--     MAX-ACCESS      read-only
--     STATUS          current
--     DESCRIPTION     "The value of tnSvcArpHostShcvChecks indicates the
--                      number of host connectivity check requests for
--                      this ARP host."
--     ::= { tnSvcArpHostEntry 14 }
--
-- tnSvcArpHostShcvReplies OBJECT-TYPE
--     SYNTAX          Unsigned32
--     MAX-ACCESS      read-only
--     STATUS          current
--     DESCRIPTION     "The value of tnSvcArpHostShcvReplies indicates the
--                      number of host connectivity replies for this ARP host."
--     ::= { tnSvcArpHostEntry 15 }
--
-- tnSvcArpHostShcvReplyTime OBJECT-TYPE
--     SYNTAX          TimeStamp
--     MAX-ACCESS      read-only
--     STATUS          current
--     DESCRIPTION     "The value of tnSvcArpHostShcvReplyTime indicates the
--                      time of the last successful host connectivity check for
--                      this ARP host."
--     ::= { tnSvcArpHostEntry 16 }
--
-- tnSvcArpHostSubscrIdent OBJECT-TYPE
--     SYNTAX          TmnxSubIdentStringOrEmpty
--     MAX-ACCESS      read-only
--     STATUS          current
--     DESCRIPTION     "The value of tnSvcArpHostSubscrIdent indicates the
--                      id of the parent subscriber of this ARP host."
--     ::= { tnSvcArpHostEntry 17 }
--
-- tnSvcArpHostSubProfString OBJECT-TYPE
--     SYNTAX          TmnxSubProfileStringOrEmpty
--     MAX-ACCESS      read-only
--     STATUS          current
--     DESCRIPTION     "The value of tnSvcArpHostSubProfString indicates the
--                      subscriber profile string applicable for this ARP host."
--     ::= { tnSvcArpHostEntry 18 }
--
-- tnSvcArpHostSlaProfString OBJECT-TYPE
--     SYNTAX          TmnxSlaProfileStringOrEmpty
--     MAX-ACCESS      read-only
--     STATUS          current
--     DESCRIPTION     "The value of tnSvcArpHostSlaProfString indicates the
--                      SLA profile string applicable for this ARP host."
--     ::= { tnSvcArpHostEntry 19 }
--
-- tnSvcArpHostAppProfString OBJECT-TYPE
--     SYNTAX          TmnxAppProfileStringOrEmpty
--     MAX-ACCESS      read-only
--     STATUS          current
--     DESCRIPTION     "The value of tnSvcArpHostAppProfString indicates the
--                      application profile string applicable for this ARP host."
--     ::= { tnSvcArpHostEntry 20 }
--
-- tnSvcArpHostAncpString OBJECT-TYPE
--     SYNTAX          TmnxAncpStringOrZero
--     MAX-ACCESS      read-only
--     STATUS          current
--     DESCRIPTION     "The object tnSvcArpHostAncpString indicates the
--                      value of the ANCP-string received from the RADIUS server."
--     ::= { tnSvcArpHostEntry 21 }
--
-- tnSvcArpHostInterDestId OBJECT-TYPE
--     SYNTAX          TmnxSubMgtIntDestIdOrEmpty
--     MAX-ACCESS      read-only
--     STATUS          current
--     DESCRIPTION     "The object tnSvcArpHostInterDestId indicates the
--                      intermediate destination identifier received from the
--                      RADIUS server."
--     ::= { tnSvcArpHostEntry 22 }
--
-- tnSvcArpHostRetailerSvcId OBJECT-TYPE
--     SYNTAX          TmnxServId
--     MAX-ACCESS      read-only
--     STATUS          current
--     DESCRIPTION     "The value of tnSvcArpHostRetailerSvcId indicates the
--                      service ID of the retailer VPRN service to which this
--                      ARP host belongs. When this object is non zero, the
--                      ARP host belongs to a retailer VPRN."
--     ::= { tnSvcArpHostEntry 23 }
--
-- tnSvcArpHostRetailerIf OBJECT-TYPE
--      SYNTAX         InterfaceIndexOrZero
--      MAX-ACCESS     read-only
--      STATUS         current
--      DESCRIPTION    "The value of tnSvcArpHostRetailerIf indicates the
--                      interface index of the retailer VPRN interface to
--                      which this ARP host belongs. When this object is
--                      non zero, the ARP host belongs to a retailer VPRN."
--      ::= { tnSvcArpHostEntry 24 }
--
-- tnSvcArpHostMacAddr OBJECT-TYPE
--      SYNTAX         MacAddress
--      MAX-ACCESS     read-only
--      STATUS         current
--      DESCRIPTION    "The value of tnSvcArpHostMacAddr indicates the
--                      MAC address of this ARP host."
--      ::= { tnSvcArpHostEntry 25 }
--
-- tnSvcArpHostPersistKey OBJECT-TYPE
--     SYNTAX          Unsigned32
--     MAX-ACCESS      read-only
--     STATUS          current
--     DESCRIPTION     "The value of tnSvcArpHostPersistKey indicates a key
--                      value that can be used to track this ARP host in the
--                      persistence file."
--     ::= { tnSvcArpHostEntry 26 }
--
-- tnSvcArpHostCategoryMapName OBJECT-TYPE
--     SYNTAX          TNamedItemOrEmpty
--     MAX-ACCESS      read-only
--     STATUS          current
--     DESCRIPTION     "The object tnSvcArpHostCategoryMapName indicates the
--                      value of the category map name received from the RADIUS
--                      server."
--     ::= { tnSvcArpHostEntry 27 }
--
-- tnSvcArpHostRadiusClassAttr OBJECT-TYPE
--     SYNTAX          OCTET STRING (SIZE (0..64))
--     MAX-ACCESS      read-only
--     STATUS          current
--     DESCRIPTION     "The value of tnSvcArpHostRadiusClassAttr indicates the
--                      Class attribute returned by the RADIUS server in an
--                      Access-Accept message.
--
--                      If no RADIUS authentication is performed for this ARP
--                      host, or RADIUS did not return this attribute, the value
--                      of this object is empty."
--     ::= { tnSvcArpHostEntry 28 }
--
-- tnSvcArpHostRadiusUserName OBJECT-TYPE
--     SYNTAX          DisplayString (SIZE (0..128))
--     MAX-ACCESS      read-only
--     STATUS          current
--     DESCRIPTION     "The value of tnSvcArpHostRadiusUserName indicates the
--                      User-Name attribute returned by the RADIUS server in an
--                      Access-Accept message.
--
--                      If RADIUS did not return this attribute, the value of this
--                      object is equal to the User-Name attribute sent in the
--                      original Access-Request message.
--
--                      If no RADIUS authentication is performed for this ARP
--                      host, the value of this object is empty."
--     ::= { tnSvcArpHostEntry 29 }

-- ---------------------------------------------------------------------
--  tnSvcArpHostIfTable
--
--
--  Sparse Dependent Extension of the tnIesIfTable.
--
--  The same indexes are used for both the base table, tnIesIfTable,
--  and the sparse dependent table, tnSvcArpHostIfTable.
--
--  This in effect extends the tnIesIfTable with additional columns.
--  A row is automatically created in the tnSvcArpHostIfTable
--  for each applicable row in the tnIesIfTable.
--
--  Deletion of a row in the tnIesIfTable results in the
--  same fate for the row in the tnSvcArpHostIfTable.
-- ---------------------------------------------------------------------

tnSvcArpHostIfTableLastMgmtChange OBJECT-TYPE
    SYNTAX      TimeStamp
    MAX-ACCESS  read-only
    STATUS      current
    DESCRIPTION
        "The value of tnSvcArpHostIfTableLastMgmtChange indicates the sysUpTime
         at the time of the most recent management-initiated change to the
         tnSvcArpHostIfTable.

         This is currently not used and always returns 0."
    ::= { tnSvcObjs 46 }

-- tnSvcArpHostIfTable OBJECT-TYPE
--     SYNTAX      SEQUENCE OF TnSvcArpHostIfEntry
--     MAX-ACCESS  not-accessible
--     STATUS      current
--     DESCRIPTION
--         "A table that contains IES interface ARP host configuration
--          information.
--
--          A row is automatically created in the tnSvcArpHostIfTable for an entry
--          in the tnIesIfTable where either the value of the object tnIesIfType
--          is equal to 'group (3)', or equal to 'subscriber (2)' while the value
--          of the objects tnIesIfFwdServId and tnIesIfFwdSubIf are not equal to zero.
--
--          The first case is referred to as 'group interface' and the second as
--          'retailer interface'."
--     ::= { tnSvcObjs 47 }
--
-- tnSvcArpHostIfEntry OBJECT-TYPE
--     SYNTAX      TnSvcArpHostIfEntry
--     MAX-ACCESS  not-accessible
--     STATUS      current
--     DESCRIPTION
--         "ARP host specific information about an IES interface."
--     INDEX { tnSysSwitchId, tnSvcId,
--             tnIesIfIndex }
--     ::= { tnSvcArpHostIfTable 1 }
--
-- TnSvcArpHostIfEntry ::=
--     SEQUENCE {
--         tnSvcArpHostIfLastMgmtChange       TimeStamp,
--         tnSvcArpHostIfAdminState           TmnxAdminState,
--         tnSvcArpHostIfMaxNumHosts          Unsigned32,
--         tnSvcArpHostIfMaxNumHostsSap       Unsigned32,
--         tnSvcArpHostIfMinAuthInterval      Unsigned32,
--         tnSvcArpHostIfNumHosts             Gauge32
--     }
--
-- tnSvcArpHostIfLastMgmtChange OBJECT-TYPE
--     SYNTAX      TimeStamp
--     MAX-ACCESS  read-only
--     STATUS      current
--     DESCRIPTION
--         "The value of tnSvcArpHostIfLastMgmtChange indicates the sysUpTime at
--          the time of the most recent management-initiated change to this
--          table row."
--     ::= { tnSvcArpHostIfEntry 1 }
--
-- tnSvcArpHostIfAdminState OBJECT-TYPE
--     SYNTAX      TmnxAdminState
--     MAX-ACCESS  read-write
--     STATUS      current
--     DESCRIPTION
--         "The value of the object tnSvcArpHostIfAdminState specifies the
--          administrative state of the ARP host functionality on this IES
--          interface.
--
--          The default value of this object is equal to 'outOfService',
--          except for a retailer interface, where it is 'inService'."
--     ::= { tnSvcArpHostIfEntry 2 }
--
-- tnSvcArpHostIfMaxNumHosts OBJECT-TYPE
--     SYNTAX      Unsigned32 (1..32767)
--     MAX-ACCESS  read-write
--     STATUS      current
--     DESCRIPTION
--         "The value of tnSvcArpHostIfMaxNumHosts specifies the maximum
--          number of ARP hosts allowed on this IES interface.
--
--          The default value of this object is equal to '1' except for a
--          retailer interface, where it is '32767'."
--     ::= { tnSvcArpHostIfEntry 3 }
--
-- tnSvcArpHostIfMaxNumHostsSap OBJECT-TYPE
--     SYNTAX      Unsigned32 (1..32767)
--     MAX-ACCESS  read-write
--     STATUS      current
--     DESCRIPTION
--         "The value of tnSvcArpHostIfMaxNumHosts specifies the maximum
--          number of ARP hosts per SAP allowed on this IES interface.
--
--          The value of this object is not relevant in case of a retailer
--          interface.
--
--          In other cases, the default value is equal to '1'."
--     ::= { tnSvcArpHostIfEntry 4 }
--
-- tnSvcArpHostIfMinAuthInterval OBJECT-TYPE
--     SYNTAX      Unsigned32 (1..6000)
--     UNITS       "minutes"
--     MAX-ACCESS  read-write
--     STATUS      current
--     DESCRIPTION
--         "The value of tnSvcArpHostIfMinAuthInterval specifies the minimum
--          interval between two consecutive authentication attempts for the
--          same ARP host.
--
--          The value of this object is not relevant in case of a retailer
--          interface.
--
--          In other cases, the default value is equal to '15'."
--     ::= { tnSvcArpHostIfEntry 5 }
--
-- tnSvcArpHostIfNumHosts OBJECT-TYPE
--     SYNTAX      Gauge32
--     MAX-ACCESS  read-only
--     STATUS      current
--     DESCRIPTION
--         "The value of tnSvcArpHostIfNumHosts indicates the actual
--          number of ARP hosts on this IES interface."
--     ::= { tnSvcArpHostIfEntry 6 }

tnSvcArpHostDefaultSessionTimeout OBJECT-TYPE
    SYNTAX      Unsigned32
    UNITS       "seconds"
    MAX-ACCESS  read-only
    STATUS      current
    DESCRIPTION
        "The value of tnSvcArpHostDefaultSessionTimeout indicates
         the default value of the ARP host session timeout.

         This default value is used if no value was specified, for instance
         by the Radius server.

         This is currently not used and always returns 0."
    ::= { tnSvcObjs 48 }

-- ---------------------------------------------------------------------
-- tnSvcIgmpTrkTable
--
--
--  Sparse Dependent Extension of the tnSvcBaseInfoTable.
--
--  The same indexes are used for both the base table, tnSvcBaseInfoTable,
--  and the sparse dependent table, tnSvcIgmpTrkTable.
--
--  This in effect extends the tnSvcBaseInfoTable with additional columns.
--  A row is automatically created in the tnSvcIgmpTrkTable for each row
--  in the tnSvcBaseInfoTable where the value of the object tnSvcType is equal to
--  'tls', 'ies' or 'vprn'.
--
--  Deletion of a row in the tnSvcBaseInfoTable results in the
--  same fate for the row in the tnSvcIgmpTrkTable.
-- ---------------------------------------------------------------------
tnSvcIgmpTrkTableLastMgmtChange OBJECT-TYPE
    SYNTAX      TimeStamp
    MAX-ACCESS  read-only
    STATUS      current
    DESCRIPTION
        "The value of tnSvcIgmpTrkTableLastMgmtChange indicates the sysUpTime
         at the time of the most recent management-initiated change to the
         tnSvcIgmpTrkTable.

         This is currently not used and always returns 0."
    ::= { tnSvcObjs 49 }

-- tnSvcIgmpTrkTable OBJECT-TYPE
--     SYNTAX      SEQUENCE OF TnSvcIgmpTrkEntry
--     MAX-ACCESS  not-accessible
--     STATUS      current
--     DESCRIPTION
--         "A table that contains IGMP host tracking information of a service."
--     ::= { tnSvcObjs 50 }
--
-- tnSvcIgmpTrkEntry OBJECT-TYPE
--     SYNTAX      TnSvcIgmpTrkEntry
--     MAX-ACCESS  not-accessible
--     STATUS      current
--     DESCRIPTION
--         "IGMP host tracking information about a specific service."
--     INDEX { tnSysSwitchId, tnSvcId }
--     ::= { tnSvcIgmpTrkTable 1 }
--
-- TnSvcIgmpTrkEntry ::=
--     SEQUENCE {
--         tnSvcIgmpTrkLastMgmtChange         TimeStamp,
--         tnSvcIgmpTrkAdminState             TmnxAdminState,
--         tnSvcIgmpTrkExpiryTime             Unsigned32
--     }
--
-- tnSvcIgmpTrkLastMgmtChange OBJECT-TYPE
--     SYNTAX      TimeStamp
--     MAX-ACCESS  read-only
--     STATUS      current
--     DESCRIPTION
--         "The value of tnSvcIgmpTrkLastMgmtChange indicates the sysUpTime at
--          the time of the most recent management-initiated change to this
--          table row."
--     ::= { tnSvcIgmpTrkEntry 1 }
--
-- tnSvcIgmpTrkAdminState OBJECT-TYPE
--     SYNTAX      TmnxAdminState
--     MAX-ACCESS  read-write
--     STATUS      current
--     DESCRIPTION
--         "The value of the object tnSvcIgmpTrkAdminState specifies the
--          administrative state of the IGMP host tracking in this service."
--     DEFVAL { outOfService }
--     ::= { tnSvcIgmpTrkEntry 2 }
--
-- tnSvcIgmpTrkExpiryTime OBJECT-TYPE
--     SYNTAX      Unsigned32 (1..65535)
--     UNITS       "seconds"
--     MAX-ACCESS  read-write
--     STATUS      current
--     DESCRIPTION
--         "The value of the object tnSvcIgmpTrkExpiryTime specifies
--          the time in seconds that this system continues to track an inactive
--          host."
--     DEFVAL { 260 }
--     ::= { tnSvcIgmpTrkEntry 3 }

-- ------------------------------------
-- IPIPE Service Table
-- ------------------------------------
tnSvcIpipeInfoTableLastMgmtChange OBJECT-TYPE
    SYNTAX       TimeStamp
    MAX-ACCESS   read-only
    STATUS       current
    DESCRIPTION
        "The value of tnSvcIpipeInfoTableLastMgmtChange indicates the
        timestamp of last change to the tnSvcIpipeInfoTable.

        This is currently not used and always returns 0."
    ::= { tnSvcObjs 51 }

-- tnSvcIpipeInfoTable OBJECT-TYPE
--     SYNTAX          SEQUENCE OF TnSvcIpipeInfoEntry
--     MAX-ACCESS      not-accessible
--     STATUS          current
--     DESCRIPTION     "A table that contains IPIPE service information."
--     ::= { tnSvcObjs 52 }
--
-- tnSvcIpipeInfoEntry OBJECT-TYPE
--     SYNTAX          TnSvcIpipeInfoEntry
--     MAX-ACCESS      not-accessible
--     STATUS          current
--     DESCRIPTION     "IPIPE specific information about a service."
--     INDEX           { tnSysSwitchId,  tnSvcId }
--     ::= { tnSvcIpipeInfoTable 1 }
--
-- TnSvcIpipeInfoEntry ::=
--     SEQUENCE {
--         tnSvcIpipeInfoLastMgmtChange       TimeStamp,
--         tnSvcIpipeCeAddressDiscovery       TmnxEnabledDisabled
--     }
--
-- tnSvcIpipeInfoLastMgmtChange        OBJECT-TYPE
--     SYNTAX      TimeStamp
--     MAX-ACCESS  read-only
--     STATUS      current
--     DESCRIPTION
--         "The value of tnSvcIpipeInfoLastMgmtChange indicates the value
--         of sysUpTime at the time of the most recent management change to
--         this row."
--     ::= { tnSvcIpipeInfoEntry 1 }
--
-- tnSvcIpipeCeAddressDiscovery OBJECT-TYPE
--     SYNTAX          TmnxEnabledDisabled
--     MAX-ACCESS      read-write
--     STATUS          current
--     DESCRIPTION     "The value of the object tnSvcIpipeCeAddressDiscovery
--                      specifies whether the service will automatically discover
--                      the CE IP addresses.
--
--                      If 'enabled', the addresses will be automatically
--                      discovered on SAPs that support address discovery, and on
--                      the Spoke SDPs.  When 'enabled', addresses configuration
--                      on the Ipipe SAP and Spoke SDPs will not be allowed.
--
--                      If 'disabled', CE IP addresses need to be manually
--                      configured for the SAPs to become operationally 'up'."
--     DEFVAL          { disabled }
--     ::= { tnSvcIpipeInfoEntry 2 }

-- ----------------------------------------
-- tnSvcDhcpLeaseStateBgpTable
-- ----------------------------------------
-- tnSvcDhcpLeaseStateBgpTable OBJECT-TYPE
--     SYNTAX          SEQUENCE OF TnSvcDhcpLeaseStateBgpEntry
--     MAX-ACCESS      not-accessible
--     STATUS          current
--     DESCRIPTION
--         "The tnSvcDhcpLeaseStateBgpTable augments the tnSvcDhcpLeaseStateTable.
--          This table contains the parameters used for BGP."
--     ::= { tnSvcObjs 53 }
--
-- tnSvcDhcpLeaseStateBgpEntry OBJECT-TYPE
--     SYNTAX          TnSvcDhcpLeaseStateBgpEntry
--     MAX-ACCESS      not-accessible
--     STATUS          current
--     DESCRIPTION
--         "Each row entry contains parameters used for BGP."
--     AUGMENTS        { tnSvcDhcpLeaseStateEntry }
--     ::= { tnSvcDhcpLeaseStateBgpTable 1 }
--
-- TnSvcDhcpLeaseStateBgpEntry ::=
--     SEQUENCE {
--         tnSvcDhcpLseStateBgpPrngPlcyName   TNamedItemOrEmpty,
--         tnSvcDhcpLseStateBgpAuthKeyChain   TNamedItemOrEmpty,
--         tnSvcDhcpLseStateBgpMD5AuthKey     OCTET STRING,
--         tnSvcDhcpLseStateBgpImportPolicy   TPolicyStatementNameOrEmpty,
--         tnSvcDhcpLseStateBgpExportPolicy   TPolicyStatementNameOrEmpty,
--         tnSvcDhcpLseStateBgpPeerAS         InetAutonomousSystemNumber,
--         tnSvcDhcpLseStateBgpPeeringStatus  BgpPeeringStatus
--     }
--
-- tnSvcDhcpLseStateBgpPrngPlcyName OBJECT-TYPE
--     SYNTAX          TNamedItemOrEmpty
--     MAX-ACCESS      read-only
--     STATUS          current
--     DESCRIPTION
--         "The value of tnSvcDhcpLseStateBgpPrngPlcyName indicates the
--          peering policy which is used to set up the BGP peer for this
--          lease state."
--     ::= { tnSvcDhcpLeaseStateBgpEntry 1 }
--
-- tnSvcDhcpLseStateBgpAuthKeyChain OBJECT-TYPE
--     SYNTAX          TNamedItemOrEmpty
--     MAX-ACCESS      read-only
--     STATUS          current
--     DESCRIPTION
--         "The value of tnSvcDhcpLseStateBgpAuthKeyChain indicates the
--          keychain which is used to sign and/or authenticate  the BGP
--          protocol stream."
--     ::= { tnSvcDhcpLeaseStateBgpEntry 2 }
--
-- tnSvcDhcpLseStateBgpMD5AuthKey OBJECT-TYPE
--     SYNTAX          OCTET STRING (SIZE(0..255))
--     MAX-ACCESS      read-only
--     STATUS          current
--     DESCRIPTION
--         "The value of tnSvcDhcpLseStateBgpMD5AuthKey indicates
--          the authentication key used between BGP
--          peers neighbors before establishing sessions. Authentication
--          is done using the MD-5 message based digest protocol."
--     ::= { tnSvcDhcpLeaseStateBgpEntry 3 }
--
-- tnSvcDhcpLseStateBgpImportPolicy OBJECT-TYPE
--     SYNTAX          TPolicyStatementNameOrEmpty
--     MAX-ACCESS      read-only
--     STATUS          current
--     DESCRIPTION
--         "The value of tnSvcDhcpLseStateBgpImportPolicy indicates
--          the import policy."
--     ::= { tnSvcDhcpLeaseStateBgpEntry 4 }
--
-- tnSvcDhcpLseStateBgpExportPolicy OBJECT-TYPE
--     SYNTAX          TPolicyStatementNameOrEmpty
--     MAX-ACCESS      read-only
--     STATUS          current
--     DESCRIPTION
--         "The value of tnSvcDhcpLseStateBgpExportPolicy indicates
--          the export policy."
--     ::= { tnSvcDhcpLeaseStateBgpEntry 5 }
--
-- tnSvcDhcpLseStateBgpPeerAS OBJECT-TYPE
--     SYNTAX          InetAutonomousSystemNumber
--     MAX-ACCESS      read-only
--     STATUS          current
--     DESCRIPTION
--         "The value of tnSvcDhcpLseStateBgpPeerAS indicates the Autonomous System
--          number for the remote peer."
--     ::= { tnSvcDhcpLeaseStateBgpEntry 6 }
--
-- tnSvcDhcpLseStateBgpPeeringStatus OBJECT-TYPE
--     SYNTAX          BgpPeeringStatus
--     MAX-ACCESS      read-only
--     STATUS          current
--     DESCRIPTION
--         "The value of tnSvcDhcpLseStateBgpPeeringStatus indicates
--          the status of the BGP peering session."
--     ::= { tnSvcDhcpLeaseStateBgpEntry 7 }

-- ----------------------------------------
-- Arp Host Managed Route Table
-- ----------------------------------------
-- tnSvcArpHostMRtTable OBJECT-TYPE
--     SYNTAX          SEQUENCE OF TnSvcArpHostMRtEntry
--     MAX-ACCESS      not-accessible
--     STATUS          current
--     DESCRIPTION     "The tnSvcArpHostMRtTable contains managed routes of
--                      ARP hosts.
--
--                      Entries in this table are created automatically
--                      by the system."
--     ::= { tnSvcObjs 54 }
--
-- tnSvcArpHostMRtEntry OBJECT-TYPE
--     SYNTAX          TnSvcArpHostMRtEntry
--     MAX-ACCESS      not-accessible
--     STATUS          current
--     DESCRIPTION     "Each row entry represents information on a specific
--                      managed route."
--     INDEX           { tnSysSwitchId,  tnSvcId,
--                       tnSvcArpHostIpAddrType,
--                       tnSvcArpHostIpAddr,
--                       tnSvcArpHostMRtAddrType,
--                       tnSvcArpHostMRtAddr,
--                       tnSvcArpHostMRtPrefixLen }
--     ::= { tnSvcArpHostMRtTable 1 }
--
-- TnSvcArpHostMRtEntry ::=
--     SEQUENCE {
--         tnSvcArpHostMRtAddrType          InetAddressType,
--         tnSvcArpHostMRtAddr              InetAddress,
--         tnSvcArpHostMRtPrefixLen         InetAddressPrefixLength,
--         tnSvcArpHostMRtStatus            TmnxManagedRouteStatus
--     }
--
-- tnSvcArpHostMRtAddrType OBJECT-TYPE
--     SYNTAX          InetAddressType
--     MAX-ACCESS      not-accessible
--     STATUS          current
--     DESCRIPTION     "The value of tnSvcArpHostMRtAddrType indicates
--                      the address type of tnSvcArpHostMRtAddr."
--     ::= { tnSvcArpHostMRtEntry 1 }
--
-- tnSvcArpHostMRtAddr OBJECT-TYPE
--     SYNTAX          InetAddress (SIZE(4|16))
--     MAX-ACCESS      not-accessible
--     STATUS          current
--     DESCRIPTION     "The value of tnSvcArpHostMRtAddr indicates
--                      the IP address of the managed route."
--     ::= { tnSvcArpHostMRtEntry 2 }
--
-- tnSvcArpHostMRtPrefixLen OBJECT-TYPE
--     SYNTAX          InetAddressPrefixLength
--     MAX-ACCESS      not-accessible
--     STATUS          current
--     DESCRIPTION     "The value of tnSvcArpHostMRtPrefixLen indicates
--                      the prefix length of the subnet associated with
--                      tnSvcArpHostMRtAddr."
--     ::= { tnSvcArpHostMRtEntry 3 }
--
-- tnSvcArpHostMRtStatus OBJECT-TYPE
--     SYNTAX          TmnxManagedRouteStatus
--     MAX-ACCESS      read-only
--     STATUS          current
--     DESCRIPTION     "The value of tnSvcArpHostMRtStatus indicates
--                      the state of this managed route."
--     ::= { tnSvcArpHostMRtEntry 4 }

-- ----------------------------------------
-- tnSvcArpHostBgpTable
--
--  Augmentation of the tnSvcArpHostTable
--  Use of AUGMENTS clause implies a one-to-one dependent relationship
--  between the base table, tnSvcArpHostTable, and the augmenting table,
--  tnSvcArpHostBgpTable. This in effect extends the tnSvcArpHostTable
--  with additional columns. Creation (or deletion) of a row in the
--  tnSvcArpHostTable results in the same fate for the row in the
--  tnSvcArpHostBgpTable.
-- ----------------------------------------
-- tnSvcArpHostBgpTable OBJECT-TYPE
--     SYNTAX          SEQUENCE OF TnSvcArpHostBgpEntry
--     MAX-ACCESS      not-accessible
--     STATUS          current
--     DESCRIPTION
--         "The tnSvcArpHostBgpTable augments the tnSvcArpHostTable.
--          This table contains the parameters used for BGP."
--     ::= { tnSvcObjs 55 }
--
-- tnSvcArpHostBgpEntry OBJECT-TYPE
--     SYNTAX          TnSvcArpHostBgpEntry
--     MAX-ACCESS      not-accessible
--     STATUS          current
--     DESCRIPTION
--         "Each row entry contains parameters used for BGP."
--     AUGMENTS        { tnSvcArpHostEntry }
--     ::= { tnSvcArpHostBgpTable 1 }
--
-- TnSvcArpHostBgpEntry ::=
--     SEQUENCE {
--         tnSvcArpHostBgpPrngPlcyName         TNamedItemOrEmpty,
--         tnSvcArpHostBgpAuthKeyChain         TNamedItemOrEmpty,
--         tnSvcArpHostBgpMD5AuthKey           OCTET STRING,
--         tnSvcArpHostBgpImportPolicy         TPolicyStatementNameOrEmpty,
--         tnSvcArpHostBgpExportPolicy         TPolicyStatementNameOrEmpty,
--         tnSvcArpHostBgpPeerAS               InetAutonomousSystemNumber,
--         tnSvcArpHostBgpPeeringStatus        BgpPeeringStatus
--     }
--
-- tnSvcArpHostBgpPrngPlcyName OBJECT-TYPE
--     SYNTAX          TNamedItemOrEmpty
--     MAX-ACCESS      read-only
--     STATUS          current
--     DESCRIPTION
--         "The value of tnSvcArpHostBgpPrngPlcyName indicates the
--          peering policy which is used to set up the BGP peer for this
--          ARP host."
--     ::= { tnSvcArpHostBgpEntry 1 }
--
-- tnSvcArpHostBgpAuthKeyChain OBJECT-TYPE
--     SYNTAX          TNamedItemOrEmpty
--     MAX-ACCESS      read-only
--     STATUS          current
--     DESCRIPTION
--         "The value of tnSvcArpHostBgpAuthKeyChain indicates
--          the keychain which is used to sign and/or authenticate  the BGP
--          protocol stream."
--     ::= { tnSvcArpHostBgpEntry 2 }
--
-- tnSvcArpHostBgpMD5AuthKey OBJECT-TYPE
--     SYNTAX          OCTET STRING (SIZE(0..255))
--     MAX-ACCESS      read-only
--     STATUS          current
--     DESCRIPTION
--         "The value of tnSvcArpHostBgpMD5AuthKey indicates
--          the authentication key used between BGP peers before establishing
--          sessions.
--
--          Authentication is done using the MD-5 message based digest protocol."
--     ::= { tnSvcArpHostBgpEntry 3 }
--
-- tnSvcArpHostBgpImportPolicy OBJECT-TYPE
--     SYNTAX          TPolicyStatementNameOrEmpty
--     MAX-ACCESS      read-only
--     STATUS          current
--     DESCRIPTION
--         "The value of tnSvcArpHostBgpImportPolicy indicates
--          the import policy."
--     ::= { tnSvcArpHostBgpEntry 4 }
--
-- tnSvcArpHostBgpExportPolicy OBJECT-TYPE
--     SYNTAX          TPolicyStatementNameOrEmpty
--     MAX-ACCESS      read-only
--     STATUS          current
--     DESCRIPTION
--         "The value of tnSvcArpHostBgpExportPolicy indicates
--          the export policy."
--     ::= { tnSvcArpHostBgpEntry 5 }
--
-- tnSvcArpHostBgpPeerAS OBJECT-TYPE
--     SYNTAX          InetAutonomousSystemNumber
--     MAX-ACCESS      read-only
--     STATUS          current
--     DESCRIPTION
--         "The value of tnSvcArpHostBgpPeerAS indicates
--          the Autonomous System number for the remote peer."
--     ::= { tnSvcArpHostBgpEntry 6 }
--
-- tnSvcArpHostBgpPeeringStatus OBJECT-TYPE
--     SYNTAX          BgpPeeringStatus
--     MAX-ACCESS      read-only
--     STATUS          current
--     DESCRIPTION
--         "The value of tnSvcArpHostBgpPeeringStatus indicates
--          the status of the BGP peering session."
--     ::= { tnSvcArpHostBgpEntry 7 }

-- ------------------------------------------------
-- tnSvcEpMcEpStatsTable table
-- ------------------------------------------------
-- tnSvcEpMcEpStatsTable OBJECT-TYPE
--     SYNTAX     SEQUENCE OF TnSvcEpMcEpStatsEntry
--     MAX-ACCESS not-accessible
--     STATUS     current
--     DESCRIPTION
--         "The tnSvcEpMcEpStatsTable has an entry for each end-point that
--          participates in a multi-chassis configuration for the indicated
--          peer."
--     ::= { tnSvcObjs 56 }
--
-- tnSvcEpMcEpStatsEntry OBJECT-TYPE
--     SYNTAX     TnSvcEpMcEpStatsEntry
--     MAX-ACCESS not-accessible
--     STATUS     current
--     DESCRIPTION
--         "Each row entry represents a collection of statistics for a end-point
--          that participates in a multi-chassis configuration with a given peer.
--
--          Entries cannot be created and deleted via SNMP SET operations."
--     INDEX       { tnSysSwitchId, tnSvcEndPointMCEPId }
--     ::= { tnSvcEpMcEpStatsTable 1 }
--
-- TnSvcEpMcEpStatsEntry ::= SEQUENCE
--    {
--        tnSvcEpMcEpStatsPktsRxConfig    Counter32,
--        tnSvcEpMcEpStatsPktsRxState     Counter32,
--        tnSvcEpMcEpStatsPktsTxConfig    Counter32,
--        tnSvcEpMcEpStatsPktsTxState     Counter32,
--        tnSvcEpMcEpStatsPktsTxFailed    Counter32
--    }
--
-- tnSvcEpMcEpStatsPktsRxConfig OBJECT-TYPE
--     SYNTAX       Counter32
--     MAX-ACCESS   read-only
--     STATUS       current
--     DESCRIPTION
--         "The value of tnSvcEpMcEpStatsPktsRxConfig indicates how many
--          multi-chassis end-point control packets of type end-point config were
--          received on this system from the peer for this end-point."
--     ::= { tnSvcEpMcEpStatsEntry 1 }
--
-- tnSvcEpMcEpStatsPktsRxState OBJECT-TYPE
--     SYNTAX       Counter32
--     MAX-ACCESS   read-only
--     STATUS       current
--     DESCRIPTION
--         "The value of tnSvcEpMcEpStatsPktsRxState indicates how many
--          multi-chassis end-point control packets of type end-point state were
--          received on this system from the peer for this end-point."
--     ::= { tnSvcEpMcEpStatsEntry 2 }
--
-- tnSvcEpMcEpStatsPktsTxConfig OBJECT-TYPE
--     SYNTAX       Counter32
--     MAX-ACCESS   read-only
--     STATUS       current
--     DESCRIPTION
--         "The value of tnSvcEpMcEpStatsPktsTxConfig indicates how many
--          multi-chassis end-point control packets of type end-point config were
--          sent on this system to the peer for this end-point."
--     ::= { tnSvcEpMcEpStatsEntry 3 }
--
-- tnSvcEpMcEpStatsPktsTxState OBJECT-TYPE
--     SYNTAX       Counter32
--     MAX-ACCESS   read-only
--     STATUS       current
--     DESCRIPTION
--         "The value of tnSvcEpMcEpStatsPktsTxState indicates how many
--          multi-chassis end-point control packets of type end-point state were
--          sent on this system to the peer for this end-point."
--     ::= { tnSvcEpMcEpStatsEntry 4 }
--
-- tnSvcEpMcEpStatsPktsTxFailed OBJECT-TYPE
--     SYNTAX       Counter32
--     MAX-ACCESS   read-only
--     STATUS       current
--     DESCRIPTION
--         "The value of tnSvcEpMcEpStatsPktsTxFailed indicates how many
--          multi-chassis end-point control packets failed to be transmitted on
--          this system to the peer for this end-point."
--     ::= { tnSvcEpMcEpStatsEntry 5 }

-- -----------------------------
-- tnSvc MAC Name table
-- -----------------------------
-- tnSvcPbbSrcBVplsMacAddr OBJECT-TYPE
--     SYNTAX          MacAddress
--     MAX-ACCESS      read-write
--     STATUS          current
--     DESCRIPTION     "The value of tnSvcPbbSrcBVplsMacAddr specifies the source
--                      Backbone MAC-Address to be used for Provider Backbone
--                      Bridging (PBB) packets.
--
--                      Value of default for this object indicates that chassis
--                      MAC address will be used for PBB packets."
--     DEFVAL { '000000000000'h }
--     ::= { tnSvcObjs 57 }
--
tnSvcMacNameTableLastChanged  OBJECT-TYPE
    SYNTAX          TimeStamp
    MAX-ACCESS      read-only
    STATUS          current
    DESCRIPTION     "The value of tnSvcMacNameTableLastChanged indicates the
                     sysUpTime at the time of the last modification of
                     tnSvcMacNameTable.

                     If no changes were made to the entry since the last
                     re-initialization of the local network management subsystem,
                     then this object contains a zero value.

                     This is currently not used and always returns 0."
    ::= { tnSvcObjs 58 }

-- tnSvcMacNameTable OBJECT-TYPE
--     SYNTAX          SEQUENCE OF TnSvcMacNameEntry
--     MAX-ACCESS      not-accessible
--     STATUS          current
--     DESCRIPTION     "The tnSvcMacNameTable contains objects related to
--                      MAC-name feature.
--
--                      Entries are created and destroyed using tnSvcMacNameRowStatus
--                      object."
--     ::= { tnSvcObjs 59 }
--
-- tnSvcMacNameEntry OBJECT-TYPE
--     SYNTAX          TnSvcMacNameEntry
--     MAX-ACCESS      not-accessible
--     STATUS          current
--     DESCRIPTION     "Each row entry contains objects that allows the
--                      modification of the MAC-name objects."
--     INDEX        { tnSysSwitchId, tnSvcMacName }
--     ::= { tnSvcMacNameTable 1 }
--
-- TnSvcMacNameEntry ::=
--     SEQUENCE {
--         tnSvcMacName                        TNamedItem,
--         tnSvcMacNameRowStatus               RowStatus,
--         tnSvcMacNameLastChngd               TimeStamp,
--         tnSvcMacNameAddr                    MacAddress
--     }
--
-- tnSvcMacName OBJECT-TYPE
--     SYNTAX          TNamedItem
--     MAX-ACCESS      not-accessible
--     STATUS          current
--     DESCRIPTION     "The value of tnSvcMacName specifies the name
--                      associated with a MAC address."
--     ::= { tnSvcMacNameEntry 1 }
--
-- tnSvcMacNameRowStatus OBJECT-TYPE
--     SYNTAX          RowStatus
--     MAX-ACCESS      read-create
--     STATUS          current
--     DESCRIPTION     "The value of tnSvcMacNameRowStatus is used for the
--                      creation and deletion of MAC information.
--
--                      To create an entry in the table, tnSvcMacNameAddr object
--                      must be set."
--     ::= { tnSvcMacNameEntry 2 }
--
-- tnSvcMacNameLastChngd        OBJECT-TYPE
--     SYNTAX          TimeStamp
--     MAX-ACCESS      read-only
--     STATUS          current
--     DESCRIPTION     "The value of tnSvcMacNameLastChngd indicates the sysUpTime at
--                      the time of the last modification of this entry.
--
--                      If no changes were made to the entry since the last
--                      re-initialization of the local network management
--                      subsystem, then this object contains a zero value."
--     ::= { tnSvcMacNameEntry 3 }
--
-- tnSvcMacNameAddr OBJECT-TYPE
--     SYNTAX          MacAddress
--     MAX-ACCESS      read-create
--     STATUS          current
--     DESCRIPTION     "The value of tnSvcMacNameAddr specifies the MAC-Address
--                      associated with the name defined in tnSvcMacName.
--
--                      This object must be set at the creation time."
--     ::= { tnSvcMacNameEntry 4 }

-- -----------------------------
-- tnSvc MAC Notification Group
-- -----------------------------

-- tnSvcMacNotificationGroup   OBJECT IDENTIFIER ::= { tnSvcObjs 60 }
--
-- tnSvcMacNotifInterval OBJECT-TYPE
--     SYNTAX          Unsigned32 (1..100)
--     UNITS           "deci-seconds"
--     MAX-ACCESS      read-write
--     STATUS          current
--     DESCRIPTION     "The value of tnSvcMacNotifInterval specifies time-interval
--                      between subsequent MAC notification messages."
--     REFERENCE       "ITU-T Y.1731 specification"
--     DEFVAL { 1 }
--     ::= { tnSvcMacNotificationGroup 1 }
--
-- tnSvcMacNotifCount OBJECT-TYPE
--     SYNTAX          Unsigned32 (1..10)
--     MAX-ACCESS      read-write
--     STATUS          current
--     DESCRIPTION     "The value of tnSvcMacNotifCount specifies number of
--                      MAC notification messages to be sent."
--     REFERENCE       "ITU-T Y.1731 specification"
--     DEFVAL { 3 }
--     ::= { tnSvcMacNotificationGroup 2 }

-- ------------------------------------
-- Implicit Protected Mac Table
-- ------------------------------------
-- tnTlsProtMacImplTable OBJECT-TYPE
--     SYNTAX          SEQUENCE OF TlsProtMacImplEntry
--     MAX-ACCESS      not-accessible
--     STATUS          current
--     DESCRIPTION     "A table that contains information about implicitly
--                      protected MAC addresses in a VPLS service."
--     ::= { tnSvcObjs 61 }
--
-- tnTlsProtMacImplEntry OBJECT-TYPE
--     SYNTAX          TlsProtMacImplEntry
--     MAX-ACCESS      not-accessible
--     STATUS          current
--     DESCRIPTION     "Each entry contains information about a specific
--                      implicitly protected MAC address.
--
--                      Rows are created or removed automatically by the system."
--     INDEX           { tnSysSwitchId,  tnSvcId,
--                       tnTlsProtMacImplMacAddr,
--                       tnTlsProtMacImplLocale,
--                       tnTlsProtMacImplPortId,
--                       tnTlsProtMacImplEncapValue,
--                       tnTlsProtMacImplSdpBindId }
--     ::= { tnTlsProtMacImplTable 1 }
--
-- TlsProtMacImplEntry ::=
--     SEQUENCE {
--         tnTlsProtMacImplMacAddr           MacAddress,
--         tnTlsProtMacImplLocale            INTEGER,
--         tnTlsProtMacImplPortId            TmnxPortID,
--         tnTlsProtMacImplEncapValue        TmnxEncapVal,
--         tnTlsProtMacImplSdpBindId         SdpBindId,
--         tnTlsProtMacImplCount             Counter32
--     }
--
-- tnTlsProtMacImplMacAddr OBJECT-TYPE
--     SYNTAX          MacAddress
--     MAX-ACCESS      not-accessible
--     STATUS          current
--     DESCRIPTION     "The value of the object tnTlsProtMacImplMacAddr indicates the
--                      48-bit IEEE 802.3 MAC address that is implicitly protected."
--     ::= { tnTlsProtMacImplEntry 1 }
--
-- tnTlsProtMacImplLocale OBJECT-TYPE
--     SYNTAX          INTEGER {
--                         any      (0),
--                         sap      (1),
--                         sdp      (2)
--                     }
--     MAX-ACCESS      not-accessible
--     STATUS          current
--     DESCRIPTION     "The value of the object tnTlsProtMacImplLocale indicates
--                      where the protection of the MAC address defined by
--                      tnTlsProtMacImplMacAddr is applied: anywhere, or only on
--                      a specific SAP or SDP."
--     ::= { tnTlsProtMacImplEntry 2 }
--
-- tnTlsProtMacImplPortId OBJECT-TYPE
--     SYNTAX          TmnxPortID
--     MAX-ACCESS      not-accessible
--     STATUS          current
--     DESCRIPTION     "When the value of tnTlsProtMacImplLocale is 'sap', this
--                      object, along with tnTlsProtMacImplEncapValue, indicates
--                      the SAP where this MAC address is protected.
--
--                      This object is otherwise insignificant and contains the
--                      value zero."
--     ::= { tnTlsProtMacImplEntry 3 }
--
-- tnTlsProtMacImplEncapValue OBJECT-TYPE
--     SYNTAX          TmnxEncapVal
--     MAX-ACCESS      not-accessible
--     STATUS          current
--     DESCRIPTION     "The value of the object tnTlsProtMacImplEncapValue indicates,
--                      when the value of tnTlsProtMacImplLocale is 'sap', along with
--                      tnTlsProtMacImplPortId, the SAP where this MAC address is
--                      protected.
--
--                      This object is otherwise insignificant and contains the
--                      value zero."
--     ::= { tnTlsProtMacImplEntry 4 }
--
-- tnTlsProtMacImplSdpBindId OBJECT-TYPE
--     SYNTAX          SdpBindId
--     MAX-ACCESS      not-accessible
--     STATUS          current
--     DESCRIPTION     "The value of the object tnTlsProtMacImplSdpBindId indicates,
--                      when the value of tnTlsProtMacImplLocale is 'sdp',
--                      the SDP Binding where this MAC address is protected.
--
--                      This object is otherwise insignificant and contains the
--                      value zero."
--     ::= { tnTlsProtMacImplEntry 5 }
--
-- tnTlsProtMacImplCount OBJECT-TYPE
--     SYNTAX          Counter32
--     MAX-ACCESS      read-only
--     STATUS          current
--     DESCRIPTION     "The value of the object tnTlsProtMacImplCount indicates
--                      how many times the protection of this MAC was activated
--                      at the indicated locale since the last re-initialization
--                      of the local network management subsystem, or the last
--                      time the system statistics were cleared."
--     ::= { tnTlsProtMacImplEntry 6 }

-- tnSvcTlsPbbIgmpSnpgMRtrTable OBJECT-TYPE
--     SYNTAX          SEQUENCE OF TnSvcTlsPbbIgmpSnpgMRtrEntry
--     MAX-ACCESS      not-accessible
--     STATUS          current
--     DESCRIPTION     "A table that contains
--                      Provider Backbone Bridging (PBB/IEEE 802.1ah) IGMP
--                      Snooping MRouter Destination information."
--     ::= { tnSvcObjs 82 }
--
-- tnSvcTlsPbbIgmpSnpgMRtrEntry OBJECT-TYPE
--     SYNTAX          TnSvcTlsPbbIgmpSnpgMRtrEntry
--     MAX-ACCESS      not-accessible
--     STATUS          current
--     DESCRIPTION     "PBB I-Component instance-specific information about a
--                      specific IGMP Snooping MRouter in the B-Component instance.
--
--                      Entries in this table can be created or deleted
--                      via SNMP operations."
--     INDEX           { tnSysSwitchId,  tnSvcTlsPbbIgmpSnpgMRtrSvcIdIVpls,
--                       tnSvcTlsPbbIgmpSnpgMRtrSvcIdBVpls,
--                       IMPLIED tnSvcTlsPbbIgmpSnpgMRtrMacName
--                     }
--     ::= { tnSvcTlsPbbIgmpSnpgMRtrTable 1 }
--
-- TnSvcTlsPbbIgmpSnpgMRtrEntry ::=
--     SEQUENCE {
--         tnSvcTlsPbbIgmpSnpgMRtrSvcIdIVpls  TmnxServId,
--         tnSvcTlsPbbIgmpSnpgMRtrSvcIdBVpls  TmnxServId,
--         tnSvcTlsPbbIgmpSnpgMRtrMacName     TNamedItem,
--         tnSvcTlsPbbIgmpSnpgMRtrRowStatus   RowStatus,
--         tnSvcTlsPbbIgmpSnpgMRtrLastCh      TimeStamp
--     }
--
-- tnSvcTlsPbbIgmpSnpgMRtrSvcIdIVpls OBJECT-TYPE
--     SYNTAX          TmnxServId
--     MAX-ACCESS      not-accessible
--     STATUS          current
--     DESCRIPTION     "The value of the object tnSvcTlsPbbIgmpSnpgMRtrSvcIdIVpls
--                      specifies the Service identifier of the I-Component
--                      instance."
--     ::= { tnSvcTlsPbbIgmpSnpgMRtrEntry 1 }
--
-- tnSvcTlsPbbIgmpSnpgMRtrSvcIdBVpls OBJECT-TYPE
--     SYNTAX          TmnxServId
--     MAX-ACCESS      not-accessible
--     STATUS          current
--     DESCRIPTION     "The value of the object tnSvcTlsPbbIgmpSnpgMRtrSvcIdBVpls
--                      specifies the Service identifier of the B-Component
--                      instance."
--     ::= { tnSvcTlsPbbIgmpSnpgMRtrEntry 2 }
--
-- tnSvcTlsPbbIgmpSnpgMRtrMacName OBJECT-TYPE
--     SYNTAX          TNamedItem
--     MAX-ACCESS      not-accessible
--     STATUS          current
--     DESCRIPTION     "The value of tnSvcTlsPbbIgmpSnpgMRtrMacName specifies
--                      the Destination MAC-Address-Name in the Backbone VPLS
--                      to reach a specific IGMP Snooping MRouter.
--
--                      In the case of an I-Component instance that is multi-homed
--                      on 2 physical nodes, an I-component instance, after
--                      becoming active, uses this MAC address as the destination
--                      MAC address to reach that IGMP Snooping MRouter.
--
--                      This allows to maintain the communication with that
--                      MRouter while no IGMP Queries from that MRouter have been
--                      snooped by this I-component instance."
--     ::= { tnSvcTlsPbbIgmpSnpgMRtrEntry 3 }
--
-- tnSvcTlsPbbIgmpSnpgMRtrRowStatus OBJECT-TYPE
--     SYNTAX          RowStatus
--     MAX-ACCESS      read-create
--     STATUS          current
--     DESCRIPTION     "The value of tnSvcTlsPbbIgmpSnpgMRtrRowStatus specifies
--                      the row status of this row.
--
--                      The only values supported during a set operation are
--                      'createAndGo' and 'destroy'."
--     ::= { tnSvcTlsPbbIgmpSnpgMRtrEntry 4 }
--
-- tnSvcTlsPbbIgmpSnpgMRtrLastCh OBJECT-TYPE
--     SYNTAX          TimeStamp
--     MAX-ACCESS      read-only
--     STATUS          current
--     DESCRIPTION
--                     "The value of tnSvcTlsPbbIgmpSnpgMRtrLastCh indicates
--                      the sysUpTime at the time of the most recent
--                      management-initiated change to this table row."
--     ::= { tnSvcTlsPbbIgmpSnpgMRtrEntry 5 }

--
-- Dummy Scalars
--
tnSvcScalar1 OBJECT-TYPE
    SYNTAX          Unsigned32
    MAX-ACCESS      read-only
    STATUS          current
    DESCRIPTION     "A dummy scalar that satisfies a SNMP get request
                     quickly when there is no 11QPE24 card provisioned.
                     Otherwise, it has to traverse the remaining 11QPE24
                     MIB to get to the next applicable item."
       ::= { tnSvcObjs 101 }

tnSvcScalar2 OBJECT-TYPE
    SYNTAX          Unsigned32
    MAX-ACCESS      read-only
    STATUS          current
    DESCRIPTION     "."
       ::= { tnSvcObjs 102 }

tnSvcScalar3 OBJECT-TYPE
    SYNTAX          Unsigned32
    MAX-ACCESS      read-only
    STATUS          current
    DESCRIPTION     "."
       ::= { tnSvcObjs 103 }

tnSvcScalar4 OBJECT-TYPE
    SYNTAX          Unsigned32
    MAX-ACCESS      read-only
    STATUS          current
    DESCRIPTION     "."
       ::= { tnSvcObjs 104 }

tnSvcScalar5 OBJECT-TYPE
    SYNTAX          Unsigned32
    MAX-ACCESS      read-only
    STATUS          current
    DESCRIPTION     "."
       ::= { tnSvcObjs 105 }

-- ------------------------------
-- Service trap objects
-- ------------------------------
-- tnMacPinningMacAddress OBJECT-TYPE
--     SYNTAX         MacAddress
--     MAX-ACCESS     accessible-for-notify
--     STATUS         current
--     DESCRIPTION    "The value of the object tnMacPinningMacAddress indicates
--                     the pinned MAC address."
--     ::= { tnSvcNotifyObjs 1 }
--
-- tnMacPinningPinnedRow OBJECT-TYPE
--     SYNTAX         RowPointer
--     MAX-ACCESS     accessible-for-notify
--     STATUS         current
--     DESCRIPTION    "The value of the object tnMacPinningPinnedRow indicates
--                     where the MAC address is currently pinned on.
--                     Its value will be the OID of the first accessible
--                     object in the row of the sapTlsInfoTable or in the
--                     sdpBindTable, depending on whether the MAC address is
--                     pinned on a SAP or a SDP Bind."
--     ::= { tnSvcNotifyObjs 2 }
--
-- tnMacPinningPinnedRowDescr OBJECT-TYPE
--     SYNTAX         DisplayString
--     MAX-ACCESS     accessible-for-notify
--     STATUS         current
--     DESCRIPTION    "The value of the object tnMacPinningPinnedRowDescr indicates
--                     where the MAC address is currently pinned on. The value
--                     will either be a SAP-id or a SDP id, presented in readable
--                     format, depending on whether the MAC is pinned to a SAP
--                     or a SDP."
--     ::= { tnSvcNotifyObjs 3 }
--
-- tnMacPinningViolatingRow OBJECT-TYPE
--     SYNTAX         RowPointer
--     MAX-ACCESS     accessible-for-notify
--     STATUS         current
--     DESCRIPTION    "The value of the object tnMacPinningViolatingRow indicates
--                     where the MAC address relearn attempt was detected.
--                     Its value will be the OID of the first accessible object
--                     in the row of the sapTlsInfoTable or in the sdpBindTable,
--                     depending on whether the MAC address is pinned on a SAP
--                     or a SDP Bind."
--     ::= { tnSvcNotifyObjs 4 }
--
-- tnMacPinningViolatingRowDescr OBJECT-TYPE
--     SYNTAX         DisplayString
--     MAX-ACCESS     accessible-for-notify
--     STATUS         current
--     DESCRIPTION    "The value of the object tnMacPinningViolatingRowDescr
--                     indicates where the MAC address relearn attempt was
--                     detected. The value will either be a SAP-id or a SDP id,
--                     presented in readable format, depending on whether the
--                     MAC address relearn attempt was detected on a SAP or a
--                     SDP."
--     ::= { tnSvcNotifyObjs 5 }
--
-- tnTlsDHCPClientLease OBJECT-TYPE
--     SYNTAX         Integer32
--     MAX-ACCESS     accessible-for-notify
--     STATUS         obsolete
--     DESCRIPTION    "The value of the object tnTlsDHCPClientLease indicates the
--                     lease time specified in the PDU causing the trap.
--                     Used by tmnxVRtrDHCPAFEntriesExceeded to report the lease
--                     time.
--                     This object was made obsolete in the 4.0 release."
--     ::= { tnSvcNotifyObjs 6 }
--
-- tnTlsDhcpLseStateOldCiAddr OBJECT-TYPE
--     SYNTAX         IpAddress
--     MAX-ACCESS     accessible-for-notify
--     STATUS         obsolete
--     DESCRIPTION    "The value of the object tnTlsDhcpLseStateOldCiAddr indicates
--                     the Client IP address that was formerly assigned to this
--                     Least state. Used in sapTlsDHCPLeaseStateOverride trap.
--                     This object was made obsolete in the 4.0 release."
--     ::= { tnSvcNotifyObjs 7 }
--
-- tnTlsDhcpLseStateOldChAddr OBJECT-TYPE
--     SYNTAX         MacAddress
--     MAX-ACCESS     accessible-for-notify
--     STATUS         obsolete
--     DESCRIPTION    "The value of the object tnTlsDhcpLseStateOldChAddr indicates
--                     the Client MAC address that was formerly assigned to this
--                     Least state. Used in sapTlsDHCPLeaseStateOverride trap.
--                     This object was made obsolete in the 4.0 release."
--     ::= { tnSvcNotifyObjs 8 }
--
-- tnTlsDhcpLseStateNewCiAddr OBJECT-TYPE
--     SYNTAX         IpAddress
--     MAX-ACCESS     accessible-for-notify
--     STATUS         obsolete
--     DESCRIPTION    "The value of the object tnTlsDhcpLseStateNewCiAddr indicates
--                     the Client IP address specified in the PDU causing
--                     the trap.
--                     This object was made obsolete in the 4.0 release."
--     ::= { tnSvcNotifyObjs 9 }
--
-- tnTlsDhcpLseStateNewChAddr OBJECT-TYPE
--     SYNTAX         MacAddress
--     MAX-ACCESS     accessible-for-notify
--     STATUS         obsolete
--     DESCRIPTION    "The value of the object tnTlsDhcpLseStateNewChAddr indicates
--                     the Client MAC address specified in the PDU causing
--                     the trap.
--                     This object was made obsolete in the 4.0 release."
--     ::= { tnSvcNotifyObjs 10 }
--
-- tnTlsDhcpRestoreLseStateCiAddr OBJECT-TYPE
--     SYNTAX         IpAddress
--     MAX-ACCESS     accessible-for-notify
--     STATUS         obsolete
--     DESCRIPTION    "The value of the object tnTlsDhcpRestoreLseStateCiAddr
--                     indicates the IP address specified in the persistency
--                     record causing the trap.
--                     This object was made obsolete in the 4.0 release."
--     ::= { tnSvcNotifyObjs 11 }
--
-- tnTlsDhcpRestoreLseStateSvcId OBJECT-TYPE
--     SYNTAX         TmnxServId
--     MAX-ACCESS     accessible-for-notify
--     STATUS         obsolete
--     DESCRIPTION    "The value of the object tnTlsDhcpRestoreLseStateSvcId
--                     indicates the serviceId specified in the persistency record
--                     causing the trap.
--                     This object was made obsolete in the 4.0 release."
--     ::= { tnSvcNotifyObjs 12 }
--
-- tnTlsDhcpRestoreLseStatePortId OBJECT-TYPE
--     SYNTAX         TmnxPortID
--     MAX-ACCESS     accessible-for-notify
--     STATUS         obsolete
--     DESCRIPTION    "The value of the object tnTlsDhcpRestoreLseStatePortId
--                     indicates the Port ID specified in the persistency record
--                     causing the trap.
--                     This object was made obsolete in the 4.0 release."
--     ::= { tnSvcNotifyObjs 13 }
--
-- tnTlsDhcpRestoreLseStateEncapVal OBJECT-TYPE
--     SYNTAX         TmnxEncapVal
--     MAX-ACCESS     accessible-for-notify
--     STATUS         obsolete
--     DESCRIPTION    "The value of the object tnTlsDhcpRestoreLseStateEncapVal
--                     indicates the SAP encap value specified in the persistency
--                     record causing the trap.
--                     This object was made obsolete in the 4.0 release."
--     ::= { tnSvcNotifyObjs 14 }
--
-- tnTlsDhcpRestoreLseStateProblem OBJECT-TYPE
--     SYNTAX         DisplayString
--     MAX-ACCESS     accessible-for-notify
--     STATUS         obsolete
--     DESCRIPTION    "The value of the object tnTlsDhcpRestoreLseStateProblem
--                     indicates why the persistency record cannot be restored.
--                     This object was made obsolete in the 4.0 release."
--     ::= { tnSvcNotifyObjs 15 }
--
-- tnTlsDhcpPacketProblem OBJECT-TYPE
--     SYNTAX         DisplayString
--     MAX-ACCESS     accessible-for-notify
--     STATUS         obsolete
--     DESCRIPTION    "The value of the object tnTlsDhcpPacketProblem indicates
--                     information on a received DHCP packet is considered
--                     suspicious by the system.
--                     This object was made obsolete in the 4.0 release."
--     ::= { tnSvcNotifyObjs 16 }
--
-- tnTlsDhcpLseStatePopulateError OBJECT-TYPE
--     SYNTAX         DisplayString
--     MAX-ACCESS     accessible-for-notify
--     STATUS         obsolete
--     DESCRIPTION    "The value of the object tnTlsDhcpLseStatePopulateError
--                     indicates  why the system was unable to update the
--                     Lease State Table upon reception of a DHCP ACK message.
--                     This object was made obsolete in the 4.0 release."
--     ::= { tnSvcNotifyObjs 17 }
--
-- tnSvcDhcpRestoreLseStateCiAddr OBJECT-TYPE
--     SYNTAX         IpAddress
--     MAX-ACCESS     accessible-for-notify
--     STATUS         current
--     DESCRIPTION    "The value of the object tnSvcDhcpRestoreLseStateCiAddr
--                     indicates the IP address specified in the persistency
--                     record causing the trap."
--     ::= { tnSvcNotifyObjs 18 }
--
-- tnSvcDhcpRestoreLseStateProblem OBJECT-TYPE
--     SYNTAX         DisplayString
--     MAX-ACCESS     accessible-for-notify
--     STATUS         current
--     DESCRIPTION    "The value of the object tnSvcDhcpRestoreLseStateProblem
--                     indicates why the persistency record cannot be restored."
--     ::= { tnSvcNotifyObjs 19 }
--
-- tnSvcDhcpLseStateOldCiAddr OBJECT-TYPE
--     SYNTAX         IpAddress
--     MAX-ACCESS     accessible-for-notify
--     STATUS         current
--     DESCRIPTION    "The value of the object tnSvcDhcpLseStateOldCiAddr indicates
--                     the client IP address that was formerly assigned to the
--                     specified DHCP lease state."
--     ::= { tnSvcNotifyObjs 20 }
--
-- tnSvcDhcpLseStateOldChAddr OBJECT-TYPE
--     SYNTAX         MacAddress
--     MAX-ACCESS     accessible-for-notify
--     STATUS         current
--     DESCRIPTION    "The value of the object tnSvcDhcpLseStateOldChAddr indicates
--                     the client MAC address that was formerly assigned to the
--                     specified DHCP lease state."
--     ::= { tnSvcNotifyObjs 21 }
--
-- tnSvcDhcpLseStateNewCiAddr OBJECT-TYPE
--     SYNTAX         IpAddress
--     MAX-ACCESS     accessible-for-notify
--     STATUS         current
--     DESCRIPTION    "The value of the object tnSvcDhcpLseStateNewCiAddr indicates
--                     the client IP address specified in the DHCP PDU causing the
--                     trap."
--     ::= { tnSvcNotifyObjs 22 }
--
-- tnSvcDhcpLseStateNewChAddr OBJECT-TYPE
--     SYNTAX         MacAddress
--     MAX-ACCESS     accessible-for-notify
--     STATUS         current
--     DESCRIPTION    "The value of the object tnSvcDhcpLseStateNewChAddr indicates
--                     the client MAC address specified in the DHCP PDU causing
--                     the trap."
--     ::= { tnSvcNotifyObjs 23 }
--
-- tnSvcDhcpClientLease OBJECT-TYPE
--     SYNTAX         Integer32
--     MAX-ACCESS     accessible-for-notify
--     STATUS         current
--     DESCRIPTION    "The value of the object tnSvcDhcpClientLease indicates the
--                     lease time specified in the DHCP PDU causing the trap."
--     ::= { tnSvcNotifyObjs 24 }
--
-- tnSvcDhcpPacketProblem OBJECT-TYPE
--     SYNTAX         DisplayString
--     MAX-ACCESS     accessible-for-notify
--     STATUS         current
--     DESCRIPTION    "The value of the object tnSvcDhcpPacketProblem indicates
--                     information on a received DHCP packet that is considered
--                     suspicious by the system."
--     ::= { tnSvcNotifyObjs 25 }
--
-- tnSvcDhcpLseStatePopulateError OBJECT-TYPE
--     SYNTAX         DisplayString
--     MAX-ACCESS     accessible-for-notify
--     STATUS         current
--     DESCRIPTION    "The value of the object tnSvcDhcpLseStatePopulateError
--                     indicates the reason why the system was unable to update
--                     the Lease State table upon reception of a DHCP ACK
--                     message."
--     ::= { tnSvcNotifyObjs 26 }
--
-- tnHostConnectivityCiAddrType OBJECT-TYPE
--     SYNTAX         InetAddressType
--     MAX-ACCESS     accessible-for-notify
--     STATUS         current
--     DESCRIPTION    "The value of the object tnHostConnectivityCiAddrType indicates
--                     the client address type causing the trap."
--     ::= { tnSvcNotifyObjs 27 }
--
-- tnHostConnectivityCiAddr OBJECT-TYPE
--     SYNTAX         InetAddress
--     MAX-ACCESS     accessible-for-notify
--     STATUS         current
--     DESCRIPTION    "The value of the object tnHostConnectivityCiAddr indicates
--                     the client INET address causing the trap."
--     ::= { tnSvcNotifyObjs 28 }
--
-- tnHostConnectivityChAddr OBJECT-TYPE
--     SYNTAX         MacAddress
--     MAX-ACCESS     accessible-for-notify
--     STATUS         current
--     DESCRIPTION    "The value of the object tnHostConnectivityChAddr indicates
--                     the client MAC address causing the trap."
--     ::= { tnSvcNotifyObjs 29 }
--
-- tnProtectedMacForNotify OBJECT-TYPE
--     SYNTAX         MacAddress
--     MAX-ACCESS     accessible-for-notify
--     STATUS         current
--     DESCRIPTION    "The value of the object tnProtectedMacForNotify indicates
--                     the protected MAC address that was received, causing the
--                     sapReceivedProtSrcMac notification."
--     ::= { tnSvcNotifyObjs 30 }
--
-- tnStaticHostDynamicMacIpAddress OBJECT-TYPE
--     SYNTAX         IpAddress
--     MAX-ACCESS     accessible-for-notify
--     STATUS         current
--     DESCRIPTION    "The value of the object tnStaticHostDynamicMacIpAddress
--                     indicates the IP address of the static host for which the
--                     sapStaticHostDynMacConflict notification is generated."
--     ::= { tnSvcNotifyObjs 31 }
--
-- tnStaticHostDynamicMacConflict OBJECT-TYPE
--     SYNTAX         DisplayString
--     MAX-ACCESS     accessible-for-notify
--     STATUS         current
--     DESCRIPTION    "The value of the object tnStaticHostDynamicMacConflict
--                     indicates the reason causing the sapStaticHostDynMacConflict
--                     notification."
--     ::= { tnSvcNotifyObjs 32 }
--
-- tnSvcObjRow OBJECT-TYPE
--     SYNTAX         RowPointer
--     MAX-ACCESS     accessible-for-notify
--     STATUS         current
--     DESCRIPTION    "The value of the object tnSvcObjRow indicates
--                     the object that has failed to perform the set action
--                     requested by the Time-Of-Day Suite.
--                     Its value will be the OID of the first accessible
--                     object in the row of the sapBaseInfoTable or in the
--                     tnCustMultiServiceSiteTable, depending on whether the object
--                     is a SAP or a Customer Multi-Service Site."
--     ::= { tnSvcNotifyObjs 33 }
--
-- tnSvcObjRowDescr OBJECT-TYPE
--     SYNTAX         DisplayString
--     MAX-ACCESS     accessible-for-notify
--     STATUS         current
--     DESCRIPTION    "The value of the object tnSvcObjRowDescr indicates
--                     the object that has failed to perform the set action
--                     requested by the Time-Of-Day Suite.
--                     The value will either be a SAP-id or
--                     a Customer Multi-Service Site id, presented in readable
--                     format, depending on whether the object
--                     is a SAP or a Customer Multi-Service Site."
--     ::= { tnSvcNotifyObjs 34 }
--
-- tnSvcObjTodSuite OBJECT-TYPE
--     SYNTAX     DisplayString
--     MAX-ACCESS accessible-for-notify
--     STATUS     current
--     DESCRIPTION
--         "The value of the object tnSvcObjTodSuite indicates the name of the
--          involved ToD Suite."
--     ::= { tnSvcNotifyObjs 35 }
--
-- tnFailureDescription OBJECT-TYPE
--     SYNTAX         DisplayString
--     MAX-ACCESS     accessible-for-notify
--     STATUS         current
--     DESCRIPTION    "The value of the object tnFailureDescription is a
--                     printable character string which contains information about
--                     the reason why the notification is sent."
--     ::= { tnSvcNotifyObjs 36 }
--
-- tnSvcDhcpProxyError OBJECT-TYPE
--     SYNTAX         DisplayString
--     MAX-ACCESS     accessible-for-notify
--     STATUS         current
--     DESCRIPTION    "The value of the object tnSvcDhcpProxyError indicates
--                     the reason why the proxy server failed to operate."
--     ::= { tnSvcNotifyObjs 37 }
--
-- tnSvcDhcpCoAError OBJECT-TYPE
--     SYNTAX         DisplayString
--     MAX-ACCESS     accessible-for-notify
--     STATUS         current
--     DESCRIPTION    "The value of the object tnSvcDhcpCoAError indicates
--                     the reason why the node failed to process a Change of
--                     Authorization (CoA) request from a Radius server."
--     ::= { tnSvcNotifyObjs 38 }
--
-- tnSvcDhcpSubAuthError OBJECT-TYPE
--     SYNTAX         DisplayString
--     MAX-ACCESS     accessible-for-notify
--     STATUS         current
--     DESCRIPTION    "The value of the object tnSvcDhcpSubAuthError is a printable
--                     character string which contains information about the
--                     problem that occurred while trying to authenticate the
--                     subscriber."
--     ::= { tnSvcNotifyObjs 39 }
--
-- tnSvcTlsMrpAttrRegFailedReason OBJECT-TYPE
--     SYNTAX         INTEGER {
--                       unknown                   (1),
--                       attribute-limit-reached   (2),
--                       system-attr-limit-reached (3),
--                       unsupported-attribute     (4),
--                       mfib-entry-create-failed  (5)
--                       }
--     MAX-ACCESS     accessible-for-notify
--     STATUS         current
--     DESCRIPTION    "The value of the object tnSvcTlsMrpAttrRegFailedReason
--                     indicates the reason for MRP attribute registration
--                     failure."
--     ::= { tnSvcNotifyObjs 40 }
--
-- tnSvcTlsMrpAttrType OBJECT-TYPE
--     SYNTAX         Unsigned32 (1..255)
--     MAX-ACCESS     accessible-for-notify
--     STATUS         current
--     DESCRIPTION    "The value of the object tnSvcTlsMrpAttrType indicates the
--                     type of MRP attribute."
--     ::= { tnSvcNotifyObjs 41 }
--
-- tnSvcTlsMrpAttrValue OBJECT-TYPE
--     SYNTAX         OCTET STRING (SIZE(0..255))
--     MAX-ACCESS     accessible-for-notify
--     STATUS         current
--     DESCRIPTION    "The value of the object tnSvcTlsMrpAttrValue indicates the
--                     value of MRP attribute."
--     ::= { tnSvcNotifyObjs 42 }
--
-- tnSvcMstiInstanceId OBJECT-TYPE
--     SYNTAX         MstiInstanceId
--     MAX-ACCESS     accessible-for-notify
--     STATUS         current
--     DESCRIPTION    "The value of the object tnSvcMstiInstanceId indicates the
--                     Multiple Spanning Tree Instance."
--     ::= { tnSvcNotifyObjs 43 }
--
-- == V7v0 feature, not in V6v1 :
-- tnSvcNotifSapPortId OBJECT-TYPE
--     SYNTAX         TmnxPortID
--     MAX-ACCESS     accessible-for-notify
--     STATUS         current
--     DESCRIPTION    "The ID of the access port where the SAP is defined."
--     ::= { tnSvcNotifyObjs 44 }
--
-- tnSvcNotifSapEncapValue OBJECT-TYPE
--     SYNTAX         TmnxEncapVal
--     MAX-ACCESS     accessible-for-notify
--     STATUS         current
--     DESCRIPTION    "The value of the label used to identify the
--                     SAP on the access port specified by sapPortId."
--     ::= { tnSvcNotifyObjs 45 }
--
-- tnSvcArpHostPopulateError OBJECT-TYPE
--     SYNTAX         DisplayString
--     MAX-ACCESS     accessible-for-notify
--     STATUS         current
--     DESCRIPTION    "The value of the object tnSvcArpHostPopulateError
--                     indicates the reason why the system failed to update
--                     the ARP Host table upon reception of an ARP message."
--     ::= { tnSvcNotifyObjs 46 }
--
-- tnSvcHostAddrType OBJECT-TYPE
--     SYNTAX         InetAddressType
--     MAX-ACCESS     accessible-for-notify
--     STATUS         current
--     DESCRIPTION    "The value of the object tnSvcHostAddrType
--                     indicates the address type of tnSvcHostAddr."
--     ::= { tnSvcNotifyObjs 47 }
--
-- tnSvcHostAddr OBJECT-TYPE
--     SYNTAX         InetAddress (SIZE(0|4|16))
--     MAX-ACCESS     accessible-for-notify
--     STATUS         current
--     DESCRIPTION    "The value of the object tnSvcHostAddr
--                     indicates the IP address specified in the persistency
--                     record causing the trap."
--     ::= { tnSvcNotifyObjs 48 }

-- ------------------------------------
-- Service traps
-- ------------------------------------
-- tnSvcCreated NOTIFICATION-TYPE
--     OBJECTS {
--         tnCustId,
--         tnSvcId,
--         tnSvcVpnId,
--         tnSvcType
--     }
--     STATUS          obsolete
--     DESCRIPTION     "This trap is sent when a new row is created
--                      in the tnSvcBaseInfoTable."
--     ::= { tnSvcTraps 1 }
--
-- tnSvcDeleted NOTIFICATION-TYPE
--     OBJECTS {
--         tnCustId,
--         tnSvcId,
--         tnSvcVpnId
--     }
--     STATUS          obsolete
--     DESCRIPTION     "This trap is sent when an existing row is
--                      deleted from the tnSvcBaseInfoTable."
--     ::= { tnSvcTraps 2 }
--
-- tnSvcStatusChanged NOTIFICATION-TYPE
--     OBJECTS {
--         tnCustId,
--         tnSvcId,
--         tnSvcVpnId,
--         tnSvcAdminStatus,
--         tnSvcOperStatus
--     }
--     STATUS          current
--     DESCRIPTION     "The tnSvcStatusChanged notification is generated when
--                      there is a change in the administrative or operating
--                      status of a service."
--     ::= { tnSvcTraps 3 }
--
-- tnSvcTlsFdbTableFullAlarmRaised NOTIFICATION-TYPE
--     OBJECTS {
--         tnCustId,
--         tnSvcId,
--         tnSvcVpnId
--     }
--     STATUS          current
--     DESCRIPTION     "The tnSvcTlsFdbTableFullAlarmRaised notification is
--                      generated when the utilization of the FDB table
--                      increases to reach the value specified by
--                      tnSvcTlsFdbTableFullHighWatermark."
--     ::= { tnSvcTraps 4 }
--
-- tnSvcTlsFdbTableFullAlarmCleared NOTIFICATION-TYPE
--     OBJECTS {
--         tnCustId,
--         tnSvcId,
--         tnSvcVpnId
--     }
--     STATUS          current
--     DESCRIPTION     "The tnSvcTlsFdbTableFullAlarmCleared notification is
--                      generated when the utilization of the FDB table
--                      drops to the value specified by
--                      tnSvcTlsFdbTableFullLowWatermark."
--     ::= { tnSvcTraps 5 }
--
-- tnIesIfCreated NOTIFICATION-TYPE
--     OBJECTS {
--         tnCustId,
--         tnSvcId,
--         tnSvcVpnId,
--         tnIesIfIndex
--     }
--     STATUS          obsolete
--     DESCRIPTION     "The tnIesIfCreated notification is generated
--                      when a new row is created in the tnIesIfTable."
--     ::= { tnSvcTraps 6 }
--
-- tnIesIfDeleted NOTIFICATION-TYPE
--     OBJECTS {
--         tnCustId,
--         tnSvcId,
--         tnSvcVpnId,
--         tnIesIfIndex
--     }
--     STATUS          obsolete
--     DESCRIPTION     "The tnIesIfDeleted notification is sent when an existing
--                      row is deleted from the tnIesIfTable."
--     ::= { tnSvcTraps 7 }
--
-- tnIesIfStatusChanged NOTIFICATION-TYPE
--     OBJECTS {
--         tnCustId,
--         tnSvcId,
--         tnSvcVpnId,
--         tnIesIfIndex,
--         tnIesIfAdminStatus,
--         tnIesIfOperStatus
--     }
--     STATUS          current
--     DESCRIPTION     "The tnIesIfStatusChanged notification is generated
--                      when there is a change in the administrative or
--                      operating status of an IES interface."
--     ::= { tnSvcTraps 8 }
--
-- tnSvcTlsMfibTableFullAlarmRaised NOTIFICATION-TYPE
--     OBJECTS {
--         tnCustId,
--         tnSvcId,
--         tnSvcVpnId
--     }
--     STATUS          current
--     DESCRIPTION     "The tnSvcTlsMfibTableFullAlarmRaised notification is
--                      generated when the utilization of the MFIB table increases
--                      to reach the value specified by
--                      tnSvcTlsMfibTableFullHighWatermark."
--     ::= { tnSvcTraps 9 }
--
-- tnSvcTlsMfibTableFullAlarmCleared NOTIFICATION-TYPE
--     OBJECTS {
--         tnCustId,
--         tnSvcId,
--         tnSvcVpnId
--     }
--     STATUS          current
--     DESCRIPTION     "The tnSvcTlsMfibTableFullAlarmCleared notification is
--                      generated when the utilization of the MFIB table
--                      drops to the value specified by
--                      tnSvcTlsMfibTableFullLowWatermark."
--     ::= { tnSvcTraps 10 }
--
-- tnSvcTlsMacPinningViolation NOTIFICATION-TYPE
--     OBJECTS {
--         tnCustId,
--         tnSvcId,
--         tnSvcVpnId,
--         tnMacPinningMacAddress,
--         tnMacPinningPinnedRow,
--         tnMacPinningPinnedRowDescr,
--         tnMacPinningViolatingRow,
--         tnMacPinningViolatingRowDescr
--     }
--     STATUS          current
--     DESCRIPTION     "The tnSvcTlsMacPinningViolation notification is
--                      generated when an attempt is made to assign a MAC
--                      address to another interface while this MAC address
--                      is pinned (i.e. assigned fixed to an interface)."
--     ::= { tnSvcTraps 11 }
--
-- tnSvcTlsDHCPLseStRestoreProblem NOTIFICATION-TYPE
--     OBJECTS {
--         tnTlsDhcpRestoreLseStateSvcId,
--         tnTlsDhcpRestoreLseStatePortId,
--         tnTlsDhcpRestoreLseStateEncapVal,
--         tnTlsDhcpRestoreLseStateCiAddr,
--         tnTlsDhcpRestoreLseStateProblem
--     }
--     STATUS          obsolete
--     DESCRIPTION     "The tnSvcTlsDHCPLseStRestoreProblem notification is
--                      generated when an an error is detected while
--                      processing a persistency record."
--     ::= { tnSvcTraps 12 }
--
-- tnSvcTlsDHCPLseStatePopulateErr NOTIFICATION-TYPE
--     OBJECTS {
--         tnCustId,
--         tnSvcId,
--         tnTlsDhcpLseStatePopulateError
--     }
--     STATUS          obsolete
--     DESCRIPTION     "The tnSvcTlsDHCPLseStatePopulateErr notification
--                      indicates that the system was unable to update the
--                      Lease State Table with the information contained in
--                      the DHCP ACK message. The DHCP ACK message has been
--                      discarded."
--     ::= { tnSvcTraps 13 }
--
-- tnSvcDHCPLseStateRestoreProblem NOTIFICATION-TYPE
--     OBJECTS {
--         tnSvcDhcpRestoreLseStateCiAddr,
--         tnSvcDhcpRestoreLseStateProblem
--     }
--     STATUS          current
--     DESCRIPTION     "The tnSvcDHCPLseStateRestoreProblem notification is
--                      generated when an an error is detected while processing a
--                      persistency record."
--     ::= { tnSvcTraps 14 }
--
-- tnSvcObjTodSuiteApplicFailed NOTIFICATION-TYPE
--     OBJECTS {
--         tnSvcObjRow,
--         tnSvcObjRowDescr,
--         tnSvcObjTodSuite,
--         tnFailureDescription
--     }
--     STATUS          current
--     DESCRIPTION     "The tnSvcObjTodSuiteApplicFailed notification is
--                      generated when the object has failed to perform the set
--                      action requested by the Time-Of-Day Suite. The object can
--                      be either a SAP or a Customer Multi-Service Site."
--     ::= { tnSvcTraps 15 }
--
-- tnEndPointTxActiveChanged       NOTIFICATION-TYPE
--     OBJECTS {
--         tnSvcEndPointTxActiveType,
--         tnSvcEndPointTxActivePortId,
--         tnSvcEndPointTxActiveEncap,
--         tnSvcEndPointTxActiveSdpId
--     }
--     STATUS          current
--     DESCRIPTION     "The tnEndPointTxActiveChanged notification is generated
--                      when the transmit active object on an endpoint changes."
--     ::= { tnSvcTraps 16 }
--
-- tnSvcPEDiscPolServOperStatChg NOTIFICATION-TYPE
--     OBJECTS {
--         tnSvcPEDiscPolServerAddressType,
--         tnSvcPEDiscPolServerAddress,
--         tnSvcPEDiscPolServerOperStatus
--     }
--     STATUS  current
--     DESCRIPTION
--         "The tnSvcPEDiscPolServOperStatChg notification is generated
--          when the operational status of a Radius server, configured for use
--          as PE Discovery Policy Server, has transitioned either from 'up' to
--          'down' or from 'down' to 'up'."
--     ::= { tnSvcTraps 17 }
--
-- tnSvcEndPointMacLimitAlarmRaised  NOTIFICATION-TYPE
--     OBJECTS {
--         tnCustId,
--         tnSvcId,
--         tnSvcVpnId,
--         tnSvcEndPointMacLimit
--     }
--     STATUS          current
--     DESCRIPTION
--         "The tnSvcEndPointMacLimitAlarmRaised notification is sent whenever the
--         number of MAC addresses stored in the FDB for this endpoint exceeds the
--         watermark specified by the object tnSvcTlsFdbTableFullHighWatermark.
--
--         This alarm also takes into consideration static MAC addresses
--         configured on the endpoint and learned MAC addresses in all spokes
--         associated with this endpoint."
--     ::= { tnSvcTraps 18 }
--
-- tnSvcEndPointMacLimitAlarmCleared  NOTIFICATION-TYPE
--     OBJECTS {
--         tnCustId,
--         tnSvcId,
--         tnSvcVpnId,
--         tnSvcEndPointMacLimit
--     }
--     STATUS          current
--     DESCRIPTION
--         "The tnSvcEndPointMacLimitAlarmCleared notification is sent whenever the
--         number of MAC addresses stored in the FDB for this endpoint drops below
--         the watermark specified by the object tnSvcTlsFdbTableFullLowWatermark.
--
--         This alarm also takes into consideration static MAC addresses
--         configured on the endpoint and learned MAC addresses in all spokes
--         associated with this endpoint."
--     ::= { tnSvcTraps 19 }
--
-- tnSvcTlsMrpAttrRegistrationFailed NOTIFICATION-TYPE
--     OBJECTS {
--         tnCustId,
--         tnSvcId,
--         tnSvcTlsMrpAttrRegFailedReason,
--         tnSvcTlsMrpAttrType,
--         tnSvcTlsMrpAttrValue
--     }
--     STATUS          current
--     DESCRIPTION     "The tnSvcTlsMrpAttrRegistrationFailed notification is
--                      generated when registration fails for an MRP attribute."
--     ::= { tnSvcTraps 20 }
--
-- tnSvcFdbMimDestTblFullAlrm NOTIFICATION-TYPE
--     OBJECTS {
--             tnSvcTotalFdbMimDestIdxEntries
--     }
--     STATUS          current
--     DESCRIPTION     "The tnSvcFdbMimDestTblFullAlrm notification is raised
--                      when system limit of Backbone MAC address indices limit is
--                      reached.
--
--                      Further traps are not generated as long as the value of
--                      tnSvcTotalFdbMimDestIdxEntries object remains under 5
--                      percent of the limit."
--    ::= { tnSvcTraps 21 }
--
-- tnSvcFdbMimDestTblFullAlrmCleared NOTIFICATION-TYPE
--     OBJECTS {
--             tnSvcTotalFdbMimDestIdxEntries
--     }
--     STATUS          current
--     DESCRIPTION     "The tnSvcFdbMimDestTblFullAlrmCleared notification is raised
--                      when number of Backbone MAC address indices used reaches
--                      under 95 percent of the system limit after
--                      tnSvcFdbMimDestTblFullAlrm notification had been raised."
--    ::= { tnSvcTraps 22 }
--
-- tnSvcDHCPMiscellaneousProblem NOTIFICATION-TYPE
--     OBJECTS {
--             tnFailureDescription
--     }
--     STATUS          current
--     DESCRIPTION     "The tnSvcDHCPMiscellaneousProblem notification is
--                      generated on miscellaneous DHCP problems."
--     ::= { tnSvcTraps 23 }
--
-- tnSvcPersistencyProblem NOTIFICATION-TYPE
--     OBJECTS {
--             tnSvcId,
--             tnFailureDescription
--     }
--     STATUS          current
--     DESCRIPTION     "The tnSvcPersistencyProblem notification is generated
--                      on persistency problems."
--     ::= { tnSvcTraps 24 }
--
-- tnSvcTlsMrpAttrTblFullAlarmRaised NOTIFICATION-TYPE
--     OBJECTS {
--         tnCustId,
--         tnSvcId,
--         tnSvcVpnId
--     }
--     STATUS          current
--     DESCRIPTION     "The tnSvcTlsMrpAttrTblFullAlarmRaised notification is
--                      generated when the utilization of the MRP attribute table
--                      is above the value specified by
--                      tnSvcTlsMrpAttrTblHighWatermark."
--     ::= { tnSvcTraps 25 }
--
-- tnSvcTlsMrpAttrTblFullAlarmCleared NOTIFICATION-TYPE
--     OBJECTS {
--         tnCustId,
--         tnSvcId,
--         tnSvcVpnId
--     }
--     STATUS          current
--     DESCRIPTION     "The tnSvcTlsMrpAttrTblFullAlarmCleared notification is
--                      generated when the utilization of the MRP attribute table
--                      is below the value specified by
--                      tnSvcTlsMrpAttrTblLowWatermark."
--     ::= { tnSvcTraps 26 }
--
-- V7v0 feature, not in V6v1 :
-- tnSvcArpHostPopulateErr NOTIFICATION-TYPE
--     OBJECTS {
--         tnSvcId,
--         tnSvcNotifSapPortId,
--         tnSvcNotifSapEncapValue,
--         tnSvcArpHostPopulateError
--     }
--     STATUS          current
--     DESCRIPTION     "The tnSvcArpHostPopulateErr notification indicates that
--                      the system failed to update the ARP Host table
--                      with the information contained in the ARP message."
--     ::= { tnSvcTraps 27 }
--
-- tnSvcEpipePbbOperStatusChanged NOTIFICATION-TYPE
--     OBJECTS {
--         tnSvcEpipePbbOperState
--     }
--     STATUS          current
--     DESCRIPTION     "The tnSvcEpipePbbOperStatusChanged notification is generated
--                      when there is a change in the operating status of the
--                      PBB tunnel associated with this E-pipe service."
--     ::= { tnSvcTraps 28 }
--
-- tnSvcEPMCEPConfigMismatch NOTIFICATION-TYPE
--    OBJECTS {
--         tnSvcEndPointMCEPId
--    }
--    STATUS       current
--    DESCRIPTION  "The tnSvcEPMCEPConfigMismatch notification is generated
--                  when service multi-chassis endpoint detects a mismatch in the
--                  config of the multi-chassis endpoint peer."
--     ::= { tnSvcTraps 29 }
--
-- tnSvcEPMCEPConfigMismatchResolved NOTIFICATION-TYPE
--    OBJECTS {
--         tnSvcEndPointMCEPId
--    }
--    STATUS       current
--    DESCRIPTION  "The tnSvcEPMCEPConfigMismatchResolved notification is generated
--                  when multi-chassis endpoint resolves the mismatch in the config
--                  of the multi-chassis endpoint peer."
--     ::= { tnSvcTraps 30 }
--
-- tnSvcEPMCEPPassiveModeActive  NOTIFICATION-TYPE
--     OBJECTS      {
--         tnSvcEndPointMCEPId
--     }
--     STATUS       current
--     DESCRIPTION
--          "The tnSvcEPMCEPPassiveModeActive notification is generated when
--          multi-chassis endpoint on a multi-chassis peer in passive-mode
--          (of multi-chassis peer) becomes passive-mode active by detecting more
--          than one active spoke-sdp in the multi-chassis endpoint with
--          'pwFwdingStandby' bit cleared per sdpBindPwPeerStatusBits object."
--     ::= { tnSvcTraps 31 }
--
-- tnSvcEPMCEPPassiveModePassive  NOTIFICATION-TYPE
--     OBJECTS      {
--         tnSvcEndPointMCEPId
--     }
--     STATUS       current
--     DESCRIPTION
--          "The tnSvcEPMCEPPassiveModePassive notification is generated when
--          multi-chassis endpoint on a multi-chassis peer in passive-mode
--          (of multi-chassis peer) becomes passive-mode passive by detecting at
--          most one active spoke-sdp in the multi-chassis endpoint with
--          'pwFwdingStandby' bit set per sdpBindPwPeerStatusBits object."
--     ::= { tnSvcTraps 32 }
--
-- tnSvcRestoreHostProblem NOTIFICATION-TYPE
--     OBJECTS {
--         tnSvcHostAddrType,
--         tnSvcHostAddr,
--         tnFailureDescription
--     }
--     STATUS          current
--     DESCRIPTION     "The tnSvcRestoreHostProblem notification is
--                      generated when an an error is detected while processing a
--                      host persistency record."
--     ::= { tnSvcTraps 33 }

-- --------------------------------------------------
-- TLS STP trap notification objects
-- --------------------------------------------------
-- tnCustomerBridgeId OBJECT-TYPE
--     SYNTAX         BridgeId
--     MAX-ACCESS     accessible-for-notify
--     STATUS         current
--     DESCRIPTION    "tnCustomerBridgeId specifies the bridge identifier
--                     of the tnCustomer's device "
--     ::= { tnTstpNotifyObjs 1 }
--
-- tnCustomerRootBridgeId OBJECT-TYPE
--     SYNTAX         BridgeId
--     MAX-ACCESS     accessible-for-notify
--     STATUS         current
--     DESCRIPTION    "tnCustomerRootBridgeId specifies the bridge identifier
--                     of the tnCustomer's designated root."
--     ::= { tnTstpNotifyObjs 2 }
--
-- tnOtherBridgeId OBJECT-TYPE
--     SYNTAX         BridgeId
--     MAX-ACCESS     accessible-for-notify
--     STATUS         current
--     DESCRIPTION    "tnOtherBridgeId specifies the bridge identifier of
--                     the device from which a BPDU was received."
--     ::= { tnTstpNotifyObjs 3 }
--
-- tnOldSdpBindTlsStpPortState OBJECT-TYPE
--     SYNTAX         TStpPortState
--     MAX-ACCESS     accessible-for-notify
--     STATUS         current
--     DESCRIPTION    "tnOldSdpBindTlsStpPortState specifies the previous
--                     state of an SDP binding."
--     ::= { tnTstpNotifyObjs 4 }
--
-- tnVcpState OBJECT-TYPE
--     SYNTAX         TStpPortState
--     MAX-ACCESS     accessible-for-notify
--     STATUS         current
--     DESCRIPTION    "tnVcpState specifies the current state of a Virtual
--                     Core Port (VCP)."
--     ::= { tnTstpNotifyObjs 5 }

-- ------------------------------------
-- TLS STP traps
-- ------------------------------------
-- tnTopologyChangeVcpState NOTIFICATION-TYPE
--     OBJECTS {
--         tnCustId,
--         tnSvcId,
--         tnVcpState
--     }
--     STATUS          current
--     DESCRIPTION     "The tnTopologyChangeVcpState   notification is generated
--                      when a VCP has transitioned its state from disabled to
--                      forwarding   or   from  forwarding  to  disabled.  The
--                      spanning  tree  topology  has been modified and it may
--                      denote  loss  of  tnCustomer access or redundancy. Check
--                      the  new  topology against the provisioned topology to
--                      determine severity of connectivity loss."
--     ::= { tnTstpTraps 3 }
--
-- tnNewRootVcpState NOTIFICATION-TYPE
--     OBJECTS {
--         tnCustId,
--         tnSvcId
--     }
--     STATUS          current
--     DESCRIPTION     "The tnNewRootVcpState notification is generated when the
--                      previous  root bridge has been aged out and a new root
--                      bridge has been elected. The new root bridge creates a
--                      new  spanning  tree topology and it may denote loss of
--                      tnCustomer  access or redundancy. Check the new topology
--                      against the provisioned topology to determine severity
--                      of connectivity loss."
--     ::= { tnTstpTraps 4 }
--
-- tnNewRootBridge NOTIFICATION-TYPE
--     OBJECTS {
--         tnCustId,
--         tnSvcId
--     }
--     STATUS          current
--     DESCRIPTION     "The tnNewRootBridge  notification is generated when this
--                      bridge  has been elected as the new root bridge. A new
--                      root  bridge  creates a new spanning tree topology and
--                      may  denote  loss  of  tnCustomer  access or redundancy.
--                      Check   the   new  topology  against  the  provisioned
--                      topology to determine severity of connectivity loss."
--     ::= { tnTstpTraps 7 }
--
-- tnVcpActiveProtocolChange NOTIFICATION-TYPE
--     OBJECTS {
--         tnCustId,
--         tnSvcId,
--         tnSvcTlsStpVcpOperProtocol
--     }
--     STATUS          current
--     DESCRIPTION     "The  tnVcpActiveProtocolChange notification is generated
--                      when  the  spanning  tree protocol on this VCP changes
--                      from  rstp  to  stp  or  vise  versa.  No  recovery is
--                      needed."
--     ::= { tnTstpTraps 32 }
--
-- tnNewCistRegionalRootBridge NOTIFICATION-TYPE
--     OBJECTS {
--         tnSvcId,
--         tnSvcTlsStpCistRegionalRoot
--     }
--     STATUS          current
--     DESCRIPTION     "The tnNewCistRegionalRootBridge notification is
--                      generated when a new regional root bridge has been elected
--                      for the Common and Internal Spanning Tree. A new regional
--                      root bridge  creates a new spanning tree topology and may
--                      denote  loss  of  tnCustomer  access or redundancy. Check
--                      the   new  topology  against  the provisioned  topology
--                      to determine severity of connectivity loss."
--     ::= { tnTstpTraps 33 }
--
-- tnNewMstiRegionalRootBridge NOTIFICATION-TYPE
--     OBJECTS {
--         tnSvcId,
--         tnSvcMstiInstanceId,
--         tnTlsMstiRegionalRoot
--     }
--     STATUS          current
--     DESCRIPTION     "The tnNewMstiRegionalRootBridge notification is
--                      generated when a new regional root bridge has been elected
--                      for the Multiple Spanning Tree Instance. A new regional
--                      root bridge  creates a new spanning tree topology and may
--                      denote  loss  of  tnCustomer  access or redundancy. Check
--                      the   new  topology  against  the provisioned  topology
--                      to determine severity of connectivity loss."
--     ::= { tnTstpTraps 34 }
--
-- tnTopologyChangePipMajorState NOTIFICATION-TYPE
--     OBJECTS {
--         tnCustId,
--         tnSvcId
--     }
--     STATUS         current
--     DESCRIPTION
--         "The tnTopologyChangePipMajorState notification is generated when
--         a PIP Uplink has transitioned its state from learning to forwarding or
--         from forwarding to blocking or broken. The spanning tree topology has
--         been modified and it may denote loss of tnCustomer access or redundancy.
--         Check the new topology against the provisioned topology to determine the
--         severity of connectivity loss."
--     ::= { tnTstpTraps 39 }
--
-- tnTopologyChangePipState NOTIFICATION-TYPE
--     OBJECTS {
--         tnCustId,
--         tnSvcId
--     }
--     STATUS          current
--     DESCRIPTION
--         "The tnTopologyChangePipState notification is generated when a PIP Uplink
--         has transitioned state to blocking or broken from a state other than
--         forwarding. This event complements what is not covered by
--         tnTopologyChangePipMajorState. The spanning tree topology has been
--         modified and it may denote loss of tnCustomer access or redundancy. Check
--         the new topology against the provisioned topology to determine severity
--         of connectivity loss."
--     ::= { tnTstpTraps 40 }
--
-- tnPipStpExcepCondStateChng NOTIFICATION-TYPE
--     OBJECTS {
--         tnCustId,
--         tnSvcId,
--         tnTlsPipStpException
--     }
--     STATUS          current
--     DESCRIPTION
--         "The tnPipStpExcepCondStateChng notification is generated when the
--         value of the object tnTlsPipStpException has changed, i.e. when the
--         exception condition changes on the indicated PIP Uplink."
--     ::= { tnTstpTraps 41 }
--
-- tnPipActiveProtocolChange NOTIFICATION-TYPE
--     OBJECTS {
--         tnCustId,
--         tnSvcId
--     }
--     STATUS          current
--     DESCRIPTION
--         "The tnPipActiveProtocolChange notification is generated when the
--         spanning tree protocol on this PIP Uplink changes from rstp to stp or
--         vice-versa.  No recovery is needed."
--     ::= { tnTstpTraps 42 }

-- ----------------------------------------------------------------------------
-- Conformance Information
-- ----------------------------------------------------------------------------
-- tnCustCompliances OBJECT IDENTIFIER ::= { tnCustConformance 1 }
-- tnCustGroups      OBJECT IDENTIFIER ::= { tnCustConformance 2 }

-- tnSvcCompliances  OBJECT IDENTIFIER ::= { tnSvcConformance 1 }
-- tnSvcGroups       OBJECT IDENTIFIER ::= { tnSvcConformance 2 }

-- tnTstpCompliances OBJECT IDENTIFIER ::= { tnTstpConformance 1 }
-- tnTstpGroups      OBJECT IDENTIFIER ::= { tnTstpConformance 2 }

-- ----------------------------------------------
-- Compliance Statements
-- ----------------------------------------------
-- tnCustCompliance MODULE-COMPLIANCE
--    STATUS  current
--    DESCRIPTION
--        "The compliance statement for management of services tnCustomers
--         on Nokia 7x50 SR series systems."
--    MODULE  this module
--        MANDATORY-GROUPS
--        {
--            tnCustV6v0Group
--        }
--    ::= { tnCustCompliances 100 }

-- tnSvc7450V6v0Compliance MODULE-COMPLIANCE
--    STATUS  obsolete
--    DESCRIPTION
--        "The compliance statement for management of services
--         on Nokia 7450 ESS series systems release R6.0."
--    MODULE  this module
--        MANDATORY-GROUPS
--        {
--            tnSvcV6v0Group,
--            tnSvcTlsV6v0Group,
--            tnSvcIesIfV6v0Group,
--            tnSvcTlsShgV6v0Group,
--            tnSvcTlsMFibV6v0Group,
--            tnSvcRdntV6v0Group,
--            tnSvcTlsMstiV6v0Group,
--            tnSvcTlsEgrV6v0Group,
--            tnSvcDhcpV6v0Group,
--            tnSvcEndPointV6v0Group,
--            tnSvcPEV6v0Group,
--            tnSvcIfDHCP6V6v0Group,
--            tnSvcTlsBackbone6v0Group,
--            tnSvcTlsBgpV6v0Group,
--            tnSvcEpipeV6v0Group,
--            tnSvcTlsPipV6v0Group,
--            tnSvcObsoletedV6v0Group,
--            tnSvcNotifyV6v0Group,
--            tmnxApipeV3v0Group
--            tnSvcRoutedCOV5v0Group
--            tnSvcBsxV6v0Group
--        }
--    ::= { tnSvcCompliances 100 }

-- tnSvc7750V6v0Compliance MODULE-COMPLIANCE
--    STATUS  obsolete
--    DESCRIPTION
--        "The compliance statement for management of services
--         on Nokia 7750 SR series systems release R6.0."
--    MODULE  this module
--        MANDATORY-GROUPS
--        {
--            tnSvcV6v0Group,
--            tnSvcTlsV6v0Group,
--            tnSvcTlsFdbV6v0Group,
--            tnSvcIesIfV6v0Group,
--            tnSvcTlsShgV6v0Group,
--            tnSvcTlsMFibV6v0Group,
--            tnSvcRdntV6v0Group,
--            tnSvcTlsMstiV6v0Group,
--            tnSvcTlsEgrV6v0Group,
--            tnSvcDhcpV6v0Group,
--            tnSvcEndPointV6v0Group,
--            tnSvcPEV6v0Group,
--            tnSvcIfDHCP6V6v0Group,
--            tnSvcTlsBackbone6v0Group,
--            tnSvcTlsBgpV6v0Group,
--            tnSvcEpipeV6v0Group,
--            tnSvcTlsPipV6v0Group,
--            tnSvcObsoletedV6v0Group,
--            tnSvcNotifyV6v0Group,
--            tmnxApipeV3v0Group,
--            tnSvcRoutedCOV5v0Group,
--            tnSvcBsxV6v0Group
--        }
--    ::= { tnSvcCompliances 101 }

-- tnSvc7710V6v0Compliance MODULE-COMPLIANCE
--    STATUS  obsolete
--    DESCRIPTION
--        "The compliance statement for management of services
--         on Nokia 7710 SR series systems release R6.0."
--    MODULE  this module
--        MANDATORY-GROUPS
--        {
--            tnSvcV6v0Group,
--            tnSvcTlsV6v0Group,
--            tnSvcTlsFdbV6v0Group,
--            tnSvcIesIfV6v0Group,
--            tnSvcTlsShgV6v0Group,
--            tnSvcTlsMFibV6v0Group,
--            tnSvcRdntV6v0Group,
--            tnSvcTlsMstiV6v0Group,
--            tnSvcTlsEgrV6v0Group,
--            tnSvcDhcpV6v0Group,
--            tnSvcEndPointV6v0Group,
--            tnSvcPEV6v0Group,
--            tnSvcIfDHCP6V6v0Group,
--            tnSvcTlsBackbone6v0Group,
--            tnSvcTlsBgpV6v0Group,
--            tnSvcEpipeV6v0Group,
--            tnSvcTlsPipV6v0Group,
--            tnSvcObsoletedV6v0Group,
--            tnSvcNotifyV6v0Group,
--            tmnxApipeV3v0Group,
--            tnSvcRoutedCOV5v0Group
--            tnSvcBsxV6v0Group   no Application Assurance on 7710
--        }
--    ::= { tnSvcCompliances 102 }

-- tnSvc7450V6v1Compliance MODULE-COMPLIANCE
--    STATUS  obsolete
--    DESCRIPTION
--        "The compliance statement for management of services
--         on Nokia 7450 ESS series systems release R6.1."
--    MODULE  this module
--        MANDATORY-GROUPS
--        {
--            tnSvcV6v0Group,
--            tnSvcTlsV6v0Group,
--            tnSvcIesIfV6v0Group,
--            tnSvcTlsShgV6v0Group,
--            tnSvcTlsMFibV6v0Group,
--            tnSvcRdntV6v0Group,
--            tnSvcTlsMstiV6v0Group,
--            tnSvcTlsEgrV6v0Group,
--            tnSvcDhcpV6v0Group,
--            tnSvcEndPointV6v0Group,
--            tnSvcPEV6v0Group,
--            tnSvcIfDHCP6V6v0Group,
--            tnSvcTlsBackbone6v1Group,
--            tnSvcTlsBgpV6v0Group,
--            tnSvcEpipeV6v0Group,
--            tnSvcTlsPipV6v0Group,
--            tnSvcObsoletedV6v0Group,
--            tnSvcNotifyV6v0Group,
--            tmnxApipeV3v0Group
--            tnSvcRoutedCOV5v0Group
--            tnSvcBsxV6v0Group
--        }
--    ::= { tnSvcCompliances 103 }

-- tnSvc7750V6v1Compliance MODULE-COMPLIANCE
--    STATUS  obsolete
--    DESCRIPTION
--        "The compliance statement for management of services
--         on Nokia 7750 SR series systems release R6.1."
--    MODULE  this module
--        MANDATORY-GROUPS
--        {
--            tnSvcV6v0Group,
--            tnSvcTlsV6v0Group,
--            tnSvcTlsFdbV6v0Group,
--            tnSvcIesIfV6v0Group,
--            tnSvcTlsShgV6v0Group,
--            tnSvcTlsMFibV6v0Group,
--            tnSvcRdntV6v0Group,
--            tnSvcTlsMstiV6v0Group,
--            tnSvcTlsEgrV6v0Group,
--            tnSvcDhcpV6v0Group,
--            tnSvcEndPointV6v0Group,
--            tnSvcPEV6v0Group,
--            tnSvcIfDHCP6V6v0Group,
--            tnSvcTlsBackbone6v1Group,
--            tnSvcTlsBgpV6v0Group,
--            tnSvcEpipeV6v0Group,
--            tnSvcTlsPipV6v0Group,
--            tnSvcObsoletedV6v0Group,
--            tnSvcNotifyV6v0Group,
--            tmnxApipeV3v0Group,
--            tnSvcRoutedCOV5v0Group,
--            tnSvcBsxV6v0Group
--        }
--    ::= { tnSvcCompliances 104 }

-- tnSvc7710V6v1Compliance MODULE-COMPLIANCE
--    STATUS  obsolete
--    DESCRIPTION
--        "The compliance statement for management of services
--         on Nokia 7710 SR series systems release R6.1."
--    MODULE  this module
--        MANDATORY-GROUPS
--        {
--            tnSvcV6v0Group,
--            tnSvcTlsV6v0Group,
--            tnSvcTlsFdbV6v0Group,
--            tnSvcIesIfV6v0Group,
--            tnSvcTlsShgV6v0Group,
--            tnSvcTlsMFibV6v0Group,
--            tnSvcRdntV6v0Group,
--            tnSvcTlsMstiV6v0Group,
--            tnSvcTlsEgrV6v0Group,
--            tnSvcDhcpV6v0Group,
--            tnSvcEndPointV6v0Group,
--            tnSvcPEV6v0Group,
--            tnSvcIfDHCP6V6v0Group,
--            tnSvcTlsBackbone6v1Group,
--            tnSvcTlsBgpV6v0Group,
--            tnSvcEpipeV6v0Group,
--            tnSvcTlsPipV6v0Group,
--            tnSvcObsoletedV6v0Group,
--            tnSvcNotifyV6v0Group,
--            tmnxApipeV3v0Group,
--            tnSvcRoutedCOV5v0Group,
--            tnSvcDhcpBgpV7v0Group
--            tnSvcBsxV6v0Group   no Application Assurance on 7710
--        }
--    ::= { tnSvcCompliances 105 }

-- tnSvc7450V7v0Compliance MODULE-COMPLIANCE
--    STATUS  current
--    DESCRIPTION
--        "The compliance statement for management of services
--         on Nokia 7450 ESS series systems release R7.0."
--    MODULE  this module
--        MANDATORY-GROUPS
--        {
--            tnSvcV6v0Group,
--            tnSvcTlsV6v0Group,
--            tnSvcIesIfV6v0Group,
--            tnSvcTlsShgV6v0Group,
--            tnSvcTlsMFibV6v0Group,
--            tnSvcRdntV6v0Group,
--            tnSvcTlsMstiV6v0Group,
--            tnSvcTlsEgrV6v0Group,
--            tnSvcDhcpV7v0Group,
--            tnSvcEndPointV6v0Group,
--            tnSvcPEV6v0Group,
--            tnSvcIfDHCP6V6v0Group,
--            tnSvcTlsBackbone6v1Group,
--            tnSvcTlsBgpV6v0Group,
--            tnSvcEpipeV6v0Group,
--            tnSvcTlsPipV7v0Group,
--            tnSvcObsoletedV6v0Group,
--            tnSvcNotifyV7v0Group,
--            tmnxApipeV3v0Group
--            tnSvcRoutedCOV7v0Group
--            tnSvcBsxV6v0Group,
--            tmnxArpHostGroup,
--            tmnxArpHostNotifyGroup,
--            tmnxArpHostBgpGroup,
--            tnSvcIgmpTrkGroup,
--            tnSvcTlsMacV7v0Group,
--            tnSvcTlsEndPointV7v0Group,
--            tnSvcMCEPNotifyGroup,
--            tnSvcDhcpBgpV7v0Group,
--            tnSvcV7v0Group,
--            tnSvcTlsV7v0Group,
--            tnSvcIesIfV7v0Group,
--            tnSvcPbbMacV7v0Group
--        }
--    ::= { tnSvcCompliances 106 }

-- tnSvc7750V7v0Compliance MODULE-COMPLIANCE
--    STATUS  current
--    DESCRIPTION
--        "The compliance statement for management of services
--         on Nokia 7750 SR series systems release R7.0."
--    MODULE  this module
--        MANDATORY-GROUPS
--        {
--            tnSvcV6v0Group,
--            tnSvcTlsV6v0Group,
--            tnSvcTlsFdbV7v0Group,
--            tnSvcIesIfV6v0Group,
--            tnSvcTlsShgV6v0Group,
--            tnSvcTlsMFibV6v0Group,
--            tnSvcRdntV6v0Group,
--            tnSvcTlsMstiV6v0Group,
--            tnSvcTlsEgrV6v0Group,
--            tnSvcDhcpV7v0Group,
--            tnSvcEndPointV6v0Group,
--            tnSvcPEV6v0Group,
--            tnSvcIfDHCP6V6v0Group,
--            tnSvcTlsBackbone6v1Group,
--            tnSvcTlsBgpV6v0Group,
--            tnSvcEpipeV6v0Group,
--            tnSvcTlsPipV7v0Group,
--            tnSvcObsoletedV6v0Group,
--            tnSvcNotifyV7v0Group,
--            tmnxApipeV3v0Group,
--            tnSvcRoutedCOV7v0Group,
--            tnSvcBsxV6v0Group,
--            tmnxArpHostGroup,
--            tmnxArpHostNotifyGroup,
--            tmnxArpHostBgpGroup,
--            tnSvcIgmpTrkGroup,
--            tnSvcTlsMacV7v0Group,
--            tnSvcTlsEndPointV7v0Group,
--            tnSvcIpipeV7v0Group,
--            tnSvcMCEPNotifyGroup,
--            tnSvcDhcpBgpV7v0Group,
--            tnSvcV7v0Group,
--            tnSvcPbbMacV7v0Group
--        }
--    ::= { tnSvcCompliances 107 }

-- tnSvc7710V7v0Compliance MODULE-COMPLIANCE
--    STATUS  current
--    DESCRIPTION
--        "The compliance statement for management of services
--         on Nokia 7710 SR series systems release R7.0."
--    MODULE  this module
--        MANDATORY-GROUPS
--        {
--            tnSvcV6v0Group,
--            tnSvcTlsV6v0Group,
--            tnSvcTlsFdbV7v0Group,
--            tnSvcIesIfV6v0Group,
--            tnSvcTlsShgV6v0Group,
--            tnSvcTlsMFibV6v0Group,
--            tnSvcRdntV6v0Group,
--            tnSvcTlsMstiV6v0Group,
--            tnSvcTlsEgrV6v0Group,
--            tnSvcDhcpV7v0Group,
--            tnSvcEndPointV6v0Group,
--            tnSvcPEV6v0Group,
--            tnSvcIfDHCP6V6v0Group,
--            tnSvcTlsBackbone6v1Group,
--            tnSvcTlsBgpV6v0Group,
--            tnSvcEpipeV6v0Group,
--            tnSvcTlsPipV7v0Group,
--            tnSvcObsoletedV6v0Group,
--            tnSvcNotifyV7v0Group,
--            tmnxApipeV3v0Group,
--            tnSvcRoutedCOV7v0Group,
--            tnSvcBsxV6v0Group   no Application Assurance on 7710
--            tmnxArpHostGroup,
--            tmnxArpHostNotifyGroup,
--            tmnxArpHostBgpGroup,
--            tnSvcIgmpTrkGroup,
--            tnSvcTlsMacV7v0Group,
--            tnSvcTlsEndPointV7v0Group,
--            tnSvcIpipeV7v0Group,
--            tnSvcMCEPNotifyGroup,
--            tnSvcV7v0Group,
--            tnSvcPbbMacV7v0Group
--        }
--    ::= { tnSvcCompliances 108 }

-- ----------------------------------------------
-- tnCustomer OBJECT-GROUPs
-- ----------------------------------------------
-- tnCustV6v0Group OBJECT-GROUP
--    OBJECTS {
--      tnCustNumEntries,
--      tnCustNextFreeId,
--      tnCustId,
--      tnCustRowStatus,
--      tnCustDescription,
--      tnCustContact,
--      tnCustPhone,
--      tnCustLastMgmtChange,
--      tnCustMultSvcSiteName,
--      tnCustMultSvcSiteRowStatus,
--      tnCustMultSvcSiteDescription,
--      tnCustMultSvcSiteScope,
--      tnCustMultSvcSiteAssignment,
--      tnCustMultSvcSiteIngressSchedulerPolicy,
--      tnCustMultSvcSiteEgressSchedulerPolicy,
--      tnCustMultSvcSiteLastMgmtChange,
--      tnCustMultSvcSiteTodSuite,
--      tnCustMultSvcSiteCurrentIngrSchedPlcy,
--      tnCustMultSvcSiteCurrentEgrSchedPlcy,
--      tnCustMultSvcSiteEgressAggRateLimit,
--      tnCustMultSvcSiteIntendedIngrSchedPlcy,
--      tnCustMultSvcSiteIntendedEgrSchedPlcy,
--      tnCustMultSvcSiteFrameBasedAccnt,
--      tnCustIngQosSchedStatsForwardedPackets,
--      tnCustIngQosSchedStatsForwardedOctets,
--      tnCustEgrQosSchedStatsForwardedPackets,
--      tnCustEgrQosSchedStatsForwardedOctets,
--      tnCustIngQosPortSchedFwdPkts,
--      tnCustIngQosPortSchedFwdOctets,
--      tnCustEgrQosPortSchedFwdPkts,
--      tnCustEgrQosPortSchedFwdOctets,
--      tnCustMssIngQosSRowStatus,
--      tnCustMssIngQosSLastMgmtChange,
--      tnCustMssIngQosSOverrideFlags,
--      tnCustMssIngQosSPIR,
--      tnCustMssIngQosSCIR,
--      tnCustMssIngQosSSummedCIR,
--      tnCustMssEgrQosSRowStatus,
--      tnCustMssEgrQosSLastMgmtChange,
--      tnCustMssEgrQosSOverrideFlags,
--      tnCustMssEgrQosSPIR,
--      tnCustMssEgrQosSCIR,
--      tnCustMssEgrQosSSummedCIR,
--      tnCustIngSchedPlcyStatsFwdPkt,
--      tnCustIngSchedPlcyStatsFwdOct,
--      tnCustEgrSchedPlcyStatsFwdPkt,
--      tnCustEgrSchedPlcyStatsFwdOct,
--      tnCustIngSchedPlcyPortStatsFwdPkt,
--      tnCustIngSchedPlcyPortStatsFwdOct,
--      tnCustEgrSchedPlcyPortStatsFwdPkt,
--      tnCustEgrSchedPlcyPortStatsFwdOct,
--      tnCustMultSvcSiteFrameBasedAccnt
--    }
--    STATUS      current
--    DESCRIPTION
--        "The group of objects supporting management of Services tnCustomers
--         general capabilities on Nokia 7x50 SR series systems."
--    ::= { tnCustGroups 100 }

-- ----------------------------------------------
-- service OBJECT-GROUPs
-- ----------------------------------------------
-- tnSvcV6v0Group OBJECT-GROUP
--    OBJECTS {
--      tnSvcNumEntries,
--      tnSvcId,
--      tnSvcRowStatus,
--      tnSvcType,
--      tnSvcCustId,
--      tnSvcIpRouting,
--      tnSvcDescription,
--      tnSvcMtu,
--      tnSvcAdminStatus,
--      tnSvcOperStatus,
--      tnSvcNumSaps,
--      tnSvcNumSdps,
--      tnSvcLastMgmtChange,
--      tnSvcDefMeshVcId,
--      tnSvcVpnId,
--      tnSvcVRouterId,
--      tnSvcAutoBind,
--      tnSvcLastStatusChange,
--      tnSvcVllType,
--      tnSvcMgmtVpls,
--      tnSvcRadiusDiscovery,
--      tnSvcRadiusUserName,
--      tnSvcRadiusUserNameType,
--      tnSvcVcSwitching,
--      tnSvcRadiusPEDiscPolicy,
--      tnSvcRadiusDiscoveryShutdown,
--      tnSvcVplsType,
--      tnSvcTotalFdbMimDestIdxEntries
--    }
--    STATUS      current
--    DESCRIPTION
--        "The group of objects supporting management of Services
--         general capabilities on Nokia 7x50 SR series systems."
--    ::= { tnSvcGroups 101 }

-- tnSvcTlsV6v0Group OBJECT-GROUP
--    OBJECTS {
--      tnSvcTlsMacLearning,
--      tnSvcTlsDiscardUnknownDest,
--      tnSvcTlsFdbTableSize,
--      tnSvcTlsFdbNumEntries,
--      tnSvcTlsFdbNumStaticEntries,
--      tnSvcTlsFdbLocalAgeTime,
--      tnSvcTlsFdbRemoteAgeTime,
--      tnSvcTlsStpAdminStatus,
--      tnSvcTlsStpPriority,
--      tnSvcTlsStpBridgeAddress,
--      tnSvcTlsStpTimeSinceTopologyChange,
--      tnSvcTlsStpTopologyChanges,
--      tnSvcTlsStpDesignatedRoot,
--      tnSvcTlsStpRootCost,
--      tnSvcTlsStpRootPort,
--      tnSvcTlsStpMaxAge,
--      tnSvcTlsStpHelloTime,
--      tnSvcTlsStpForwardDelay,
--      tnSvcTlsStpBridgeMaxAge,
--      tnSvcTlsStpBridgeHelloTime,
--      tnSvcTlsStpBridgeForwardDelay,
--      tnSvcTlsStpOperStatus,
--      tnSvcTlsStpVirtualRootBridgeStatus,
--      tnSvcTlsMacAgeing,
--      tnSvcTlsStpTopologyChangeActive,
--      tnSvcTlsFdbTableFullHighWatermark,
--      tnSvcTlsFdbTableFullLowWatermark,
--      tnSvcTlsVpnId,
--      tnSvcTlsCustId,
--      tnSvcTlsStpVersion,
--      tnSvcTlsStpHoldCount,
--      tnSvcTlsStpPrimaryBridge,
--      tnSvcTlsStpBridgeInstanceId,
--      tnSvcTlsStpVcpOperProtocol,
--      tnSvcTlsMacMoveMaxRate,
--      tnSvcTlsMacMoveRetryTimeout,
--      tnSvcTlsMacMoveAdminStatus,
--      tnSvcTlsMacRelearnOnly,
--      tnSvcTlsMfibTableSize,
--      tnSvcTlsMfibTableFullHighWatermark,
--      tnSvcTlsMfibTableFullLowWatermark,
--      tnSvcTlsMacFlushOnFail,
--      tnSvcTlsStpRegionName,
--      tnSvcTlsStpRegionRevision,
--      tnSvcTlsStpBridgeMaxHops,
--      tnSvcTlsStpCistRegionalRoot,
--      tnSvcTlsStpCistIntRootCost,
--      tnSvcTlsStpCistRemainingHopCount,
--      tnSvcTlsStpCistRegionalRootPort,
--      tnSvcTlsFdbNumLearnedEntries,
--      tnSvcTlsFdbNumOamEntries,
--      tnSvcTlsFdbNumDhcpEntries,
--      tnSvcTlsFdbNumHostEntries,
--      tnSvcTlsShcvAction,
--      tnSvcTlsShcvSrcIp,
--      tnSvcTlsShcvSrcMac,
--      tnSvcTlsShcvInterval,
--      tnSvcTlsPriPortsCumulativeFactor,
--      tnSvcTlsSecPortsCumulativeFactor,
--      tnSvcTlsL2ptTermEnabled,
--      tnSvcTlsPropagateMacFlush,
--      tnSvcTlsMrpAdminStatus,
--      tnSvcTlsMrpMaxAttributes,
--      tnSvcTlsMrpAttributeCount,
--      tnSvcTlsMrpFailedRegisterCount,
--      tnSvcTlsMrpFloodTime,
--      tnSvcTlsMrpAttrTblHighWatermark,
--      tnSvcTlsMrpAttrTblLowWatermark,
--      tnSvcTlsMcPathMgmtPlcyName,
--      tnTlsEgrMcGrpAdminQinqFixedTagVal
--    }
--    STATUS      current
--    DESCRIPTION
--        "The group of objects supporting management of Services TLS
--         general capabilities on Nokia 7x50 SR series systems."
--    ::= { tnSvcGroups 102 }

-- tnSvcTlsFdbV6v0Group OBJECT-GROUP
--    OBJECTS {
--      tnTlsFdbMacAddr,
--      tnTlsFdbRowStatus,
--      tnTlsFdbType,
--      tnTlsFdbLocale,
--      tnTlsFdbPortId,
--      tnTlsFdbEncapValue,
--      tnTlsFdbSdpId,
--      tnTlsFdbVcId,
--      tnTlsFdbVpnId,
--      tnTlsFdbCustId,
--      tnTlsFdbLastStateChange,
--      tnTlsFdbProtected,
--      tnTlsFdbBackboneDstMac,
--      tnTlsFdbNumIVplsMac,
--      tnTlsFdbEndPointName,
--      tnTlsFdbEPMacOperSdpId,
--      tnTlsFdbEPMacOperVcId,
--      tnTlsFdbPbbNumEpipes,
--      tnTlsProtMacRowStatus,
--      tnTlsProtMacLastMgmtChange
--    }
--    STATUS      obsolete
--    DESCRIPTION
--        "The group of objects supporting management of Services TLS FDB
--         capabilities on Nokia 7x50 SR series systems."
--    ::= { tnSvcGroups 103 }

-- tnSvcIesIfV6v0Group OBJECT-GROUP
--    OBJECTS {
--      tnIesIfIndex,
--      tnIesIfRowStatus,
--      tnIesIfName,
--      tnIesIfDescription,
--      tnIesIfAdminStatus,
--      tnIesIfOperStatus,
--      tnIesIfLastMgmtChange,
--      tnIesIfVpnId,
--      tnIesIfCustId,
--      tnIesIfLoopback,
--      tnIesIfLastStatusChange,
--      tnIesIfType,
--      tnIesIfShcvSource,
--      tnIesIfShcvAction,
--      tnIesIfShcvInterval,
--      tnIesGrpIfOperUpWhileEmpty
--    }
--    STATUS      current
--    DESCRIPTION
--        "The group of objects supporting management of Services IES
--         interface capabilities on Nokia 7x50 SR series systems."
--    ::= { tnSvcGroups 104 }

-- tnSvcTlsShgV6v0Group OBJECT-GROUP
--    OBJECTS {
--      tnTlsShgRowStatus,
--      tnTlsShgCustId,
--      tnTlsShgInstanceId,
--      tnTlsShgDescription,
--      tnTlsShgLastMgmtChange,
--      tnTlsShgResidential,
--      tnTlsShgRestProtSrcMac,
--      tnTlsShgRestUnprotDstMac,
--      tnTlsShgCreationOrigin,
--      tnTlsShgRestProtSrcMacAction
--    }
--    STATUS      current
--    DESCRIPTION
--        "The group of objects supporting management of Services TLS
--         Split Hoirizon Group capabilities on Nokia 7x50 SR series systems."
--    ::= { tnSvcGroups 105 }

-- tnSvcTlsMFibV6v0Group OBJECT-GROUP
--    OBJECTS {
--      tnTlsMFibFwdOrBlk,
--      tnTlsMFibSvcId,
--      tnTlsMFibStatsForwardedPkts,
--      tnTlsMFibStatsForwardedOctets
--    }
--    STATUS      current
--    DESCRIPTION
--        "The group of objects supporting management of Services TLS MFib
--         capabilities on Nokia 7x50 SR series systems."
--    ::= { tnSvcGroups 106 }

-- tnSvcRdntV6v0Group OBJECT-GROUP
--    OBJECTS {
--      tnTlsRdntGrpRowStatus,
--      tnTlsRdntGrpDescription,
--      tnTlsRdntGrpLastMgmtChange,
--      tnTlsRdntGrpMemberRowStatus,
--      tnTlsRdntGrpMemberLastMgmtChange
--    }
--    STATUS      current
--    DESCRIPTION
--        "The group of objects supporting management of Services Redundancy
--         group capabilities on Nokia 7x50 SR series systems."
--    ::= { tnSvcGroups 107 }

-- tnSvcTlsMstiV6v0Group OBJECT-GROUP
--    OBJECTS {
--      tnTlsMstiRowStatus,
--      tnTlsMstiPriority,
--      tnTlsMstiLastMgmtChange,
--      tnTlsMstiRegionalRoot,
--      tnTlsMstiIntRootCost,
--      tnTlsMstiRemainingHopCount,
--      tnTlsMstiRegionalRootPort,
--      tnTlsMstiMvplsRowStatus
--    }
--    STATUS      current
--    DESCRIPTION
--        "The group of objects supporting management of Services TLS MSTI
--         capabilities on Nokia 7x50 SR series systems."
--    ::= { tnSvcGroups 108 }

-- tnSvcTlsEgrV6v0Group OBJECT-GROUP
--    OBJECTS {
--      tnTlsEgrMcGrpRowStatus,
--      tnTlsEgrMcGrpLastMgmtChange,
--      tnTlsEgrMcGrpDescription,
--      tnTlsEgrMcGrpChainLimit,
--      tnTlsEgrMcGrpEncapType,
--      tnTlsEgrMcGrpDot1qEtherType,
--      tnTlsEgrMcGrpQinqEtherType,
--      tnTlsEgrMcGrpMacFilterId,
--      tnTlsEgrMcGrpIpFilterId,
--      tnTlsEgrMcGrpIpv6FilterId,
--      tnTlsEgrMcGrpQinqFixedTagPosition,
--      tnTlsEgrMcGrpOperQinqFixedTagVal
--    }
--    STATUS      current
--    DESCRIPTION
--        "The group of objects supporting management of Services TLS Egress
--         capabilities on Nokia 7x50 SR series systems."
--    ::= { tnSvcGroups 109 }
--
-- tnSvcDhcpV6v0Group OBJECT-GROUP
--    OBJECTS {
--      tnSvcDhcpLseStateLocale,
--      tnSvcDhcpLseStatePortId,
--      tnSvcDhcpLseStateEncapValue,
--      tnSvcDhcpLseStateSdpId,
--      tnSvcDhcpLseStateVcId,
--      tnSvcDhcpLseStateChAddr,
--      tnSvcDhcpLseStateRemainLseTime,
--      tnSvcDhcpLseStateOption82,
--      tnSvcDhcpLseStatePersistKey,
--      tnSvcDhcpLseStateSubscrIdent,
--      tnSvcDhcpLseStateSubProfString,
--      tnSvcDhcpLseStateSlaProfString,
--      tnSvcDhcpLseStateShcvOperState,
--      tnSvcDhcpLseStateShcvChecks,
--      tnSvcDhcpLseStateShcvReplies,
--      tnSvcDhcpLseStateShcvReplyTime,
--      tnSvcDhcpLseStateClientId,
--      tnSvcDhcpLseStateIAID,
--      tnSvcDhcpLseStateIAIDType,
--      tnSvcDhcpLseStateCiAddrMaskLen,
--      tnSvcDhcpLseStateRetailerSvcId,
--      tnSvcDhcpLseStateRetailerIf,
--      tnSvcDhcpLseStateAncpString,
--      tnSvcDhcpLseStateFramedIpNetMaskTp,
--      tnSvcDhcpLseStateFramedIpNetMask,
--      tnSvcDhcpLseStateBCastIpAddrType,
--      tnSvcDhcpLseStateBCastIpAddr,
--      tnSvcDhcpLseStateDefaultRouterTp,
--      tnSvcDhcpLseStateDefaultRouter,
--      tnSvcDhcpLseStatePrimaryDnsType,
--      tnSvcDhcpLseStatePrimaryDns,
--      tnSvcDhcpLseStateSecondaryDnsType,
--      tnSvcDhcpLseStateSecondaryDns,
--      tnSvcDhcpLseStateSessionTimeout,
--      tnSvcDhcpLseStateServerLeaseStart,
--      tnSvcDhcpLseStateServerLastRenew,
--      tnSvcDhcpLseStateServerLeaseEnd,
--      tnSvcDhcpLseStateDhcpServerAddrType,
--      tnSvcDhcpLseStateDhcpServerAddr,
--      tnSvcDhcpLseStateOriginSubscrId,
--      tnSvcDhcpLseStateOriginStrings,
--      tnSvcDhcpLseStateOriginLeaseInfo,
--      tnSvcDhcpLseStateDhcpClientAddrType,
--      tnSvcDhcpLseStateDhcpClientAddr,
--      tnSvcDhcpLseStateLeaseSplitActive,
--      tnSvcDhcpLseStateInterDestId,
--      tnSvcDhcpLseStatePrimaryNbnsType,
--      tnSvcDhcpLseStatePrimaryNbns,
--      tnSvcDhcpLseStateSecondaryNbnsType,
--      tnSvcDhcpLseStateSecondaryNbns,
--      tnSvcDhcpLseStateNextHopMacAddr,
--      tnSvcDhcpLseStateModifySubIndent,
--      tnSvcDhcpLseStateModifySubProfile,
--      tnSvcDhcpLseStateModifySlaProfile,
--      tnSvcDhcpLseStateEvaluateState,
--      tnSvcDhcpLseStateModInterDestId,
--      tnSvcDhcpLseStateModifyAncpString,
--      tnSvcDhcpLseStateForceRenew,
--      tnSvcDhcpManagedRouteStatus
--    }
--    STATUS      obsolete
--    DESCRIPTION
--        "The group of objects supporting management of Services DHCP Lease
--         capabilities on Nokia 7x50 SR series systems."
--    ::= { tnSvcGroups 110 }

-- tnSvcEndPointV6v0Group OBJECT-GROUP
--    OBJECTS {
--      tnSvcEndPointRowStatus,
--      tnSvcEndPointDescription,
--      tnSvcEndPointTxActiveType,
--      tnSvcEndPointTxActivePortId,
--      tnSvcEndPointTxActiveEncap,
--      tnSvcEndPointTxActiveSdpId,
--      tnSvcEndPointForceSwitchOver,
--      tnSvcEndPointForceSwitchOverSdpId,
--      tnSvcEndPointActiveHoldDelay,
--      tnSvcEndPointIgnoreStandbySig,
--      tnSvcEndPointMacPinning,
--      tnSvcEndPointMacLimit,
--      tnSvcEndPointSuppressStandbySig,
--      tnSvcEndPointTxActiveChangeCount,
--      tnSvcEndPointTxActiveLastChange,
--      tnSvcEndPointTxActiveUpTime,
--      tnSvcEndPointRevertTime,
--      tnSvcEndPointRevertTimeCountDn
--    }
--    STATUS      current
--    DESCRIPTION
--        "The group of objects supporting management of Services endpoint
--         capabilities on Nokia 7x50 SR series systems."
--    ::= { tnSvcGroups 111 }

-- tnSvcPEV6v0Group OBJECT-GROUP
--    OBJECTS {
--      tnSvcPEDiscoveryPolicyRowStatus,
--      tnSvcPEDiscoveryPolicyPassword,
--      tnSvcPEDiscoveryPolicyInterval,
--      tnSvcPEDiscoveryPolicyTimeout,
--      tnSvcPEDiscPolServerRowStatus,
--      tnSvcPEDiscPolServerAddressType,
--      tnSvcPEDiscPolServerAddress,
--      tnSvcPEDiscPolServerSecret,
--      tnSvcPEDiscPolServerOperStatus,
--      tnSvcPEDiscPolServerPort
--    }
--    STATUS      current
--    DESCRIPTION
--        "The group of objects supporting management of Services PE Discovery
--         capabilities on Nokia 7x50 SR series systems."
--    ::= { tnSvcGroups 112 }

-- tnSvcIfDHCP6V6v0Group OBJECT-GROUP
--    OBJECTS {
--      tnSvcIfDHCP6MsgStatsLstClrd,
--      tnSvcIfDHCP6MsgStatsRcvd,
--      tnSvcIfDHCP6MsgStatsSent,
--      tnSvcIfDHCP6MsgStatsDropped
--    }
--    STATUS      current
--    DESCRIPTION
--        "The group of objects supporting management of Services interface DHCP
--         capabilities on Nokia 7x50 SR series systems."
--    ::= { tnSvcGroups 114 }

-- tnSvcTlsBackbone6v0Group OBJECT-GROUP
--    OBJECTS {
--      tnSvcTlsBackboneSrcMac,
--      tnSvcTlsBackboneVplsSvcId,
--      tnSvcTlsBackboneVplsSvcISID,
--      tnSvcTlsBackboneOperSrcMac,
--      tnSvcTlsBackboneOperVplsSvcISID,
--      tnSvcTlsBackboneLDPMacFlush,
--      tnSvcTlsBackboneVplsStp
--    }
--    STATUS      obsolete
--    DESCRIPTION
--        "The group of objects supporting management of Services PBB
--         capabilities on Nokia 7x50 SR series systems."
--    ::= { tnSvcGroups 115 }

-- tnSvcTlsBgpV6v0Group OBJECT-GROUP
--    OBJECTS {
--      tnSvcTlsBgpADTableLastChanged,
--      tnSvcTlsBgpADRowStatus,
--      tnSvcTlsBgpADLastChanged,
--      tnSvcTlsBgpADVplsId,
--      tnSvcTlsBgpADVsiPrefix,
--      tnSvcTlsBgpADVsiRD,
--      tnSvcTlsBgpADExportRteTarget,
--      tnSvcTlsBgpADVsiExportPolicy1,
--      tnSvcTlsBgpADVsiExportPolicy2,
--      tnSvcTlsBgpADVsiExportPolicy3,
--      tnSvcTlsBgpADVsiExportPolicy4,
--      tnSvcTlsBgpADVsiExportPolicy5,
--      tnSvcTlsBgpADImportRteTarget,
--      tnSvcTlsBgpADVsiImportPolicy1,
--      tnSvcTlsBgpADVsiImportPolicy2,
--      tnSvcTlsBgpADVsiImportPolicy3,
--      tnSvcTlsBgpADVsiImportPolicy4,
--      tnSvcTlsBgpADVsiImportPolicy5,
--      tnSvcTlsBgpADAdminStatus
--    }
--    STATUS      current
--    DESCRIPTION
--        "The group of objects supporting management of Services BGP AD
--         capabilities on Nokia 7x50 SR series systems."
--    ::= { tnSvcGroups 116 }
--
-- tnSvcEpipeV6v0Group OBJECT-GROUP
--    OBJECTS {
--      tnSvcEpipePbbTableLastChanged,
--      tnSvcEpipePbbRowStatus,
--      tnSvcEpipePbbLastChngd,
--      tnSvcEpipePbbBvplsSvcId,
--      tnSvcEpipePbbBvplsDstMac,
--      tnSvcEpipePbbSvcISID,
--      tnSvcEpipePbbOperState,
--      tnSvcEpipePbbFlooding,
--      tnSvcEpipePbbLastStatusChange
--    }
--    STATUS      current
--    DESCRIPTION
--        "The group of objects supporting management of Services PBB Epipe
--         capabilities on Nokia 7x50 SR series systems."
--    ::= { tnSvcGroups 117 }

-- tnSvcTlsPipV6v0Group OBJECT-GROUP
--    OBJECTS {
--      tnTlsPipStpPortState,
--      tnTlsPipStpPortRole,
--      tnTlsPipStpDesignatedBridge,
--      tnTlsPipStpDesignatedPort,
--      tnTlsPipStpException,
--      tnTlsPipStpForwardTransitions,
--      tnTlsPipStpInConfigBpdus,
--      tnTlsPipStpInTcnBpdus,
--      tnTlsPipStpInRstBpdus,
--      tnTlsPipStpInMstBpdus,
--      tnTlsPipStpInBadBpdus,
--      tnTlsPipStpOutConfigBpdus,
--      tnTlsPipStpOutTcnBpdus,
--      tnTlsPipStpOutRstBpdus,
--      tnTlsPipStpOutMstBpdus,
--      tnTlsPipStpOperStatus,
--      tnTlsPipStpMvplsPruneState,
--      tnTlsPipStpOperProtocol,
--      tnTlsPipStpPortNum,
--      tnTlsPipMstiPortRole,
--      tnTlsPipMstiPortState,
--      tnTlsPipMstiDesignatedBridge,
--      tnTlsPipMstiDesignatedPort
--    }
--    STATUS      obsolete
--    DESCRIPTION
--        "The group of objects supporting management of Services TLS PIP
--         capabilities on Nokia 7x50 SR series systems."
--    ::= { tnSvcGroups 118 }

-- This groups is not in 7450
-- tmnxApipeV3v0Group OBJECT-GROUP
--    OBJECTS {
--        tnSvcApipeInterworking
--    }
--    STATUS      current
--    DESCRIPTION
--        "The  group  of  objects supporting management of APIPE services on
--         Nokia 7x50 SR series systems release 3.0."
--    ::= { tnSvcGroups 119 }

-- This groups is not in 7450
-- tnSvcRoutedCOV5v0Group OBJECT-GROUP
--    OBJECTS {
--        tnIesIfParentIf,
--        tnIesIfFwdServId,
--        tnIesIfFwdSubIf,
--        tnIesGrpIfRedInterface,
--        tnSvcWholesalerNumStaticHosts,
--        tnSvcWholesalerNumDynamicHosts
--    }
--    STATUS      obsolete
--    DESCRIPTION
--        "The group of objects supporting routed CO Nokia 7x50 SR systems."
--    ::= { tnSvcGroups 120 }

-- tmnxArpHostGroup OBJECT-GROUP
--    OBJECTS {
--        tnSvcArpHostTableLastChanged,
--        tnSvcArpHostLocale,
--        tnSvcArpHostSapPortId,
--        tnSvcArpHostSapEncapValue,
--        tnSvcArpHostSdpId,
--        tnSvcArpHostVcId,
--        tnSvcArpHostSessionTimeout,
--        tnSvcArpHostStart,
--        tnSvcArpHostLastAuth,
--        tnSvcArpHostRefresh,
--        tnSvcArpHostRemainingTime,
--        tnSvcArpHostShcvOperState,
--        tnSvcArpHostShcvChecks,
--        tnSvcArpHostShcvReplies,
--        tnSvcArpHostShcvReplyTime,
--        tnSvcArpHostSubscrIdent,
--        tnSvcArpHostSubProfString,
--        tnSvcArpHostSlaProfString,
--        tnSvcArpHostAppProfString,
--        tnSvcArpHostAncpString,
--        tnSvcArpHostInterDestId,
--        tnSvcArpHostRetailerSvcId,
--        tnSvcArpHostRetailerIf,
--        tnSvcArpHostMacAddr,
--        tnSvcArpHostPersistKey,
--        tnSvcArpHostCategoryMapName,
--        tnSvcArpHostRadiusClassAttr,
--        tnSvcArpHostRadiusUserName,
--        tnSvcArpHostIfTableLastMgmtChange,
--        tnSvcArpHostIfLastMgmtChange,
--        tnSvcArpHostIfAdminState,
--        tnSvcArpHostIfMaxNumHosts,
--        tnSvcArpHostIfMaxNumHostsSap,
--        tnSvcArpHostIfMinAuthInterval,
--        tnSvcArpHostIfNumHosts,
--        tnSvcArpHostDefaultSessionTimeout,
--        tnSvcArpHostMRtStatus
--    }
--    STATUS      current
--    DESCRIPTION
--        "The group of objects supporting management of Services ARP hosts
--         capabilities on Nokia 7xxx series systems."
--    ::= { tnSvcGroups 130 }

-- This group is not in 7710
-- tnSvcBsxV6v0Group OBJECT-GROUP
--    OBJECTS {
--      tnSvcDhcpLseStateAppProfString,
--      tnSvcDhcpLseStateModifyAppProfile
--    }
--    STATUS      current
--    DESCRIPTION
--        "The group of objects supporting management of BSX (Application
--         Assurance) capabilities on Nokia 7x50 SR series systems."
--    ::= { tnSvcGroups 121 }

-- tnSvcTlsBackbone6v1Group OBJECT-GROUP
--    OBJECTS {
--      tnSvcTlsBackboneSrcMac,
--      tnSvcTlsBackboneVplsSvcId,
--      tnSvcTlsBackboneVplsSvcISID,
--      tnSvcTlsBackboneOperSrcMac,
--      tnSvcTlsBackboneOperVplsSvcISID,
--      tnSvcTlsBackboneLDPMacFlush,
--      tnSvcTlsBackboneLDPMacFlushNotMine,
--      tnSvcTlsBackboneVplsStp
--    }
--    STATUS      current
--    DESCRIPTION
--        "The group of objects supporting management of Services PBB
--         capabilities on Nokia 7x50 SR series systems."
--    ::= { tnSvcGroups 122 }

-- tnSvcIgmpTrkGroup OBJECT-GROUP
--    OBJECTS {
--        tnSvcIgmpTrkTableLastMgmtChange,
--        tnSvcIgmpTrkLastMgmtChange,
--        tnSvcIgmpTrkAdminState,
--        tnSvcIgmpTrkExpiryTime
--    }
--    STATUS      current
--    DESCRIPTION
--        "The group of objects supporting management of Services IGMP host
--         tracking capabilities on Nokia 7xxx series systems."
--    ::= { tnSvcGroups 131 }

-- tnSvcTlsMacV7v0Group OBJECT-GROUP
--    OBJECTS {
--       tnSvcTlsMacMoveNumRetries,
--       tnSvcTlsMacSubNetLen,
--       tnSvcTlsSendFlushOnBVplsFail,
--       tnSvcTlsPropMacFlushFromBVpls
--    }
--    STATUS      current
--    DESCRIPTION
--        "The group of objects supporting management of Services mac-related
--         capabilities on Nokia 7xxx series systems in 7.0 release."
--    ::= { tnSvcGroups 132 }

-- This group is not in 7450
-- tnSvcRoutedCOV7v0Group OBJECT-GROUP
--    OBJECTS {
--        tnIesIfParentIf,
--        tnIesIfFwdServId,
--        tnIesIfFwdSubIf,
--        tnIesGrpIfRedInterface,
--        tnSvcWholesalerNumStaticHosts,
--        tnSvcWholesalerNumDynamicHosts,
--        tnIesIfPrivateRetailSubnets,
--        tnSvcWholesalerNumDhcpLeaseStates,
--        tnSvcWholesalerNumPppoeSessions,
--        tnSvcWholesalerNumArpHosts
--    }
--    STATUS      current
--    DESCRIPTION
--        "The group of objects supporting routed CO Nokia 7x50 SR systems."
--    ::= { tnSvcGroups 133 }

-- tnSvcTlsEndPointV7v0Group OBJECT-GROUP
--    OBJECTS {
--       tnSvcEndPointMCEPId,
--       tnSvcEndPointMCEPPeerAddr,
--       tnSvcEndPointMCEPPeerAddrType,
--       tnSvcEndPointMCEPPeerName,
--       tnSvcEndPointMCEPPsvModeActive,
--       tnSvcEndPointBlockOnMeshFail,
--       tnSvcEpMcEpStatsPktsRxConfig,
--       tnSvcEpMcEpStatsPktsRxState,
--       tnSvcEpMcEpStatsPktsTxConfig,
--       tnSvcEpMcEpStatsPktsTxFailed,
--       tnSvcEpMcEpStatsPktsTxState
--    }
--    STATUS      current
--    DESCRIPTION
--        "The group of objects supporting management of Services End-point
--         capabilities on Nokia 7xxx series systems in 7.0 release."
--    ::= { tnSvcGroups 134 }

-- tnSvcIpipeV7v0Group OBJECT-GROUP
--    OBJECTS {
--      tnSvcIpipeInfoLastMgmtChange,
--      tnSvcIpipeCeAddressDiscovery,
--      tnSvcIpipeInfoTableLastMgmtChange
--    }
--    STATUS      current
--    DESCRIPTION
--        "The group of objects supporting management of IPIPE Service
--         on Nokia 7x50 SR series systems."
--    ::= { tnSvcGroups 135 }

-- tnSvcDhcpBgpV7v0Group OBJECT-GROUP
--    OBJECTS {
--      tnSvcDhcpLseStateBgpPrngPlcyName,
--      tnSvcDhcpLseStateBgpAuthKeyChain,
--      tnSvcDhcpLseStateBgpMD5AuthKey,
--      tnSvcDhcpLseStateBgpImportPolicy,
--      tnSvcDhcpLseStateBgpExportPolicy,
--      tnSvcDhcpLseStateBgpPeerAS,
--      tnSvcDhcpLseStateBgpPeeringStatus
--    }
--    STATUS      current
--    DESCRIPTION
--        "The group of objects containing the BGP-parameters set by DHCP."
--    ::= { tnSvcGroups 136 }

-- tnSvcTlsPipV7v0Group OBJECT-GROUP
--    OBJECTS {
--      tnTlsPipStpPortState,
--      tnTlsPipStpPortRole,
--      tnTlsPipStpDesignatedBridge,
--      tnTlsPipStpDesignatedPort,
--      tnTlsPipStpException,
--      tnTlsPipStpForwardTransitions,
--      tnTlsPipStpInConfigBpdus,
--      tnTlsPipStpInTcnBpdus,
--      tnTlsPipStpInRstBpdus,
--      tnTlsPipStpInMstBpdus,
--      tnTlsPipStpInBadBpdus,
--      tnTlsPipStpOutConfigBpdus,
--      tnTlsPipStpOutTcnBpdus,
--      tnTlsPipStpOutRstBpdus,
--      tnTlsPipStpOutMstBpdus,
--      tnTlsPipStpOperStatus,
--      tnTlsPipStpMvplsPruneState,
--      tnTlsPipStpOperProtocol,
--      tnTlsPipStpPortNum,
--      tnTlsPipMstiPortRole,
--      tnTlsPipMstiPortState,
--      tnTlsPipMstiDesignatedBridge,
--      tnTlsPipMstiDesignatedPort,
--      tnTlsPipStpInsideRegion
--    }
--    STATUS      current
--    DESCRIPTION
--        "The group of objects supporting management of Services TLS PIP
--         capabilities on Nokia 7x50 SR series systems."
--    ::= { tnSvcGroups 137 }

-- tmnxArpHostBgpGroup OBJECT-GROUP
--    OBJECTS {
--        tnSvcArpHostBgpPrngPlcyName,
--        tnSvcArpHostBgpAuthKeyChain,
--        tnSvcArpHostBgpMD5AuthKey,
--        tnSvcArpHostBgpImportPolicy,
--        tnSvcArpHostBgpExportPolicy,
--        tnSvcArpHostBgpPeerAS,
--        tnSvcArpHostBgpPeeringStatus
--    }
--    STATUS      current
--    DESCRIPTION
--        "The group of objects supporting management of Services ARP hosts'
--         BGP capabilities on Nokia 7xxx series systems."
--    ::= { tnSvcGroups 138 }

-- tnSvcDhcpV7v0Group OBJECT-GROUP
--    OBJECTS {
--      tnSvcDhcpLseStateLocale,
--      tnSvcDhcpLseStatePortId,
--      tnSvcDhcpLseStateEncapValue,
--      tnSvcDhcpLseStateSdpId,
--      tnSvcDhcpLseStateVcId,
--      tnSvcDhcpLseStateChAddr,
--      tnSvcDhcpLseStateRemainLseTime,
--      tnSvcDhcpLseStateOption82,
--      tnSvcDhcpLseStatePersistKey,
--      tnSvcDhcpLseStateSubscrIdent,
--      tnSvcDhcpLseStateSubProfString,
--      tnSvcDhcpLseStateSlaProfString,
--      tnSvcDhcpLseStateShcvOperState,
--      tnSvcDhcpLseStateShcvChecks,
--      tnSvcDhcpLseStateShcvReplies,
--      tnSvcDhcpLseStateShcvReplyTime,
--      tnSvcDhcpLseStateClientId,
--      tnSvcDhcpLseStateIAID,
--      tnSvcDhcpLseStateIAIDType,
--      tnSvcDhcpLseStateCiAddrMaskLen,
--      tnSvcDhcpLseStateRetailerSvcId,
--      tnSvcDhcpLseStateRetailerIf,
--      tnSvcDhcpLseStateAncpString,
--      tnSvcDhcpLseStateFramedIpNetMaskTp,
--      tnSvcDhcpLseStateFramedIpNetMask,
--      tnSvcDhcpLseStateBCastIpAddrType,
--      tnSvcDhcpLseStateBCastIpAddr,
--      tnSvcDhcpLseStateDefaultRouterTp,
--      tnSvcDhcpLseStateDefaultRouter,
--      tnSvcDhcpLseStatePrimaryDnsType,
--      tnSvcDhcpLseStatePrimaryDns,
--      tnSvcDhcpLseStateSecondaryDnsType,
--      tnSvcDhcpLseStateSecondaryDns,
--      tnSvcDhcpLseStateSessionTimeout,
--      tnSvcDhcpLseStateServerLeaseStart,
--      tnSvcDhcpLseStateServerLastRenew,
--      tnSvcDhcpLseStateServerLeaseEnd,
--      tnSvcDhcpLseStateDhcpServerAddrType,
--      tnSvcDhcpLseStateDhcpServerAddr,
--      tnSvcDhcpLseStateOriginSubscrId,
--      tnSvcDhcpLseStateOriginStrings,
--      tnSvcDhcpLseStateOriginLeaseInfo,
--      tnSvcDhcpLseStateDhcpClientAddrType,
--      tnSvcDhcpLseStateDhcpClientAddr,
--      tnSvcDhcpLseStateLeaseSplitActive,
--      tnSvcDhcpLseStateInterDestId,
--      tnSvcDhcpLseStatePrimaryNbnsType,
--      tnSvcDhcpLseStatePrimaryNbns,
--      tnSvcDhcpLseStateSecondaryNbnsType,
--      tnSvcDhcpLseStateSecondaryNbns,
--      tnSvcDhcpLseStateNextHopMacAddr,
--      tnSvcDhcpLseStateCategoryMapName,
--      tnSvcDhcpLseStateNakNextRenew,
--      tnSvcDhcpLseStateRadiusClassAttr,
--      tnSvcDhcpLseStateRadiusUserName,
--      tnSvcDhcpLseStateModifySubIndent,
--      tnSvcDhcpLseStateModifySubProfile,
--      tnSvcDhcpLseStateModifySlaProfile,
--      tnSvcDhcpLseStateEvaluateState,
--      tnSvcDhcpLseStateModInterDestId,
--      tnSvcDhcpLseStateModifyAncpString,
--      tnSvcDhcpLseStateForceRenew,
--      tnSvcDhcpManagedRouteStatus
--    }
--    STATUS      current
--    DESCRIPTION
--        "The group of objects supporting management of Services DHCP Lease
--         capabilities on Nokia 7x50 SR series systems."
--    ::= { tnSvcGroups 139 }

-- tnSvcPbbMacV7v0Group OBJECT-GROUP
--    OBJECTS {
--     tnSvcEpipePbbBvplsDstMacName,
--     tnSvcEpipePbbBvplsOperDstMac,
--     tnSvcMacNameAddr,
--     tnSvcMacNameLastChngd,
--     tnSvcMacNameRowStatus,
--     tnSvcMacNameTableLastChanged,
--     tnSvcPbbSrcBVplsMacAddr,
--     tnSvcMacNotifCount,
--     tnSvcMacNotifInterval,
--     tnSvcTlsMacNotifAdminState,
--     tnSvcTlsMacNotifCount,
--     tnSvcTlsMacNotifInterval,
--     tnSvcTlsBackboneUseSapBMac,
--     tnSvcTlsPbbIgmpSnpgMRtrRowStatus,
--     tnSvcTlsPbbIgmpSnpgMRtrLastCh
--    }
--    STATUS      current
--    DESCRIPTION
--        "The group of objects supporting management of Services PBB MAC
--         capabilities on Nokia 7x50 SR series systems."
--    ::= { tnSvcGroups 140 }

-- tnSvcV7v0Group OBJECT-GROUP
--    OBJECTS {
--      tnSvcNumMcStandbySaps,
--      tnSvcName
--    }
--    STATUS      current
--    DESCRIPTION
--        "The group of objects supporting management of Services
--         capabilities on Nokia 7x50 SR series systems for release 7.0."
--    ::= { tnSvcGroups 142 }

-- tnSvcTlsFdbV7v0Group OBJECT-GROUP
--    OBJECTS {
--      tnTlsFdbMacAddr,
--      tnTlsFdbRowStatus,
--      tnTlsFdbType,
--      tnTlsFdbLocale,
--      tnTlsFdbPortId,
--      tnTlsFdbEncapValue,
--      tnTlsFdbSdpId,
--      tnTlsFdbVcId,
--      tnTlsFdbVpnId,
--      tnTlsFdbCustId,
--      tnTlsFdbLastStateChange,
--      tnTlsFdbProtected,
--      tnTlsFdbBackboneDstMac,
--      tnTlsFdbNumIVplsMac,
--      tnTlsFdbEndPointName,
--      tnTlsFdbEPMacOperSdpId,
--      tnTlsFdbEPMacOperVcId,
--      tnTlsFdbPbbNumEpipes,
--      tnTlsProtMacRowStatus,
--      tnTlsProtMacLastMgmtChange,
--      tnTlsProtMacImplCount
--    }
--    STATUS      current
--    DESCRIPTION
--        "The group of objects supporting management of Services TLS FDB
--         capabilities on Nokia 7x50 SR series systems."
--    ::= { tnSvcGroups 141 }

-- Notification objects group

-- tnSvcNotifyObjsV6v0Group OBJECT-GROUP
--    OBJECTS {
--      tnSvcDhcpRestoreLseStateCiAddr,
--      tnSvcDhcpRestoreLseStateProblem,
--      tnSvcDhcpLseStateOldCiAddr,
--      tnSvcDhcpLseStateOldChAddr,
--      tnSvcDhcpLseStateNewCiAddr,
--      tnSvcDhcpLseStateNewChAddr,
--      tnSvcDhcpClientLease,
--      tnSvcDhcpPacketProblem,
--      tnSvcDhcpLseStatePopulateError,
--      tnHostConnectivityCiAddrType,
--      tnHostConnectivityCiAddr,
--      tnHostConnectivityChAddr,
--      tnProtectedMacForNotify,
--      tnStaticHostDynamicMacIpAddress,
--      tnStaticHostDynamicMacConflict,
--      tnSvcObjRow,
--      tnSvcObjRowDescr,
--      tnSvcObjTodSuite,
--      tnFailureDescription,
--      tnSvcDhcpProxyError,
--      tnSvcDhcpCoAError,
--      tnSvcDhcpSubAuthError,
--      tnSvcTlsMrpAttrRegFailedReason,
--      tnSvcTlsMrpAttrType,
--      tnSvcTlsMrpAttrValue,
--      tnSvcMstiInstanceId,
--      tnCustomerBridgeId,
--      tnCustomerRootBridgeId,
--      tnOtherBridgeId,
--      tnOldSdpBindTlsStpPortState,
--      tnVcpState,
--      tnMacPinningMacAddress,
--      tnMacPinningPinnedRow,
--      tnMacPinningPinnedRowDescr,
--      tnMacPinningViolatingRow,
--      tnMacPinningViolatingRowDescr
--    }
--    STATUS      obsolete
--    DESCRIPTION
--        "The group of objects supporting management of Services
--         notification objects on Nokia 7x50 SR series systems."
--    ::= { tnSvcGroups 200 }

-- V7v0 feature, not in V6v1 :
-- tmnxArpHostNotifyObjsGroup OBJECT-GROUP
--    OBJECTS {
--      tnSvcNotifSapPortId,
--      tnSvcNotifSapEncapValue,
--      tnSvcArpHostPopulateError
--    }
--    STATUS      current
--    DESCRIPTION
--        "The group of objects supporting management of Services
--         notification objects on Nokia 7x50 SR series systems."
--    ::= { tnSvcGroups 201 }

-- tnSvcNotifyObjsV7v0Group OBJECT-GROUP
--    OBJECTS {
--      tnSvcDhcpRestoreLseStateCiAddr,
--      tnSvcDhcpRestoreLseStateProblem,
--      tnSvcDhcpLseStateOldCiAddr,
--      tnSvcDhcpLseStateOldChAddr,
--      tnSvcDhcpLseStateNewCiAddr,
--      tnSvcDhcpLseStateNewChAddr,
--      tnSvcDhcpClientLease,
--      tnSvcDhcpPacketProblem,
--      tnSvcDhcpLseStatePopulateError,
--      tnHostConnectivityCiAddrType,
--      tnHostConnectivityCiAddr,
--      tnHostConnectivityChAddr,
--      tnProtectedMacForNotify,
--      tnStaticHostDynamicMacIpAddress,
--      tnStaticHostDynamicMacConflict,
--      tnSvcObjRow,
--      tnSvcObjRowDescr,
--      tnSvcObjTodSuite,
--      tnFailureDescription,
--      tnSvcDhcpProxyError,
--      tnSvcDhcpCoAError,
--      tnSvcDhcpSubAuthError,
--      tnSvcTlsMrpAttrRegFailedReason,
--      tnSvcTlsMrpAttrType,
--      tnSvcTlsMrpAttrValue,
--      tnSvcMstiInstanceId,
--      tnCustomerBridgeId,
--      tnCustomerRootBridgeId,
--      tnOtherBridgeId,
--      tnOldSdpBindTlsStpPortState,
--      tnVcpState,
--      tnMacPinningMacAddress,
--      tnMacPinningPinnedRow,
--      tnMacPinningPinnedRowDescr,
--      tnMacPinningViolatingRow,
--      tnMacPinningViolatingRowDescr,
--      tnSvcHostAddrType,
--      tnSvcHostAddr
--    }
--    STATUS      current
--    DESCRIPTION
--        "The group of objects supporting management of Services
--         notification objects on Nokia 7x50 SR series systems."
--    ::= { tnSvcGroups 202 }

-- Obsoleted (300)

-- tnSvcObsoletedV6v0Group OBJECT-GROUP
--    OBJECTS {
--      tnSvcTlsStpHoldTime,
--      tnTlsMFibInfoFwdOrBlk,
--      tnTlsMFibInfoSvcId,
--      tnTlsMFibGrpSrcStatsForwardedPkts,
--      tnTlsMFibGrpSrcStatsForwardedOctets,
--      tnTlsDHCPClientLease,
--      tnTlsDhcpLseStateOldCiAddr,
--      tnTlsDhcpLseStateOldChAddr,
--      tnTlsDhcpLseStateNewCiAddr,
--      tnTlsDhcpLseStateNewChAddr,
--      tnTlsDhcpRestoreLseStateCiAddr,
--      tnTlsDhcpRestoreLseStateSvcId,
--      tnTlsDhcpRestoreLseStatePortId,
--      tnTlsDhcpRestoreLseStateEncapVal,
--      tnTlsDhcpRestoreLseStateProblem,
--      tnTlsDhcpPacketProblem,
--      tnTlsDhcpLseStatePopulateError
--    }
--    STATUS      current
--    DESCRIPTION
--        "The group of obsolete objects for the services feature
--         on Nokia 7x50 SR series systems."
--    ::= { tnSvcGroups 300 }


-- ----------------------------
-- NOTIFICATION group
-- ----------------------------
-- tnSvcNotifyV6v0Group NOTIFICATION-GROUP
--    NOTIFICATIONS   {
--      tnSvcStatusChanged,
--      tnSvcTlsFdbTableFullAlarmRaised,
--      tnSvcTlsFdbTableFullAlarmCleared,
--      tnIesIfStatusChanged,
--      tnSvcTlsMfibTableFullAlarmRaised,
--      tnSvcTlsMfibTableFullAlarmCleared,
--      tnSvcTlsMacPinningViolation,
--      tnSvcDHCPLseStateRestoreProblem,
--      tnSvcObjTodSuiteApplicFailed,
--      tnEndPointTxActiveChanged,
--      tnSvcPEDiscPolServOperStatChg,
--      tnSvcEndPointMacLimitAlarmRaised,
--      tnSvcEndPointMacLimitAlarmCleared,
--      tnSvcTlsMrpAttrRegistrationFailed,
--      tnSvcTlsMrpAttrTblFullAlarmRaised,
--      tnSvcTlsMrpAttrTblFullAlarmCleared,
--      tnSvcEpipePbbOperStatusChanged,
--      tnTopologyChangeVcpState,
--      tnNewRootVcpState,
--      tnNewRootBridge,
--      tnVcpActiveProtocolChange,
--      tnNewCistRegionalRootBridge,
--      tnNewMstiRegionalRootBridge,
--      tnTopologyChangePipMajorState,
--      tnTopologyChangePipState,
--      tnPipStpExcepCondStateChng,
--      tnPipActiveProtocolChange,
--      tnSvcFdbMimDestTblFullAlrm,
--      tnSvcFdbMimDestTblFullAlrmCleared,
--      tnSvcDHCPMiscellaneousProblem,
--      tnSvcPersistencyProblem
--    }
--    STATUS      obsolete
--    DESCRIPTION
--        "The group of notifications for the services feature
--         on Nokia 7x50 SR series systems."
--    ::= { tnSvcGroups 401 }

-- tnSvcNotifyObsoletedGroup NOTIFICATION-GROUP
--    NOTIFICATIONS   {
--      tnCustCreated,
--      tnCustDeleted,
--      tnCustMultSvcSiteCreated,
--      tnCustMultSvcSiteDeleted,
--      tnSvcCreated,
--      tnSvcDeleted,
--      tnIesIfCreated,
--      tnIesIfDeleted,
--      tnSvcTlsDHCPLseStRestoreProblem,
--      tnSvcTlsDHCPLseStatePopulateErr
--    }
--    STATUS      current
--    DESCRIPTION
--        "The group of notifications for the services feature
--         on Nokia 7x50 SR series systems."
--    ::= { tnSvcGroups 402 }

-- tmnxArpHostNotifyGroup NOTIFICATION-GROUP
--    NOTIFICATIONS   {
--      tnSvcArpHostPopulateErr
--    }
--    STATUS      current
--    DESCRIPTION
--        "The group of notifications for the Services ARP hosts
--         feature on Nokia 7xxx series systems."
--    ::= { tnSvcGroups 403 }

-- tnSvcMCEPNotifyGroup NOTIFICATION-GROUP
--    NOTIFICATIONS   {
--         tnSvcEPMCEPConfigMismatch,
--         tnSvcEPMCEPConfigMismatchResolved,
--         tnSvcEPMCEPPassiveModeActive,
--         tnSvcEPMCEPPassiveModePassive
--    }
--    STATUS      current
--    DESCRIPTION
--        "The group of notifications for the Services multi-chassis endpoint
--         feature on Nokia 7xxx series systems."
--    ::= { tnSvcGroups 404 }

-- tnSvcNotifyV7v0Group NOTIFICATION-GROUP
--    NOTIFICATIONS   {
--      tnSvcStatusChanged,
--      tnSvcTlsFdbTableFullAlarmRaised,
--      tnSvcTlsFdbTableFullAlarmCleared,
--      tnIesIfStatusChanged,
--      tnSvcTlsMfibTableFullAlarmRaised,
--      tnSvcTlsMfibTableFullAlarmCleared,
--      tnSvcTlsMacPinningViolation,
--      tnSvcDHCPLseStateRestoreProblem,
--      tnSvcObjTodSuiteApplicFailed,
--      tnEndPointTxActiveChanged,
--      tnSvcPEDiscPolServOperStatChg,
--      tnSvcEndPointMacLimitAlarmRaised,
--      tnSvcEndPointMacLimitAlarmCleared,
--      tnSvcTlsMrpAttrRegistrationFailed,
--      tnSvcTlsMrpAttrTblFullAlarmRaised,
--      tnSvcTlsMrpAttrTblFullAlarmCleared,
--      tnSvcEpipePbbOperStatusChanged,
--      tnTopologyChangeVcpState,
--      tnNewRootVcpState,
--      tnNewRootBridge,
--      tnVcpActiveProtocolChange,
--      tnNewCistRegionalRootBridge,
--      tnNewMstiRegionalRootBridge,
--      tnTopologyChangePipMajorState,
--      tnTopologyChangePipState,
--      tnPipStpExcepCondStateChng,
--      tnPipActiveProtocolChange,
--      tnSvcFdbMimDestTblFullAlrm,
--      tnSvcFdbMimDestTblFullAlrmCleared,
--      tnSvcDHCPMiscellaneousProblem,
--      tnSvcPersistencyProblem,
--      tnSvcRestoreHostProblem
--    }
--    STATUS      current
--    DESCRIPTION
--        "The group of notifications for the services feature
--         on Nokia 7x50 SR series systems."
--    ::= { tnSvcGroups 405 }

END
