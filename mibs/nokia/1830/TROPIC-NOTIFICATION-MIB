TROPIC-NOTIFICATION-MIB DEFINITIONS ::= BEGIN

-- (c) Copyright 2023 Nokia Networks.  All rights reserved.
-- This software is the confidential and proprietary property of
-- Nokia and may only be used in accordance with the terms of the
-- license agreement provided with this software.

IMPORTS
      SnmpAdminString                         FROM SNMP-FRAMEWORK-MIB
      MODULE-IDENTITY, OBJECT-TYPE,
      Unsigned32, NOTIFICATION-TYPE           FROM SNMPv2-SMI
      MODULE-COMPLIANCE, OBJECT-GROUP         FROM SNMPv2-CONF
      TruthValue                              FROM SNMPv2-TC
      TnTrapCategory,
      TnEntityType,
      TnCondition                             FROM TROPIC-TC
      tnSlotProgrammedType                    FROM TROPIC-SLOT-MIB
      InetAddress                             FROM INET-ADDRESS-MIB
      tnSystemModules, tnNotificationMIB      FROM TROPIC-GLOBAL-REG;

  tnNotificationMIBModule MODULE-IDENTITY
      LAST-UPDATED    "202302171200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION "The notification MIB, including alarms/conditions/events
                   and the SNMP trap buffer."

      REVISION    "202302171200Z"
      DESCRIPTION "Added the following objectId types:
                   ipV6DhcpRelayObjectId(44)
                   to
                   dhppOjbjectid(52)."

      REVISION    "202302031200Z"
      DESCRIPTION "Added the following notifications:
                   tnBgpPeer1IPv4PrefixThresholdRaisedNotif (tnV2AlarmNotificationsRel2 2995)
                   to
                   tnShelfTypeMismatchClearedNotif          (tnV2AlarmNotificationsRel2 3012)."

      REVISION    "202301131200Z"
      DESCRIPTION "Added the following notifications:
                   tnLofSdfecRaisedNotif  (tnV2AlarmNotificationsRel2 2993)
                   tnLofSdfecClearedNotif (tnV2AlarmNotificationsRel2 2994)."

      REVISION    "202301061200Z"
      DESCRIPTION "Added the following notification:
                   tnSecurityChangeRadAttrNotif (tnV2SecurityNotifications 85)."

      REVISION    "202212231200Z"
      DESCRIPTION "Added the following notifications:
                   tnDhppAlsRaisedNotif  (tnV2AlarmNotificationsRel2 2991)
                   tnDhppAlsClearedNotif (tnV2AlarmNotificationsRel2 2992)."

      REVISION    "202211251200Z"
      DESCRIPTION "1) Added the following notifications:
                      tnEntropyFailRaisedNotif     (tnV2AlarmNotificationsRel2 2975)
                      to
                      tnDhppNoResponseClearedNotif (tnV2AlarmNotificationsRel2 2990).
                   2) Added the following notifications:
                      tnDhppFrcdWkSwBkChangeNotif (tnV2EventNotificationsRel2 176)
                      to
                      tnDhppNRFeChangeNotif       (tnV2EventNotificationsRel2 193)."

      REVISION    "202210071200Z"
      DESCRIPTION "Added the following notifications:
                   tnLagDiffLinkIdRaisedNotif   (tnV2AlarmNotificationsRel2 2967)
                   to
                   tnLagDiffSvcConvClearedNotif (tnV2AlarmNotificationsRel2 2974)."

      REVISION    "202209301200Z"
      DESCRIPTION "Added the following notifications:
                   tnMaint1AllowedRemoteRaisedNotif (tnV2AlarmNotificationsRel2 2957)
                   to
                   tnMaintAllowedLocalClearedNotif  (tnV2AlarmNotificationsRel2 2962)."

      REVISION    "202209091200Z"
      DESCRIPTION "Added the following notifications:
                   tnTPmonRoeDecapPktMissing15MinRaisedNotif (tnV2AlarmNotificationsRel2 2963)
                   to
                   tnTPmonRoeDecapPktMissing1DayClearedNotif (tnV2AlarmNotificationsRel2 2966)."

      REVISION    "202208261200Z"
      DESCRIPTION "Added the following notifications:
                   tnConfigFailOtsigRaisedNotif  (tnV2AlarmNotificationsRel2 2955)
                   tnConfigFailOtsigClearedNotif (tnV2AlarmNotificationsRel2 2956)."

      REVISION    "202208191200Z"
      DESCRIPTION "Added the following notification:
                   tnSecurityChangeUserMgmtAttrNotif (tnV2SecurityNotifications 84)."

      REVISION    "202207151200Z"
      DESCRIPTION "Added the following notifications:
                   tnTFcpktCrc15MinRaisedNotif  (tnV2AlarmNotificationsRel2 2947)
                   to
                   tnTFcpktCrct1DayClearedNotif (tnV2AlarmNotificationsRel2 2954)."

      REVISION    "202206101200Z"
      DESCRIPTION "Added the following notifications:
                   tnKeyMismatchRaisedNotif  (tnV2AlarmNotificationsRel2 2945)
                   tnKeyMismatchClearedNotif (tnV2AlarmNotificationsRel2 2946)."

      REVISION    "202205271200Z"
      DESCRIPTION "Added the following notifications:
                   tnComLosModRaisedNotif  (tnV2AlarmNotificationsRel2 2943)
                   tnComLosModClearedNotif (tnV2AlarmNotificationsRel2 2944)."

      REVISION    "202205061200Z"
      DESCRIPTION "1) Added the following notifications:
                      tnGnssTimeFrngRaisedNotif       (tnV2AlarmNotificationsRel2 2919)
                      to
                      tnPtsfSyncUncertainClearedNotif (tnV2AlarmNotificationsRel2 2942).
                   2) tnSecurityCertValidationNotif   (tnV2SecurityNotifications 83)."

      REVISION    "202204221200Z"
      DESCRIPTION "Added the following notifications:
                   tnOSPFADJV3RaisedNotif  (tnV2AlarmNotificationsRel2 2917)
                   tnOSPFADJV3ClearedNotif (tnV2AlarmNotificationsRel2 2918)."

      REVISION    "202204151200Z"
      DESCRIPTION "1) Added the following notifications:
                      tnLofDoRaisedNotif  (tnV2AlarmNotificationsRel2 2915)
                      tnLofDoClearedNotif (tnV2AlarmNotificationsRel2 2916).
                   2) Added the following notification:
                      tnSecurityChangeConnectedStateNotif (tnV2SecurityNotifications 82)."

      REVISION    "202203181200Z"
      DESCRIPTION "Added the following notifications:
                   tnPwrLimitHighRaisedNotif (tnV2AlarmNotificationsRel2 2905)
                   to
                   tnCapUpgInprClearedNotif  (tnV2AlarmNotificationsRel2 2914)."

      REVISION    "202203111200Z"
      DESCRIPTION "Added the following notifications:
                   tnLosInferredRaisedNotif  (tnV2AlarmNotificationsRel2 2903)
                   tnLosInferredClearedNotif (tnV2AlarmNotificationsRel2 2904)."

      REVISION    "202202251200Z"
      DESCRIPTION "Added the following notifications:
                   tnTOchOprh15MinRaisedNotif (tnV2AlarmNotificationsRel2 2895)
                   to
                   tnTOchOprl1DayClearedNotif (tnV2AlarmNotificationsRel2 2902)."

      REVISION    "202202181200Z"
      DESCRIPTION "Added the following notifications:
                   tnSciLinkInitRaisedNotif ( tnV2AlarmNotificationsRel2 2875 )
                   to
                   tnFmmFlexOClearedNotif   ( tnV2AlarmNotificationsRel2 2894 )."

      REVISION    "202111261200Z"
      DESCRIPTION "Updated information for the following:
                   otnEntityObjectId(25)."

      REVISION    "202111191200Z"
      DESCRIPTION "Added the following notifications:
                   tnAutoDownCITStateChangeNotif          (tnV2EventNotificationsRel2 173)
                   to
                   tnAutoNotApplicableCITStateChangeNotif (tnV2EventNotificationsRel2 175)."

      REVISION    "202111051200Z"
      DESCRIPTION "Marked the following as obsolete:
                   tnSwUpdateIPRaisedNotif  (tnV2AlarmNotificationsRel2 2841)
                   tnSwUpdateIPClearedNotif (tnV2AlarmNotificationsRel2 2842)."

      REVISION    "202110221200Z"
      DESCRIPTION "Added the following notifications:
                   tnTrustCertValidityWarnRaisedNotif (tnV2AlarmNotificationsRel2 2863)
                   to
                   tnNeCertRevClearedNotif            (tnV2AlarmNotificationsRel2 2874)."

      REVISION    "202109241200Z"
      DESCRIPTION "Added the following notifications:
                   tnSwFeatureUnknownRaisedNotif (tnV2AlarmNotificationsRel2 2859)
                   to
                   tnSwRefreshFailClearedNotif   (tnV2AlarmNotificationsRel2 2862)."

      REVISION    "202109171200Z"
      DESCRIPTION "Added the following notifications:
                   tnCableFailRaisedNotif  (tnV2AlarmNotificationsRel2 2857)
                   tnCableFailClearedNotif (tnV2AlarmNotificationsRel2 2858)."

      REVISION    "202109101200Z"
      DESCRIPTION "Added the following notification:
                   tnNeColdResetPendingNotif (tnV2EventNotificationsRel2 172)."

      REVISION    "202108061200Z"
      DESCRIPTION "Added the following notifications:
                   tnDelayModeRaisedNotif  (tnV2AlarmNotificationsRel2 2855)
                   tnDelayModeClearedNotif (tnV2AlarmNotificationsRel2 2856)."

      REVISION    "202107301200Z"
      DESCRIPTION "Added the following notifications:
                   tnCardPowerFailRaisedNotif  (tnV2AlarmNotificationsRel2 2853)
                   tnCardPowerFailClearedNotif (tnV2AlarmNotificationsRel2 2854)."

      REVISION    "202107231200Z"
      DESCRIPTION "Added the following notifications:
                   tnEpsImpairedRaisedNotif  (tnV2AlarmNotificationsRel2 2851)
                   tnEpsImpairedClearedNotif (tnV2AlarmNotificationsRel2 2852)."

      REVISION    "202107161200Z"
      DESCRIPTION "Changed SYNTAX of the following from (SIZE(0..960)) to
                   (SIZE(0..2048)):
                   tnTrapData."

      REVISION    "202107091200Z"
      DESCRIPTION "Added the following notifications:
                   tnNotifsThrottledRaisedNotif  (tnV2AlarmNotificationsRel2 2849)
                   tnNotifsThrottledClearedNotif (tnV2AlarmNotificationsRel2 2850)."

      REVISION    "202106111200Z"
      DESCRIPTION "Added the following notifications:
                   tnComErrModRaisedNotif  (tnV2AlarmNotificationsRel2 2847)
                   tnComErrModClearedNotif (tnV2AlarmNotificationsRel2 2848)."

      REVISION    "202105071200Z"
      DESCRIPTION "Added the following notifications:
                   tnSwMissingRaisedNotif (tnV2AlarmNotificationsRel2 2839)
                   to
                   tnLOAClearedNotif      (tnV2AlarmNotificationsRel2 2846)."

      REVISION    "202103191200Z"
      DESCRIPTION "Added the following notifications:
                   tnLRCRaisedNotif               (tnV2AlarmNotificationsRel2 2825)
                   to
                   tnSyslogTransferIPClearedNotif (tnV2AlarmNotificationsRel2 2838)."

      REVISION    "202102051200Z"
      DESCRIPTION "Added the following notifications:
                   tnOadoorRaisedNotif      (tnV2AlarmNotificationsRel2 2821)
                   to
                   tnCvFailEqptClearedNotif (tnV2AlarmNotificationsRel2 2824)."

      REVISION    "202101151200Z"
      DESCRIPTION "Added the following notifications:
                   tnPortFPGAInit1RaisedNotif    (tnV2AlarmNotificationsRel2 2767)
                   to
                   tnPortFPGAFailNSAClearedNotif (tnV2AlarmNotificationsRel2 2820)."

      REVISION    "202012111200Z"
      DESCRIPTION "Added the following notifications:
                   tnThermShutdModRaisedNotif (tnV2AlarmNotificationsRel2 2763)
                   to
                   tnTempOorModClearedNotif   (tnV2AlarmNotificationsRel2 2766)."

      REVISION    "202012041200Z"
      DESCRIPTION "Added the following notifications:
                   tnTRNGNoiseSourceFailRaisedNotif (tnV2AlarmNotificationsRel2 2753)
                   to
                   tnTRNGHwFailClearedNotif         (tnV2AlarmNotificationsRel2 2762)."

      REVISION    "202011271200Z"
      DESCRIPTION "Added the following notifications:
                   tnOchFailedLLRaisedNotif     (tnV2AlarmNotificationsRel2 2749)
                   to
                   tnOchFailedLLOutClearedNotif (tnV2AlarmNotificationsRel2 2752)."

      REVISION    "202011131200Z"
      DESCRIPTION "Added the following notifications:
                   tnRmdDInitRaisedNotif  (tnV2AlarmNotificationsRel2 2747)
                   tnRmdDInitClearedNotif (tnV2AlarmNotificationsRel2 2748)."

      REVISION    "202011061200Z"
      DESCRIPTION "Added the following notifications:
                   tnPnacPortAuthFailRaisedNotif  (tnV2AlarmNotificationsRel2 2745)
                   tnPnacPortAuthFailClearedNotif (tnV2AlarmNotificationsRel2 2746)."

      REVISION    "202010231200Z"
      DESCRIPTION "Added the following notifications:
                   tnCardDgrOmRaisedNotif   (tnV2AlarmNotificationsRel2 2741)
                   to
                   tnHiSpanLossClearedNotif (tnV2AlarmNotificationsRel2 2744)."

      REVISION    "202010161200Z"
      DESCRIPTION "Added the following notifications:
                   tnAdjHiFiberLossRaisedNotif (tnV2AlarmNotificationsRel2 2713)
                   to
                   tnRmdMepUNPRClearedNotif    (tnV2AlarmNotificationsRel2 2740)."

      REVISION    "202009251200Z"
      DESCRIPTION "Added the following notifications:
                   tnConfigPortFailRaisedNotif  (tnV2AlarmNotificationsRel2 2711)
                   tnConfigPortFailClearedNotif (tnV2AlarmNotificationsRel2 2712)."

      REVISION    "202009111200Z"
      DESCRIPTION "Added the following notifications:
                   tnASEAMPFAILRaisedNotif  (tnV2AlarmNotificationsRel2 2709)
                   tnASEAMPFAILClearedNotif (tnV2AlarmNotificationsRel2 2710)."

      REVISION    "202008211200Z"
      DESCRIPTION "Added the following notifications:
                   tnPFFANFAULTRaisedNotif  (tnV2AlarmNotificationsRel2 2707)
                   tnPFFANFAULTClearedNotif (tnV2AlarmNotificationsRel2 2708)."

      REVISION    "202007311200Z"
      DESCRIPTION "Added the following notifications:
                   tnFanModFailLeftRaisedNotif        (tnV2AlarmNotificationsRel2 2553)
                   to
                   tnPMACIfOutPackets1DayClearedNotif (tnV2AlarmNotificationsRel2 2706)."

      REVISION    "202007241200Z"
      DESCRIPTION "Added the following notifications:
                   tnFODRaisedNotif  (tnV2AlarmNotificationsRel2 2551)
                   tnFODClearedNotif (tnV2AlarmNotificationsRel2 2552)."

      REVISION    "202007101200Z"
      DESCRIPTION "Added the following notifications:
                   tnLOLCKRaisedNotif  (tnV2AlarmNotificationsRel2 2549)
                   tnLOLCKClearedNotif (tnV2AlarmNotificationsRel2 2550)."

      REVISION    "202007031200Z"
      DESCRIPTION "Updated information for the following:
                   syncObjectId(18)
                   ptpObjectId(28).
                   roeObjectId(43)."

      REVISION    "202006191200Z"
      DESCRIPTION "Added the following notifications:
                   tnCardDgrRaisedNotif  (tnV2AlarmNotificationsRel2 2547)
                   tnCardDgrClearedNotif (tnV2AlarmNotificationsRel2 2548)."

      REVISION    "202005221200Z"
      DESCRIPTION "Added the following notifications:
                   tnIfReplUnitMissMODRaisedNotif  (tnV2AlarmNotificationsRel2 2545)
                   tnIfReplUnitMissMODClearedNotif (tnV2AlarmNotificationsRel2 2546)."

      REVISION    "202005011200Z"
      DESCRIPTION "1) Marked the following as obsolete:
                      tnPwrVOARailedLowCRaisedNotif  (tnV2AlarmNotificationsRel2 2199)
                      tnPwrVOARailedLowCClearedNotif (tnV2AlarmNotificationsRel2 2200).
                   2) Added the following notifications:
                      tnPwrVOARailedLowRaisedNotif   (tnV2AlarmNotificationsRel2 2517)
                      tnPwrVOARailedLowClearedNotif  (tnV2AlarmNotificationsRel2 2518)."

      REVISION    "202004241200Z"
      DESCRIPTION "Added the following notifications:
                   tnAllChanHighLRaisedNotif       (tnV2AlarmNotificationsRel2 2505)
                   to
                   tnGainUnderPlannedLClearedNotif (tnV2AlarmNotificationsRel2 2516)
                   tnNETRaisedNotif                (tnV2AlarmNotificationsRel2 2543)
                   tnNETClearedNotif               (tnV2AlarmNotificationsRel2 2544)."

      REVISION    "202004171200Z"
      DESCRIPTION "1) Added the following notifications:
                      tnTQmarginL15MinRaisedNotif (tnV2AlarmNotificationsRel2 2539)
                      to
                      tnTQmarginL1DayClearedNotif (tnV2AlarmNotificationsRel2 2542).
                   2) Added the following event notifications:
                      tnQsfpHeaterEnableNotif     (tnV2EventNotificationsRel2 170)
                      tnQsfpHeaterDisableNotif    (tnV2EventNotificationsRel2 171)."

      REVISION    "202004101200Z"
      DESCRIPTION "1) Added the following notifications:
                      tnDispShortPushRaisedNotif (tnV2AlarmNotificationsRel2 2531)
                      to
                      tnDispDialogClearedNotif   (tnV2AlarmNotificationsRel2 2538).
                   2) Added the following event notification:
                      tnAutoTrapRebootNotif      (tnV2EventNotificationsRel2 169)."

      REVISION    "202004031200Z"
      DESCRIPTION "Added the following notifications:
                   tnDuplicateMainShelfRaisedNotif (tnV2AlarmNotificationsRel2 2525)
                   to
                   tnExShelfMissingClearedNotif    (tnV2AlarmNotificationsRel2 2530)."

      REVISION    "202003271200Z"
      DESCRIPTION "Added the following event notification:
                   tnDiscoverMeChangeNotif      (tnV2EventNotificationsRel2 168)."

      REVISION    "202003201200Z"
      DESCRIPTION "1) Added description for roeObjectId(43).
                   2) Added the following notifications:
                      tnNvmLowRaisedNotif         (tnV2AlarmNotificationsRel2 2519)
                      to
                      tnAprRamPumpOrlClearedNotif (tnV2AlarmNotificationsRel2 2524)."

      REVISION    "202002211200Z"
      DESCRIPTION "Added the following notifications:
                   tnQsfpHeaterFailRaisedNotif  (tnV2AlarmNotificationsRel2 2501)
                   to
                   tnCpcMismatchClearedNotif    (tnV2AlarmNotificationsRel2 2504)."

      REVISION    "202002071200Z"
      DESCRIPTION "Added the following notifications:
                   tnOchXcInvalidRaisedNotif  (tnV2AlarmNotificationsRel2 2489)
                   to
                   tnBGPPEER4NESTClearedNotif (tnV2AlarmNotificationsRel2 2500)."

      REVISION    "202001101200Z"
      DESCRIPTION "1) Added the following notifications:
                      tnRoeLOLRaisedNotif      (tnV2AlarmNotificationsRel2 2485)
                      to
                      tnDbBuRfsIncClearedNotif (tnV2AlarmNotificationsRel2 2488).
                   2) Added the following event notification:
                      tnNtpChkSigChangeNotif   (tnV2EventNotificationsRel2 167)."

      REVISION    "201912061200Z"
      DESCRIPTION "Added the following notifications:
                   tnPktBkplComRaisedNotif  (tnV2AlarmNotificationsRel2 2483)
                   tnPktBkplComClearedNotif (tnV2AlarmNotificationsRel2 2484)."

      REVISION    "201911151200Z"
      DESCRIPTION "1) Added the following notifications:
                      tnPnacPortBasedHWFailRaisedNotif (tnV2AlarmNotificationsRel2 2479)
                      to
                      tnBITSNotSupportedClearedNotif   (tnV2AlarmNotificationsRel2 2482).
                   2) Added the following event notification:
                      tnPnacPortAuthStateChangeNotif   (tnV2EventNotificationsRel2 166)."

      REVISION    "201911011200Z"
      DESCRIPTION "Added the following notifications:
                   tnZtpIpRaisedNotif          (tnV2AlarmNotificationsRel2 2463)
                   to
                   tnZtpFailClearedNotif       (tnV2AlarmNotificationsRel2 2466)
                   tnDecryptionFailRaisedNotif (tnV2AlarmNotificationsRel2 2473)
                   to
                   tnEncrLinkfailClearedNotif  (tnV2AlarmNotificationsRel2 2478)."

      REVISION    "201910251200Z"
      DESCRIPTION "Added the following notifications:
                   tnODNCRaisedNotif  (tnV2AlarmNotificationsRel2 2471)
                   tnODNCClearedNotif (tnV2AlarmNotificationsRel2 2472)."

      REVISION    "201910111200Z"
      DESCRIPTION "Added the following notifications:
                   tnPcfgdwnlRaisedNotif  (tnV2AlarmNotificationsRel2 2469)
                   tnPcfgdwnlClearedNotif (tnV2AlarmNotificationsRel2 2470)."

      REVISION    "201909271200Z"
      DESCRIPTION "1) Added the following notifications:
                      tnPktBkplMateRaisedNotif  (tnV2AlarmNotificationsRel2 2467)
                      tnPktBkplMateClearedNotif (tnV2AlarmNotificationsRel2 2468).
                   2) Added the following event notification:
                      tnErpOperStateChngNotif   (tnV2EventNotificationsRel2 165)."

      REVISION    "201908161200Z"
      DESCRIPTION "Added the following notifications:
                   tnTopoMissingRaisedNotif  (tnV2AlarmNotificationsRel2 2461)
                   tnTopoMissingClearedNotif (tnV2AlarmNotificationsRel2 2462)."

      REVISION    "201907261200Z"
      DESCRIPTION "1) Added the following event notifications:
                      tnLicReqRedirectedNotif   (tnV2EventNotificationsRel2 163)
                      tnLicClmUnknownErrorNotif (tnV2EventNotificationsRel2 164).
                   2) Added the following notifications:
                      tnZtpTriggerInfoNotif     (tnV2SecurityNotifications 80)
                      tnZtpDhcpIpNotif          (tnV2SecurityNotifications 81)."

      REVISION    "201907191200Z"
      DESCRIPTION "Added the following notifications:
                   tnDbArRaisedNotif           (tnV2AlarmNotificationsRel2 2457)
                   to
                   tnEqptAccessDgrClearedNotif (tnV2AlarmNotificationsRel2 2460)."

      REVISION    "201907121200Z"
      DESCRIPTION "Added the following notifications:
                   tnConfigNotValidRaisedNotif  (tnV2AlarmNotificationsRel2 2455)
                   tnConfigNotValidClearedNotif (tnV2AlarmNotificationsRel2 2456)."

      REVISION    "201907061200Z"
      DESCRIPTION "Added the following notifications:
                   tnGainOverPlannedRaisedNotif   (tnV2AlarmNotificationsRel2 2451)
                   to
                   tnGainUnderPlannedClearedNotif (tnV2AlarmNotificationsRel2 2454)."

      REVISION    "201906211200Z"
      DESCRIPTION "Added the following event notification:
                   tnOchXcCreationDataNotif (tnV2EventNotificationsRel2 162)."

      REVISION    "201906141200Z"
      DESCRIPTION "Changed SYNTAX of the following from (SIZE(0..255)) to (SIZE(0..960)):
                   tnTrapData."

      REVISION    "201906071200Z"
      DESCRIPTION "1) Added the following notifications:
                      tnPktLOSSRaisedNotif            (tnV2AlarmNotificationsRel2 2427)
                      to
                      tnCPRIRAIClearedNotif           (tnV2AlarmNotificationsRel2 2450).
                   2) Added the following event notifications:
                      tnPresentationTimeTooLargeNotif (tnV2EventNotificationsRel2 160)
                      tnPresentationTimeTooSmallNotif (tnV2EventNotificationsRel2 161).
                   3) Added the following notifications:
                      tnClmSigningCertNotif           (tnV2SecurityNotifications 78)
                      tnClmHttpsConnectionNotif       (tnV2SecurityNotifications 79)."

      REVISION    "201905171200Z"
      DESCRIPTION "Added the following notifications:
                   tnRampumpbaseRaisedNotif  (tnV2AlarmNotificationsRel2 2423)
                   to
                   tnHirampumpbrClearedNotif (tnV2AlarmNotificationsRel2 2426)."

      REVISION    "201905031200Z"
      DESCRIPTION "Added the following notifications:
                   tnAllChanHighRaisedNotif   (tnV2AlarmNotificationsRel2 2397)
                   to
                   tnBkplLinkInitClearedNotif (tnV2AlarmNotificationsRel2 2422)."

      REVISION    "201904121200Z"
      DESCRIPTION "Added the following notifications:
                   tnTSIFreezeRaisedNotif  (tnV2AlarmNotificationsRel2 2391)
                   to
                   tnContInfraClearedNotif (tnV2AlarmNotificationsRel2 2396)."

      REVISION    "201904051200Z"
      DESCRIPTION "Added the following notifications:
                   tnLicClmAddressInvalidRaisedNotif (tnV2AlarmNotificationsRel2 2383)
                   to
                   tnDegUcbClearedNotif              (tnV2AlarmNotificationsRel2 2390)."

      REVISION    "201903151200Z"
      DESCRIPTION "1) Added description for cardFacilityGrpObjectId(40).
                   2) Added the following notifications:
                      tnSdpMeshOprDwnRaisedNotif            (tnV2AlarmNotificationsRel2 2379)
                      to
                      tnSdpTlsMacAddrLimitAlarmClearedNotif (tnV2AlarmNotificationsRel2 2382).
                   3) Added the following event notifications:
                      tnSdpMeshStatusChangedNotif           (tnV2EventNotificationsRel2 158)
                      tnSdpTlsMacMoveExceededNotif          (tnV2EventNotificationsRel2 159)."

      REVISION    "201902151200Z"
      DESCRIPTION "Added the following notifications:
                   tnPktBkplSC1RaisedNotif  (tnV2AlarmNotificationsRel2 2367)
                   to
                   tnPktBkplSC6ClearedNotif (tnV2AlarmNotificationsRel2 2378)."

      REVISION    "201902011200Z"
      DESCRIPTION "Added the following notifications:
                   tnEQPTCPCRaisedNotif       (tnV2AlarmNotificationsRel2 2361)
                   to
                   tnCPCALIGNFAILClearedNotif (tnV2AlarmNotificationsRel2 2366)."

      REVISION    "201901251200Z"
      DESCRIPTION "1) Added the following notifications:
                      tnLicActiveCLMUnavailRaisedNotif (tnV2AlarmNotificationsRel2 2309)
                      to
                      tnPTPCOMClearedNotif             (tnV2AlarmNotificationsRel2 2360).
                   2) Added the following event notification:
                      tnLastTrapDeltaFileNotif         (tnV2EventNotificationsRel2 157)."

      REVISION    "201901181200Z"
      DESCRIPTION "Marked the following as obsolete:
                   tnLicenseViolationERRaisedNotif  (tnV2AlarmNotificationsRel2 2163)
                   to
                   tnLicenseViolationHCClearedNotif (tnV2AlarmNotificationsRel2 2166)."

      REVISION    "201901041200Z"
      DESCRIPTION "Added the following notifications:
                   tnSHELFMODERaisedNotif  (tnV2AlarmNotificationsRel2 2307)
                   tnSHELFMODEClearedNotif (tnV2AlarmNotificationsRel2 2308)."

      REVISION    "201812211200Z"
      DESCRIPTION "Added the following notification:
                   tnSecuritySyslogReopenNotif (tnV2SecurityNotifications 77)."

      REVISION    "201812061200Z"
      DESCRIPTION "Added the following event notification:
                   tnDeltaFileRolledOverNotif (tnV2EventNotificationsRel2 156)."

      REVISION    "201811301200Z"
      DESCRIPTION "Added the following MIB attribute:
                   tnTrapResetCount."

      REVISION    "201811261200Z"
      DESCRIPTION "Renamed the following notifications:
                   tnSSMQLDEGRaisedNotif
                   tnSSMQLDEGClearedNotif
                   tnSYNCUNLOCKRaisedNotif
                   tnSYNCUNLOCKClearedNotif
                   tnLOESMCRaisedNotif
                   tnLOESMCClearedNotif
                   tnTTreffoffh15MinRaisedNotif
                   tnTTreffoffh15MinClearedNotif
                   tnTTreffoffh1DayRaisedNotif
                   tnTTreffoffh1DayClearedNotif
                   tnTTreffoffl15MinRaisedNotif
                   tnTTreffoffl15MinClearedNotif
                   tnTTreffoffl1DayRaisedNotif
                   tnTTreffoffl1DayClearedNotif
                   to
                   tnSsmQLDegRaisedNotif
                   tnSsmQLDegClearedNotif
                   tnSyncUnlockRaisedNotif
                   tnSyncUnlockClearedNotif
                   tnLOEsmCRaisedNotif
                   tnLOEsmCClearedNotif
                   tnTFreoffHigh15MinRaisedNotif
                   tnTFreoffHigh15MinClearedNotif
                   tnTFreoffHigh1DayRaisedNotif
                   tnTFreoffHigh1DayClearedNotif
                   tnTFreoffLow15MinRaisedNotif
                   tnTFreoffLow15MinClearedNotif
                   tnTFreoffLow1DayRaisedNotif
                   tnTFreoffLow1DayClearedNotif."

      REVISION    "201811161200Z"
      DESCRIPTION "Added the following notifications:
                   tnLOSN3RaisedNotif  (tnV2AlarmNotificationsRel2 2305)
                   tnLOSN3ClearedNotif (tnV2AlarmNotificationsRel2 2306)."

      REVISION    "201810191200Z"
      DESCRIPTION "Added the following notifications:
                   tnUsAlsLagRaisedNotif  (tnV2AlarmNotificationsRel2 2303)
                   tnUsAlsLagClearedNotif (tnV2AlarmNotificationsRel2 2304)."

      REVISION    "201810121200Z"
      DESCRIPTION "Updated the 'Breakdown of MIB attributes
                   tnTrapObjectID/tnTrapObjectIDType' section."

      REVISION    "201808171200Z"
      DESCRIPTION "Added the following notifications:
                   tnRAMCAPACITYWARNINGRaisedNotif  (tnV2AlarmNotificationsRel2 2301)
                   tnRAMCAPACITYWARNINGClearedNotif (tnV2AlarmNotificationsRel2 2302)."

      REVISION    "201808031200Z"
      DESCRIPTION "Added the following notifications:
                   tnSecurityChangeMinPwdObsIntNotif   (tnV2SecurityNotifications 68)
                   to
                   tnSecurityChangeMinIntInvloginNotif (tnV2SecurityNotifications 76)."

      REVISION    "201807271200Z"
      DESCRIPTION "Added the following alarm notifications:
                   tnOpsProtFailRaisedNotif       (tnV2AlarmNotificationsRel2 2297)
                   to
                   tnOpsProtRedunLossClearedNotif (tnV2AlarmNotificationsRel2 2300)."

      REVISION    "201807161200Z"
      DESCRIPTION "Added the following alarm notifications:
                   tnFanMismatchRaisedNotif (tnV2AlarmNotificationsRel2 2293)
                   to
                   tnDegTransClearedNotif   (tnV2AlarmNotificationsRel2 2296)."

      REVISION    "201806291200Z"
      DESCRIPTION "1) Added the following alarm notifications:
                      tnMacShortageRaisedNotif      (tnV2AlarmNotificationsRel2 2291)
                      to
                      tnMacShortageClearedNotif     (tnV2AlarmNotificationsRel2 2292).
                   2) Added the following notifications:
                      tnSecurityACLLoggingNotif     (tnV2SecurityNotifications 66)
                      tnSecurityACLLoggingIpv6Notif (tnV2SecurityNotifications 67).
                   3) Updated DESCRIPTIONs of the following:
                      tnTrapObjectIDType
                      tnTrapObjectID."

      REVISION    "201806081200Z"
      DESCRIPTION "1) Added the following alarm notifications:
                      tnPTPINPUTDEGRaisedNotif    (tnV2AlarmNotificationsRel2 2277)
                      to
                      tnTPteffefh1DayClearedNotif (tnV2AlarmNotificationsRel2 2290).
                   2) Added the following event notification:
                      tnPTPStatSwitchNotif        (tnV2EventNotificationsRel2 155)."

      REVISION    "201805251200Z"
      DESCRIPTION "Added the following alarm notifications:
                   tnOchXcTechErrRxRaisedNotif  (tnV2AlarmNotificationsRel2 2271)
                   to
                   tnCrdPwrIntFltClearedNotif   (tnV2AlarmNotificationsRel2 2276)."

      REVISION    "201805111200Z"
      DESCRIPTION "Added the following event notifications:
                   tnSyncEStatusChangeNotif            (tnV2EventNotificationsRel2 152)
                   to
                   tnSyncESwitchTimingReferenceT4Notif (tnV2EventNotificationsRel2 154)."

      REVISION    "201805041200Z"
      DESCRIPTION "Added the following notifications:
                   tnSecurityChangeMaxSessionLoginsNotif     (tnV2SecurityNotifications 64)
                   tnSecurityChangeMaxSessionLoginsIpv6Notif (tnV2SecurityNotifications 65)."

      REVISION    "201804271200Z"
      DESCRIPTION "1) Added the following alarm notifications:
                      tnPortProvRaisedNotif       (tnV2AlarmNotificationsRel2 2269)
                      tnPortProvClearedNotif      (tnV2AlarmNotificationsRel2 2270).
                   2) Marked the following as deprecated:
                      tnImageNotReadyRaisedNotif  (tnV2AlarmNotificationsRel2 1799)
                      tnImageNotReadyClearedNotif (tnV2AlarmNotificationsRel2 1800)."

      REVISION    "201803161200Z"
      DESCRIPTION "Added the following alarm notifications:
                   tnOSPFADJv3RaisedNotif  (tnV2AlarmNotificationsRel2 2267)
                   tnOSPFADJv3ClearedNotif (tnV2AlarmNotificationsRel2 2268)."

      REVISION    "201803021200Z"
      DESCRIPTION "Added the following alarm notifications:
                   tnLTIRaisedNotif             (tnV2AlarmNotificationsRel2 2249)
                   to
                   tnTFreoffLow1DayClearedNotif (tnV2AlarmNotificationsRel2 2266)."

      REVISION    "201802231200Z"
      DESCRIPTION "Updated the contact info."

      REVISION    "201712011200Z"
      DESCRIPTION "Added the following alarm notifications:
                   tnTodNotSupportedRaisedNotif  (tnV2AlarmNotificationsRel2 2247)
                   tnTodNotSupportedClearedNotif (tnV2AlarmNotificationsRel2 2248)."

      REVISION    "201711241200Z"
      DESCRIPTION "1) Added the following alarm notifications:
                      tnHiSerRaisedNotif  (tnV2AlarmNotificationsRel2 2245)
                      tnHiSerClearedNotif (tnV2AlarmNotificationsRel2 2246).
                   2) Added the following event notifications:
                      tnCardInsertNotif   (tnV2EventNotificationsRel2 150)
                      tnCardExtractNotif  (tnV2EventNotificationsRel2 151)."

      REVISION    "201711171200Z"
      DESCRIPTION "Added the following alarm notifications:
                   tnCardErrorRaisedNotif             (tnV2AlarmNotificationsRel2 2241)
                   to
                   tnMacAllocationPendingClearedNotif (tnV2AlarmNotificationsRel2 2244)."

      REVISION    "201711031200Z"
      DESCRIPTION "Added the following event notification:
                   tnMplsTpLspPDUChangeNotif (tnV2EventNotificationsRel2 149)."

      REVISION    "201710271200Z"
      DESCRIPTION "Added the following alarm notifications:
                   tnDbBkupIPRaisedNotif  (tnV2AlarmNotificationsRel2 2237)
                   to
                   tnDbRstrIPClearedNotif (tnV2AlarmNotificationsRel2 2240)."

      REVISION    "201709151200Z"
      DESCRIPTION "Marked the following Hermes notifications as obsolete:
                   tnCabinAlarm1RaisedNotif   (tnV2AlarmNotificationsRel2 3109)
                   to
                   tnApsSuspendedClearedNotif (tnV2AlarmNotificationsRel2 3218)."

      REVISION    "201709011200Z"
      DESCRIPTION "Added the following alarm notifications:
                   tnLotRaisedNotif        (tnV2AlarmNotificationsRel2 2227)
                   to
                   tnUruOtsTxLClearedNotif (tnV2AlarmNotificationsRel2 2236)."

      REVISION    "201708181200Z"
      DESCRIPTION "Added the following alarm notifications:
                   tnProtectionFrozenRaisedNotif  (tnV2AlarmNotificationsRel2 2225)
                   tnProtectionFrozenClearedNotif (tnV2AlarmNotificationsRel2 2226)."

      REVISION    "201707281200Z"
      DESCRIPTION "Added the following alarm notifications:
                   tnMixedOperationRaisedNotif     (tnV2AlarmNotificationsRel2 2221)
                   tnBandwidthExceededClearedNotif (tnV2AlarmNotificationsRel2 2224)."

      REVISION    "201707141200Z"
      DESCRIPTION "Added the following alarm notifications:
                   tnLagProtLosRaisedNotif  (tnV2AlarmNotificationsRel2 3219)
                   tnLagProtLosClearedNotif (tnV2AlarmNotificationsRel2 3220)."

      REVISION    "201707071200Z"
      DESCRIPTION "Fixed MIB compile issues."

      REVISION    "201706091200Z"
      DESCRIPTION "Added the following notification:
                   tnSwAssistedNonceChangeNotif (tnV2SecurityNotifications 63)."

      REVISION    "201705311200Z"
      DESCRIPTION "Added the following notifications:
                   tnSSFEthernetRaisedNotif  (tnV2CardNotifications 191)
                   tnSSFEthernetClearedNotif (tnV2CardNotifications 192)."

      REVISION    "201705241200Z"
      DESCRIPTION "1) Added the following notifications:
                      tnSecurityAclVialationIpv6Notif (tnV2SecurityNotifications 35)
                      to
                      tnDormantUserIpv6Notif          (tnV2SecurityNotifications 62).
                   2) Added the following to tnMultipleTypeTrapBufferTable:
                      tnMultipleTypeTrapObjectIDIpV6.
                   3) Added the following to tnTrapBufferTable:
                      tnTrapObjectIDIpV6."

      REVISION    "201705191200Z"
      DESCRIPTION "1) Added the following alarm notifications:
                      tnSyncIfTimingRef3AlarmRaisedNotif  (tnV2AlarmNotificationsRel2 2219)
                      tnSyncIfTimingRef3AlarmClearedNotif (tnV2AlarmNotificationsRel2 2220).
                   2) Marked the following notifications as obsolete:
                      tnLspFailedApeRaisedNotif           (tnV2AlarmNotificationsRel2 1543)
                      to
                      tnEptUploadErrClearedNotif          (tnV2AlarmNotificationsRel2 1600 }
                      tnCommDegRaisedNotif                (tnV2AlarmNotificationsRel2 1603 }
                      to
                      tnNvMismatchClearedNotif            (tnV2AlarmNotificationsRel2 1606)
                      tnFrequencySlotMismatchRaisedNotif  (tnV2AlarmNotificationsRel2 1941)
                      tnFrequencySlotMismatchClearedNotif (tnV2AlarmNotificationsRel2 1942)."

      REVISION    "201704261200Z"
      DESCRIPTION "Added the following event notifications:
                   tnLagPortActStdChangeNotif (tnV2EventNotificationsRel2 146)
                   to
                   tnMcLagStateChangeNotif    (tnV2EventNotificationsRel2 148)."

      REVISION    "201703311200Z"
      DESCRIPTION "1) Added the following alarm notifications:
                      tnApsSuspendedRaisedNotif      (tnV2AlarmNotificationsRel2 3217)
                      tnApsSuspendedClearedNotif     (tnV2AlarmNotificationsRel2 3218).
                   2) Added the following event notification:
                      tnOamTestHeadTestCompleteNotif (tnV2EventNotificationsRel2 145)."

      REVISION    "201702171200Z"
      DESCRIPTION "Added the following alarm notifications:
                   tnPwrVOARailedLowCRaisedNotif (tnV2AlarmNotificationsRel2 2199)
                   to
                   tnFuatClearedNotif            (tnV2AlarmNotificationsRel2 2218)."

      REVISION    "201702031200Z"
      DESCRIPTION "Added the following alarm notification:
                   tnIfTypeUserUnassignNotif (tnV2SystemNotifications 11)."

      REVISION    "201701131200Z"
      DESCRIPTION "Added the following alarm notifications:
                   tnUnprovChanRaisedNotif      (tnV2AlarmNotificationsRel2 2191)
                   to
                   tnUnprovChanOutLClearedNotif (tnV2AlarmNotificationsRel2 2198)."

      REVISION    "201701111200Z"
      DESCRIPTION "Added the following Hermes alarm notifications:
                   tnTxSquelchRaisedNotif  (tnV2AlarmNotificationsRel2 3215)
                   to
                   tnTxSquelchClearedNotif (tnV2AlarmNotificationsRel2 3216)."

      REVISION    "201612221200Z"
      DESCRIPTION "Added the following Hermes alarm notifications:
                   tnApsLOSyncRaisedNotif   (tnV2AlarmNotificationsRel2 3211)
                   to
                   tnAuditBlockClearedNotif (tnV2AlarmNotificationsRel2 3214)."

      REVISION    "201612151200Z"
      DESCRIPTION "Added the following alarm notifications:
                   tnRemVoltageFailRaisedNotif   (tnV2AlarmNotificationsRel2 2187)
                   to
                   tnBpskFrmtNotSuppClearedNotif (tnV2AlarmNotificationsRel2 2190)."

      REVISION    "201611161200Z"
      DESCRIPTION "Updated the contact info."

      REVISION    "201610261200Z"
      DESCRIPTION "Added the following alarm notifications:
                   tnOmsSSFCRaisedNotif     (tnV2AlarmNotificationsRel2 2167)
                   to
                   tnLossOfPLDLClearedNotif (tnV2AlarmNotificationsRel2 2186)."

      REVISION    "201610251200Z"
      DESCRIPTION "Added the following Hermes alarm notifications:
                   tnCabinAlarm1RaisedNotif (tnV2AlarmNotificationsRel2 3109)
                   to
                   tnApsBlockClearedNotif   (tnV2AlarmNotificationsRel2 3210)."

      REVISION    "201610181200Z"
      DESCRIPTION "1) Added the following alarm notifications:
                      tnLicenseViolationERRaisedNotif  (tnV2AlarmNotificationsRel2 2163)
                      to
                      tnLicenseViolationHCClearedNotif (tnV2AlarmNotificationsRel2 2166).
                   2) Changed the name of following event notification:
                      tnClusterUplinkDeletedNotif      (tnV2EventNotificationsRel2 123)
                      to
                      tnClusterDeletedNotif            (tnV2EventNotificationsRel2 123).
                   3) Added the following event notifications:
                      tnAbsNodeCreatedNotif            (tnV2EventNotificationsRel2 142)
                      to
                      tnAbsNodeModifiedNotif           (tnV2EventNotificationsRel2 144)."

      REVISION    "201610051200Z"
      DESCRIPTION "Added the following alarm notifications:
                   tnFuseFailRaisedNotif           (tnV2AlarmNotificationsRel2 2155)
                   to
                   tnFilterCloggedHighClearedNotif (tnV2AlarmNotificationsRel2 2162)."

      REVISION    "201609161200Z"
      DESCRIPTION "1) Marked the following as obsolete:
                      tnHwRevisionNotSupportedRaisedNotif  (tnV2GenericCardNotifications 35)
                      tnHwRevisionNotSupportedClearedNotif (tnV2GenericCardNotifications 36)
                   2) Added the following alarm notifications:
                      tnConfigCardMismatchRaisedNotif      (tnV2AlarmNotificationsRel2 2153)
                      tnConfigCardMismatchClearedNotif     (tnV2AlarmNotificationsRel2 2154)
                   3) Added the following event notification:
                      tnFmReadyNotif                       (tnV2EventNotificationsRel2 141)."

      REVISION    "201607211200Z"
      DESCRIPTION "1) Added the following event notifications:
                      tnPmTelemetryCounterNotif      (tnV2EventNotificationsRel2 139)
                      tnTsbFabSwitchStateChangeNotif (tnV2EventNotificationsRel2 140)
                   2) Added the following alarm notifications:
                      tnOchXcWidthNarrowRaisedNotif  (tnV2AlarmNotificationsRel2 2151),
                      tnOchXcWidthNarrowClearedNotif (tnV2AlarmNotificationsRel2 2152)."

      REVISION    "201607121200Z"
      DESCRIPTION "Added the following notifications:
                   tnFopOperationMismatchRaisedNotif       (tnV2AlarmNotificationsRel2 2107)
                   to
                   tnApsExerciseOnProtectionFeClearedNotif (tnV2AlarmNotificationsRel2 2140)."

      REVISION    "201606151200Z"
      DESCRIPTION "Added the following table:
                   tnMultipleTypeTrapTable
                   tnMultipleTypeTrapBufferTable."

      REVISION    "201605261200Z"
      DESCRIPTION "Renamed the following notifications:
                   tnCBandLossOfSignalCRaisedNotif  (tnV2AlarmNotificationsRel2 2063),
                   tnCBandLossOfSignalCClearedNotif (tnV2AlarmNotificationsRel2 2064),
                   tnCBandLossOfSignalLRaisedNotif  (tnV2AlarmNotificationsRel2 2065),
                   tnCBandLossOfSignalLClearedNotif (tnV2AlarmNotificationsRel2 2066)
                   to
                   tnBandLossOfSignalCRaisedNotif   (tnV2AlarmNotificationsRel2 2063),
                   tnBandLossOfSignalCClearedNotif  (tnV2AlarmNotificationsRel2 2064),
                   tnBandLossOfSignalLRaisedNotif   (tnV2AlarmNotificationsRel2 2065),
                   tnBandLossOfSignalLClearedNotif  (tnV2AlarmNotificationsRel2 2066)."

      REVISION    "201605251200Z"
      DESCRIPTION "Added the following notifications:
                   tnCKWKATMismatchRaisedNotif (tnV2AlarmNotificationsRel2 2099)
                   to
                   tnBdLnkSpdClearedNotif      (tnV2AlarmNotificationsRel2 2106)."

      REVISION    "201605141200Z"
      DESCRIPTION "Added the following notifications:
                   tnSyncChannelARaisedNotif     (tnV2AlarmNotificationsRel2 2093)
                   to
                   tnSyncChannelBothClearedNotif (tnV2AlarmNotificationsRel2 2098)."

      REVISION    "201605101200Z"
      DESCRIPTION "Added the following notifications:
                   tnCardFailCruRaisedNotif             (tnV2AlarmNotificationsRel2 2087)
                   to
                   tnShelfInventoryMismatchClearedNotif (tnV2AlarmNotificationsRel2 2092)."

      REVISION    "201605031200Z"
      DESCRIPTION "Added the following notifications:
                   tnAprBandRaisedNotif                    (tnV2AlarmNotificationsRel2 2141)
                   to
                   tnWavelengthTrackerFailureLClearedNotif (tnV2AlarmNotificationsRel2 2150)."

      REVISION    "201604281200Z"
      DESCRIPTION "Added the following notifications:
                   tnCardPowerOffRaisedNotif  (tnV2AlarmNotificationsRel2 2085),
                   tnCardPowerOffClearedNotif (tnV2AlarmNotificationsRel2 2086)."

      REVISION    "201604271200Z"
      DESCRIPTION "Added the following notifications:
                   tnLldpRemTablesChangeNotif (tnV2EventNotificationsRel2 138)."

      REVISION    "201604081200Z"
      DESCRIPTION "Added the following notifications:
                   tnDbCrcTypeMisRaisedNotif  (tnV2AlarmNotificationsRel2 2083),
                   tnDbCrcTypeMisClearedNotif (tnV2AlarmNotificationsRel2 2084)."

      REVISION    "201604061200Z"
      DESCRIPTION "Added the following notifications:
                   tnEcModeMismatchRaisedNotif  (tnV2AlarmNotificationsRel2 2081),
                   tnEcModeMismatchClearedNotif (tnV2AlarmNotificationsRel2 2082)."

      REVISION    "201603301200Z"
      DESCRIPTION "Added the following notifications:
                   tnIntTsiFailureRaisedNotif  (tnV2AlarmNotificationsRel2 2079),
                   tnIntTsiFailureClearedNotif (tnV2AlarmNotificationsRel2 2080).
                   tnIntTsiFailureClearedNotif (tnV2AlarmNotificationsRel2 2080)."

      REVISION    "201603181200Z"
      DESCRIPTION "Added the following notifications:
                   tnInvalidModuleRaisedNotif  (tnV2AlarmNotificationsRel2 2077),
                   tnInvalidModuleClearedNotif (tnV2AlarmNotificationsRel2 2078)."

      REVISION    "201603151200Z"
      DESCRIPTION "Added the following notifications:
                   tnEthRingStateChangeNotif     (tnV2EventNotificationsRel2 136),
                   tnEthRingPortStateChangeNotif (tnV2EventNotificationsRel2 137)."

      REVISION    "201603081200Z"
      DESCRIPTION "Added the following notifications:
                   tnIntOhFailRaisedNotif  (tnV2AlarmNotificationsRel2 2075),
                   tnIntOhFailClearedNotif (tnV2AlarmNotificationsRel2 2076)."

      REVISION    "201602171200Z"
      DESCRIPTION "Added the following notifications:
                   tnOAPumpLaserBiasCurrentHighCRaisedNotif (tnV2AlarmNotificationsRel2 2031)
                   to
                   tnPwrMaxGainLClearedNotif                (tnV2AlarmNotificationsRel2 2074)."

      REVISION    "201602151200Z"
      DESCRIPTION "Added the following notifications:
                   tnSoftwareErrorRaisedNotif  (tnV2AlarmNotificationsRel2 2029),
                   tnSoftwareErrorClearedNotif (tnV2AlarmNotificationsRel2 2030)."

      REVISION    "201602011200Z"
      DESCRIPTION "Added the following notifications:
                   tnFaceplateMissingRaisedNotif  (tnV2AlarmNotificationsRel2 2027),
                   tnFaceplateMissingClearedNotif (tnV2AlarmNotificationsRel2 2028)."

      REVISION    "201512291200Z"
      DESCRIPTION "Added the following notifications:
                   tnSC1LinkFailRaisedNotif    (tnV2AlarmNotificationsRel2 2011)
                   to
                   tnSCLinkDegradeClearedNotif (tnV2AlarmNotificationsRel2 2026)."

      REVISION    "201512221200Z"
      DESCRIPTION "Added the following notifications:
                   tnCardThermShutdownRaisedNotif  (tnV2AlarmNotificationsRel2 2009),
                   tnCardThermShutdownClearedNotif (tnV2AlarmNotificationsRel2 2010)."

      REVISION    "201512071200Z"
      DESCRIPTION "Added the following notifications:
                   tnXcMismatchRaisedNotif (tnV2AlarmNotificationsRel2 2005),
                   to
                   tnInvalidXcClearedNotif (tnV2AlarmNotificationsRel2 2008)."

      REVISION    "201511231200Z"
      DESCRIPTION "Added the following notifications:
                   tnLatchOpenRaisedNotif  (tnV2AlarmNotificationsRel2 2003),
                   tnLatchOpenClearedNotif (tnV2AlarmNotificationsRel2 2004)."

      REVISION    "201511201200Z"
      DESCRIPTION "Added the following notifications:
                   tnEcTypeMisRaisedNotif  (tnV2AlarmNotificationsRel2 2001),
                   tnEcTypeMisClearedNotif (tnV2AlarmNotificationsRel2 2002)."

      REVISION    "201511131200Z"
      DESCRIPTION "Added the following notifications:
                   tnHwrvUnknownRaisedNotif  (tnV2AlarmNotificationsRel2 1999),
                   tnHwrvUnknownClearedNotif (tnV2AlarmNotificationsRel2 2000)."

      REVISION    "201511061200Z"
      DESCRIPTION "Added the following notifications:
                   tnOCCPCRRaisedNotif                     (tnV2AlarmNotificationsRel2 1991)
                   to
                   tnShelfAirFilterMaintenanceClearedNotif (tnV2AlarmNotificationsRel2 1998)
                   tnSdpBindEndPointTxActiveChangedNotif   (tnV2EventNotificationsRel2 131)
                   to
                   tnSdpBindTraceTestCompleteNotif         (tnV2EventNotificationsRel2 135)."

      REVISION    "201510121200Z"
      DESCRIPTION "1) Removed the following alarms from notifications:
                      tnVRtrBfdSessExtDownRaisedNotif        (tnV2AlarmNotificationsRel2 1977)
                      to
                      tnVRtrBfdSessExtProtChangeClearedNotif (tnV2AlarmNotificationsRel2 1982)
                   2) Added below events to notifications:
                      tnVRtrBfdSessExtDownNotif              (tnV2EventNotificationsRel2 127)
                      to
                      tnVRtrBfdSessExtUpNotif                (tnV2EventNotificationsRel2 130)."

      REVISION    "201510091200Z"
      DESCRIPTION "Added the following notifications:
                   tnClusterUnavailRaisedNotif  (tnV2AlarmNotificationsRel2 1995)
                   tnClusterUnavailClearedNotif (tnV2AlarmNotificationsRel2 1996)
                   tnClusterAuditSuccessNotif   (tnV2EventNotificationsRel2 121)
                   to
                   tnClusterTrapFailNotif       (tnV2EventNotificationsRel2 126)."

      REVISION    "201509291200Z"
      DESCRIPTION "Added the following notifications:
                   tnNoAssociationRaisedNotif          (tnV2AlarmNotificationsRel2 1987)
                   to
                   tnB1SignalDegradeEgressClearedNotif (tnV2AlarmNotificationsRel2 1994)."

      REVISION    "201509181200Z"
      DESCRIPTION "Added the following notifications:
                   tnMplsMepLocRaisedNotif (tnV2AlarmNotificationsRel2 1967)
                   to
                   tnMplsTpLspRvrtMsmtchClearedNotif (tnV2AlarmNotificationsRel2 1986)."

      REVISION    "201509021200Z"
      DESCRIPTION "Added the following notifications:
                   tnEnvInput9ActiveRaisedNotif   (tnV2AlarmNotificationsRel2 1951)
                   to
                   tnEnvInput16ActiveClearedNotif (tnV2AlarmNotificationsRel2 1966)."

      REVISION    "201507221200Z"
      DESCRIPTION "1) Added the following notifications:
                      tnMJCPFRaisedNotif         (tnV2AlarmNotificationsRel2 1943)
                      to
                      tnSdpSpkOprDwnClearedNotif (tnV2AlarmNotificationsRel2 1950)
                   2) Added the following notifications:
                      tnSdpOprStatChgNotif       (tnV2EventNotificationsRel2 102)
                      to
                      tnSdpBindOprStateChgNotif  (tnV2EventNotificationsRel2 120)"

      REVISION    "201506291200Z"
      DESCRIPTION "Added the following notifications:
                   tnMplsTpLspPingTestCompleteNotif  (tnV2EventNotificationsRel2 100)
                   tnMplsTpLspTraceTestCompleteNotif (tnV2EventNotificationsRel2 101)."

      REVISION    "201506241200Z"
      DESCRIPTION "Added the following notifications:
                   tnFrequencySlotMismatchRaisedNotif  (tnV2AlarmNotificationsRel2 1941)
                   tnFrequencySlotMismatchClearedNotif (tnV2AlarmNotificationsRel2 1942)."

      REVISION    "201505211200Z"
      DESCRIPTION "1) Marked the following as obsolete:
                      tnUruOtuRaisedNotif              (tnV2AlarmNotificationsRel2 681)
                      tnUruOtuClearedNotif             (tnV2AlarmNotificationsRel2 682).
                   2) Added the following notifications:
                      tnHiRamanGainRaisedNotif         (tnV2AlarmNotificationsRel2 1931)
                      to
                      tnMplsLspDownClearedNotif        (tnV2AlarmNotificationsRel2 1940)
                      tnmplsIfStateChangeNotif         (tnV2EventNotificationsRel2 96)
                      to
                      tnmplsTpLspActivePathChangeNotif (tnV2EventNotificationsRel2 99)."

      REVISION    "201504271200Z"
      DESCRIPTION "Added the following notifications:
                   tnIntfcOprDwnRaisedNotif  (tnV2AlarmNotificationsRel2 1929)
                   tnIntfcOprDwnClearedNotif (tnV2AlarmNotificationsRel2 1930)."

      REVISION    "201502131200Z"
      DESCRIPTION "Added the following notifications:
                   tnSapPortStateChangeProcessedNotif
                   tnSapTlsMacMoveExceededNotif."

      REVISION    "201412121200Z"
      DESCRIPTION "Added the following notifications:
                   tnGfpExmRaisedNotif     (tnV2AlarmNotificationsRel2 1925)
                   to
                   tnSyncMisc1ClearedNotif (tnV2AlarmNotificationsRel2 1928)."

      REVISION    "201410311200Z"
      DESCRIPTION "Added the following notifications:
                   tnVwmIDFailRaisedNotif  (tnV2AlarmNotificationsRel2 1923)
                   tnVwmIDFailClearedNotif (tnV2AlarmNotificationsRel2 1924)."

      REVISION    "201409241200Z"
      DESCRIPTION "Added the following notifications:
                   tnSDKMismatchRaisedNotif             (tnV2AlarmNotificationsRel2 1907)
                   to
                   tnRestrictedConnectivityClearedNotif (tnV2AlarmNotificationsRel2 1922)."

      REVISION    "201408291200Z"
      DESCRIPTION "Added the following notifications:
                   tnLagPortAddSuccessNotif     (tnV2EventNotificationsRel2 93).
                   tnFTDEncrypt15MinRaisedNotif (tnV2AlarmNotificationsRel2 1903)
                   to
                   tnFTDEncrypt1DayClearedNotif (tnV2AlarmNotificationsRel2 1906)."

      REVISION    "201408211200Z"
      DESCRIPTION "Added the following notifications:
                   tnHwAccessFailureRaisedNotif  (tnV2AlarmNotificationsRel2 1901)
                   tnHwAccessFailureClearedNotif (tnV2AlarmNotificationsRel2 1902)."

      REVISION    "201408141200Z"
      DESCRIPTION "Added the following notifications:
                   tnOpticalTestRaisedNotif  (tnV2AlarmNotificationsRel2 1899)
                   tnOpticalTestClearedNotif (tnV2AlarmNotificationsRel2 1900)."

      REVISION    "201406161200Z"
      DESCRIPTION "Added the following notifications:
                   tnConfigMMRaisedNotif  (tnV2AlarmNotificationsRel2 1897)
                   tnConfigMMClearedNotif (tnV2AlarmNotificationsRel2 1898)."

      REVISION    "201406061200Z"
      DESCRIPTION "Added the following notification:
                   tnSecurityEncryptActionRejectNotif (tnV2SecurityNotifications 34)."

      REVISION    "201404161200Z"
      DESCRIPTION "Added the following notifications:
                   tnSpiReadErrorRaisedNotif (tnV2AlarmNotificationsRel2 1893)
                   to
                   tnShelfInconClearedNotif  (tnV2AlarmNotificationsRel2 1896)."

      REVISION    "201404151200Z"
      DESCRIPTION "Added the following notifications:
                   tnAPRFORCEDRaisedNotif  (tnV2AlarmNotificationsRel2 1891)
                   to
                   tnAPRFORCEDClearedNotif (tnV2AlarmNotificationsRel2 1892)."

      REVISION    "201403201200Z"
      DESCRIPTION "Added the following notifications:
                   tnInsertModNotif   (tnV2EventNotificationsRel2 88)
                   to
                   tnDiscoverModNotif (tnV2EventNotificationsRel2 92)."

      REVISION    "201403191200Z"
      DESCRIPTION "Added the following notifications:
                   tnFRCRFCKSELRaisedNotif  (tnV2AlarmNotificationsRel2 1885)
                   to
                   tnAPRLIMITEDClearedNotif (tnV2AlarmNotificationsRel2 1890)."

      REVISION    "201402281200Z"
      DESCRIPTION "Added the following notifications:
                   tnPacketCardInitRaisedNotif  (tnV2AlarmNotificationsRel2 1883)
                   to
                   tnPacketCardInitClearedNotif (tnV2AlarmNotificationsRel2 1884)."

      REVISION    "201402261200Z"
      DESCRIPTION "Added description for generalObjectId(32)."

      REVISION    "201401301200Z"
      DESCRIPTION "Added the following notifications:
                   tnLagStateChangeNotif           (tnV2EventNotificationsRel2 86)
                   tnLagMemberPortStateChangeNotif (tnV2EventNotificationsRel2 87)."

      REVISION    "201401241200Z"
      DESCRIPTION "Added the following notifications:
                   tnFwMismatchRaisedNotif   (tnV2AlarmNotificationsRel2 1857)
                   to
                   tnFPGAFAILNSAClearedNotif (tnV2AlarmNotificationsRel2 1882)."

      REVISION    "201401161200Z"
      DESCRIPTION "Added the following notifications:
                   tnCardClkOffFreqRaisedNotif     (tnV2AlarmNotificationsRel2 1853)
                   to
                   tnShelfInVoltMaxCurClearedNotif (tnV2AlarmNotificationsRel2 1856)."

      REVISION    "201401131200Z"
      DESCRIPTION "Added the following notifications:
                   tnBadClkFreqRaisedNotif         (tnV2AlarmNotificationsRel2 1801)
                   to
                   tnEsCableMismatch24ClearedNotif (tnV2AlarmNotificationsRel2 1852)."

      REVISION    "201312061200Z"
      DESCRIPTION "Added the following notifications:
                   tnTOprhLane1RaisedNotif     (tnV2AlarmNotificationsRel2 1719)
                   to
                   tnImageNotReadyClearedNotif (tnV2AlarmNotificationsRel2 1800)."

      REVISION    "201312051200Z"
      DESCRIPTION "Added the following notifications:
                   tnRmdTypeMismatchNotif (tnV2EventNotificationsRel2 82)
                   to
                   tnRmdJbRecenteredNotif (tnV2EventNotificationsRel2 85)."

      REVISION    "201311221200Z"
      DESCRIPTION "Added the following notifications:
                   tnTCMAisRaisedNotif  (tnV2AlarmNotificationsRel2 1717)
                   to
                   tnTCMAisClearedNotif (tnV2AlarmNotificationsRel2 1718)."

      REVISION    "201311161200Z"
      DESCRIPTION "Added the following notification:
                   tnRmdDiscoveredDeviceNotif (tnV2EventNotificationsRel2 81)."

      REVISION    "201311061200Z"
      DESCRIPTION "Added the following notifications:
                   tnRmdNimLOFRaisedNotif  (tnV2AlarmNotificationsRel2 1711)
                   to
                   tnPwrSuspRxClearedNotif (tnV2AlarmNotificationsRel2 1716)."

      REVISION    "201309241200Z"
      DESCRIPTION "Added the following notifications:
                   tnTUasOdu15MinOutRaisedNotif   (tnV2AlarmNotificationsRel2 1671)
                   to
                   tnRmdCesChannelRPLClearedNotif (tnV2AlarmNotificationsRel2 1710)."

      REVISION    "201309131200Z"
      DESCRIPTION "1) Added the following notifications:
                      tnTPmonDmanfd15MinRaisedNotif         (tnV2AlarmNotificationsRel2 1607)
                      to
                      tnTPmonSlmafflrContinuousClearedNotif (tnV2AlarmNotificationsRel2 1670).
                   2) Added the following notification:
                      tnSRTCANotif (tnV2EventNotificationsRel2 80)."

      REVISION    "201309101200Z"
      DESCRIPTION "1) Added the following notifications:
                      tnLspFailedApeRaisedNotif (tnV2AlarmNotificationsRel2 1543)
                      to
                      tnSsfOduTpClearedNotif    (tnV2AlarmNotificationsRel2 1610).
                   2) Added the following notifications:
                      tnGmreLspCreationNotif (tnV2EventNotificationsRel2 66)
                      to
                      tnGmreLmpDeletionNotif (tnV2EventNotificationsRel2 79)."

      REVISION    "201309051200Z"
      DESCRIPTION "Added the following to the 'Breakdown of MIB attributes'
                   section (descriptions):
                   SR_OamSaaCtl = 72
                   OamSaaCtl - test name."

      REVISION    "201308021200Z"
      DESCRIPTION "Added the following notifications:
                   tnCfmLmTestCompleteRaisedNotif (tnV2AlarmNotificationsRel2 1537)
                   to
                   tnCbr10G3RxLSSClearedNotif     (tnV2AlarmNotificationsRel2 1542)."

      REVISION    "201306241200Z"
      DESCRIPTION "Updated bit mask of objectIdType of tnTrapObjectIDType
                   from 0x0000FFFF to 0x0000003F."

      REVISION    "201306191200Z"
      DESCRIPTION "Added the following notifications:
                   tnTPmonSapIngressPktsDropped15MinRaisedNotif (tnV2AlarmNotificationsRel2 1393)
                   to
                   tnTPmonDmxfFdv1DayClearedNotif               (tnV2AlarmNotificationsRel2 1536)."

      REVISION    "201306151200Z"
      DESCRIPTION "Added details for srObjectId."

      REVISION    "201305241200Z"
      DESCRIPTION "Added the following notification:
                   tnDot1agCfmLmTestCompleteNotif (tnV2EventNotificationsRel2 65)"

      REVISION    "201305211200Z"
      DESCRIPTION "Added the following notifications:
                   tnLOSOAMPRaisedNotif  (tnV2AlarmNotificationsRel2 1391)
                   tnLOSOAMPClearedNotif (tnV2AlarmNotificationsRel2 1392)."

      REVISION    "201305171200Z"
      DESCRIPTION "Added the following notifications:
                   tnFAN32HRQDRaisedNotif  (tnV2AlarmNotificationsRel2 1389)
                   tnFAN32HRQDClearedNotif (tnV2AlarmNotificationsRel2 1390)."

      REVISION    "201305141200Z"
      DESCRIPTION "Added the following notifications:
                   tnOchKeyUnavailRaisedNotif  (tnV2AlarmNotificationsRel2 1383)
                   to
                   tnOchKeysReusedClearedNotif (tnV2AlarmNotificationsRel2 1388)."

      REVISION    "201305071200Z"
      DESCRIPTION "Marked the following as obsolete:
                   tnPTPGMDegradeRaisedNotif   (tnV2AlarmNotificationsRel2 1277)
                   to
                   tnPTPPortSwitchClearedNotif (tnV2AlarmNotificationsRel2 1284)."

      REVISION    "201304261200Z"
      DESCRIPTION "Added the following notifications:
                   tnGfpLofRaisedNotif  (tnV2AlarmNotificationsRel2 1381)
                   tnGfpLofClearedNotif (tnV2AlarmNotificationsRel2 1382)."

      REVISION    "201304241200Z"
      DESCRIPTION "Added the following notifications:
                   tnSecurityChangeUiModeNotif       (tnV2SecurityNotifications 30)
                   tnSecurityChangeEncryptStateNotif (tnV2SecurityNotifications 33)."

      REVISION    "201304091200Z"
      DESCRIPTION "Added the following notifications:
                   tnTODRefUnstableRaisedNotif  (tnV2AlarmNotificationsRel2 1375)
                   tnTODRefUnstableClearedNotif (tnV2AlarmNotificationsRel2 1376)."

      REVISION    "201303291200Z"
      DESCRIPTION "1) Marked the following as obsolete:
                      tnFIPSSFMISMATCHRaisedNotif  (tnV2AlarmNotificationsRel2 1295)
                      tnFIPSSFMISMATCHClearedNotif (tnV2AlarmNotificationsRel2 1296).
                   2) Added the following notifications:
                      tnFipsSwMismatchRaisedNotif  (tnV2AlarmNotificationsRel2 1373)
                      tnFipsSwMismatchClearedNotif (tnV2AlarmNotificationsRel2 1374).
                   3) Added information to description of rmdObjectId."

      REVISION    "201303211200Z"
      DESCRIPTION "Added the following notifications:
                   tnOSNRMESCRaisedNotif        (tnV2AlarmNotificationsRel2 1371)
                   tnOSNRMESCClearedNotif       (tnV2AlarmNotificationsRel2 1372)
                   tnFipsFailureRaisedNotif     (tnV2AlarmNotificationsRel2 1377)
                   to
                   tnAesFipsFailureClearedNotif (tnV2AlarmNotificationsRel2 1380)."

      REVISION    "201303141200Z"
      DESCRIPTION "Added the following notifications:
                   tnTRUSVCVOLTFLTRaisedNotif (tnV2AlarmNotificationsRel2 1367)
                   to
                   tnTRUBRKROPENClearedNotif  (tnV2AlarmNotificationsRel2 1370)."

      REVISION    "201303061200Z"
      DESCRIPTION "Added the following notifications:
                   tnTFecUbc15MinRaisedNotif (tnV2AlarmNotificationsRel2 1363)
                   to
                   tnTFecUbc1DayClearedNotif (tnV2AlarmNotificationsRel2 1366)."

      REVISION    "201303011200Z"
      DESCRIPTION "Added the following notifications:
                   tnSsfSectionOutRaisedNotif  (tnV2AlarmNotificationsRel2 1361)
                   tnSsfSectionOutClearedNotif (tnV2AlarmNotificationsRel2 1362)."

      REVISION    "201302261200Z"
      DESCRIPTION "1) Added the following notifications:
                      tnLockedIndicationEgressRaisedNotif (tnV2AlarmNotificationsRel2 1343)
                      to
                      tnGfpUpmClearedNotif                (tnV2AlarmNotificationsRel2 1360).
                   2) Marked the following as obsolete:
                      tnLockedIndicationEgressNotif    (tnV2EventNotificationsRel2 21)
                      to
                      tnServerSignalFailureEgressNotif (tnV2EventNotificationsRel2 27)."

      REVISION    "201302221200Z"
      DESCRIPTION "Added the following notifications:
                   tnRmdIfEFMLOPRaisedNotif  (tnV2AlarmNotificationsRel2 1329)
                   to
                   tnFPGAPRELOADClearedNotif (tnV2AlarmNotificationsRel2 1342)
                   tnAutoSyncSwNotif         (tnV2EventNotificationsRel2 63)
                   tnAutoSyncSwT4Notif       (tnV2EventNotificationsRel2 64)."

      REVISION    "201302211200Z"
      DESCRIPTION "Added the following notifications:
                   tnSLCCARDINITRaisedNotif (tnV2AlarmNotificationsRel2 1313)
                   to
                   tnSLCCLKSYNCClearedNotif (tnV2AlarmNotificationsRel2 1328)."

      REVISION    "201302201200Z"
      DESCRIPTION "1) Added the following notifications:
                      tnNtpChkSigNotif     (tnV2EventNotificationsRel2 59)
                      to
                      tnPTPPathSwitchNotif (tnV2EventNotificationsRel2 62).
                   2) Updated DESCRIPTIONs of the following:
                      tnTrapObjectIDType
                      tnTrapObjectID."

      REVISION    "201302141200Z"
      DESCRIPTION "Added the following notifications:
                   tnFIPSSFMISMATCHRaisedNotif (tnV2AlarmNotificationsRel2 1295)
                   to
                   tnRmdMepRDIClearedNotif     (tnV2AlarmNotificationsRel2 1312)."

      REVISION    "201302111200Z"
      DESCRIPTION "Added the following notifications:
                   tnLosPRaisedNotif  (tnV2AlarmNotificationsRel2 1293)
                   to
                   tnLosPClearedNotif (tnV2AlarmNotificationsRel2 1294)."

      REVISION    "201301261200Z"
      DESCRIPTION "Added the following notifications:
                   tnRmdNDFRaisedNotif  (tnV2AlarmNotificationsRel2 1285)
                   to
                   tnRmdEQFClearedNotif (tnV2AlarmNotificationsRel2 1292)."

      REVISION    "201301201200Z"
      DESCRIPTION "1) Updated the 'Breakdown of MIB attributes
                      tnTrapObjectID/tnTrapObjectIDType' section.
                   2) Marked 121 unsupported traps as obsolete."

      REVISION    "201212181200Z"
      DESCRIPTION "Added the following notifications:
                   tnCsfGfpOutRaisedNotif      (tnV2AlarmNotificationsRel2 1259)
                   to
                   tnPTPPortSwitchClearedNotif (tnV2AlarmNotificationsRel2 1284)."

      REVISION    "201211261200Z"
      DESCRIPTION "Added the following notifications:
                   tnCPUPERFORMANCERaisedNotif (tnV2AlarmNotificationsRel2 1255)
                   to
                   tnContEqptSplitClearedNotif (tnV2AlarmNotificationsRel2 1258)."

      REVISION    "201210221200Z"
      DESCRIPTION "Added the following notifications:
                   tnOduAisOutRaisedNotif    (tnV2AlarmNotificationsRel2 1249)
                   to
                   tnLOFLOMOututClearedNotif (tnV2AlarmNotificationsRel2 1254)."

      REVISION    "201210021200Z"
      DESCRIPTION "Added the following notifications:
                   tnLOSEDFARaisedNotif  (tnV2AlarmNotificationsRel2 1247)
                   tnLOSEDFAClearedNotif (tnV2AlarmNotificationsRel2 1248)."

      REVISION    "201209271200Z"
      DESCRIPTION "Added the following notifications:
                   tnCardInitBcmRaisedNotif     (tnV2AlarmNotificationsRel2 1243)
                   to
                   tnCardInitNonBcmClearedNotif (tnV2AlarmNotificationsRel2 1246)."

      REVISION    "201209201200Z"
      DESCRIPTION "Added the following notifications:
                   tnBITSLosRaisedNotif            (tnV2AlarmNotificationsRel2 1223)
                   to
                   tnLockoutOfTimRefT4ClearedNotif (tnV2AlarmNotificationsRel2 1242)."

      REVISION    "201209071200Z"
      DESCRIPTION "Added the following notifications:
                   tnPwrEdfaMarginRaisedNotif  (tnV2AlarmNotificationsRel2 1221)
                   to
                   tnPwrEdfaMarginClearedNotif (tnV2AlarmNotificationsRel2 1222)."

      REVISION    "201209051200Z"
      DESCRIPTION "1) Added the following notifications:
                      tnMirrorDestEnableRaisedNotif   (tnV2AlarmNotificationsRel2 1215)
                      to
                      tnDCConfigFailClearedNotif      (tnV2AlarmNotificationsRel2 1220).
                   2) Added the following notifications:
                      tnMirrorDestinationEnabledNotif (tnV2EventNotificationsRel2 56)
                      to
                      tnDCConfigFailNotif             (tnV2EventNotificationsRel2 58)."

      REVISION    "201208281200Z"
      DESCRIPTION "Added the following notifications:
                   tnWtocmaOsnrOomrRaisedNotif  (tnV2AlarmNotificationsRel2 1203)
                   to
                   tnShelfInVoltLowClearedNotif (tnV2AlarmNotificationsRel2 1214)."

      REVISION    "201208091200Z"
      DESCRIPTION "Added the following notifications:
                   tnOTMCPFRaisedNotif  (tnV2AlarmNotificationsRel2 1201)
                   to
                   tnOTMCPFClearedNotif (tnV2AlarmNotificationsRel2 1202)."

      REVISION    "201208061200Z"
      DESCRIPTION "Added the following notifications:
                   tnLolRaisedNotif               (tnV2AlarmNotificationsRel2 1169)
                   to
                   tnMirrorSrcDisableClearedNotif (tnV2AlarmNotificationsRel2 1200)."

      REVISION    "201207181200Z"
      DESCRIPTION "Added the following notifications:
                   tnEthRingPathFwdStateChangeNotif (tnV2EventNotificationsRel2 40)
                   to
                   tnMirrorSourceDisabledNotif      (tnV2EventNotificationsRel2 55)."

      REVISION    "201205251200Z"
      DESCRIPTION "Added the following notifications:
                   tnESMRaisedNotif        (tnV2AlarmNotificationsRel2 1123)
                   to
                   tnTimOduOutClearedNotif (tnV2AlarmNotificationsRel2 1136)."

      REVISION    "201205241200Z"
      DESCRIPTION "Added the following notifications:
                   tnLagLosRaisedNotif               (tnV2AlarmNotificationsRel2 1069)
                   to
                   tnLinkoamLoopDetectedClearedNotif (tnV2AlarmNotificationsRel2 1122)."

      REVISION    "201203191200Z"
      DESCRIPTION "Added the following notification:
                   tnDataErrNotif (tnV2EventNotificationsRel2 39)."

      REVISION    "201202281200Z"
      DESCRIPTION "Added the following notifications:
                   tnCSFODUEGRRaisedNotif  (tnV2AlarmNotificationsRel2 1067)
                   to
                   tnCSFODUEGRClearedNotif (tnV2AlarmNotificationsRel2 1068)."

      REVISION    "201202211200Z"
      DESCRIPTION "Added the following notifications:
                   tnAlienEgrLOSRaisedNotif (tnV2AlarmNotificationsRel2 1061)
                   to
                   tnFDICLTClearedNotif     (tnV2AlarmNotificationsRel2 1066)."

      REVISION    "201201121200Z"
      DESCRIPTION "Added the following notifications:
                   tnEgressSSFRaisedNotif (tnV2AlarmNotificationsRel2 1057)
                   to
                   tnOmsSSFClearedNotif   (tnV2AlarmNotificationsRel2 1060)."

      REVISION    "201112141200Z"
      DESCRIPTION "Added the following notifications:
                   tnPwrTiltParamsRaisedNotif  (tnV2AlarmNotificationsRel2 1055)
                   tnPwrTiltParamsClearedNotif (tnV2AlarmNotificationsRel2 1056)."

      REVISION    "201112121200Z"
      DESCRIPTION "Added the following notifications:
                   tnSsfCltEgrRaisedNotif  (tnV2AlarmNotificationsRel2 1053)
                   tnSsfCltEgrClearedNotif (tnV2AlarmNotificationsRel2 1054)."

      REVISION    "201111281200Z"
      DESCRIPTION "Added the following notifications:
                   tnOcsAuditSuccessNotif (tnV2EventNotificationsRel2 34)
                   to
                   tnOcsDataFltNotif      (tnV2EventNotificationsRel2 38).
                   tnSyncEqptRaisedNotif  (tnV2AlarmNotificationsRel2 1047)
                   to
                   tnUruOmsTxClearedNotif (tnV2AlarmNotificationsRel2 1052)."

      REVISION    "201111161200Z"
      DESCRIPTION "Added the following notifications:
                   tnOcsUnavailRaisedNotif (tnV2AlarmNotificationsRel2 1041)
                   to
                   tnNKMClearedNotif       (tnV2AlarmNotificationsRel2 1046)."

      REVISION    "201110241200Z"
      DESCRIPTION "Added the following notifications:
                   tnNEModeMismatchRaisedNotif  (tnV2ControlCardNotifications 23)
                   tnNEModeMismatchClearedNotif (tnV2ControlCardNotifications 24)."

      REVISION    "201110031200Z"
      DESCRIPTION "Added the following notifications:
                   tnSwColdResetRequestNotif (tnV2EventNotificationsRel2 31)
                   to
                   tnFmRa2pGainFailureNotif  (tnV2EventNotificationsRel2 33)."

      REVISION    "201109201200Z"
      DESCRIPTION "Added the following notifications:
                   tnPrcdrErrTopoOutRaisedNotif (tnV2AlarmNotificationsRel2 1031)
                   to
                   tnPWRADJREQDRPClearedNotif   (tnV2AlarmNotificationsRel2 1040)."

      REVISION    "201108311200Z"
      DESCRIPTION "Added the following notifications:
                   tnLotOutRaisedNotif  (tnV2AlarmNotificationsRel2 1029)
                   tnLotOutClearedNotif (tnV2AlarmNotificationsRel2 1030)."

      REVISION    "201108031200Z"
      DESCRIPTION "Added the following notifications:
                   tnCardBootRaisedNotif  (tnV2AlarmNotificationsRel2 1027)
                   tnCardBootClearedNotif (tnV2AlarmNotificationsRel2 1028)."

      REVISION    "201107021200Z"
      DESCRIPTION "Added the following notifications:
                   tnLanSfRaisedNotif  (tnV2AlarmNotificationsRel2 1025)
                   tnLanSfClearedNotif (tnV2AlarmNotificationsRel2 1026)."

      REVISION    "201105251200Z"
      DESCRIPTION "Added the following notifications:
                   tnPwrAdjCommsRaisedNotif  (tnV2AlarmNotificationsRel2 1023)
                   tnPwrAdjCommsClearedNotif (tnV2AlarmNotificationsRel2 1024)."

      REVISION    "201105111200Z"
      DESCRIPTION "Added the following notifications:
                   tnESCLATCHFAILRaisedNotif  (tnV2AlarmNotificationsRel2 1021)
                   tnESCLATCHFAILClearedNotif (tnV2AlarmNotificationsRel2 1022)."

      REVISION    "201105021200Z"
      DESCRIPTION "Added the following notifications:
                   tnTcmServerSignalFailureRaisedNotif (tnV2AlarmNotificationsRel2 835)
                   to
                   tnTFeUasTcm1DayClearedNotif         (tnV2AlarmNotificationsRel2 890)."

      REVISION    "201104141200Z"
      DESCRIPTION "Added the following notifications:
                   tnMepLocRaisedNotif    (tnV2AlarmNotificationsRel2 1007)
                   to
                   tnAsonTopoClearedNotif (tnV2AlarmNotificationsRel2 1020)."

      REVISION    "201104041200Z"
      DESCRIPTION "Added the following notifications:
                   tnInventoryErrorRaisedNotif  (tnV2AlarmNotificationsRel2 1005)
                   tnInventoryErrorClearedNotif (tnV2AlarmNotificationsRel2 1006)."

      REVISION    "201104031200Z"
      DESCRIPTION "Added the following notification:
                   tnNTPClkAdjNotif (tnV2EventNotificationsRel2 30)."

      REVISION    "201103301200Z"
      DESCRIPTION "Added the following notifications:
                   tnNtpLorRaisedNotif  (tnV2AlarmNotificationsRel2 1003)
                   tnNtpLorClearedNotif (tnV2AlarmNotificationsRel2 1004)."

      REVISION    "201103281200Z"
      DESCRIPTION "Added the following notifications:
                   tnTransferLogFLRaisedNotif  (tnV2AlarmNotificationsRel2 995)
                   to
                   tnTransferLogIPClearedNotif (tnV2AlarmNotificationsRel2 1000)."

      REVISION    "201103251200Z"
      DESCRIPTION "Updated description of tnTrapObjectID and
                   tnTrapObjectIDType."

      REVISION    "201103081200Z"
      DESCRIPTION "Added the following notifications:
                   tnAutoSyncSwRaisedNotif  (tnV2AlarmNotificationsRel2 1001)
                   tnAutoSyncSwClearedNotif (tnV2AlarmNotificationsRel2 1002)."

      REVISION    "201102221200Z"
      DESCRIPTION "Added the following notifications:
                   tnAuAisPRaisedNotif  (tnV2AlarmNotificationsRel2 985)
                   to
                   tnHpRdiPClearedNotif (tnV2AlarmNotificationsRel2 994)."

      REVISION    "201102061200Z"
      DESCRIPTION "Added the following notifications:
                   tnOptIntBaseRaisedNotif  (tnV2AlarmNotificationsRel2 983)
                   tnOptIntBaseClearedNotif (tnV2AlarmNotificationsRel2 984)."

      REVISION    "201102041200Z"
      DESCRIPTION "Added the following notifications:
                   tnLOFLOMRaisedNotif  (tnV2AlarmNotificationsRel2 981)
                   tnLOFLOMClearedNotif (tnV2AlarmNotificationsRel2 982)."

      REVISION    "201101211200Z"
      DESCRIPTION "Added the following notification:
                   tnOdukXcCreationNotif (tnV2EventNotificationsRel2 29)."

      REVISION    "201101181200Z"
      DESCRIPTION "Added the following notification:
                   tnSecurityOptIntrusionNotif (tnV2SecurityNotifications 29)."

      REVISION    "201101161200Z"
      DESCRIPTION "Added the following notifications:
                   tnFDIRaisedNotif              (tnV2AlarmNotificationsRel2 969)
                   to
                   tnTBerPostFec1DayClearedNotif (tnV2AlarmNotificationsRel2 980)."

      REVISION    "201012091200Z"
      DESCRIPTION "Added the following notifications:
                   tnPCSGeneratorRaisedNotif (tnV2AlarmNotificationsRel2 965)
                   to
                   tnOSPFADJClearedNotif     (tnV2AlarmNotificationsRel2 968)."

      REVISION    "201011301200Z"
      DESCRIPTION "Added the following notifications:
                   tnManSwToIntRaisedNotif   (tnV2AlarmNotificationsRel2 949)
                   to
                   tnSyncRefUnEqClearedNotif (tnV2AlarmNotificationsRel2 964)."

      REVISION    "201011161200Z"
      DESCRIPTION "Added the following notifications:
                   tnIntrusionRaisedNotif  (tnV2AlarmNotificationsRel2 947)
                   tnIntrusionClearedNotif (tnV2AlarmNotificationsRel2 948)."

      REVISION    "201011091200Z"
      DESCRIPTION "1) Marked the following as obsolete:
                      tnUruOtsRaisedNotif     (tnV2AlarmNotificationsRel2 679)
                      tnUruOtsClearedNotif    (tnV2AlarmNotificationsRel2 680)
                      tnUruOmsRaisedNotif     (tnV2AlarmNotificationsRel2 893)
                      tnUruOmsClearedNotif    (tnV2AlarmNotificationsRel2 894).
                   2) Added the following notifications:
                      tnOptIntDetRaisedNotif  (tnV2AlarmNotificationsRel2 933)
                      to
                      tnUruOchLosClearedNotif (tnV2AlarmNotificationsRel2 946)."

      REVISION    "201010161200Z"
      DESCRIPTION "Added the following notifications:
                   tnUruOmsRaisedNotif     (tnV2AlarmNotificationsRel2 893)
                   to
                   tnAprSwitchClearedNotif (tnV2AlarmNotificationsRel2 932)."

      REVISION    "201009161200Z"
      DESCRIPTION "Added the following notifications:
                   tnFrngSyncRaisedNotif (tnV2AlarmNotificationsRel2 827)
                   to
                   tnWtrClearedNotif     (tnV2AlarmNotificationsRel2 834)."

      REVISION    "201009031200Z"
      DESCRIPTION "Added the following notifications:
                   tnLoamRaisedNotif  (tnV2AlarmNotificationsRel2 805)
                   tnLoamClearedNotif (tnV2AlarmNotificationsRel2 806)."

      REVISION    "201008291200Z"
      DESCRIPTION "Added the following notifications:
                   tnLosOtsRaisedNotif        (tnV2AlarmNotificationsRel2 807)
                   to
                   tnOduAisEgressClearedNotif (tnV2AlarmNotificationsRel2 826)."

      REVISION    "201007291200Z"
      DESCRIPTION "1) Renamed tnPostFecSdRaisedNotif to tnFecUbcSdRaisedNotif
                      and tnPostFecSdClearedNotif to tnFecUbcSdClearedNotif.
                   2) Added the following notifications:
                      tnEberoRaisedNotif (tnV2AlarmNotificationsRel2 751)
                      to
                      tnMsimClearedNotif (tnV2AlarmNotificationsRel2 804)."

      REVISION    "201007151200Z"
      DESCRIPTION "Added the following notifications:
                   tnPwrTiltSuspRaisedNotif  (tnV2AlarmNotificationsRel2 749)
                   tnPwrTiltSuspClearedNotif (tnV2AlarmNotificationsRel2 750)."

      REVISION    "201007121200Z"
      DESCRIPTION "Added the following notifications:
                   tnUruSRaisedNotif  (tnV2AlarmNotificationsRel2 747)
                   tnUruSClearedNotif (tnV2AlarmNotificationsRel2 748)."

      REVISION    "201007071200Z"
      DESCRIPTION "Added the following notifications:
                   tnExcessLossRaisedNotif (tnV2AlarmNotificationsRel2 741)
                   to
                   tnPostFecSdClearedNotif (tnV2AlarmNotificationsRel2 746)."

      REVISION    "201006041200Z"
      DESCRIPTION "1) Marked the following conditions as obsolete:
                      tnLosPldRaisedNotif        (tnV2AlarmNotificationsRel2 685)
                      tnLosPldClearedNotif       (tnV2AlarmNotificationsRel2 686).
                   2) Added the following notifications:
                      tnAprUnavailOscRaisedNotif (tnV2AlarmNotificationsRel2 699)
                      to
                      tnTUasPt15MinClearedNotif  (tnV2AlarmNotificationsRel2 732)
                      tnE1LosRaisedNotif         (tnV2AlarmNotificationsE1 1)
                      to
                      tnE1RaiEgrClearedNotif     (tnV2AlarmNotificationsE1 18)."

      REVISION    "201006021200Z"
      DESCRIPTION "Added the following notifications:
                   tnBoardEqptRaisedNotif
                   tnBoardEqptClearedNotif"

      REVISION    "201005271200Z"
      DESCRIPTION "Added the following notifications:
                   tnEqptDgrOchRaisedNotif   (tnV2AlarmNotificationsRel2 643)
                   to
                   tnIncompatFanClearedNotif (tnV2AlarmNotificationsRel2 696)."

      REVISION    "201005181200Z"
      DESCRIPTION "1) Renamed the R3.0 PM trap names for 15 minute bins by
                      adding <15Min> to the original names.  For example:
                      tnTBbeOtuRaisedNotif  --> tnTBbeOtu15MinRaisedNotif
                      tnTBbeOtuClearedNotif --> tnTBbeOtu15MinClearedNotif
                   2) Added R3.0 PM trap names for 1 day bins by adding
                      <1Day> to the original names.  For example:
                      tnTBbeOtuRaisedNotif  --> tnTBbeOtu1DayRaisedNotif
                      tnTBbeOtuClearedNotif --> tnTBbeOtu1DayClearedNotif"

      REVISION    "201005101200Z"
      DESCRIPTION "Added the following notifications:
                   tnTBbeOtuRaisedNotif  (tnV2AlarmNotificationsRel2 467)
                   to
                   tnTUasRstClearedNotif (tnV2AlarmNotificationsRel2 554)."

      REVISION    "201003031200Z"
      DESCRIPTION "Added the following notifications:
                   tnMixedPFUsedRaisedNotif  (tnV2AlarmNotificationsRel2 465)
                   tnMixedPFUsedClearedNotif (tnV2AlarmNotificationsRel2 466)"

      REVISION    "201002251200Z"
      DESCRIPTION "Added the following notifications:
                   tnDegOtuRaisedNotif  (tnV2AlarmNotificationsRel2 463)
                   tnDegOtuClearedNotif (tnV2AlarmNotificationsRel2 464)."

      REVISION    "201002161200Z"
      DESCRIPTION "Added the following notifications:
                   tnFanSpeedManuallySetMaximumRaisedNotif  (tnV2AlarmNotificationsRel2 461)
                   tnFanSpeedManuallySetMaximumClearedNotif (tnV2AlarmNotificationsRel2 462)."

      REVISION    "201002081200Z"
      DESCRIPTION "1) Renamed
                      tnFECECSignalDegradeRaisedNotif
                      tnFECECSignalDegradeClearedNotif
                      to
                      tnFecEcSignalDegradeRaisedNotif
                      tnFecEcSignalDegradeClearedNotif
                   2) Added the following notifications:
                      tnCardNotAllowedRaisedNotif  (tnV2AlarmNotificationsRel2 459)
                      tnCardNotAllowedClearedNotif (tnV2AlarmNotificationsRel2 460)."

      REVISION    "201002011200Z"
      DESCRIPTION "Added the following notifications:
                   tnRcvrOptProgRaisedNotif  (tnV2AlarmNotificationsRel2 457)
                   tnRcvrOptProgClearedNotif (tnV2AlarmNotificationsRel2 458)."

      REVISION    "201001151200Z"
      DESCRIPTION "1) Replaced
                      tnLaserOutputPowerOutOfRangeRaisedNotif
                      tnLaserOutputPowerOutOfRangeClearedNotif
                      with
                      tnLaserEndOfLifeRaisedNotif
                      tnLaserEndOfLifeClearedNotif
                   2) Renamed
                      tnSfpOrXfpLaserTemperatureOutOfRangeRaisedNotif
                      tnSfpOrXfpLaserTemperatureOutOfRangeClearedNotif
                      tnSfpOrXfpLaserEndOfLifeRaisedNotif
                      tnSfpOrXfpLaserEndOfLifeClearedNotif
                      tnSfpOrXfpOpticalTransmitPowerOutOfRangeRaisedNotif
                      tnSfpOrXfpOpticalTransmitPowerOutOfRangeClearedNotif
                      tnSfpOrXfpOpticalReceiverPowerOutOfRangeRaisedNotif
                      tnSfpOrXfpOpticalReceiverPowerOutOfRangeClearedNotif
                      to
                      tnSfpTempOORRaisedNotif
                      tnSfpTempOORClearedNotif
                      tnSfpEOLRaisedNotif
                      tnSfpEOLClearedNotif
                      tnSfpTrmtPwrOORRaisedNotif
                      tnSfpTrmtPwrOORClearedNotif
                      tnSfpReceiverPwrOORRaisedNotif
                      tnSfpReceiverPwrOORClearedNotif"

      REVISION    "201001081200Z"
      DESCRIPTION "Added the following notifications:
                   tnRamanSupRaisedNotif  (tnV2AlarmNotificationsRel2 455)
                   tnRamanSupClearedNotif (tnV2AlarmNotificationsRel2 456)."

      REVISION    "201001061200Z"
      DESCRIPTION "Marked the following as obsolete:
                   tnVtsOpenConnectionIndication[1-10]RaisedNotif
                   tnVtsOpenConnectionIndication[1-10]ClearedNotif
                   tnVtsForwardDefectIndication[1-10]RaisedNotif
                   tnVtsForwardDefectIndication[1-10]ClearedNotif."

      REVISION    "200912231200Z"
      DESCRIPTION "Added the following notifications:
                   tnB1SignalDegradeRaisedNotif   (tnV2CardNotifications 189)
                   tnB1SignalDegradeCleareddNotif (tnV2CardNotifications 190)
                   tnOAPumpLaserBiasCurrentHighRaisedNotif (tnV2AlarmNotificationsRel2 435)
                   to
                   tnOAPumpLaserTempHighClearedNotif       (tnV2AlarmNotificationsRel2 454)."

      REVISION    "200910231200Z"
      DESCRIPTION "Added description pertaining to new VTS objectId."

      REVISION    "200908261200Z"
      DESCRIPTION "Added the following notification:
                   tnEcReconnectedNotif (tnV2EventNotificationsRel2 28)."

      REVISION    "200907171200Z"
      DESCRIPTION "1) Added the following notifications:
                      tnLockedIndicationEgressNotif    (tnV2EventNotificationsRel2 21)
                      to
                      tnServerSignalFailureEgressNotif (tnV2EventNotificationsRel2 27).
                   2) Replaced tnVtsOpenConnectionIndication[11-32]RaisedNotif,
                      tnVtsOpenConnectionIndication[11-32]ClearedNotif,
                      tnVtsForwardDefectIndication[11-32]RaisedNotif, and
                      tnVtsForwardDefectIndication[11-32]ClearedNotif,
                      with tnVtsOpenConnectionIndicationRaisedNotif,
                      tnVtsOpenConnectionIndicationClearedNotif,
                      tnVtsForwardDefectIndicationRaisedNotif, and
                      tnVtsForwardDefectIndicationClearedNotif,
                      respectively.
                   3) Marked the following as deprecated:
                      tnVtsOpenConnectionIndication[1-10]RaisedNotif
                      tnVtsOpenConnectionIndication[1-10]ClearedNotif
                      tnVtsForwardDefectIndication[1-10]RaisedNotif
                      tnVtsForwardDefectIndication[1-10]ClearedNotif."

      REVISION    "200906181200Z"
      DESCRIPTION "Added the following notifications:
                   tnVtsConnCreationNotif   (tnV2EventNotificationsRel2 20)
                   tnDormantUserNotif       (tnV2SecurityNotifications 26)
                   to
                   tnLogBufOvflSecuLogNotif (tnV2SecurityNotifications 28)."

      REVISION    "200906041200Z"
      DESCRIPTION "Added the following notifications:
                   tnEnvInput3ActiveRaisedNotif  (tnV2AlarmNotificationsRel2 423)
                   to
                   tnEnvInput8ActiveClearedNotif (tnV2AlarmNotificationsRel2 434)."

      REVISION    "200905221200Z"
      DESCRIPTION "Added the following notifications:
                   tnVtsOpenConnectionIndication11RaisedNotif (tnV2AlarmNotificationsRel2 419)
                   to
                   tnVtsForwardDefectIndication32ClearedNotif (tnV2AlarmNotificationsRel2 506)."

      REVISION    "200905051200Z"
      DESCRIPTION "Added the following notifications:
                   tnEtrMismatchRaisedNotif  (tnV2AlarmNotificationsRel2 417)
                   tnEtrMismatchClearedNotif (tnV2AlarmNotificationsRel2 418)."

      REVISION    "200904271200Z"
      DESCRIPTION "Added the following notifications:
                   tnFarEndLosRaisedNotif (tnV2AlarmNotificationsRel2 413)
                   to
                   tnAprLineClearedNotif  (tnV2AlarmNotificationsRel2 416)."

      REVISION    "200903051200Z"
      DESCRIPTION "Added the following notifications:
                   tnHwRevisionNotSupportedRaisedNotif  (tnV2GenericCardNotifications 35)
                   tnHwRevisionNotSupportedClearedNotif (tnV2GenericCardNotifications 36)."

      REVISION    "200902101200Z"
      DESCRIPTION "Added the following notifications:
                   tnDataErrRaisedNotif  (tnV2AlarmNotificationsRel2 411)
                   tnDataErrClearedNotif (tnV2AlarmNotificationsRel2 412)."

      REVISION    "200901071200Z"
      DESCRIPTION "Added the following notifications:
                   tnInvalidThresholdRaisedNotif  (tnV2AlarmNotificationsRel2 409)
                   tnInvalidThresholdClearedNotif (tnV2AlarmNotificationsRel2 410)."

      REVISION    "200901061200Z"
      DESCRIPTION "Added the following notifications:
                   tnSecurityChangeMaxFailedLoginsNotif    (tnV2SecurityNotifications 23)
                   to
                   tnSecurityDatabaseBackupAndRestoreNotif (tnV2SecurityNotifications 25)."

      REVISION    "200811141200Z"
      DESCRIPTION "Added the following notifications:
                   tnPwrMaxGainRaisedNotif  (tnV2AlarmNotificationsRel2 407)
                   tnPwrMaxGainClearedNotif (tnV2AlarmNotificationsRel2 408)."

      REVISION    "200811031200Z"
      DESCRIPTION "Added the following notifications:
                   tnBatteryOffRaisedNotif (tnV2AlarmNotificationsRel2 397)
                   to
                   tnFpgaFailClearedNotif  (tnV2AlarmNotificationsRel2 406)."

      REVISION    "200809261200Z"
      DESCRIPTION "Corrected SystemReady notification."

      REVISION    "200809241200Z"
      DESCRIPTION "Added the following notification:
                   tnSystemReadyNotif (tnV2EventNotificationsRel2 19)."

      REVISION    "200809111200Z"
      DESCRIPTION "Added NTP, DB, FW notifications."

      REVISION    "200806251200Z"
      DESCRIPTION "Added VTS OCI and FDI notifications."

      REVISION    "200805221200Z"
      DESCRIPTION "Added the following notifications:
                   tnApsSwitchedToWorkRaisedNotif (tnV2AlarmNotificationsRel2 343)
                   to
                   tnSignalDegradeClearedNotif    (tnV2AlarmNotificationsRel2 346)
                   tnPmBaselineNotif              (tnV2StatisticsNotifications 6)."

      REVISION    "200805061200Z"
      DESCRIPTION "Added the following notifications:
                   tnSystemInitializationInProgressRaisedNotif (tnV2AlarmNotificationsRel2 335)
                   to
                   tnInputVoltageDefectClearedNotif            (tnV2AlarmNotificationsRel2 342)."

      REVISION    "200803281200Z"
      DESCRIPTION "Added the missing env input notifications."

      REVISION    "200803201200Z"
      DESCRIPTION "1) Updated the MIB file description.
                   2) Added the reakdown of MIB attributes
                      tnTrapObjectID/tnTrapObjectIDType.
                   3) Added the following notifications:
                      tnLosDcmRaisedNotif     (tnV2AlarmNotificationsRel2 285)
                      to
                      tnRfiEgressClearedNotif (tnV2AlarmNotificationsRel2 330)."

      ::= { tnSystemModules 2 }

    tnNotificationConf          OBJECT IDENTIFIER ::= { tnNotificationMIB  1 }
    tnNotificationGroups        OBJECT IDENTIFIER ::= { tnNotificationConf 1 }
    tnNotificationCompliances   OBJECT IDENTIFIER ::= { tnNotificationConf 2 }
    tnNotificationObjs          OBJECT IDENTIFIER ::= { tnNotificationMIB  2 }
    tnTrapBuffering             OBJECT IDENTIFIER ::= { tnNotificationObjs 1 }
    tnNotifications             OBJECT IDENTIFIER ::= { tnNotificationObjs 2 }
    tnNotificationsRel2         OBJECT IDENTIFIER ::= { tnNotificationObjs 3 }
    tnNotificationsSdh          OBJECT IDENTIFIER ::= { tnNotificationObjs 4 }
    tnNotificationsUnregistered OBJECT IDENTIFIER ::= { tnNotificationObjs 5 }
    tnNotificationsSecurity     OBJECT IDENTIFIER ::= { tnNotificationObjs 6 }
    tnNotificationsE1           OBJECT IDENTIFIER ::= { tnNotificationObjs 7 }

-- -------------------------------------------------------------
-- Breakdown of MIB attributes tnTrapObjectID/tnTrapObjectIDType
-- -------------------------------------------------------------
--
-- primaryObjectIdData == tnTrapObjectID;
-- extraObjectIdData == (tnTrapObjectIDType & 0xFFFF0000) >> 16;
-- objectIdType == tnTrapObjectIDType & 0x0000003F;
--
-- valid objectIdTypes:
--   physicalObjectId         == 1  // physical location
--   iPaddrObjectId           == 2  // IP address
--   serviceObjectId          == 3
--   connectionObjectId       == 5  // cross connection
--   ifIdObjectId             == 6  // control network link
--   l1protectionObjectId     == 7  // protection group or member
--   rawDataObjectId          == 8
--   pmProfileObjectId        == 9  // performance monitoring profile
--   pmGroupObjectId          == 10
--   pmIntervalObjectId       == 11 // performance monitoring interval
--   ipStaticRouteObjectId    == 12 // control network static route
--   processorObjectId        == 13
--   rmonObjectId             == 14
--   vtsConnectionObjectId    == 15 // vts connection
--   vtsMapObjectId           == 16 // vts map
--   logicalObjectId          == 17 // logical location
--   syncObjectId             == 18 // sync location
--   ccmObjectId              == 19 // ccm location
--   odukConnectionObjectId   == 20 // oduk connection
--   vtsObjectId              == 21 // vts location
--   mepObjectId              == 22
--   custObjectId             == 23
--   srObjectId               == 24
--   otnEntityObjectId        == 25
--   DXconnectionObjectId     == 26
--   ospfIPRangeObjectId      == 27
--   ptpObjectId              == 28
--   lagObjectId              == 29
--   rmdObjectId              == 31 // Remote Managed Device
--   generalObjectId          == 32 // GMPLS and XCOM
--   ntpObjectId              == 33 //new for 7.0 for NTP
--   netIfObjectId            == 34
--   ipV6StaticRouteObjectId  == 35
--   ethIfIdObjectId          == 36
--   ethIfInterfaceObjectId   == 37
--   idTypeObjectId           == 38
--   spectrumObjectId         == 39
--   cardFacilityGrpObjectId  == 40
--   pdtConnectivityObjectId  == 41
--   keyStoreObjectId         == 42
--   roeObjectId              == 43 // reserved for 1830TPS roe alarm reporting
--   ipV6DhcpRelayObjectId    == 44 // created for dhcpV6 nodeagent traps.
--   ipV6SanObjectId          == 45
--   ipV6CsrSanObjectId       == 46
--   domainCsrSanObjectId     == 47
--   domainSanObjectId        == 48
--   snodelOscLanIfIdObjectId == 49
--   snodelOscLanIfObjectId   == 50
--   bgpObjectId              == 51
--   dhppOjbjectid            == 52 // reserved for 1830TPS roe alarm reporting

--   (See switch statement below for objectId bit assignments.)
--
-- valid directions:
--   nil    == 0
--   Tx/Out == 1
--   Rx/In  == 2
--
-- valid portTypes:
--   nil              == 0
--   optical          == 1
--   backplanePort    == 2
--   extendedPortType == 3
--   stsPortType      == (0 << 2) + extendedPortType  // Deliberately the same as extendedPortType
--   subPort          == (1 << 2) + extendedPortType
--   tcmPort          == (2 << 2) + extendedPortType
--   gmreImpPort      == (3 << 2) + extendedPortType  // R3.6: GmreRepeater: GMRE OptLine Impairment (OMS Line Tx)
--   pwrOffsetPort    == (4 << 2) + extendedPortType  // R3.6: PowerManagerTargetOffsetRepeater: Och Target Power Offset
--
-- band range: 1-8
--
-- channel range: 1-4
--
-- switch (objectIdType) {
--     case physicalObjectId (1): // physical location
--         shelf     = (primaryObjectIdData & 0xFF000000) >> 24;
--         slot      = (primaryObjectIdData & 0x00FF0000) >> 16; // if the MSB is set, the slot is a B slot
--         port      = (primaryObjectIdData & 0x0000FF00) >> 8;
--         direction = (primaryObjectIdData & 0x000000C0) >> 6;
--         band      = (primaryObjectIdData & 0x0000003C) >> 2;
--         portType  = primaryObjectIdData & 0x00000003;
--         channel   = extraObjectIdData;
--         break;
--
--     case IPaddrObjectId (2): // IP address
--         IPaddr1 = (primaryObjectIdData & 0xFF000000) >> 24;
--         IPaddr2 = (primaryObjectIdData & 0x00FF0000) >> 16;
--         IPaddr3 = (primaryObjectIdData & 0x0000FF00) >> 8;
--         IPaddr4 = primaryObjectIdData & 0x000000FF;
--         break;
--
--     case connectionObjectId (5):     // cross connection
--     case vtsConnectionObjectId (15): //using the same data struct as connectionObjectId
--     case odukConnectionObjectId (20):
--         connectionId = primaryObjectIdData;
--         break;
--
--     case ifIdObjectId (6): // control network link
--         ifId = primaryObjectIdData;
--         break;
--
--     case l1protectionObjectId (7): // protection group or member
--         groupId = extraObjectIdData;
--         shelf   = (primaryObjectIdData & 0xFF000000) >> 24;
--         slot    = (primaryObjectIdData & 0x00FF0000) >> 16; // if the MSB is set, the slot is a B slot
--         port    = (primaryObjectIdData & 0x0000FF00) >> 8;
--         break;
--
--     case pmProfileObjectId (9): // performance monitoring profile
--         pmGroup   = (primaryObjectIdData & 0xFF000000) >> 24;
--         pmProfile = (primaryObjectIdData & 0x00FF0000) >> 16;
--         pmMember  = primaryObjectIdData & 0x0000FFFF;
--         break;
--
--     case pmIntervalObjectId (11): // performance monitoring interval
--         shelf      = (primaryObjectIdData & 0xFF000000) >> 24;
--         slot       = (primaryObjectIdData & 0x00FF0000) >> 16; // if the MSB is set, the slot is a B slot
--         port       = (primaryObjectIdData & 0x0000FF00) >> 8;
--         pmGroup    = primaryObjectIdData & 0x000000FF;
--         pmInterval = extraObjectIdData;
--         break;
--
--     case ipStaticRouteObjectId (12): // control network static route
--         destinationIp = primaryObjectIdData;
--         break;
--
--     case vtsMapObjectId (16):
--         vtsMapVts = extraOjectIdData;
--         vtsMapIfIndex = primaryObjectIdData;
--         break;
--
--     case logicalObjectId (17):
--         // The entity type is
--         //  LOGIC_OTU         = 1, LOGIC_HOODU    = 2, LOGIC_Layer1LOODU = 3,
--         //  LOGIC_Layer2LOODU = 4, LOGIC_ODUPTF   = 5, LOGIC_OPTSG       = 6,
--         //  LOGIC_OTU_PORT    = 7, LOGIC_ODU_PORT = 8, // for Odu under client port
--         //  LOGIC_OPTSG_PORT  = 9, // for Optsg under client port
--         shelf           = (primaryObjectIdData & 0xFF000000) >> 24;
--         slot            = (primaryObjectIdData & 0x00FC0000) >> 18;
--         port/oduptf     = (primaryObjectIdData & 0x0003F000) >> 12;
--         entityType      = (primaryObjectIdData & 0x00000F00) >> 8;
--         looduid/optsgId =  primaryObjectIdData & 0x000000FF;
--         direction       = extraObjectIdData;
--         break;
--
--     case syncObjectId (18):
--         shelf          = (primaryObjectIdData & 0xFF000000) >> 24;
--         slot           = (primaryObjectIdData & 0x00FF0000) >> 16; // if the MSB is set, the slot is a B slot
--         syncEntityType = (primaryObjectIdData & 0x0000FF00) >> 8; //SYNC_Sync =1;SYNC_LineRef =2;SYNC_SClock =3;
--         LineRef        = primaryObjectIdData & 0x000000FF; //when syncEntityType == SYNC_LineRef
--         break;
--
--     case vtsObjectId (21):
--         shelf = (primaryObjectIdData & 0xFF000000) >> 24;
--         slot  = (primaryObjectIdData & 0x00FF0000) >> 16;
--         port  = (primaryObjectIdData & 0x0000FF00) >> 8;
--         vts   =  primaryObjectIdData & 0x000000FF;
--         direction  = extraObjectIdData;
--         break;
--
--     case mepObjectId (22):
--         shelf = (primaryObjectIdData & 0xFF000000) >> 24;
--         slot  = (primaryObjectIdData & 0x00FF0000) >> 16;
--         md    = (primaryObjectIdData & 0x0000F800) >> 11;
--         ma    =  primaryObjectIdData & 0x000007FF;
--         mepid  = (extraObjectIdData & 0xFFFC0000) >> 18;
--         direction =  (extraObjectIdData & 0x00030000) >> 16;
--         break;
--
--     case srObjectId (24):
--         shelf        = (primaryObjectIdData & 0xFF000000) >> 24;
--         slot         = (primaryObjectIdData & 0x00FF0000) >> 16;
--         srEntityType = extraObjectIdData;
--         break;
--
--       Supported srEntityType
--         SR_SVC        = 1
--         SR_SAP        = 5
--         SR_ERP_PATH   = 9
--         SR_ETHCFM_MEP = 16
--         SR_LINK_OAM   = 18
--         SR_SyncE      = 45
--         SR_OamSaaCtl  = 72
--
--       Based on the srEntityType obtained in extraObjectIdData, tnTrapData
--       would contain a string with the appropriate indices
--         Service   - customer id, service id
--         Sap       - customer id, service id, port number, encap value
--         Erp path  - ring index, path index
--         Mep       - domain index, association index, mep index
--         LinkOam   - port number
--         SyncE     - no additional info available in tnTrapData
--         OamSaaCtl - test name
--
--       For example, tnTrapData for Service would be "1 100" for Service
--       with customer id of 1 and service id of 100.
--
--     case otnEntityObjectId (25):
--         shelf          = (U8) (primaryObjectIdData & 0xFF000000) >> 24;
--         slot           = (U8) (primaryObjectIdData & 0x00FF0000) >> 16;
--         buf            = 0;
--         port_hoodu     = (U16) (primaryObjectIdData & 0x00007FFC) >> 2;
--         dir            = (U16) (primaryObjectIdData & 0x00000003);
--         loodu_optsg    = (extraObjectIdData & 0xFF80) >> 7;
--         tcm            = (extraObjectIdData & 0x0070) >> 4;
--         pos            = (extraObjectIdData & 0x000C) >> 2;
--         interval       = (extraObjectIdData & 0x0003);
--         facType        = (U8) (primaryObjectIdData & 0x0000F000) >> 12;
--         subFac         = (U8) (primaryObjectIdData & 0x00000FC0) >> 6;
--         typeOfObjectId = (U8) (primaryObjectIdData & 0x0000003F);
--
--     case ptpObjectId (28):
--         shelf         = (U8) ((primaryData & 0xFF000000) >> 24 );
--         slot          = (U8) ((primaryData & 0x00FF0000) >> 16 );
--         ptpClock      = (U8) (((extraObjectIdData & 0x001F) << 3) | (primaryData & 0x0000E000) >> 13 ); // ptpclock 1-255
--         ptpPort       = (U16) ((primaryData & 0x00001FFF) );
--
--     case rmdObjectId (31):
--         shelf         = (primaryObjectIdData & 0xFF000000) >> 24;
--         slot          = (primaryObjectIdData & 0x00FF0000) >> 16;
--         deviceId      = (primaryObjectIdData & 0x0000FF00) >> 8;
--         dir           = (primaryObjectIdData & 0x000000C0) >> 6;
--         portId        = primaryObjectIdData & 0x0000003F;
--         rmdEntityType = (extraObjectIdData & 0xF0000000) >> 28;
--         rmdEntityId   = (extraObjectIdData & 0x0FFF0000) >> 16;
--         break;
--
--       Supported rmdEntityType
--         RMD_DEVICE = 2
--         RMD_CFM    = 3
--         RMD_IF     = 5
--         RMD_IF_MAU = 7
--         RMD_TSOP   = 9
--         RMD_NIM    = 10
--
--       Based on the rmdEntityType obtained in extraObjectIdData, tnTrapData
--       would contain a string with the appropriate indices
--          RMD_CFM   - MepIdentifier
--
--       For example, tnTrapData for RMD_CFM  would be "101" with MEP identifier
--       of 101.  Currently only one RMD_CFM MEP is supported.
--
--     case generalObjectId (32):
--         subId        = (primaryObjectIdData & 0xFFFF0000) >> 16;
--         facType      = (primaryObjectIdData & 0x0000F000) >> 12;
--         0            = (primaryObjectIdData & 0x00000FC0) >> 6;
--         32           = (primaryObjectIdData & 0x0000003F);
--         break;
--
--     case cardFacilityGrpObjectId (40):
--         shelf        = (primaryObjectIdData & 0xFF000000) >> 24;
--         slot         = (primaryObjectIdData & 0x00FF0000) >> 16;
--         grpType      = (primaryObjectIdData & 0x0000FF00) >> 8;
--         grpId        = (primaryObjectIdData & 0x000000FF);
--         break;
--
--     case roeObjectId (43):
--         shelf = (primaryObjectIdData & 0xFF000000) >> 24;
--         slot = (primaryObjectIdData & 0x00FF0000) >> 16;
--         port = (primaryObjectIdData & 0x0000FF00) >> 8;
--         roeEntityType= (primaryObjectIdData & 0x000000FF)
--         id = extraObjectIdData; //mapperid/demapperid/ethlinkId
--         break;
--
--       Supported roeEntityType
--         ROE            = 0
--         ROE_MAPPER     = 1
--         ROE_DEMAPPER   = 2
--         ROE_EthLink    = 3
--
--     case dhppOjbjectid (52):
--         shelf       = (primaryObjectIdData & 0xFF000000) >> 24;
--         dhppgroupid = (primaryObjectIdData & 0x00FF0000) >> 16;
--         break;
-- }
--
-- valid pmGroups:
--   InvalidGroup                       = 0
--   EthernetStats                      = 1
--   DataStats                          = 2
--   SonetStats                         = 3
--   DCInOpticalPowerStats              = 4
--   SystemStats                        = 5
--   DCTxOpticalPowerStats              = 6
--   DCRxOpticalPowerStats              = 7
--   WTTxOpticalPowerStats              = 8
--   InterfaceStats                     = 9
--   WTRxOpticalPowerStats              = 10
--   PreFECBERStats                     = 11
--   DCOutOpticalPowerStats             = 12
--   DwStats                            = 13
--   LbcStats                           = 14
--   LaserTempStats                     = 15
--   CdStats                            = 16
--   DgdStats                           = 17
--   OpLanePwrStats                     = 18
--   FECPMStats                         = 19
--   PhyCodeSubLayerStats               = 20
--   FoffStats                          = 21
--   E1Stats                            = 22
--   PreFecBitsStats                    = 23
--   OduTcmStats                        = 24
--   EncryptStats                       = 25
--   OtuStats                           = 26
--   OsnrStats                          = 27
--   OduStatsRx                         = 28
--   OduStatsTx                         = 29
--   DmStats                            = 30
--   FecStats                           = 31
--   OPINC                              = 32
--   OPINL                              = 33
--   OPOUTC                             = 34
--   OPOUTL                             = 35
--   FlexChannels                       = 36
--   EthFecPMStats                      = 37
--   SyncEStats                         = 38
--   PTPTimeOffset                      = 39
--   PTPTMSDelay                        = 40
--   PTPTSMDelay                        = 41
--   PTPMeanPathDelay                   = 42
--   PTPTimeErrorbyReferenceComparison  = 43
--   PTPTimeOffsetAccumulation          = 44
--   PacketWanifStats                   = 45
--   CsrStats                           = 46
--   QmarginStats                       = 47

-- -------------------------------------------------------------
-- Notifications
-- -------------------------------------------------------------

-- -------------------------------------------------------------
-- System Notifications
-- -------------------------------------------------------------
    tnSystemNotifications OBJECT IDENTIFIER ::= { tnNotifications 1 }
    tnV2SystemNotifications OBJECT IDENTIFIER ::= { tnSystemNotifications 0 }

    tnChangeNotif NOTIFICATION-TYPE
        OBJECTS {
            tnTrapTime,
            tnTrapObjectIDType,
            tnTrapObjectID,
            tnTrapCategory,
            tnTrapDescr,
            tnTrapData,
            tnTrapChangedObject
        }
        STATUS         current
        DESCRIPTION    "."
        ::= { tnV2SystemNotifications 1 }

    tnStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SystemNotifications 2 }

    tnActiveAlarmResyncStartNotif NOTIFICATION-TYPE
        OBJECTS {
            tnTrapTime,
            tnTrapObjectIDType,
            tnTrapObjectID,
            tnTrapCategory,
            tnTrapDescr
        }
        STATUS         current
        DESCRIPTION    "."
        ::= { tnV2SystemNotifications 3 }

    tnActiveAlarmResyncEndNotif NOTIFICATION-TYPE
        OBJECTS {
            tnTrapTime,
            tnTrapObjectIDType,
            tnTrapObjectID,
            tnTrapCategory,
            tnTrapDescr
        }
        STATUS         current
        DESCRIPTION    "."
        ::= { tnV2SystemNotifications 4 }

    tnControlCardActivityChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SystemNotifications 5 }

    tnSeepDeviceFullNotif NOTIFICATION-TYPE
        OBJECTS {
            tnTrapTime,
            tnTrapObjectIDType,
            tnTrapObjectID,
            tnTrapCategory,
            tnTrapDescr
        }
        STATUS         current
        DESCRIPTION    "."
        ::= { tnV2SystemNotifications 6 }

    tnSeepScrubJumperNotif NOTIFICATION-TYPE
        OBJECTS {
            tnTrapTime,
            tnTrapObjectIDType,
            tnTrapObjectID,
            tnTrapCategory,
            tnTrapDescr
        }
        STATUS         current
        DESCRIPTION    "."
        ::= { tnV2SystemNotifications 7 }

    tnSeepCRCErrorNotif NOTIFICATION-TYPE
        OBJECTS {
            tnTrapTime,
            tnTrapObjectIDType,
            tnTrapObjectID,
            tnTrapCategory,
            tnTrapDescr
        }
        STATUS         current
        DESCRIPTION    "."
        ::= { tnV2SystemNotifications 8 }

    tnUnknownNotif NOTIFICATION-TYPE
        OBJECTS {
            tnTrapTime,
            tnTrapObjectIDType,
            tnTrapObjectID
        }
        STATUS         current
        DESCRIPTION    "."
        ::= { tnV2SystemNotifications 9 }

    tnSystemInitializedNotif NOTIFICATION-TYPE
        OBJECTS {
            tnTrapTime,
            tnTrapObjectIDType,
            tnTrapObjectID,
            tnTrapCategory,
            tnTrapDescr
        }
        STATUS         current
        DESCRIPTION    "."
        ::= { tnV2SystemNotifications 10 }

    tnIfTypeUserUnassignNotif NOTIFICATION-TYPE
        OBJECTS {
            tnTrapTime,
            tnTrapObjectIDType,
            tnTrapObjectID,
            tnTrapCategory,
            tnTrapDescr,
            tnTrapData,
            tnTrapChangedObject
        }
        STATUS         current
        DESCRIPTION    "."
        ::= { tnV2SystemNotifications 11 }

-- -------------------------------------------------------------
-- Equipment Notifications
-- -------------------------------------------------------------
    tnEquipmentNotifications OBJECT IDENTIFIER ::= { tnNotifications 2 }

-- -------------------------------------------------------------
-- Equipment - Card Notifications
-- -------------------------------------------------------------
    tnCardNotifications OBJECT IDENTIFIER ::= { tnEquipmentNotifications 1 }
    tnV2CardNotifications OBJECT IDENTIFIER ::= { tnCardNotifications 0 }

    tnEthernetLinkDownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 1 }

    tnEthernetLinkDownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 2 }

--    obsolete
--    tnBreakerTrippedRaisedNotif           NOTIFICATION-TYPE ::= { tnV2CardNotifications 3 }
--    tnBreakerTrippedClearedNotif          NOTIFICATION-TYPE ::= { tnV2CardNotifications 4 }
--    tnBreakerOverCurrentRaisedNotif       NOTIFICATION-TYPE ::= { tnV2CardNotifications 5 }
--    tnBreakerOverCurrentClearedNotif      NOTIFICATION-TYPE ::= { tnV2CardNotifications 6 }
--    tnBreakerBatteryFeedDownRaisedNotif   NOTIFICATION-TYPE ::= { tnV2CardNotifications 7 }
--    tnBreakerBatteryFeedDownClearedNotif  NOTIFICATION-TYPE ::= { tnV2CardNotifications 8 }
--    tnBreakerAlarmOverCurrentRaisedNotif  NOTIFICATION-TYPE ::= { tnV2CardNotifications 9 }
--    tnBreakerAlarmOverCurrentClearedNotif NOTIFICATION-TYPE ::= { tnV2CardNotifications 10 }
--    tnBreakerFanOverCurrentRaisedNotif    NOTIFICATION-TYPE ::= { tnV2CardNotifications 11 }
--    tnBreakerFanOverCurrentClearedNotif   NOTIFICATION-TYPE ::= { tnV2CardNotifications 12 }

    tnBreakerCardsMismatchedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 13 }

    tnBreakerCardsMismatchedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 14 }

--    obsolete
--    tnFanSpeedTooHighRaisedNotif               NOTIFICATION-TYPE ::= { tnV2CardNotifications 15 }
--    tnFanSpeedTooHighClearedNotif              NOTIFICATION-TYPE ::= { tnV2CardNotifications 16 }
--    tnFanSpeedTooLowRaisedNotif                NOTIFICATION-TYPE ::= { tnV2CardNotifications 17 }
--    tnFanSpeedTooLowClearedNotif               NOTIFICATION-TYPE ::= { tnV2CardNotifications 18 }
--    tnCardStartupDiagFailureRaisedNotif        NOTIFICATION-TYPE ::= { tnV2CardNotifications 19 }
--    tnCardStartupDiagFailureClearedNotif       NOTIFICATION-TYPE ::= { tnV2CardNotifications 20 }
--    tnCardStartupDiagNotExecRaisedNotif        NOTIFICATION-TYPE ::= { tnV2CardNotifications 21 }
--    tnCardStartupDiagNotExecClearedNotif       NOTIFICATION-TYPE ::= { tnV2CardNotifications 22 }
--    tnOpticalBandMismatchRaisedNotif           NOTIFICATION-TYPE ::= { tnV2CardNotifications 23 }
--    tnOpticalBandMismatchClearedNotif          NOTIFICATION-TYPE ::= { tnV2CardNotifications 24 }
--    tnCardDeviceFailureRaisedNotif             NOTIFICATION-TYPE ::= { tnV2CardNotifications 25 }
--    tnCardDeviceFailureClearedNotif            NOTIFICATION-TYPE ::= { tnV2CardNotifications 26 }
--    tnDspCommEquipFailureRaisedNotif           NOTIFICATION-TYPE ::= { tnV2CardNotifications 27 }
--    tnDspCommEquipFailureClearedNotif          NOTIFICATION-TYPE ::= { tnV2CardNotifications 28 }
--    tnWaveKeySignalOpticalOverloadRaisedNotif  NOTIFICATION-TYPE ::= { tnV2CardNotifications 29 }
--    tnWaveKeySignalOpticalOverloadClearedNotif NOTIFICATION-TYPE ::= { tnV2CardNotifications 30 }
--    tnOpticalPowerOverloadRaisedNotif          NOTIFICATION-TYPE ::= { tnV2CardNotifications 31 }
--    tnOpticalPowerOverloadClearedNotif         NOTIFICATION-TYPE ::= { tnV2CardNotifications 32 }
--    tnCardDSPOverflowRaisedNotif               NOTIFICATION-TYPE ::= { tnV2CardNotifications 33 }
--    tnCardDSPOverflowClearedNotif              NOTIFICATION-TYPE ::= { tnV2CardNotifications 34 }
--    tnDspMemoryEquipFailureRaisedNotif         NOTIFICATION-TYPE ::= { tnV2CardNotifications 35 }
--    tnDspMemoryEquipFailureClearedNotif        NOTIFICATION-TYPE ::= { tnV2CardNotifications 36 }
--    tnDspADCEquipFailureRaisedNotif            NOTIFICATION-TYPE ::= { tnV2CardNotifications 37 }
--    tnDspADCEquipFailureClearedNotif           NOTIFICATION-TYPE ::= { tnV2CardNotifications 38 }
--    tnDspDMAEquipFailureRaisedNotif            NOTIFICATION-TYPE ::= { tnV2CardNotifications 39 }
--    tnDspDMAEquipFailureClearedNotif           NOTIFICATION-TYPE ::= { tnV2CardNotifications 40 }
--    tnLossOfLightRaisedNotif                   NOTIFICATION-TYPE ::= { tnV2CardNotifications 41 }
--    tnLossOfLightClearedNotif                  NOTIFICATION-TYPE ::= { tnV2CardNotifications 42 }

    tnOpticalOutputPowerUnachievableRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 43 }

    tnOpticalOutputPowerUnachievableClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 44 }

    tnOpticalPowerDeviationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 45 }

    tnOpticalPowerDeviationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 46 }

    tnWaveKeyInsertionFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 47 }

    tnWaveKeyInsertionFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 48 }

    tnUnexpectedWaveKeyRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 49 }

    tnUnexpectedWaveKeyClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 50 }

    tnMissingWaveKeyRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 51 }

    tnMissingWaveKeyClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 52 }

    tnChannelPowerOutOfRangeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 53 }

    tnChannelPowerOutOfRangeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 54 }

--    obsolete
--    tnOscLinkDownRaisedNotif           NOTIFICATION-TYPE ::= { tnV2CardNotifications 55 }
--    tnOscLinkDownClearedNotif          NOTIFICATION-TYPE ::= { tnV2CardNotifications 56 }
--    tnCardDisabledOverTempRaisedNotif  NOTIFICATION-TYPE ::= { tnV2CardNotifications 57 }
--    tnCardDisabledOverTempClearedNotif NOTIFICATION-TYPE ::= { tnV2CardNotifications 58 }

    tnAmpDisabledOpticalPowerOverloadRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 59 }

    tnAmpDisabledOpticalPowerOverloadClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 60 }

--    obsolete
--    tnOpticalTransmitterFailureRaisedNotif  NOTIFICATION-TYPE ::= { tnV2CardNotifications 61 }
--    tnOpticalTransmitterFailureClearedNotif NOTIFICATION-TYPE ::= { tnV2CardNotifications 62 }

    tnAmpDisabledRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 63 }

    tnAmpDisabledClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 64 }

--    obsolete
--    tnAmpOutputPowerEquipFailureRaisedNotif  NOTIFICATION-TYPE ::= { tnV2CardNotifications 65 }
--    tnAmpOutputPowerEquipFailureClearedNotif NOTIFICATION-TYPE ::= { tnV2CardNotifications 66 }
--    tnAmpEndOfLifeRaisedNotif                NOTIFICATION-TYPE ::= { tnV2CardNotifications 67 }
--    tnAmpEndOfLifeClearedNotif               NOTIFICATION-TYPE ::= { tnV2CardNotifications 68 }
--    tnAmpAboveOperationalTempRaisedNotif     NOTIFICATION-TYPE ::= { tnV2CardNotifications 69 }
--    tnAmpAboveOperationalTempClearedNotif    NOTIFICATION-TYPE ::= { tnV2CardNotifications 70 }
--    tnAmpBelowOperationalTempRaisedNotif     NOTIFICATION-TYPE ::= { tnV2CardNotifications 71 }
--    tnAmpBelowOperationalTempClearedNotif    NOTIFICATION-TYPE ::= { tnV2CardNotifications 72 }
--    tnAmpOutOfOperationalRangeRaisedNotif    NOTIFICATION-TYPE ::= { tnV2CardNotifications 73 }
--    tnAmpOutOfOperationalRangeClearedNotif   NOTIFICATION-TYPE ::= { tnV2CardNotifications 74 }
--    tnAmpDisabledOverTempRaisedNotif         NOTIFICATION-TYPE ::= { tnV2CardNotifications 75 }
--    tnAmpDisabledOverTempClearedNotif        NOTIFICATION-TYPE ::= { tnV2CardNotifications 76 }
--    tnDcmCompDistanceMismatchRaisedNotif     NOTIFICATION-TYPE ::= { tnV2CardNotifications 77 }
--    tnDcmCompDistanceMismatchClearedNotif    NOTIFICATION-TYPE ::= { tnV2CardNotifications 78 }

    tnProtSwitchDeviceFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 79 }

    tnProtSwitchDeviceFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 80 }

--    obsolete
--    tnLossOfApsServiceRaisedNotif  NOTIFICATION-TYPE ::= { tnV2CardNotifications 81 }
--    tnLossOfApsServiceClearedNotif NOTIFICATION-TYPE ::= { tnV2CardNotifications 82 }
--    tnLossOfRedundancyRaisedNotif  NOTIFICATION-TYPE ::= { tnV2CardNotifications 83 }
--    tnLossOfRedundancyClearedNotif NOTIFICATION-TYPE ::= { tnV2CardNotifications 84 }
--    tnSignalFailRaisedNotif        NOTIFICATION-TYPE ::= { tnV2CardNotifications 85 }
--    tnSignalFailClearedNotif       NOTIFICATION-TYPE ::= { tnV2CardNotifications 86 }

    tnApsModeMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 87 }

    tnApsModeMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 88 }

    tnApsChannelMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 89 }

    tnApsChannelMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 90 }

    tnApsProtSwitchByteFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 91 }

    tnApsProtSwitchByteFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 92 }

    tnApsFarEndProtLineFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 93 }

    tnApsFarEndProtLineFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 94 }

--    obsolete
--    tnPortMissingRaisedNotif  NOTIFICATION-TYPE ::= { tnV2CardNotifications 95 }
--    tnPortMissingClearedNotif NOTIFICATION-TYPE ::= { tnV2CardNotifications 96 }

    tnLossOfSignalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 97 }

    tnLossOfSignalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 98 }

--    obsolete
--    tnLossOfLockRaisedNotif  NOTIFICATION-TYPE ::= { tnV2CardNotifications 99 }
--    tnLossOfLockClearedNotif NOTIFICATION-TYPE ::= { tnV2CardNotifications 100 }

    tnSonetLossOfSignalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 101 }

    tnSonetLossOfSignalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 102 }

    tnSonetLossOfClockRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 103 }

    tnSonetLossOfClockClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 104 }

    tnSonetLossOfFrameRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 105 }

    tnSonetLossOfFrameClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 106 }

    tnSonetAlarmIndicationSignalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 107 }

    tnSonetAlarmIndicationSignalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 108 }

--    obsolete
--    tnSonetRemoteFailureIndicationRaisedNotif  NOTIFICATION-TYPE ::= { tnV2CardNotifications 109 }
--    tnSonetRemoteFailureIndicationClearedNotif NOTIFICATION-TYPE ::= { tnV2CardNotifications 110 }

    tnOpticsModuleMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 111 }

    tnOpticsModuleMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 112 }

    tnPortMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 113 }

    tnPortMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 114 }

--    obsolete
--    tnDwLossOfLightRaisedNotif   NOTIFICATION-TYPE ::= { tnV2CardNotifications 115 }
--    tnDwLossOfLightClearedNotif  NOTIFICATION-TYPE ::= { tnV2CardNotifications 116 }
--    tnDwLossOfSignalRaisedNotif  NOTIFICATION-TYPE ::= { tnV2CardNotifications 117 }
--    tnDwLossOfSignalClearedNotif NOTIFICATION-TYPE ::= { tnV2CardNotifications 118 }
--    tnDwLossOfClockRaisedNotif   NOTIFICATION-TYPE ::= { tnV2CardNotifications 119 }
--    tnDwLossOfClockClearedNotif  NOTIFICATION-TYPE ::= { tnV2CardNotifications 120 }

    tnDwLossOfFrameRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 121 }

    tnDwLossOfFrameClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 122 }

    tnDwSignalFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 123 }

    tnDwSignalFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 124 }

--    obsolete
--    tnInternalClockFailureRaisedNotif  NOTIFICATION-TYPE ::= { tnV2CardNotifications 125 }
--    tnInternalClockFailureClearedNotif NOTIFICATION-TYPE ::= { tnV2CardNotifications 126 }

    tnSonetSignalFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 127 }

    tnSonetSignalFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 128 }

    tnSonetSignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 129 }

    tnSonetSignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 130 }

--    obsolete
--    tnCardDeviceFailureADConverterRaisedNotif           NOTIFICATION-TYPE ::= { tnV2CardNotifications 131 }
--    tnCardDeviceFailureADConverterClearedNotif          NOTIFICATION-TYPE ::= { tnV2CardNotifications 132 }
--    tnCardDeviceFailureBootRaisedNotif                  NOTIFICATION-TYPE ::= { tnV2CardNotifications 133 }
--    tnCardDeviceFailureBootClearedNotif                 NOTIFICATION-TYPE ::= { tnV2CardNotifications 134 }
--    tnCardDeviceFailureCommsRaisedNotif                 NOTIFICATION-TYPE ::= { tnV2CardNotifications 135 }
--    tnCardDeviceFailureCommsClearedNotif                NOTIFICATION-TYPE ::= { tnV2CardNotifications 136 }
--    tnCardDeviceFailureInitializationRaisedNotif        NOTIFICATION-TYPE ::= { tnV2CardNotifications 137 }
--    tnCardDeviceFailureInitializationClearedNotif       NOTIFICATION-TYPE ::= { tnV2CardNotifications 138 }
--    tnCardTransponderSerialEEPROMFailureRaisedNotif     NOTIFICATION-TYPE ::= { tnV2CardNotifications 139 }
--    tnCardTransponderSerialEEPROMFailureClearedNotif    NOTIFICATION-TYPE ::= { tnV2CardNotifications 140 }
--    tnCardTransponderSerialEEPROMTagMissingRaisedNotif  NOTIFICATION-TYPE ::= { tnV2CardNotifications 141 }
--    tnCardTransponderSerialEEPROMTagMissingClearedNotif NOTIFICATION-TYPE ::= { tnV2CardNotifications 142 }
--    tnOpticsModuleCalibrationIncorrectRaisedNotif       NOTIFICATION-TYPE ::= { tnV2CardNotifications 143 }
--    tnOpticsModuleCalibrationIncorrectClearedNotif      NOTIFICATION-TYPE ::= { tnV2CardNotifications 144 }

    tnDwAlarmIndicationSignalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 145 }

    tnDwAlarmIndicationSignalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 146 }

    tnDwSignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 147 }

    tnDwSignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 148 }

    tnPortTransmissionFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 149 }

    tnPortTransmissionFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 150 }

--    obsolete
--    tnTransmitFifoOverrunRaisedNotif        NOTIFICATION-TYPE ::= { tnV2CardNotifications 151 }
--    tnTransmitFifoOverrunClearedNotif       NOTIFICATION-TYPE ::= { tnV2CardNotifications 152 }
--    tnDeviceFailureLaserDegradeRaisedNotif  NOTIFICATION-TYPE ::= { tnV2CardNotifications 153 }
--    tnDeviceFailureLaserDegradeClearedNotif NOTIFICATION-TYPE ::= { tnV2CardNotifications 154 }
--    tnLaserTempOutOfOperRangeRaisedNotif    NOTIFICATION-TYPE ::= { tnV2CardNotifications 155 }
--    tnLaserTempOutOfOperRangeClearedNotif   NOTIFICATION-TYPE ::= { tnV2CardNotifications 156 }
--    tnLaserTransmitFailureRaisedNotif       NOTIFICATION-TYPE ::= { tnV2CardNotifications 157 }
--    tnLaserTransmitFailureClearedNotif      NOTIFICATION-TYPE ::= { tnV2CardNotifications 158 }

    tnLossOfClockRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 159 }

    tnLossOfClockClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 160 }

    tnRemoteFailureIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 161 }

    tnRemoteFailureIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 162 }

--    obsolete
--    tnSonetLossOfPathRaisedNotif                   NOTIFICATION-TYPE ::= { tnV2CardNotifications 163 }
--    tnSonetLossOfPathClearedNotif                  NOTIFICATION-TYPE ::= { tnV2CardNotifications 164 }
--    tnSonetPathAlarmIndicationSignalRaisedNotif    NOTIFICATION-TYPE ::= { tnV2CardNotifications 165 }
--    tnSonetPathAlarmIndicationSignalClearedNotif   NOTIFICATION-TYPE ::= { tnV2CardNotifications 166 }
--    tnSonetPathPayloadLabelMismatchRaisedNotif     NOTIFICATION-TYPE ::= { tnV2CardNotifications 167 }
--    tnSonetPathPayloadLabelMismatchClearedNotif    NOTIFICATION-TYPE ::= { tnV2CardNotifications 168 }
--    tnSonetPathTraceIdentifierMismatchRaisedNotif  NOTIFICATION-TYPE ::= { tnV2CardNotifications 169 }
--    tnSonetPathTraceIdentifierMismatchClearedNotif NOTIFICATION-TYPE ::= { tnV2CardNotifications 170 }
--    tnSonetPathUnequippedRaisedNotif               NOTIFICATION-TYPE ::= { tnV2CardNotifications 171 }
--    tnSonetPathUnequippedClearedNotif              NOTIFICATION-TYPE ::= { tnV2CardNotifications 172 }
--    tnSonetPathPayloadDefectIndicationRaisedNotif  NOTIFICATION-TYPE ::= { tnV2CardNotifications 173 }
--    tnSonetPathPayloadDefectIndicationClearedNotif NOTIFICATION-TYPE ::= { tnV2CardNotifications 174 }

    tnSonetLineRemoteFailureIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 175 }

    tnSonetLineRemoteFailureIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 176 }

--    obsolete
--    tnSonetPathRemoteFailureIndicationRaisedNotif  NOTIFICATION-TYPE ::= { tnV2CardNotifications 177 }
--    tnSonetPathRemoteFailureIndicationClearedNotif NOTIFICATION-TYPE ::= { tnV2CardNotifications 178 }
--    tnDCCEquipmentFailureRaisedNotif               NOTIFICATION-TYPE ::= { tnV2CardNotifications 179 }
--    tnDCCEquipmentFailureClearedNotif              NOTIFICATION-TYPE ::= { tnV2CardNotifications 180 }

    tnSonetSectionTraceMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 181 }

    tnSonetSectionTraceMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 182 }

--    obsolete
--    tnSonetLineAlarmIndicationSignalRaisedNotif  NOTIFICATION-TYPE ::= { tnV2CardNotifications 183 }
--    tnSonetLineAlarmIndicationSignalClearedNotif NOTIFICATION-TYPE ::= { tnV2CardNotifications 184 }
--    tnLaserTransmitPowerLowRaisedNotif           NOTIFICATION-TYPE ::= { tnV2CardNotifications 185 }
--    tnLaserTransmitPowerLowClearedNotif          NOTIFICATION-TYPE ::= { tnV2CardNotifications 186 }

    tnApsWorkingSwitchedToProtectRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 187 }

    tnApsWorkingSwitchedToProtectClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 188 }

    tnB1SignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 189 }

    tnB1SignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 190 }

    tnSSFEthernetRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 191 }

    tnSSFEthernetClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2CardNotifications 192 }

-- -------------------------------------------------------------
-- Equipment - Generic Card Notifications
-- -------------------------------------------------------------
    tnGenericCardNotifications OBJECT IDENTIFIER ::= { tnEquipmentNotifications 2 }
    tnV2GenericCardNotifications OBJECT IDENTIFIER ::= { tnGenericCardNotifications 0 }

    tnCardInitializedNotif NOTIFICATION-TYPE
        OBJECTS {
            tnTrapTime,
            tnTrapObjectIDType,
            tnTrapObjectID,
            tnTrapCategory,
            tnTrapDescr,
            tnTrapData,
            tnSlotProgrammedType
        }
        STATUS         current
        DESCRIPTION    "."
        ::= { tnV2GenericCardNotifications 1 }

    tnCardUnseatedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2GenericCardNotifications 2 }

    tnCardMissingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 3 }

    tnCardMissingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 4 }

    tnCardMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 5 }

    tnCardMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 6 }

    tnCardSanityFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 7 }

    tnCardSanityFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 8 }

    tnCardFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 9 }

    tnCardFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 10 }

    tnInterCardCommsFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 11 }

    tnInterCardCommsFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 12 }

--    obsolete
--    tnCardStartupInitFailureRaisedNotif      NOTIFICATION-TYPE ::= { tnV2GenericCardNotifications 13 }
--    tnCardStartupInitFailureClearedNotif     NOTIFICATION-TYPE ::= { tnV2GenericCardNotifications 14 }
--    tnCardSerialEEPROMFailureRaisedNotif     NOTIFICATION-TYPE ::= { tnV2GenericCardNotifications 15 }
--    tnCardSerialEEPROMFailureClearedNotif    NOTIFICATION-TYPE ::= { tnV2GenericCardNotifications 16 }
--    tnCardCpldMismatchRaisedNotif            NOTIFICATION-TYPE ::= { tnV2GenericCardNotifications 17 }
--    tnCardCpldMismatchClearedNotif           NOTIFICATION-TYPE ::= { tnV2GenericCardNotifications 18 }
--    tnCardSerialEEPROMTagMissingRaisedNotif  NOTIFICATION-TYPE ::= { tnV2GenericCardNotifications 19 }
--    tnCardSerialEEPROMTagMissingClearedNotif NOTIFICATION-TYPE ::= { tnV2GenericCardNotifications 20 }
--    tnCardRunningBootLoadRaisedNotif         NOTIFICATION-TYPE ::= { tnV2GenericCardNotifications 21 }
--    tnCardRunningBootLoadClearedNotif        NOTIFICATION-TYPE ::= { tnV2GenericCardNotifications 22 }

    tnCardUnknownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 23 }

    tnCardUnknownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2GenericCardNotifications 24 }

--    obsolete
--    tnCardCpldFailureRaisedNotif            NOTIFICATION-TYPE ::= { tnV2GenericCardNotifications 25 }
--    tnCardCpldFailureClearedNotif           NOTIFICATION-TYPE ::= { tnV2GenericCardNotifications 26 }
--    tnCardAboveOperationalTempRaisedNotif   NOTIFICATION-TYPE ::= { tnV2GenericCardNotifications 27 }
--    tnCardAboveOperationalTempClearedNotif  NOTIFICATION-TYPE ::= { tnV2GenericCardNotifications 28 }
--    tnCardBelowOperationalTempRaisedNotif   NOTIFICATION-TYPE ::= { tnV2GenericCardNotifications 29 }
--    tnCardBelowOperationalTempClearedNotif  NOTIFICATION-TYPE ::= { tnV2GenericCardNotifications 30 }
--    tnPortInitializationFailureRaisedNotif  NOTIFICATION-TYPE ::= { tnV2GenericCardNotifications 31 }
--    tnPortInitializationFailureClearedNotif NOTIFICATION-TYPE ::= { tnV2GenericCardNotifications 32 }
--    tnCardCalibrationIncorrectRaisedNotif   NOTIFICATION-TYPE ::= { tnV2GenericCardNotifications 33 }
--    tnCardCalibrationIncorrectClearedNotif  NOTIFICATION-TYPE ::= { tnV2GenericCardNotifications 34 }
--    tnHwRevisionNotSupportedRaisedNotif     NOTIFICATION-TYPE ::= { tnV2GenericCardNotifications 35 }
--    tnHwRevisionNotSupportedClearedNotif    NOTIFICATION-TYPE ::= { tnV2GenericCardNotifications 36 }

-- -------------------------------------------------------------
-- Equipment - Control Card Notifications
-- -------------------------------------------------------------
    tnControlCardNotifications OBJECT IDENTIFIER ::= { tnEquipmentNotifications 3 }
    tnV2ControlCardNotifications OBJECT IDENTIFIER ::= { tnControlCardNotifications 0 }

    tnDatabaseSyncFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2ControlCardNotifications 1 }

    tnDatabaseSyncFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2ControlCardNotifications 2 }

    tnDatabaseInvalidRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2ControlCardNotifications 3 }

    tnDatabaseInvalidClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2ControlCardNotifications 4 }

--    obsolete
--    tnShelfBatteryPowerLowRaisedNotif        NOTIFICATION-TYPE ::= { tnV2ControlCardNotifications 5 }
--    tnShelfBatteryPowerLowClearedNotif       NOTIFICATION-TYPE ::= { tnV2ControlCardNotifications 6 }
--    tnCardMustBePowerCycledRaisedNotif       NOTIFICATION-TYPE ::= { tnV2ControlCardNotifications 7 }
--    tnCardMustBePowerCycledClearedNotif      NOTIFICATION-TYPE ::= { tnV2ControlCardNotifications 8 }
--    tnDatabaseFreeSpaceExhaustedRaisedNotif  NOTIFICATION-TYPE ::= { tnV2ControlCardNotifications 9 }
--    tnDatabaseFreeSpaceExhaustedClearedNotif NOTIFICATION-TYPE ::= { tnV2ControlCardNotifications 10 }
--    tnDatabaseFreeSpaceLowRaisedNotif        NOTIFICATION-TYPE ::= { tnV2ControlCardNotifications 11 }
--    tnDatabaseFreeSpaceLowClearedNotif       NOTIFICATION-TYPE ::= { tnV2ControlCardNotifications 12 }
--    tnDiskFreeSpaceExhaustedRaisedNotif      NOTIFICATION-TYPE ::= { tnV2ControlCardNotifications 13 }
--    tnDiskFreeSpaceExhaustedClearedNotif     NOTIFICATION-TYPE ::= { tnV2ControlCardNotifications 14 }
--    tnDiskFreeSpaceLowRaisedNotif            NOTIFICATION-TYPE ::= { tnV2ControlCardNotifications 15 }
--    tnDiskFreeSpaceLowClearedNotif           NOTIFICATION-TYPE ::= { tnV2ControlCardNotifications 16 }

    tnInterShelfLossofCommsRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2ControlCardNotifications 17 }

    tnInterShelfLossofCommsClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2ControlCardNotifications 18 }

--    obsolete
--    tnRamSpaceFailureRaisedNotif  NOTIFICATION-TYPE ::= { tnV2ControlCardNotifications 19 }
--    tnRamSpaceFailureClearedNotif NOTIFICATION-TYPE ::= { tnV2ControlCardNotifications 20 }
--    tnRamSpaceWarningRaisedNotif  NOTIFICATION-TYPE ::= { tnV2ControlCardNotifications 21 }
--    tnRamSpaceWarningClearedNotif NOTIFICATION-TYPE ::= { tnV2ControlCardNotifications 22 }

    tnNEModeMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2ControlCardNotifications 23 }

    tnNEModeMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2ControlCardNotifications 24 }

-- -------------------------------------------------------------
-- Equipment - Miscellaneous Non Alarmed Notifications
-- -------------------------------------------------------------
    tnMiscNonAlarmedCardNotifications OBJECT IDENTIFIER ::= { tnEquipmentNotifications 4 }
    tnV2MiscNonAlarmedCardNotifications OBJECT IDENTIFIER ::= { tnMiscNonAlarmedCardNotifications 0 }

    tnUnexpectedWaveKeySetChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2MiscNonAlarmedCardNotifications 1 }

    tnLineCardConfigurationFailedNotif NOTIFICATION-TYPE
        OBJECTS {
            tnTrapTime,
            tnTrapObjectIDType,
            tnTrapObjectID,
            tnTrapCategory,
            tnTrapDescr,
            tnTrapData,
            tnTrapServiceAffecting
        }
        STATUS         current
        DESCRIPTION    "."
        ::= { tnV2MiscNonAlarmedCardNotifications 2 }

-- -------------------------------------------------------------
-- Diagnostics Notifications
-- -------------------------------------------------------------
    tnDiagnosticsNotifications OBJECT IDENTIFIER ::= { tnNotifications 3 }
    tnV2DiagnosticsNotifications OBJECT IDENTIFIER ::= { tnDiagnosticsNotifications 0 }

--    obsolete
--    tnDiagnosticsFailureRaisedNotif  NOTIFICATION-TYPE ::= { tnV2DiagnosticsNotifications 1 }
--    tnDiagnosticsFailureClearedNotif NOTIFICATION-TYPE ::= { tnV2DiagnosticsNotifications 2 }

-- -------------------------------------------------------------
-- Services Notifications
-- -------------------------------------------------------------
    tnServicesNotifications OBJECT IDENTIFIER ::= { tnNotifications 4 }

-- -------------------------------------------------------------
-- Statistics Notifications
-- -------------------------------------------------------------
    tnStatisticsNotifications OBJECT IDENTIFIER ::= { tnNotifications 5 }
    tnV2StatisticsNotifications OBJECT IDENTIFIER ::= { tnStatisticsNotifications 0 }

--    obsolete
--    tnWarningTCANotif  NOTIFICATION-TYPE ::= { tnV2StatisticsNotifications 1 }
--    tnMinorTCANotif    NOTIFICATION-TYPE ::= { tnV2StatisticsNotifications 2 }
--    tnMajorTCANotif    NOTIFICATION-TYPE ::= { tnV2StatisticsNotifications 3 }
--    tnCriticalTCANotif NOTIFICATION-TYPE ::= { tnV2StatisticsNotifications 4 }

    tnTCANotif NOTIFICATION-TYPE
        OBJECTS {
            tnTrapTime,
            tnTrapObjectIDType,
            tnTrapObjectID,
            tnTrapCategory,
            tnTrapDescr,
            tnTrapData
        }
        STATUS         current
        DESCRIPTION    "."
        ::= { tnV2StatisticsNotifications 5 }

    tnPmBaselineNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2StatisticsNotifications 6 }

-- -------------------------------------------------------------
-- Software Downloading Notifications
-- -------------------------------------------------------------
    tnSwdlNotifications OBJECT IDENTIFIER ::= { tnNotifications 6 }
    tnV2SwdlNotifications OBJECT IDENTIFIER ::= { tnSwdlNotifications 0 }

--    obsolete
--    tnSoftwareMismatchRaisedNotif  NOTIFICATION-TYPE ::= { tnV2SwdlNotifications 1 }
--    tnSoftwareMismatchClearedNotif NOTIFICATION-TYPE ::= { tnV2SwdlNotifications 2 }

    tnSoftwareUpgradeInProgressRaisedNotif NOTIFICATION-TYPE
        OBJECTS {
            tnTrapTime,
            tnTrapObjectIDType,
            tnTrapObjectID,
            tnTrapCategory,
            tnTrapDescr,
            tnTrapServiceAffecting,
            tnTrapEntityType,
            tnTrapCondition
        }
        STATUS         current
        DESCRIPTION    "A software upgrade is running on the node."
        ::= { tnV2SwdlNotifications 3 }

    tnSoftwareUpgradeInProgressClearedNotif NOTIFICATION-TYPE
        OBJECTS {
            tnTrapTime,
            tnTrapObjectIDType,
            tnTrapObjectID,
            tnTrapCategory,
            tnTrapDescr,
            tnTrapServiceAffecting,
            tnTrapEntityType,
            tnTrapCondition
        }
        STATUS         current
        DESCRIPTION    "A software upgrade is no longer running on the
                        node."
        ::= { tnV2SwdlNotifications 4 }

    tnSoftwareUpgradeFailureRaisedNotif NOTIFICATION-TYPE
        OBJECTS {
            tnTrapTime,
            tnTrapObjectIDType,
            tnTrapObjectID,
            tnTrapCategory,
            tnTrapDescr,
            tnTrapServiceAffecting,
            tnTrapEntityType,
            tnTrapCondition
        }
        STATUS         current
        DESCRIPTION    "A software upgrade has failed on the node."
        ::= { tnV2SwdlNotifications 5 }

    tnSoftwareUpgradeFailureClearedNotif NOTIFICATION-TYPE
        OBJECTS {
            tnTrapTime,
            tnTrapObjectIDType,
            tnTrapObjectID,
            tnTrapCategory,
            tnTrapDescr,
            tnTrapServiceAffecting,
            tnTrapEntityType,
            tnTrapCondition
        }
        STATUS         current
        DESCRIPTION    "A software upgrade failure condition has been
                        cleared on the node."
        ::= { tnV2SwdlNotifications 6 }

    tnSoftwareNotCommittedRaisedNotif NOTIFICATION-TYPE
        OBJECTS {
            tnTrapTime,
            tnTrapObjectIDType,
            tnTrapObjectID,
            tnTrapCategory,
            tnTrapDescr,
            tnTrapServiceAffecting,
            tnTrapEntityType,
            tnTrapCondition
        }
        STATUS         current
        DESCRIPTION    "The NE software is not committed."
        ::= { tnV2SwdlNotifications 7 }

    tnSoftwareNotCommittedClearedNotif NOTIFICATION-TYPE
        OBJECTS {
            tnTrapTime,
            tnTrapObjectIDType,
            tnTrapObjectID,
            tnTrapCategory,
            tnTrapDescr,
            tnTrapServiceAffecting,
            tnTrapEntityType,
            tnTrapCondition
        }
        STATUS         current
        DESCRIPTION    "The NE software has been committed."
        ::= { tnV2SwdlNotifications 8 }

-- -------------------------------------------------------------
-- Alarm Notifications Release 2
-- -------------------------------------------------------------
    tnAlarmNotificationsRel2 OBJECT IDENTIFIER ::= { tnNotificationsRel2 1 }
    tnV2AlarmNotificationsRel2 OBJECT IDENTIFIER ::= { tnAlarmNotificationsRel2 0 }

--    obsolete
--    tnCardUpgradeFailureRaisedNotif  NOTIFICATION-TYPE ::= { tnV2AlarmNotificationsRel2 1 }
--    tnCardUpgradeFailureClearedNotif NOTIFICATION-TYPE ::= { tnV2AlarmNotificationsRel2 2 }

    tnCardInitializingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3 }

    tnCardInitializingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 4 }

    tnLossOfFrameRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 5 }

    tnLossOfFrameClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 6 }

--    obsolete
--    tnSfpFailureRaisedNotif         NOTIFICATION-TYPE ::= { tnV2AlarmNotificationsRel2 7 }
--    tnSfpFailureClearedNotif        NOTIFICATION-TYPE ::= { tnV2AlarmNotificationsRel2 8 }
--    tnPowerUnmeasurableRaisedNotif  NOTIFICATION-TYPE ::= { tnV2AlarmNotificationsRel2 9 }
--    tnPowerUnmeasurableClearedNotif NOTIFICATION-TYPE ::= { tnV2AlarmNotificationsRel2 10 }

    tnChannelCollisionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 11 }

    tnChannelCollisionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 12 }

    tnWavelengthTrackerFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 13 }

    tnWavelengthTrackerFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 14 }

    tnPortFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 15 }

    tnPortFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 16 }

    tnPortTransmissionDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 17 }

    tnPortTransmissionDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 18 }

--    obsolete
--    tnAmpInputTooLowRaisedNotif   NOTIFICATION-TYPE ::= { tnV2AlarmNotificationsRel2 19 }
--    tnAmpInputTooLowClearedNotif  NOTIFICATION-TYPE ::= { tnV2AlarmNotificationsRel2 20 }
--    tnAmpInputTooHighRaisedNotif  NOTIFICATION-TYPE ::= { tnV2AlarmNotificationsRel2 21 }
--    tnAmpInputTooHighClearedNotif NOTIFICATION-TYPE ::= { tnV2AlarmNotificationsRel2 22 }

    tnAmpGainTooLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 23 }

    tnAmpGainTooLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 24 }

    tnAmpGainTooHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 25 }

    tnAmpGainTooHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 26 }

    tnAmpOutputPowerUnachievableRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 27 }

    tnAmpOutputPowerUnachievableClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 28 }

--    obsolete
--    tnAmpShutdownFailureOpticalPowerOverloadRaisedNotif  NOTIFICATION-TYPE ::= { tnV2AlarmNotificationsRel2 29 }
--    tnAmpShutdownFailureOpticalPowerOverloadClearedNotif NOTIFICATION-TYPE ::= { tnV2AlarmNotificationsRel2 30 }

    tnChannelSwitchingFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 31 }

    tnChannelSwitchingFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 32 }

--    obsolete
--    tnOpticalPowerFluctuationRaisedNotif     NOTIFICATION-TYPE ::= { tnV2AlarmNotificationsRel2 33 }
--    tnOpticalPowerFluctuationClearedNotif    NOTIFICATION-TYPE ::= { tnV2AlarmNotificationsRel2 34 }
--    tnOpticsAboveOperationalTempRaisedNotif  NOTIFICATION-TYPE ::= { tnV2AlarmNotificationsRel2 35 }
--    tnOpticsAboveOperationalTempClearedNotif NOTIFICATION-TYPE ::= { tnV2AlarmNotificationsRel2 36 }

    tnLocalFaultRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 37 }

    tnLocalFaultClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 38 }

--    obsolete
--    tnWavelengthTrackerUnmanageableRaisedNotif  NOTIFICATION-TYPE ::= { tnV2AlarmNotificationsRel2 39 }
--    tnWavelengthTrackerUnmanageableClearedNotif NOTIFICATION-TYPE ::= { tnV2AlarmNotificationsRel2 40 }

    tnBreaker1BatteryFeedDownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 41 }

    tnBreaker1BatteryFeedDownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 42 }

--    obsolete
--    tnBreaker1TrippedRaisedNotif           NOTIFICATION-TYPE ::= { tnV2AlarmNotificationsRel2 43 }
--    tnBreaker1TrippedClearedNotif          NOTIFICATION-TYPE ::= { tnV2AlarmNotificationsRel2 44 }
--    tnBreaker1AlarmOverCurrentRaisedNotif  NOTIFICATION-TYPE ::= { tnV2AlarmNotificationsRel2 45 }
--    tnBreaker1AlarmOverCurrentClearedNotif NOTIFICATION-TYPE ::= { tnV2AlarmNotificationsRel2 46 }
--    tnBreaker1FanOverCurrentRaisedNotif    NOTIFICATION-TYPE ::= { tnV2AlarmNotificationsRel2 47 }
--    tnBreaker1FanOverCurrentClearedNotif   NOTIFICATION-TYPE ::= { tnV2AlarmNotificationsRel2 48 }

    tnBreaker2BatteryFeedDownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 49 }

    tnBreaker2BatteryFeedDownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 50 }

--    obsolete
--    tnBreaker2TrippedRaisedNotif           NOTIFICATION-TYPE ::= { tnV2AlarmNotificationsRel2 51 }
--    tnBreaker2TrippedClearedNotif          NOTIFICATION-TYPE ::= { tnV2AlarmNotificationsRel2 52 }
--    tnBreaker2AlarmOverCurrentRaisedNotif  NOTIFICATION-TYPE ::= { tnV2AlarmNotificationsRel2 53 }
--    tnBreaker2AlarmOverCurrentClearedNotif NOTIFICATION-TYPE ::= { tnV2AlarmNotificationsRel2 54 }
--    tnBreaker2FanOverCurrentRaisedNotif    NOTIFICATION-TYPE ::= { tnV2AlarmNotificationsRel2 55 }
--    tnBreaker2FanOverCurrentClearedNotif   NOTIFICATION-TYPE ::= { tnV2AlarmNotificationsRel2 56 }
--    tnAutoPowerMgmtDisabledRaisedNotif     NOTIFICATION-TYPE ::= { tnV2AlarmNotificationsRel2 57 }
--    tnAutoPowerMgmtDisabledClearedNotif    NOTIFICATION-TYPE ::= { tnV2AlarmNotificationsRel2 58 }

    tnUnknownWaveKeyForConnectionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 59 }

    tnUnknownWaveKeyForConnectionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 60 }

--    obsolete
--    tnInvalidTopologyForConnectionRaisedNotif  NOTIFICATION-TYPE ::= { tnV2AlarmNotificationsRel2 61 }
--    tnInvalidTopologyForConnectionClearedNotif NOTIFICATION-TYPE ::= { tnV2AlarmNotificationsRel2 62 }
--    tnManualOverrideOfConnectionRaisedNotif    NOTIFICATION-TYPE ::= { tnV2AlarmNotificationsRel2 63 }
--    tnManualOverrideOfConnectionClearedNotif   NOTIFICATION-TYPE ::= { tnV2AlarmNotificationsRel2 64 }
--    tnLostRedundantLineReferenceRaisedNotif    NOTIFICATION-TYPE ::= { tnV2AlarmNotificationsRel2 65 }
--    tnLostRedundantLineReferenceClearedNotif   NOTIFICATION-TYPE ::= { tnV2AlarmNotificationsRel2 66 }
--    tnLostRedundantBITSReferenceRaisedNotif    NOTIFICATION-TYPE ::= { tnV2AlarmNotificationsRel2 67 }
--    tnLostRedundantBITSReferenceClearedNotif   NOTIFICATION-TYPE ::= { tnV2AlarmNotificationsRel2 68 }
--    tnLostBothLineReferencesRaisedNotif        NOTIFICATION-TYPE ::= { tnV2AlarmNotificationsRel2 69 }
--    tnLostBothLineReferencesClearedNotif       NOTIFICATION-TYPE ::= { tnV2AlarmNotificationsRel2 70 }
--    tnLostBothBITSReferencesRaisedNotif        NOTIFICATION-TYPE ::= { tnV2AlarmNotificationsRel2 71 }
--    tnLostBothBITSReferencesClearedNotif       NOTIFICATION-TYPE ::= { tnV2AlarmNotificationsRel2 72 }

    tnDuplicateWaveKeyRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 73 }

    tnDuplicateWaveKeyClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 74 }

    tnWaveKeyOverlapRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 75 }

    tnWaveKeyOverlapClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 76 }

    tnDuplicateTrailNameRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 77 }

    tnDuplicateTrailNameClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 78 }

--    obsolete
--    tnSubtendedShelfLinkFailureRaisedNotif  NOTIFICATION-TYPE ::= { tnV2AlarmNotificationsRel2 79 }
--    tnSubtendedShelfLinkFailureClearedNotif NOTIFICATION-TYPE ::= { tnV2AlarmNotificationsRel2 80 }

    tnTunableLaserNotProvisionedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 81 }

    tnTunableLaserNotProvisionedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 82 }

    tnSystemTimingMisconfigurationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 83 }

    tnSystemTimingMisconfigurationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 84 }

--    obsolete
--    tnSystemTimingSynchronizationUnitFailureRaisedNotif  NOTIFICATION-TYPE ::= { tnV2AlarmNotificationsRel2 85 }
--    tnSystemTimingSynchronizationUnitFailureClearedNotif NOTIFICATION-TYPE ::= { tnV2AlarmNotificationsRel2 86 }
--    tnSystemTimingInputControlUnitFailureRaisedNotif     NOTIFICATION-TYPE ::= { tnV2AlarmNotificationsRel2 87 }
--    tnSystemTimingInputControlUnitFailureClearedNotif    NOTIFICATION-TYPE ::= { tnV2AlarmNotificationsRel2 88 }
--    tnSystemTimingNotSupportedRaisedNotif                NOTIFICATION-TYPE ::= { tnV2AlarmNotificationsRel2 89 }
--    tnSystemTimingNotSupportedClearedNotif               NOTIFICATION-TYPE ::= { tnV2AlarmNotificationsRel2 90 }
--    tnBITSAModuleMissingRaisedNotif                      NOTIFICATION-TYPE ::= { tnV2AlarmNotificationsRel2 91 }
--    tnBITSAModuleMissingClearedNotif                     NOTIFICATION-TYPE ::= { tnV2AlarmNotificationsRel2 92 }
--    tnBITSBModuleMissingRaisedNotif                      NOTIFICATION-TYPE ::= { tnV2AlarmNotificationsRel2 93 }
--    tnBITSBModuleMissingClearedNotif                     NOTIFICATION-TYPE ::= { tnV2AlarmNotificationsRel2 94 }

    tnSubtendedShelfIdAssignmentFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 95 }

    tnSubtendedShelfIdAssignmentFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 96 }

--    obsolete
--    tnSystemTimingEqptMismatchOnCCsRaisedNotif        NOTIFICATION-TYPE ::= { tnV2AlarmNotificationsRel2 97 }
--    tnSystemTimingEqptMismatchOnCCsClearedNotif       NOTIFICATION-TYPE ::= { tnV2AlarmNotificationsRel2 98 }
--    tnPowerMgmtEgressAdjustmentInProgressRaisedNotif  NOTIFICATION-TYPE ::= { tnV2AlarmNotificationsRel2 99 }
--    tnPowerMgmtEgressAdjustmentInProgressClearedNotif NOTIFICATION-TYPE ::= { tnV2AlarmNotificationsRel2 100 }

    tnCBandLossOfSignalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 101 }

    tnCBandLossOfSignalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 102 }

    tnControlCardRedundancyCompromisedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 103 }

    tnControlCardRedundancyCompromisedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 104 }

--    obsolete
--    tnAutoLaserOffDueToNearEndFaultRaisedNotif  NOTIFICATION-TYPE ::= { tnV2AlarmNotificationsRel2 105 }
--    tnAutoLaserOffDueToNearEndFaultClearedNotif NOTIFICATION-TYPE ::= { tnV2AlarmNotificationsRel2 106 }
--    tnAutoLaserOffDueToFarEndFaultRaisedNotif   NOTIFICATION-TYPE ::= { tnV2AlarmNotificationsRel2 107 }
--    tnAutoLaserOffDueToFarEndFaultClearedNotif  NOTIFICATION-TYPE ::= { tnV2AlarmNotificationsRel2 108 }
--    tnFarEndFaultRaisedNotif                    NOTIFICATION-TYPE ::= { tnV2AlarmNotificationsRel2 109 }
--    tnFarEndFaultClearedNotif                   NOTIFICATION-TYPE ::= { tnV2AlarmNotificationsRel2 110 }
--    tnAislInsertedDueToNearEndFaultRaisedNotif  NOTIFICATION-TYPE ::= { tnV2AlarmNotificationsRel2 111 }
--    tnAislInsertedDueToNearEndFaultClearedNotif NOTIFICATION-TYPE ::= { tnV2AlarmNotificationsRel2 112 }
--    tnAislInsertedDueToFarEndFaultRaisedNotif   NOTIFICATION-TYPE ::= { tnV2AlarmNotificationsRel2 113 }
--    tnAislInsertedDueToFarEndFaultClearedNotif  NOTIFICATION-TYPE ::= { tnV2AlarmNotificationsRel2 114 }
--    tnServiceRequiredRaisedNotif                NOTIFICATION-TYPE ::= { tnV2AlarmNotificationsRel2 115 }
--    tnServiceRequiredClearedNotif               NOTIFICATION-TYPE ::= { tnV2AlarmNotificationsRel2 116 }

    tnSystemTimingLossOfBothClocksRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 117 }

    tnSystemTimingLossOfBothClocksClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 118 }

    tnSystemTimingLossOfClockRedundancyRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 119 }

    tnSystemTimingLossOfClockRedundancyClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 120 }

--    obsolete
--    tnSystemTimingClockModeChangedFromNormalRaisedNotif     NOTIFICATION-TYPE ::= { tnV2AlarmNotificationsRel2 121 }
--    tnSystemTimingClockModeChangedFromNormalClearedNotif    NOTIFICATION-TYPE ::= { tnV2AlarmNotificationsRel2 122 }
--    tnSystemTimingModeSecondaryRaisedNotif                  NOTIFICATION-TYPE ::= { tnV2AlarmNotificationsRel2 123 }
--    tnSystemTimingModeSecondaryClearedNotif                 NOTIFICATION-TYPE ::= { tnV2AlarmNotificationsRel2 124 }
--    tnSwitchToSecondaryReferenceInRevertiveModeRaisedNotif  NOTIFICATION-TYPE ::= { tnV2AlarmNotificationsRel2 125 }
--    tnSwitchToSecondaryReferenceInRevertiveModeClearedNotif NOTIFICATION-TYPE ::= { tnV2AlarmNotificationsRel2 126 }
--    tnSystemTimingForcedStateRaisedNotif                    NOTIFICATION-TYPE ::= { tnV2AlarmNotificationsRel2 127 }
--    tnSystemTimingForcedStateClearedNotif                   NOTIFICATION-TYPE ::= { tnV2AlarmNotificationsRel2 128 }
--    tnHardDriveReadFailureRaisedNotif                       NOTIFICATION-TYPE ::= { tnV2AlarmNotificationsRel2 129 }
--    tnHardDriveReadFailureClearedNotif                      NOTIFICATION-TYPE ::= { tnV2AlarmNotificationsRel2 130 }
--    tnHardDriveWriteFailureRaisedNotif                      NOTIFICATION-TYPE ::= { tnV2AlarmNotificationsRel2 131 }
--    tnHardDriveWriteFailureClearedNotif                     NOTIFICATION-TYPE ::= { tnV2AlarmNotificationsRel2 132 }

    tnLineFacilityLoopbackActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 133 }

    tnLineFacilityLoopbackActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 134 }

    tnDiagnosticTerminalLoopbackActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 135 }

    tnDiagnosticTerminalLoopbackActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 136 }

    tnOneTimingModuleFailedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 137 }

    tnOneTimingModuleFailedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 138 }

    tnBothTimingModulesFailedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 139 }

    tnBothTimingModulesFailedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 140 }

    tnApsWorkingForceSwitchedToProtectRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 141 }

    tnApsWorkingForceSwitchedToProtectClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 142 }

    tnApsWorkingManualSwitchedToProtectRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 143 }

    tnApsWorkingManualSwitchedToProtectClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 144 }

    tnApsWorkingForceSwitchedBackToWorkingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 145 }

    tnApsWorkingForceSwitchedBackToWorkingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 146 }

    tnApsWorkingManualSwitchedBackToWorkingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 147 }

    tnApsWorkingManualSwitchedBackToWorkingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 148 }

    tnApsLockoutOfProtectionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 149 }

    tnApsLockoutOfProtectionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 150 }

--    obsolete
--    tnPowerHigherThanPlannedRaisedNotif  NOTIFICATION-TYPE ::= { tnV2AlarmNotificationsRel2 151 }
--    tnPowerHigherThanPlannedClearedNotif NOTIFICATION-TYPE ::= { tnV2AlarmNotificationsRel2 152 }
--    tnPowerLowerThanPlannedRaisedNotif   NOTIFICATION-TYPE ::= { tnV2AlarmNotificationsRel2 153 }
--    tnPowerLowerThanPlannedClearedNotif  NOTIFICATION-TYPE ::= { tnV2AlarmNotificationsRel2 154 }

    tnLostRedundantTimingReferenceRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 155 }

    tnLostRedundantTimingReferenceClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 156 }

    tnLostBothTimingReferencesRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 157 }

    tnLostBothTimingReferencesClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 158 }

    tnLossOfPrimaryLineTimingClockRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 159 }

    tnLossOfPrimaryLineTimingClockClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 160 }

    tnLossOfSecondaryLineTimingClockRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 161 }

    tnLossOfSecondaryLineTimingClockClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 162 }

--    obsolete
--    tnLineTimingLossOfBothClocksRaisedNotif                    NOTIFICATION-TYPE ::= { tnV2AlarmNotificationsRel2 163 }
--    tnLineTimingLossOfBothClocksClearedNotif                   NOTIFICATION-TYPE ::= { tnV2AlarmNotificationsRel2 164 }
--    tnLineTimingLossOfClockRedundancyClockAMissingRaisedNotif  NOTIFICATION-TYPE ::= { tnV2AlarmNotificationsRel2 165 }
--    tnLineTimingLossOfClockRedundancyClockAMissingClearedNotif NOTIFICATION-TYPE ::= { tnV2AlarmNotificationsRel2 166 }
--    tnLineTimingLossOfClockRedundancyClockBMissingRaisedNotif  NOTIFICATION-TYPE ::= { tnV2AlarmNotificationsRel2 167 }
--    tnLineTimingLossOfClockRedundancyClockBMissingClearedNotif NOTIFICATION-TYPE ::= { tnV2AlarmNotificationsRel2 168 }

    tnSonetLossOfPointerRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 169 }

    tnSonetLossOfPointerClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 170 }

    tnLossOfSyncRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 171 }

    tnLossOfSyncClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 172 }

--    obsolete
--    tnEncapsulationMismatchRaisedNotif  NOTIFICATION-TYPE ::= { tnV2AlarmNotificationsRel2 173 }
--    tnEncapsulationMismatchClearedNotif NOTIFICATION-TYPE ::= { tnV2AlarmNotificationsRel2 174 }
--    tnUpstreamFaultDetectedRaisedNotif  NOTIFICATION-TYPE ::= { tnV2AlarmNotificationsRel2 175 }
--    tnUpstreamFaultDetectedClearedNotif NOTIFICATION-TYPE ::= { tnV2AlarmNotificationsRel2 176 }

    tnAlarmReportingControlInhibitedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 177 }

    tnAlarmReportingControlInhibitedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 178 }

--    obsolete
--    tnServerSignalFailRaisedNotif                           NOTIFICATION-TYPE ::= { tnV2AlarmNotificationsRel2 179 }
--    tnServerSignalFailClearedNotif                          NOTIFICATION-TYPE ::= { tnV2AlarmNotificationsRel2 180 }
--    tnLinkDownInactiveCommunicationRaisedNotif              NOTIFICATION-TYPE ::= { tnV2AlarmNotificationsRel2 181 }
--    tnLinkDownInactiveCommunicationClearedNotif             NOTIFICATION-TYPE ::= { tnV2AlarmNotificationsRel2 182 }
--    tnMaintIdleSignalInsertedDueToUpstreamFaultRaisedNotif  NOTIFICATION-TYPE ::= { tnV2AlarmNotificationsRel2 183 }
--    tnMaintIdleSignalInsertedDueToUpstreamFaultClearedNotif NOTIFICATION-TYPE ::= { tnV2AlarmNotificationsRel2 184 }

    tnAutoLaserOffDueToUpstreamFaultRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 185 }

    tnAutoLaserOffDueToUpstreamFaultClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 186 }

--    obsolete
--    tnSystemTimingInFreerunRaisedNotif            NOTIFICATION-TYPE ::= { tnV2AlarmNotificationsRel2 187 }
--    tnSystemTimingInFreerunClearedNotif           NOTIFICATION-TYPE ::= { tnV2AlarmNotificationsRel2 188 }
--    tnSystemTimingInHoldoverRaisedNotif           NOTIFICATION-TYPE ::= { tnV2AlarmNotificationsRel2 189 }
--    tnSystemTimingInHoldoverClearedNotif          NOTIFICATION-TYPE ::= { tnV2AlarmNotificationsRel2 190 }
--    tnPortCommunicationsFailureRaisedNotif        NOTIFICATION-TYPE ::= { tnV2AlarmNotificationsRel2 191 }
--    tnPortCommunicationsFailureClearedNotif       NOTIFICATION-TYPE ::= { tnV2AlarmNotificationsRel2 192 }
--    tnLineTimingLossOfClockRedundancyRaisedNotif  NOTIFICATION-TYPE ::= { tnV2AlarmNotificationsRel2 193 }
--    tnLineTimingLossOfClockRedundancyClearedNotif NOTIFICATION-TYPE ::= { tnV2AlarmNotificationsRel2 194 }

    tnVcatLossOfAlignmentRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 195 }

    tnVcatLossOfAlignmentClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 196 }

--    obsolete
--    tnVcatMappingErrorRaisedNotif                 NOTIFICATION-TYPE ::= { tnV2AlarmNotificationsRel2 197 }
--    tnVcatMappingErrorClearedNotif                NOTIFICATION-TYPE ::= { tnV2AlarmNotificationsRel2 198 }
--    tnSonetPathPayloadDefectIndicatorRaisedNotif  NOTIFICATION-TYPE ::= { tnV2AlarmNotificationsRel2 199 }
--    tnSonetPathPayloadDefectIndicatorClearedNotif NOTIFICATION-TYPE ::= { tnV2AlarmNotificationsRel2 200 }

    tnOchFdiRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 201 }

    tnOchFdiClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 202 }

--    obsolete
--    tnOchPowerUnstableForCrossConnectionRaisedNotif  NOTIFICATION-TYPE ::= { tnV2AlarmNotificationsRel2 203 }
--    tnOchPowerUnstableForCrossConnectionClearedNotif NOTIFICATION-TYPE ::= { tnV2AlarmNotificationsRel2 204 }

    tnSoftwareVersionMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 205 }

    tnSoftwareVersionMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 206 }

    tnCardProvisioningFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 207 }

    tnCardProvisioningFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 208 }

    tnCardDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 209 }

    tnCardDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 210 }

    tnOpticsModuleUnknownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 211 }

    tnOpticsModuleUnknownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 212 }

--    obsolete
--    tnOpticsModuleUnsupportedRaisedNotif  NOTIFICATION-TYPE ::= { tnV2AlarmNotificationsRel2 213 }
--    tnOpticsModuleUnsupportedClearedNotif NOTIFICATION-TYPE ::= { tnV2AlarmNotificationsRel2 214 }

    tnPowerAdjustFailedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 215 }

    tnPowerAdjustFailedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 216 }

    tnPowerAdjustRequiredRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 217 }

    tnPowerAdjustRequiredClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 218 }

    tnPortDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 219 }

    tnPortDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 220 }

--    obsolete
--    tnAisLineInsertedDueToUpstreamConditionRaisedNotif         NOTIFICATION-TYPE ::= { tnV2AlarmNotificationsRel2 221 }
--    tnAisLineInsertedDueToUpstreamConditionClearedNotif        NOTIFICATION-TYPE ::= { tnV2AlarmNotificationsRel2 222 }
--    tnDataStreamHasSurpassedSignalFailureThresholdRaisedNotif  NOTIFICATION-TYPE ::= { tnV2AlarmNotificationsRel2 223 }
--    tnDataStreamHasSurpassedSignalFailureThresholdClearedNotif NOTIFICATION-TYPE ::= { tnV2AlarmNotificationsRel2 224 }

    tnEncapsulationFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 225 }

    tnEncapsulationFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 226 }

    tnTrailTraceIdentifierMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 227 }

    tnTrailTraceIdentifierMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 228 }

    tnPayloadTypeMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 229 }

    tnPayloadTypeMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 230 }

    tnPowerMgmtSuspendedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 231 }

    tnPowerMgmtSuspendedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 232 }

--    obsolete
--    tnManualSyncSwitchToPrimaryReferenceRaisedNotif    NOTIFICATION-TYPE ::= { tnV2AlarmNotificationsRel2 233 }
--    tnManualSyncSwitchToPrimaryReferenceClearedNotif   NOTIFICATION-TYPE ::= { tnV2AlarmNotificationsRel2 234 }
--    tnManualSyncSwitchToSecondaryReferenceRaisedNotif  NOTIFICATION-TYPE ::= { tnV2AlarmNotificationsRel2 235 }
--    tnManualSyncSwitchToSecondaryReferenceClearedNotif NOTIFICATION-TYPE ::= { tnV2AlarmNotificationsRel2 236 }

    tnWavelengthTrackerEncodeDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 237 }

    tnWavelengthTrackerEncodeDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 238 }

    tnAddPowerControlFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 239 }

    tnAddPowerControlFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 240 }

--    obsolete
--    tnVcatMfiErrorRaisedNotif                                      NOTIFICATION-TYPE ::= { tnV2AlarmNotificationsRel2 241 }
--    tnVcatMfiErrorClearedNotif                                     NOTIFICATION-TYPE ::= { tnV2AlarmNotificationsRel2 242 }
--    tnSystemTimingInputControlUnitCommunicationFailureRaisedNotif  NOTIFICATION-TYPE ::= { tnV2AlarmNotificationsRel2 243 }
--    tnSystemTimingInputControlUnitCommunicationFailureClearedNotif NOTIFICATION-TYPE ::= { tnV2AlarmNotificationsRel2 244 }
--    tnLinkDownMateCommunicationsRaisedNotif                        NOTIFICATION-TYPE ::= { tnV2AlarmNotificationsRel2 245 }
--    tnLinkDownMateCommunicationsClearedNotif                       NOTIFICATION-TYPE ::= { tnV2AlarmNotificationsRel2 246 }

    tnSystemTimingCardMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 247 }

    tnSystemTimingCardMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 248 }

--    obsolete
--    tnSystemTimingInputControlUnitLoadRequiresUpgradingRaisedNotif  NOTIFICATION-TYPE ::= { tnV2AlarmNotificationsRel2 249 }
--    tnSystemTimingInputControlUnitLoadRequiresUpgradingClearedNotif NOTIFICATION-TYPE ::= { tnV2AlarmNotificationsRel2 250 }

    tnOchPdiRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 251 }

    tnOchPdiClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 252 }

    tnPowerAdjustLossMarginExceededRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 253 }

    tnPowerAdjustLossMarginExceededClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 254 }

    tnTransmitLaserOffRxFaultDuringLineLoopbackRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 255 }

    tnTransmitLaserOffRxFaultDuringLineLoopbackClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 256 }

--    obsolete
--    tnInconsistentBackplaneSignalsRaisedNotif          NOTIFICATION-TYPE ::= { tnV2AlarmNotificationsRel2 257 }
--    tnInconsistentBackplaneSignalsClearedNotif         NOTIFICATION-TYPE ::= { tnV2AlarmNotificationsRel2 258 }
--    tnSignalingLinkCongestionRaisedNotif               NOTIFICATION-TYPE ::= { tnV2AlarmNotificationsRel2 259 }
--    tnSignalingLinkCongestionClearedNotif              NOTIFICATION-TYPE ::= { tnV2AlarmNotificationsRel2 260 }
--    tnAutomaticPmReportingControlInhibitedRaisedNotif  NOTIFICATION-TYPE ::= { tnV2AlarmNotificationsRel2 261 }
--    tnAutomaticPmReportingControlInhibitedClearedNotif NOTIFICATION-TYPE ::= { tnV2AlarmNotificationsRel2 262 }

    tnInMaintenanceRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 263 }

    tnInMaintenanceClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 264 }

    tnOtuAisRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 265 }

    tnOtuAisClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 266 }

--    obsolete
--    tnBITSAModuleMismatchRaisedNotif  NOTIFICATION-TYPE ::= { tnV2AlarmNotificationsRel2 267 }
--    tnBITSAModuleMismatchClearedNotif NOTIFICATION-TYPE ::= { tnV2AlarmNotificationsRel2 268 }
--    tnBITSBModuleMismatchRaisedNotif  NOTIFICATION-TYPE ::= { tnV2AlarmNotificationsRel2 269 }
--    tnBITSBModuleMismatchClearedNotif NOTIFICATION-TYPE ::= { tnV2AlarmNotificationsRel2 270 }

    tnLossTooHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 271 }

    tnLossTooHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 272 }

    tnLossTooLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 273 }

    tnLossTooLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 274 }

    tnDwLossOfMultiFrameRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 275 }

    tnDwLossOfMultiFrameClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 276 }

    tnTopologyInvalidRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 277 }

    tnTopologyInvalidClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 278 }

    tnCardDegradeMonitorFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 279 }

    tnCardDegradeMonitorFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 280 }

    tnShelfMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 281 }

    tnShelfMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 282 }

    tnUserEqptMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 283 }

    tnUserEqptMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 284 }

    tnEnvInput1ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 285 }

    tnEnvInput1ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 286 }

    tnEnvInput2ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 287 }

    tnEnvInput2ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 288 }

    tnLosDcmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 289 }

    tnLosDcmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 290 }

    tnIncomingSupvyLosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 291 }

    tnIncomingSupvyLosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 292 }

    tnIncomingSupvyLofRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 293 }

    tnIncomingSupvyLofClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 294 }

    tnSupvySignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 295 }

    tnSupvySignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 296 }

    tnExcessiveCurrentLoadRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 297 }

    tnExcessiveCurrentLoadClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 298 }

    tnFarEndPortMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 299 }

    tnFarEndPortMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 300 }

    tnServerSignalFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 301 }

    tnServerSignalFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 302 }

    tnLockedIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 303 }

    tnLockedIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 304 }

    tnOpenConnectionIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 305 }

    tnOpenConnectionIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 306 }

    tnBackwardDefectIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 307 }

    tnBackwardDefectIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 308 }

    tnOchLosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 309 }

    tnOchLosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 310 }

    tnLossOfFrameEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 311 }

    tnLossOfFrameEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 312 }

    tnVcgServerSignalFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 313 }

    tnVcgServerSignalFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 314 }

    tnLossOfFrameDelineationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 315 }

    tnLossOfFrameDelineationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 316 }

    tnUserPayloadMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 317 }

    tnUserPayloadMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 318 }

    tnFarEndLossOfSignalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 319 }

    tnFarEndLossOfSignalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 320 }

    tnFarEndLossOfSynchronizationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 321 }

    tnFarEndLossOfSynchronizationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 322 }

    tnFarEndLfiRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 323 }

    tnFarEndLfiClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 324 }

    tnFarEndRfiRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 325 }

    tnFarEndRfiClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 326 }

    tnHighBerRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 327 }

    tnHighBerClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 328 }

    tnLossOfSynchronizationEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 329 }

    tnLossOfSynchronizationEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 330 }

    tnLfiEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 331 }

    tnLfiEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 332 }

    tnRfiEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 333 }

    tnRfiEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 334 }

--    obsolete
--    tnSystemInitializationInProgressRaisedNotif  NOTIFICATION-TYPE ::= { tnV2AlarmNotificationsRel2 335 }
--    tnSystemInitializationInProgressClearedNotif NOTIFICATION-TYPE ::= { tnV2AlarmNotificationsRel2 336 }

    tnDbFailureLocalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 337 }

    tnDbFailureLocalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 338 }

    tnDbFailureTransportRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 339 }

    tnDbFailureTransportClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 340 }

--    obsolete
--    tnInputVoltageDefectRaisedNotif  NOTIFICATION-TYPE ::= { tnV2AlarmNotificationsRel2 341 }
--    tnInputVoltageDefectClearedNotif NOTIFICATION-TYPE ::= { tnV2AlarmNotificationsRel2 342 }

    tnApsSwitchedToWorkRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 343 }

    tnApsSwitchedToWorkClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 344 }

    tnSignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 345 }

    tnSignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 346 }

--    obsolete
--    tnVtsOpenConnectionIndication1RaisedNotif   NOTIFICATION-TYPE ::= { tnV2AlarmNotificationsRel2 347 }
--    tnVtsOpenConnectionIndication1ClearedNotif  NOTIFICATION-TYPE ::= { tnV2AlarmNotificationsRel2 348 }
--    tnVtsOpenConnectionIndication2RaisedNotif   NOTIFICATION-TYPE ::= { tnV2AlarmNotificationsRel2 349 }
--    tnVtsOpenConnectionIndication2ClearedNotif  NOTIFICATION-TYPE ::= { tnV2AlarmNotificationsRel2 350 }
--    tnVtsOpenConnectionIndication3RaisedNotif   NOTIFICATION-TYPE ::= { tnV2AlarmNotificationsRel2 351 }
--    tnVtsOpenConnectionIndication3ClearedNotif  NOTIFICATION-TYPE ::= { tnV2AlarmNotificationsRel2 352 }
--    tnVtsOpenConnectionIndication4RaisedNotif   NOTIFICATION-TYPE ::= { tnV2AlarmNotificationsRel2 353 }
--    tnVtsOpenConnectionIndication4ClearedNotif  NOTIFICATION-TYPE ::= { tnV2AlarmNotificationsRel2 354 }
--    tnVtsOpenConnectionIndication5RaisedNotif   NOTIFICATION-TYPE ::= { tnV2AlarmNotificationsRel2 355 }
--    tnVtsOpenConnectionIndication5ClearedNotif  NOTIFICATION-TYPE ::= { tnV2AlarmNotificationsRel2 356 }
--    tnVtsOpenConnectionIndication6RaisedNotif   NOTIFICATION-TYPE ::= { tnV2AlarmNotificationsRel2 357 }
--    tnVtsOpenConnectionIndication6ClearedNotif  NOTIFICATION-TYPE ::= { tnV2AlarmNotificationsRel2 358 }
--    tnVtsOpenConnectionIndication7RaisedNotif   NOTIFICATION-TYPE ::= { tnV2AlarmNotificationsRel2 359 }
--    tnVtsOpenConnectionIndication7ClearedNotif  NOTIFICATION-TYPE ::= { tnV2AlarmNotificationsRel2 360 }
--    tnVtsOpenConnectionIndication8RaisedNotif   NOTIFICATION-TYPE ::= { tnV2AlarmNotificationsRel2 361 }
--    tnVtsOpenConnectionIndication8ClearedNotif  NOTIFICATION-TYPE ::= { tnV2AlarmNotificationsRel2 362 }
--    tnVtsOpenConnectionIndication9RaisedNotif   NOTIFICATION-TYPE ::= { tnV2AlarmNotificationsRel2 363 }
--    tnVtsOpenConnectionIndication9ClearedNotif  NOTIFICATION-TYPE ::= { tnV2AlarmNotificationsRel2 364 }
--    tnVtsOpenConnectionIndication10RaisedNotif  NOTIFICATION-TYPE ::= { tnV2AlarmNotificationsRel2 365 }
--    tnVtsOpenConnectionIndication10ClearedNotif NOTIFICATION-TYPE ::= { tnV2AlarmNotificationsRel2 366 }
--    tnVtsForwardDefectIndication1RaisedNotif    NOTIFICATION-TYPE ::= { tnV2AlarmNotificationsRel2 367 }
--    tnVtsForwardDefectIndication1ClearedNotif   NOTIFICATION-TYPE ::= { tnV2AlarmNotificationsRel2 368 }
--    tnVtsForwardDefectIndication2RaisedNotif    NOTIFICATION-TYPE ::= { tnV2AlarmNotificationsRel2 369 }
--    tnVtsForwardDefectIndication2ClearedNotif   NOTIFICATION-TYPE ::= { tnV2AlarmNotificationsRel2 370 }
--    tnVtsForwardDefectIndication3RaisedNotif    NOTIFICATION-TYPE ::= { tnV2AlarmNotificationsRel2 371 }
--    tnVtsForwardDefectIndication3ClearedNotif   NOTIFICATION-TYPE ::= { tnV2AlarmNotificationsRel2 372 }
--    tnVtsForwardDefectIndication4RaisedNotif    NOTIFICATION-TYPE ::= { tnV2AlarmNotificationsRel2 373 }
--    tnVtsForwardDefectIndication4ClearedNotif   NOTIFICATION-TYPE ::= { tnV2AlarmNotificationsRel2 374 }
--    tnVtsForwardDefectIndication5RaisedNotif    NOTIFICATION-TYPE ::= { tnV2AlarmNotificationsRel2 375 }
--    tnVtsForwardDefectIndication5ClearedNotif   NOTIFICATION-TYPE ::= { tnV2AlarmNotificationsRel2 376 }
--    tnVtsForwardDefectIndication6RaisedNotif    NOTIFICATION-TYPE ::= { tnV2AlarmNotificationsRel2 377 }
--    tnVtsForwardDefectIndication6ClearedNotif   NOTIFICATION-TYPE ::= { tnV2AlarmNotificationsRel2 378 }
--    tnVtsForwardDefectIndication7RaisedNotif    NOTIFICATION-TYPE ::= { tnV2AlarmNotificationsRel2 379 }
--    tnVtsForwardDefectIndication7ClearedNotif   NOTIFICATION-TYPE ::= { tnV2AlarmNotificationsRel2 380 }
--    tnVtsForwardDefectIndication8RaisedNotif    NOTIFICATION-TYPE ::= { tnV2AlarmNotificationsRel2 381 }
--    tnVtsForwardDefectIndication8ClearedNotif   NOTIFICATION-TYPE ::= { tnV2AlarmNotificationsRel2 382 }
--    tnVtsForwardDefectIndication9RaisedNotif    NOTIFICATION-TYPE ::= { tnV2AlarmNotificationsRel2 383 }
--    tnVtsForwardDefectIndication9ClearedNotif   NOTIFICATION-TYPE ::= { tnV2AlarmNotificationsRel2 384 }
--    tnVtsForwardDefectIndication10RaisedNotif   NOTIFICATION-TYPE ::= { tnV2AlarmNotificationsRel2 385 }
--    tnVtsForwardDefectIndication10ClearedNotif  NOTIFICATION-TYPE ::= { tnV2AlarmNotificationsRel2 386 }

    tnNetworkTimingProtocolOutOfSyncRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 387 }

    tnNetworkTimingProtocolOutOfSyncClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 388 }

    tnDatabaseUnsyncRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 389 }

    tnDatabaseUnsyncClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 390 }

    tnFirmwareVersionNotDefaultRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 391 }

    tnFirmwareVersionNotDefaultClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 392 }

    tnFirmwareUpgradePendingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 393 }

    tnFirmwareUpgradePendingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 394 }

    tnFirmwarePendingObsoleteRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 395 }

    tnFirmwarePendingObsoleteClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 396 }

    tnBatteryOffRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 397 }

    tnBatteryOffClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 398 }

    tnBackplaneBatteryOffRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 399 }

    tnBackplaneBatteryOffClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 400 }

    tnFpgaInitRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 401 }

    tnFpgaInitClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 402 }

    tnFpgaTimeoutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 403 }

    tnFpgaTimeoutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 404 }

    tnFpgaFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 405 }

    tnFpgaFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 406 }

    tnPwrMaxGainRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 407 }

    tnPwrMaxGainClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 408 }

    tnInvalidThresholdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 409 }

    tnInvalidThresholdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 410 }

    tnDataErrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 411 }

    tnDataErrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 412 }

    tnFarEndLosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 413 }

    tnFarEndLosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 414 }

    tnAprLineRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 415 }

    tnAprLineClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 416 }

    tnEtrMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 417 }

    tnEtrMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 418 }

    tnVtsOpenConnectionIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 419 }

    tnVtsOpenConnectionIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 420 }

    tnVtsForwardDefectIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 421 }

    tnVtsForwardDefectIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 422 }

    tnEnvInput3ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 423 }

    tnEnvInput3ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 424 }

    tnEnvInput4ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 425 }

    tnEnvInput4ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 426 }

    tnEnvInput5ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 427 }

    tnEnvInput5ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 428 }

    tnEnvInput6ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 429 }

    tnEnvInput6ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 430 }

    tnEnvInput7ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 431 }

    tnEnvInput7ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 432 }

    tnEnvInput8ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 433 }

    tnEnvInput8ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 434 }

    tnOAPumpLaserBiasCurrentHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 435 }

    tnOAPumpLaserBiasCurrentHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 436 }

    tnOAPumpLaserTempHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 437 }

    tnOAPumpLaserTempHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 438 }

    tnLaserEndOfLifeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 439 }

    tnLaserEndOfLifeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 440 }

    tnModulatorOutputPowerOutOfRangeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 441 }

    tnModulatorOutputPowerOutOfRangeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 442 }

    tnOpticalPowerReceivedOutOfRangeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 443 }

    tnOpticalPowerReceivedOutOfRangeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 444 }

    tnFecEcSignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 445 }

    tnFecEcSignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 446 }

    tnSfpTempOORRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 447 }

    tnSfpTempOORClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 448 }

    tnSfpEOLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 449 }

    tnSfpEOLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 450 }

    tnSfpTrmtPwrOORRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 451 }

    tnSfpTrmtPwrOORClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 452 }

    tnSfpReceiverPwrOORRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 453 }

    tnSfpReceiverPwrOORClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 454 }

    tnRamanSupRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 455 }

    tnRamanSupClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 456 }

    tnRcvrOptProgRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 457 }

    tnRcvrOptProgClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 458 }

    tnCardNotAllowedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 459 }

    tnCardNotAllowedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 460 }

    tnFanSpeedManuallySetMaximumRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 461 }

    tnFanSpeedManuallySetMaximumClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 462 }

--    obsolete
--    tnDegOtuRaisedNotif  NOTIFICATION-TYPE ::= { tnV2AlarmNotificationsRel2 463 }
--    tnDegOtuClearedNotif NOTIFICATION-TYPE ::= { tnV2AlarmNotificationsRel2 464 }

    tnMixedPFUsedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 465 }

    tnMixedPFUsedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 466 }

    tnTBbeOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 467 }

    tnTBbeOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 468 }

    tnTBbeRs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 469 }

    tnTBbeRs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 470 }

    tnTCv15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 471 }

    tnTCv15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 472 }

    tnTCvPcs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 473 }

    tnTCvPcs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 474 }

    tnTCvPcst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 475 }

    tnTCvPcst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 476 }

    tnTCvs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 477 }

    tnTCvs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 478 }

    tnTCvst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 479 }

    tnTCvst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 480 }

    tnTEs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 481 }

    tnTEs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 482 }

    tnTEsOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 483 }

    tnTEsOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 484 }

    tnTEsRs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 485 }

    tnTEsRs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 486 }

    tnTEsPcs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 487 }

    tnTEsPcs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 488 }

    tnTEsPcst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 489 }

    tnTEsPcst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 490 }

    tnTEss15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 491 }

    tnTEss15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 492 }

    tnTEthpkter15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 493 }

    tnTEthpkter15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 494 }

    tnTEthpktert15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 495 }

    tnTEthpktert15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 496 }

    tnTFecc15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 497 }

    tnTFecc15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 498 }

    tnTFecUbu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 499 }

    tnTFecUbu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 500 }

    tnTOprh15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 501 }

    tnTOprh15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 502 }

    tnTOprl15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 503 }

    tnTOprl15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 504 }

    tnTOpth15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 505 }

    tnTOpth15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 506 }

    tnTOptl15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 507 }

    tnTOptl15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 508 }

    tnTSefs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 509 }

    tnTSefs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 510 }

    tnTSefsPcs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 511 }

    tnTSefsPcs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 512 }

    tnTSefsPcst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 513 }

    tnTSefsPcst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 514 }

    tnTSefss15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 515 }

    tnTSefss15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 516 }

    tnTSefsst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 517 }

    tnTSefsst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 518 }

    tnTSes15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 519 }

    tnTSes15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 520 }

    tnTSesOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 521 }

    tnTSesOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 522 }

    tnTSesPcs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 523 }

    tnTSesPcs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 524 }

    tnTSesPcst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 525 }

    tnTSesPcst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 526 }

    tnTSesRs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 527 }

    tnTSesRs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 528 }

    tnTSess15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 529 }

    tnTSess15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 530 }

    tnTSesst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 531 }

    tnTSesst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 532 }

    tnTUasOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 533 }

    tnTUasOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 534 }

    tnTUasRs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 535 }

    tnTUasRs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 536 }

    tnTEsst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 537 }

    tnTEsst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 538 }

    tnTBbeOdu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 539 }

    tnTBbeOdu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 540 }

    tnTEsOdu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 541 }

    tnTEsOdu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 542 }

    tnTSesOdu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 543 }

    tnTSesOdu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 544 }

    tnTUasOdu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 545 }

    tnTUasOdu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 546 }

    tnTBbeRst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 547 }

    tnTBbeRst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 548 }

    tnTEsRst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 549 }

    tnTEsRst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 550 }

    tnTSesRst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 551 }

    tnTSesRst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 552 }

    tnTUasRst15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 553 }

    tnTUasRst15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 554 }

    tnTBbeOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 555 }

    tnTBbeOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 556 }

    tnTBbeRs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 557 }

    tnTBbeRs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 558 }

    tnTCv1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 559 }

    tnTCv1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 560 }

    tnTCvPcs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 561 }

    tnTCvPcs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 562 }

    tnTCvPcst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 563 }

    tnTCvPcst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 564 }

    tnTCvs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 565 }

    tnTCvs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 566 }

    tnTCvst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 567 }

    tnTCvst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 568 }

    tnTEs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 569 }

    tnTEs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 570 }

    tnTEsOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 571 }

    tnTEsOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 572 }

    tnTEsRs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 573 }

    tnTEsRs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 574 }

    tnTEsPcs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 575 }

    tnTEsPcs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 576 }

    tnTEsPcst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 577 }

    tnTEsPcst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 578 }

    tnTEss1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 579 }

    tnTEss1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 580 }

    tnTEthpkter1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 581 }

    tnTEthpkter1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 582 }

    tnTEthpktert1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 583 }

    tnTEthpktert1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 584 }

    tnTFecc1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 585 }

    tnTFecc1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 586 }

    tnTFecUbu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 587 }

    tnTFecUbu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 588 }

    tnTOprh1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 589 }

    tnTOprh1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 590 }

    tnTOprl1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 591 }

    tnTOprl1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 592 }

    tnTOpth1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 593 }

    tnTOpth1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 594 }

    tnTOptl1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 595 }

    tnTOptl1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 596 }

    tnTSefs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 597 }

    tnTSefs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 598 }

    tnTSefsPcs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 599 }

    tnTSefsPcs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 600 }

    tnTSefsPcst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 601 }

    tnTSefsPcst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 602 }

    tnTSefss1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 603 }

    tnTSefss1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 604 }

    tnTSefsst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 605 }

    tnTSefsst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 606 }

    tnTSes1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 607 }

    tnTSes1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 608 }

    tnTSesOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 609 }

    tnTSesOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 610 }

    tnTSesPcs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 611 }

    tnTSesPcs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 612 }

    tnTSesPcst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 613 }

    tnTSesPcst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 614 }

    tnTSesRs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 615 }

    tnTSesRs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 616 }

    tnTSess1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 617 }

    tnTSess1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 618 }

    tnTSesst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 619 }

    tnTSesst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 620 }

    tnTUasOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 621 }

    tnTUasOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 622 }

    tnTUasRs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 623 }

    tnTUasRs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 624 }

    tnTEsst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 625 }

    tnTEsst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 626 }

    tnTBbeOdu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 627 }

    tnTBbeOdu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 628 }

    tnTEsOdu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 629 }

    tnTEsOdu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 630 }

    tnTSesOdu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 631 }

    tnTSesOdu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 632 }

    tnTUasOdu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 633 }

    tnTUasOdu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 634 }

    tnTBbeRst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 635 }

    tnTBbeRst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 636 }

    tnTEsRst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 637 }

    tnTEsRst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 638 }

    tnTSesRst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 639 }

    tnTSesRst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 640 }

    tnTUasRst1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 641 }

    tnTUasRst1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 642 }

    tnEqptDgrOchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 643 }

    tnEqptDgrOchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 644 }

    tnEqptDgrOchOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 645 }

    tnEqptDgrOchOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 646 }

    tnEtrMismatchModRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 647 }

    tnEtrMismatchModClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 648 }

    tnFanSpeedHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 649 }

    tnFanSpeedHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 650 }

    tnFanSpeedLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 651 }

    tnFanSpeedLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 652 }

    tnIntTempHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 653 }

    tnIntTempHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 654 }

    tnIntTempLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 655 }

    tnIntTempLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 656 }

    tnIntTempOptRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 657 }

    tnIntTempOptClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 658 }

--    obsolete
--    tnOprLossLowRaisedNotif   NOTIFICATION-TYPE ::= { tnV2AlarmNotificationsRel2 659 }
--    tnOprLossLowClearedNotif  NOTIFICATION-TYPE ::= { tnV2AlarmNotificationsRel2 660 }
--    tnOprLossHighRaisedNotif  NOTIFICATION-TYPE ::= { tnV2AlarmNotificationsRel2 661 }
--    tnOprLossHighClearedNotif NOTIFICATION-TYPE ::= { tnV2AlarmNotificationsRel2 662 }

    tnOprTxRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 663 }

    tnOprTxClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 664 }

    tnOprPwrLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 665 }

    tnOprPwrLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 666 }

    tnOprPwrHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 667 }

    tnOprPwrHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 668 }

    tnTrmtMODRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 669 }

    tnTrmtMODClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 670 }

    tnReplUnitMissMODRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 671 }

    tnReplUnitMissMODClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 672 }

    tnVoltageHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 673 }

    tnVoltageHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 674 }

    tnVoltageLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 675 }

    tnVoltageLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 676 }

    tnEqptPortRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 677 }

    tnEqptPortClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 678 }

--    obsolete
--    tnUruOtsRaisedNotif  NOTIFICATION-TYPE ::= { tnV2AlarmNotificationsRel2 679 }
--    tnUruOtsClearedNotif NOTIFICATION-TYPE ::= { tnV2AlarmNotificationsRel2 680 }
--    tnUruOtuRaisedNotif  NOTIFICATION-TYPE ::= { tnV2AlarmNotificationsRel2 681 }
--    tnUruOtuClearedNotif NOTIFICATION-TYPE ::= { tnV2AlarmNotificationsRel2 682 }

    tnMismatchFiberRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 683 }

    tnMismatchFiberClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 684 }

--    obsolete
--    tnLosPldRaisedNotif  NOTIFICATION-TYPE ::= { tnV2AlarmNotificationsRel2 685 }
--    tnLosPldClearedNotif NOTIFICATION-TYPE ::= { tnV2AlarmNotificationsRel2 686 }

    tnAprNodeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 687 }

    tnAprNodeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 688 }

    tnAprOscRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 689 }

    tnAprOscClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 690 }

    tnAprUnavailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 691 }

    tnAprUnavailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 692 }

    tnAprInvalidTopoRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 693 }

    tnAprInvalidTopoClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 694 }

    tnIncompatFanRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 695 }

    tnIncompatFanClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 696 }

    tnBoardEqptRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 697 }

    tnBoardEqptClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 698 }

    tnAprUnavailOscRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 699 }

    tnAprUnavailOscClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 700 }

    tnTBbeP15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 701 }

    tnTBbeP15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 702 }

    tnTEsP15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 703 }

    tnTEsP15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 704 }

    tnTSesP15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 705 }

    tnTSesP15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 706 }

    tnTUasP15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 707 }

    tnTUasP15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 708 }

    tnTEsL15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 709 }

    tnTEsL15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 710 }

    tnTSesL15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 711 }

    tnTSesL15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 712 }

    tnTBbeP1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 713 }

    tnTBbeP1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 714 }

    tnTEsP1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 715 }

    tnTEsP1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 716 }

    tnTSesP1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 717 }

    tnTSesP1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 718 }

    tnTUasP1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 719 }

    tnTUasP1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 720 }

    tnTEsL1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 721 }

    tnTEsL1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 722 }

    tnTSesL1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 723 }

    tnTSesL1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 724 }

    tnTBbePt15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 725 }

    tnTBbePt15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 726 }

    tnTEsPt15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 727 }

    tnTEsPt15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 728 }

    tnTSesPt15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 729 }

    tnTSesPt15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 730 }

    tnTUasPt15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 731 }

    tnTUasPt15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 732 }

    tnTBbePt1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 733 }

    tnTBbePt1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 734 }

    tnTEsPt1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 735 }

    tnTEsPt1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 736 }

    tnTSesPt1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 737 }

    tnTSesPt1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 738 }

    tnTUasPt1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 739 }

    tnTUasPt1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 740 }

    tnExcessLossRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 741 }

    tnExcessLossClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 742 }

    tnLosOcmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 743 }

    tnLosOcmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 744 }

    tnFecUbcSignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 745 }

    tnFecUbcSignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 746 }

    tnUruSRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 747 }

    tnUruSClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 748 }

    tnPwrTiltSuspRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 749 }

    tnPwrTiltSuspClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 750 }

    tnEberoRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 751 }

    tnEberoClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 752 }

    tnTPrefec15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 753 }

    tnTPrefec15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 754 }

    tnTPostfec15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 755 }

    tnTPostfec15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 756 }

    tnTPrefec1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 757 }

    tnTPrefec1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 758 }

    tnTPostfec1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 759 }

    tnTPostfec1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 760 }

    tnTIAESOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 761 }

    tnTIAESOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 762 }

    tnTBIAESOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 763 }

    tnTBIAESOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 764 }

    tnTIAESOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 765 }

    tnTIAESOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 766 }

    tnTBIAESOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 767 }

    tnTBIAESOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 768 }

    tnTFeBbeOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 769 }

    tnTFeBbeOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 770 }

    tnTFeEsOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 771 }

    tnTFeEsOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 772 }

    tnTFeSesOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 773 }

    tnTFeSesOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 774 }

    tnTFeUasOtu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 775 }

    tnTFeUasOtu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 776 }

    tnTFeBbeOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 777 }

    tnTFeBbeOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 778 }

    tnTFeEsOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 779 }

    tnTFeEsOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 780 }

    tnTFeSesOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 781 }

    tnTFeSesOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 782 }

    tnTFeUasOtu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 783 }

    tnTFeUasOtu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 784 }

    tnTFeBbeOdu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 785 }

    tnTFeBbeOdu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 786 }

    tnTFeEsOdu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 787 }

    tnTFeEsOdu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 788 }

    tnTFeSesOdu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 789 }

    tnTFeSesOdu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 790 }

    tnTFeUasOdu15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 791 }

    tnTFeUasOdu15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 792 }

    tnTFeBbeOdu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 793 }

    tnTFeBbeOdu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 794 }

    tnTFeEsOdu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 795 }

    tnTFeEsOdu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 796 }

    tnTFeSesOdu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 797 }

    tnTFeSesOdu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 798 }

    tnTFeUasOdu1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 799 }

    tnTFeUasOdu1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 800 }

    tnOduAisRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 801 }

    tnOduAisClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 802 }

    tnMsimRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 803 }

    tnMsimClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 804 }

    tnLoamRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 805 }

    tnLoamClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 806 }

    tnLosOtsRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 807 }

    tnLosOtsClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 808 }

    tnInvalidThresholdOtsRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 809 }

    tnInvalidThresholdOtsClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 810 }

    tnPwrUnbalanceRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 811 }

    tnPwrUnbalanceClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 812 }

    tnSpLoAdjFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 813 }

    tnSpLoAdjFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 814 }

    tnLosOmsRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 815 }

    tnLosOmsClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 816 }

    tnInvalidThresholdOmsRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 817 }

    tnInvalidThresholdOmsClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 818 }

    tnLaserBackFacetOptPwrTcaRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 819 }

    tnLaserBackFacetOptPwrTcaClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 820 }

    tnLaserCoolingCurTcaRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 821 }

    tnLaserCoolingCurTcaClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 822 }

    tnPwrUnbalanceOmsRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 823 }

    tnPwrUnbalanceOmsClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 824 }

    tnOduAisEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 825 }

    tnOduAisEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 826 }

    tnFrngSyncRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 827 }

    tnFrngSyncClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 828 }

    tnHldOvrSyncRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 829 }

    tnHldOvrSyncClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 830 }

    tnSyncRefFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 831 }

    tnSyncRefFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 832 }

    tnWtrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 833 }

    tnWtrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 834 }

    tnTcmServerSignalFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 835 }

    tnTcmServerSignalFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 836 }

    tnTcmLockedIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 837 }

    tnTcmLockedIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 838 }

    tnTcmOpenConnectionIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 839 }

    tnTcmOpenConnectionIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 840 }

    tnTcmSignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 841 }

    tnTcmSignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 842 }

    tnTcmBackwardDefectIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 843 }

    tnTcmBackwardDefectIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 844 }

    tnTcmTrailTraceIdentifierMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 845 }

    tnTcmTrailTraceIdentifierMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 846 }

    tnTcmLossofTandemConnectionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 847 }

    tnTcmLossofTandemConnectionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 848 }

    tnAisTcmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 849 }

    tnAisTcmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 850 }

    tnTIAESTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 851 }

    tnTIAESTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 852 }

    tnTBbeTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 853 }

    tnTBbeTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 854 }

    tnTEsTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 855 }

    tnTEsTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 856 }

    tnTSesTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 857 }

    tnTSesTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 858 }

    tnTUasTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 859 }

    tnTUasTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 860 }

    tnTBIAESTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 861 }

    tnTBIAESTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 862 }

    tnTFeBbeTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 863 }

    tnTFeBbeTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 864 }

    tnTFeEsTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 865 }

    tnTFeEsTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 866 }

    tnTFeSesTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 867 }

    tnTFeSesTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 868 }

    tnTFeUasTcm15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 869 }

    tnTFeUasTcm15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 870 }

    tnTIAESTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 871 }

    tnTIAESTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 872 }

    tnTBbeTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 873 }

    tnTBbeTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 874 }

    tnTEsTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 875 }

    tnTEsTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 876 }

    tnTSesTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 877 }

    tnTSesTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 878 }

    tnTUasTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 879 }

    tnTUasTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 880 }

    tnTBIAESTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 881 }

    tnTBIAESTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 882 }

    tnTFeBbeTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 883 }

    tnTFeBbeTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 884 }

    tnTFeEsTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 885 }

    tnTFeEsTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 886 }

    tnTFeSesTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 887 }

    tnTFeSesTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 888 }

    tnTFeUasTcm1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 889 }

    tnTFeUasTcm1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 890 }

--    obsolete
--    tnUruOmsRaisedNotif  NOTIFICATION-TYPE ::= { tnV2AlarmNotificationsRel2 893 }
--    tnUruOmsClearedNotif NOTIFICATION-TYPE ::= { tnV2AlarmNotificationsRel2 894 }

    tnTBbeMs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 895 }

    tnTBbeMs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 896 }

    tnTEsMs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 897 }

    tnTEsMs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 898 }

    tnTSesMs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 899 }

    tnTSesMs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 900 }

    tnTUasMs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 901 }

    tnTUasMs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 902 }

    tnTFeBbeMs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 903 }

    tnTFeBbeMs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 904 }

    tnTFeEsMs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 905 }

    tnTFeEsMs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 906 }

    tnTFeSesMs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 907 }

    tnTFeSesMs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 908 }

    tnTFeUasMs15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 909 }

    tnTFeUasMs15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 910 }

    tnTBbeMs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 911 }

    tnTBbeMs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 912 }

    tnTEsMs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 913 }

    tnTEsMs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 914 }

    tnTSesMs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 915 }

    tnTSesMs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 916 }

    tnTUasMs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 917 }

    tnTUasMs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 918 }

    tnTFeBbeMs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 919 }

    tnTFeBbeMs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 920 }

    tnTFeEsMs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 921 }

    tnTFeEsMs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 922 }

    tnTFeSesMs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 923 }

    tnTFeSesMs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 924 }

    tnTFeUasMs1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 925 }

    tnTFeUasMs1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 926 }

    tnLosOOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 927 }

    tnLosOOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 928 }

    tnInvalidEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 929 }

    tnInvalidEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 930 }

    tnAprSwitchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 931 }

    tnAprSwitchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 932 }

    tnOptIntDetRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 933 }

    tnOptIntDetClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 934 }

    tnOptIntSuspRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 935 }

    tnOptIntSuspClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 936 }

    tnUruOtsRxRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 937 }

    tnUruOtsRxClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 938 }

    tnUruOtsTxRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 939 }

    tnUruOtsTxClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 940 }

    tnUruOmsRxRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 941 }

    tnUruOmsRxClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 942 }

    tnUruOtsLosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 943 }

    tnUruOtsLosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 944 }

    tnUruOchLosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 945 }

    tnUruOchLosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 946 }

    tnIntrusionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 947 }

    tnIntrusionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 948 }

    tnManSwToIntRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 949 }

    tnManSwToIntClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 950 }

    tnAutoSwTimRefRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 951 }

    tnAutoSwTimRefClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 952 }

    tnManSwTimRefRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 953 }

    tnManSwTimRefClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 954 }

    tnFrcdSwTimRefRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 955 }

    tnFrcdSwTimRefClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 956 }

    tnLockoutOfTimRefRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 957 }

    tnLockoutOfTimRefClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 958 }

    tnManLRRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 959 }

    tnManLRClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 960 }

    tnSLTMSIGRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 961 }

    tnSLTMSIGClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 962 }

    tnSyncRefUnEqRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 963 }

    tnSyncRefUnEqClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 964 }

    tnPCSGeneratorActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 965 }

    tnPCSGeneratorActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 966 }

    tnOSPFADJRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 967 }

    tnOSPFADJClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 968 }

    tnFDIRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 969 }

    tnFDIClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 970 }

    tnTsMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 971 }

    tnTsMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 972 }

    tnTBerPreFec15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 973 }

    tnTBerPreFec15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 974 }

    tnTBerPreFec1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 975 }

    tnTBerPreFec1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 976 }

    tnTBerPostFec15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 977 }

    tnTBerPostFec15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 978 }

    tnTBerPostFec1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 979 }

    tnTBerPostFec1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 980 }

    tnLOFLOMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 981 }

    tnLOFLOMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 982 }

    tnOptIntBaseRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 983 }

    tnOptIntBaseClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 984 }

    tnAuAisPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 985 }

    tnAuAisPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 986 }

    tnAuLopPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 987 }

    tnAuLopPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 988 }

    tnHpUneqPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 989 }

    tnHpUneqPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 990 }

    tnHpPlmPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 991 }

    tnHpPlmPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 992 }

    tnHpRdiPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 993 }

    tnHpRdiPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 994 }

    tnTransferLogFLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 995 }

    tnTransferLogFLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 996 }

    tnTransferLogFTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 997 }

    tnTransferLogFTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 998 }

    tnTransferLogIPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 999 }

    tnTransferLogIPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1000 }

    tnAutoSyncSwRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1001 }

    tnAutoSyncSwClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1002 }

    tnNtpLorRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1003 }

    tnNtpLorClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1004 }

    tnInventoryErrorRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1005 }

    tnInventoryErrorClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1006 }

    tnMepLocRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1007 }

    tnMepLocClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1008 }

    tnMepMmgRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1009 }

    tnMepMmgClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1010 }

    tnUnMOrUnPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1011 }

    tnUnMOrUnPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1012 }

    tnEthCSFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1013 }

    tnEthCSFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1014 }

    tnRDIRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1015 }

    tnRDIClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1016 }

    tnCFCAPACITYWARNINGRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1017 }

    tnCFCAPACITYWARNINGClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1018 }

    tnAsonTopoRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1019 }

    tnAsonTopoClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1020 }

    tnESCLATCHFAILRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1021 }

    tnESCLATCHFAILClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1022 }

    tnPwrAdjCommsRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1023 }

    tnPwrAdjCommsClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1024 }

    tnLanSfRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1025 }

    tnLanSfClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1026 }

    tnCardBootRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1027 }

    tnCardBootClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1028 }

    tnLotOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1029 }

    tnLotOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1030 }

    tnPrcdrErrTopoOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1031 }

    tnPrcdrErrTopoOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1032 }

    tnPWRADJFAILADDRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1033 }

    tnPWRADJFAILADDClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1034 }

    tnPWRADJFAILDRPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1035 }

    tnPWRADJFAILDRPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1036 }

    tnPWRADJREQADDRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1037 }

    tnPWRADJREQADDClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1038 }

    tnPWRADJREQDRPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1039 }

    tnPWRADJREQDRPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1040 }

    tnOcsUnavailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1041 }

    tnOcsUnavailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1042 }

    tnCKMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1043 }

    tnCKMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1044 }

    tnNKMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1045 }

    tnNKMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1046 }

    tnSyncEqptRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1047 }

    tnSyncEqptClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1048 }

    tnSyncOosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1049 }

    tnSyncOosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1050 }

    tnUruOmsTxRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1051 }

    tnUruOmsTxClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1052 }

    tnSsfCltEgrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1053 }

    tnSsfCltEgrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1054 }

    tnPwrTiltParamsRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1055 }

    tnPwrTiltParamsClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1056 }

    tnEgressSSFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1057 }

    tnEgressSSFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1058 }

    tnOmsSSFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1059 }

    tnOmsSSFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1060 }

    tnAlienEgrLOSRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1061 }

    tnAlienEgrLOSClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1062 }

    tnCSFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1063 }

    tnCSFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1064 }

    tnFDICLTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1065 }

    tnFDICLTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1066 }

    tnCSFODUEGRRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1067 }

    tnCSFODUEGRClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1068 }

    tnLagLosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1069 }

    tnLagLosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1070 }

    tnLagDegRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1071 }

    tnLagDegClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1072 }

    tnUNLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1073 }

    tnUNLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1074 }

    tnUNMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1075 }

    tnUNMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1076 }

    tnUNPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1077 }

    tnUNPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1078 }

    tnUNPrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1079 }

    tnUNPrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1080 }

    tnToDLOSRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1081 }

    tnToDLOSClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1082 }

    tnToDDEGRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1083 }

    tnToDDEGClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1084 }

    tnLossOfLockRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1085 }

    tnLossOfLockClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1086 }

    tnFaultyRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1087 }

    tnFaultyClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1088 }

    tnPPSLosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1089 }

    tnPPSLosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1090 }

    tnEthRingPathProvMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1091 }

    tnEthRingPathProvMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1092 }

    tnMepMacErrorRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1093 }

    tnMepMacErrorClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1094 }

    tnMepXconRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1095 }

    tnMepXconClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1096 }

    tnMepErrorRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1097 }

    tnMepErrorClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1098 }

    tnMepRemoteRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1099 }

    tnMepRemoteClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1100 }

    tnMepAISRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1101 }

    tnMepAISClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1102 }

    tnSvcOperDownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1103 }

    tnSvcOperDownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1104 }

    tnSvcTlsFwdTblFullAlarmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1105 }

    tnSvcTlsFwdTblFullAlarmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1106 }

    tnSvcTlsMfibTblFullAlarmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1107 }

    tnSvcTlsMfibTblFullAlarmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1108 }

    tnSapOperDownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1109 }

    tnSapOperDownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1110 }

    tnSapTlsMacAddrLimitAlarmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1111 }

    tnSapTlsMacAddrLimitAlarmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1112 }

    tnLagPortAddFailedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1113 }

    tnLagPortAddFailedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1114 }

    tnSyncIfTimingHoldoverRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1115 }

    tnSyncIfTimingHoldoverClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1116 }

    tnSyncIfTimingRef1AlarmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1117 }

    tnSyncIfTimingRef1AlarmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1118 }

    tnSyncIfTimingRef2AlarmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1119 }

    tnSyncIfTimingRef2AlarmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1120 }

    tnLinkoamLoopDetectedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1121 }

    tnLinkoamLoopDetectedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1122 }

    tnESMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1123 }

    tnESMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1124 }

    tnSsfOduOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1125 }

    tnSsfOduOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1126 }

    tnLckOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1127 }

    tnLckOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1128 }

    tnOciOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1129 }

    tnOciOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1130 }

    tnDegOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1131 }

    tnDegOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1132 }

    tnBdiOduOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1133 }

    tnBdiOduOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1134 }

    tnTimOduOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1135 }

    tnTimOduOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1136 }

    tnLolRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1169 }

    tnLolClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1170 }

--    obsolete
--    tnErpFwdStateChngRaisedNotif         NOTIFICATION-TYPE ::= { tnV2AlarmNotificationsRel2 1171 }
--    tnErpFwdStateChngClearedNotif        NOTIFICATION-TYPE ::= { tnV2AlarmNotificationsRel2 1172 }
--    tnLagSubGrpSelectRaisedNotif         NOTIFICATION-TYPE ::= { tnV2AlarmNotificationsRel2 1173 }
--    tnLagSubGrpSelectClearedNotif        NOTIFICATION-TYPE ::= { tnV2AlarmNotificationsRel2 1174 }
--    tnLinkoamPeerChngRaisedNotif         NOTIFICATION-TYPE ::= { tnV2AlarmNotificationsRel2 1175 }
--    tnLinkoamPeerChngClearedNotif        NOTIFICATION-TYPE ::= { tnV2AlarmNotificationsRel2 1176 }
--    tnLinkoamNonThreshRaisedNotif        NOTIFICATION-TYPE ::= { tnV2AlarmNotificationsRel2 1177 }
--    tnLinkoamNonThreshClearedNotif       NOTIFICATION-TYPE ::= { tnV2AlarmNotificationsRel2 1178 }
--    tnSvcStateChngRaisedNotif            NOTIFICATION-TYPE ::= { tnV2AlarmNotificationsRel2 1179 }
--    tnSvcStateChngClearedNotif           NOTIFICATION-TYPE ::= { tnV2AlarmNotificationsRel2 1180 }
--    tnSapStateChngRaisedNotif            NOTIFICATION-TYPE ::= { tnV2AlarmNotificationsRel2 1181 }
--    tnSapStateChngClearedNotif           NOTIFICATION-TYPE ::= { tnV2AlarmNotificationsRel2 1182 }
--    tnCfmFltEvntRaisedNotif              NOTIFICATION-TYPE ::= { tnV2AlarmNotificationsRel2 1183 }
--    tnCfmFltEvntClearedNotif             NOTIFICATION-TYPE ::= { tnV2AlarmNotificationsRel2 1184 }
--    tnCfmAisEvntRaisedNotif              NOTIFICATION-TYPE ::= { tnV2AlarmNotificationsRel2 1185 }
--    tnCfmAisEvntClearedNotif             NOTIFICATION-TYPE ::= { tnV2AlarmNotificationsRel2 1186 }
--    tnCfmSlmTestCompleteRaisedNotif      NOTIFICATION-TYPE ::= { tnV2AlarmNotificationsRel2 1187 }
--    tnCfmSlmTestCompleteClearedNotif     NOTIFICATION-TYPE ::= { tnV2AlarmNotificationsRel2 1188 }
--    tnCfmDmTestCompleteRaisedNotif       NOTIFICATION-TYPE ::= { tnV2AlarmNotificationsRel2 1189 }
--    tnCfmDmTestCompleteClearedNotif      NOTIFICATION-TYPE ::= { tnV2AlarmNotificationsRel2 1190 }
--    tnCfmLbmTestCompleteRaisedNotif      NOTIFICATION-TYPE ::= { tnV2AlarmNotificationsRel2 1191 }
--    tnCfmLbmTestCompleteClearedNotif     NOTIFICATION-TYPE ::= { tnV2AlarmNotificationsRel2 1192 }
--    tnCfmLtmTestCompleteRaisedNotif      NOTIFICATION-TYPE ::= { tnV2AlarmNotificationsRel2 1193 }
--    tnCfmLtmTestCompleteClearedNotif     NOTIFICATION-TYPE ::= { tnV2AlarmNotificationsRel2 1194 }
--    tnIgmpSnpgSrcLimitExceedRaisedNotif  NOTIFICATION-TYPE ::= { tnV2AlarmNotificationsRel2 1195 }
--    tnIgmpSnpgSrcLimitExceedClearedNotif NOTIFICATION-TYPE ::= { tnV2AlarmNotificationsRel2 1196 }
--    tnMirrorSrcEnableRaisedNotif         NOTIFICATION-TYPE ::= { tnV2AlarmNotificationsRel2 1197 }
--    tnMirrorSrcEnableClearedNotif        NOTIFICATION-TYPE ::= { tnV2AlarmNotificationsRel2 1198 }
--    tnMirrorSrcDisableRaisedNotif        NOTIFICATION-TYPE ::= { tnV2AlarmNotificationsRel2 1199 }
--    tnMirrorSrcDisableClearedNotif       NOTIFICATION-TYPE ::= { tnV2AlarmNotificationsRel2 1200 }

    tnOTMCPFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1201 }

    tnOTMCPFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1202 }

    tnWtocmaOsnrOomrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1203 }

    tnWtocmaOsnrOomrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1204 }

    tnLanLolRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1205 }

    tnLanLolClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1206 }

    tnPlmOduOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1207 }

    tnPlmOduOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1208 }

    tnCsfOduOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1209 }

    tnCsfOduOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1210 }

    tnShelfInVoltHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1211 }

    tnShelfInVoltHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1212 }

    tnShelfInVoltLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1213 }

    tnShelfInVoltLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1214 }

--    obsolete
--    tnMirrorDestEnableRaisedNotif   NOTIFICATION-TYPE ::= { tnV2AlarmNotificationsRel2 1215 }
--    tnMirrorDestEnableClearedNotif  NOTIFICATION-TYPE ::= { tnV2AlarmNotificationsRel2 1216 }
--    tnMirrorDestDisableRaisedNotif  NOTIFICATION-TYPE ::= { tnV2AlarmNotificationsRel2 1217 }
--    tnMirrorDestDisableClearedNotif NOTIFICATION-TYPE ::= { tnV2AlarmNotificationsRel2 1218 }
--    tnDCConfigFailRaisedNotif       NOTIFICATION-TYPE ::= { tnV2AlarmNotificationsRel2 1219 }
--    tnDCConfigFailClearedNotif      NOTIFICATION-TYPE ::= { tnV2AlarmNotificationsRel2 1220 }

    tnPwrEdfaMarginRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1221 }

    tnPwrEdfaMarginClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1222 }

    tnBITSLosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1223 }

    tnBITSLosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1224 }

    tnBITSLofRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1225 }

    tnBITSLofClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1226 }

    tnBITSAISRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1227 }

    tnBITSAISClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1228 }

    tnBITSMANRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1229 }

    tnBITSMANClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1230 }

    tnSyncOosT4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1231 }

    tnSyncOosT4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1232 }

    tnSyncT4OutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1233 }

    tnSyncT4OutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1234 }

    tnAutoSwTimRefT4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1235 }

    tnAutoSwTimRefT4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1236 }

    tnManSwTimRefT4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1237 }

    tnManSwTimRefT4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1238 }

    tnFrcdSwTimRefT4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1239 }

    tnFrcdSwTimRefT4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1240 }

    tnLockoutOfTimRefT4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1241 }

    tnLockoutOfTimRefT4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1242 }

    tnCardInitBcmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1243 }

    tnCardInitBcmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1244 }

    tnCardInitNonBcmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1245 }

    tnCardInitNonBcmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1246 }

    tnLOSEDFARaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1247 }

    tnLOSEDFAClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1248 }

    tnOduAisOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1249 }

    tnOduAisOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1250 }

    tnTsMismatchOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1251 }

    tnTsMismatchOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1252 }

    tnLOFLOMOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1253 }

    tnLOFLOMOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1254 }

    tnCPUPERFORMANCERaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1255 }

    tnCPUPERFORMANCEClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1256 }

    tnContEqptSplitRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1257 }

    tnContEqptSplitClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1258 }

    tnCsfGfpOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1259 }

    tnCsfGfpOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1260 }

    tnGfpLofOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1261 }

    tnGfpLofOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1262 }

    tnSsfSectionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1263 }

    tnSsfSectionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1264 }

    tnPTPRefUnstableRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1265 }

    tnPTPRefUnstableClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1266 }

    tnPTPFreeRunRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1267 }

    tnPTPFreeRunClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1268 }

    tnPTPRefLossRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1269 }

    tnPTPRefLossClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1270 }

    tnAnnounceLossRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1271 }

    tnAnnounceLossClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1272 }

    tnSyncLossRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1273 }

    tnSyncLossClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1274 }

    tnDelayResLossRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1275 }

    tnDelayResLossClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1276 }

--    obsolete
--    tnPTPGMDegradeRaisedNotif   NOTIFICATION-TYPE ::= { tnV2AlarmNotificationsRel2 1277 }
--    tnPTPGMDegradeClearedNotif  NOTIFICATION-TYPE ::= { tnV2AlarmNotificationsRel2 1278 }
--    tnPTPGMSwitchRaisedNotif    NOTIFICATION-TYPE ::= { tnV2AlarmNotificationsRel2 1279 }
--    tnPTPGMSwitchClearedNotif   NOTIFICATION-TYPE ::= { tnV2AlarmNotificationsRel2 1280 }
--    tnPTPPathSwitchRaisedNotif  NOTIFICATION-TYPE ::= { tnV2AlarmNotificationsRel2 1281 }
--    tnPTPPathSwitchClearedNotif NOTIFICATION-TYPE ::= { tnV2AlarmNotificationsRel2 1282 }
--    tnPTPPortSwitchRaisedNotif  NOTIFICATION-TYPE ::= { tnV2AlarmNotificationsRel2 1283 }
--    tnPTPPortSwitchClearedNotif NOTIFICATION-TYPE ::= { tnV2AlarmNotificationsRel2 1284 }

    tnRmdNDFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1285 }

    tnRmdNDFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1286 }

    tnRmdDNRRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1287 }

    tnRmdDNRClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1288 }

    tnRmdWDPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1289 }

    tnRmdWDPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1290 }

    tnRmdEQFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1291 }

    tnRmdEQFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1292 }

    tnLosPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1293 }

    tnLosPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1294 }

--    obsolete
--    tnFIPSSFMISMATCHRaisedNotif  NOTIFICATION-TYPE ::= { tnV2AlarmNotificationsRel2 1295 }
--    tnFIPSSFMISMATCHClearedNotif NOTIFICATION-TYPE ::= { tnV2AlarmNotificationsRel2 1296 }

    tnEQPTCRYPTORaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1297 }

    tnEQPTCRYPTOClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1298 }

    tnRmdPWRRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1299 }

    tnRmdPWRClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1300 }

    tnRmdMepUNLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1301 }

    tnRmdMepUNLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1302 }

    tnRmdMepMMGRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1303 }

    tnRmdMepMMGClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1304 }

    tnRmdMepUNMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1305 }

    tnRmdMepUNMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1306 }

    tnRmdMepLOCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1307 }

    tnRmdMepLOCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1308 }

    tnRmdMepUNPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1309 }

    tnRmdMepUNPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1310 }

    tnRmdMepRDIRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1311 }

    tnRmdMepRDIClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1312 }

    tnSLCCARDINITRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1313 }

    tnSLCCARDINITClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1314 }

    tnSLCBOOTCONTCOMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1315 }

    tnSLCBOOTCONTCOMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1316 }

    tnSLCCONTCOMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1317 }

    tnSLCCONTCOMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1318 }

    tnSLCDATAFLTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1319 }

    tnSLCDATAFLTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1320 }

    tnSLCEQPTBOOTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1321 }

    tnSLCEQPTBOOTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1322 }

    tnSLCNOTINSERVICERaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1323 }

    tnSLCNOTINSERVICEClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1324 }

    tnSLCMISMATCHRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1325 }

    tnSLCMISMATCHClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1326 }

    tnSLCCLKSYNCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1327 }

    tnSLCCLKSYNCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1328 }

    tnRmdIfEFMLOPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1329 }

    tnRmdIfEFMLOPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1330 }

    tnRmdIfMauLOSRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1331 }

    tnRmdIfMauLOSClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1332 }

    tnRmdIfMauANMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1333 }

    tnRmdIfMauANMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1334 }

    tnRmdIfMauEQFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1335 }

    tnRmdIfMauEQFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1336 }

    tnRmdIfMauUNIRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1337 }

    tnRmdIfMauUNIClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1338 }

    tnRmdIfMauWUPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1339 }

    tnRmdIfMauWUPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1340 }

    tnFPGAPRELOADRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1341 }

    tnFPGAPRELOADClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1342 }

    tnLockedIndicationEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1343 }

    tnLockedIndicationEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1344 }

    tnOpenConnectionIndicationEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1345 }

    tnOpenConnectionIndicationEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1346 }

    tnSignalDegradeEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1347 }

    tnSignalDegradeEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1348 }

    tnBackwardDefectIndicationEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1349 }

    tnBackwardDefectIndicationEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1350 }

    tnTrailTraceIdentifierMismatchEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1351 }

    tnTrailTraceIdentifierMismatchEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1352 }

    tnPayloadTypeMismatchEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1353 }

    tnPayloadTypeMismatchEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1354 }

    tnServerSignalFailureEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1355 }

    tnServerSignalFailureEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1356 }

    tnCsfGfpRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1357 }

    tnCsfGfpClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1358 }

    tnGfpUpmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1359 }

    tnGfpUpmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1360 }

    tnSsfSectionOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1361 }

    tnSsfSectionOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1362 }

    tnTFecUbc15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1363 }

    tnTFecUbc15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1364 }

    tnTFecUbc1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1365 }

    tnTFecUbc1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1366 }

    tnTRUSVCVOLTFLTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1367 }

    tnTRUSVCVOLTFLTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1368 }

    tnTRUBRKROPENRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1369 }

    tnTRUBRKROPENClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1370 }

    tnOSNRMESCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1371 }

    tnOSNRMESCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1372 }

    tnFipsSwMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1373 }

    tnFipsSwMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1374 }

    tnTODRefUnstableRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1375 }

    tnTODRefUnstableClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1376 }

    tnFipsFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1377 }

    tnFipsFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1378 }

    tnAesFipsFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1379 }

    tnAesFipsFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1380 }

    tnGfpLofRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1381 }

    tnGfpLofClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1382 }

    tnOchKeyUnavailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1383 }

    tnOchKeyUnavailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1384 }

    tnKeyDomainErrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1385 }

    tnKeyDomainErrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1386 }

    tnOchKeysReusedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1387 }

    tnOchKeysReusedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1388 }

    tnFAN32HRQDRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1389 }

    tnFAN32HRQDClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1390 }

    tnLOSOAMPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1391 }

    tnLOSOAMPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1392 }

    tnTPmonSapIngressPktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1393 }

    tnTPmonSapIngressPktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1394 }

    tnTPmonSapIngressOctetsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1395 }

    tnTPmonSapIngressOctetsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1396 }

    tnTPmonPortIfInPackets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1397 }

    tnTPmonPortIfInPackets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1398 }

    tnTPmonPortIfOutPackets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1399 }

    tnTPmonPortIfOutPackets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1400 }

    tnTPmonPortIfInOctets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1401 }

    tnTPmonPortIfInOctets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1402 }

    tnTPmonPortIfOutOctets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1403 }

    tnTPmonPortIfOutOctets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1404 }

    tnTPmonPortIfInDiscards15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1405 }

    tnTPmonPortIfInDiscards15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1406 }

    tnTPmonPortIfOutDiscards15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1407 }

    tnTPmonPortIfOutDiscards15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1408 }

    tnTPmonPortIfInErrors15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1409 }

    tnTPmonPortIfInErrors15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1410 }

    tnTPmonPortIfOutErrors15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1411 }

    tnTPmonPortIfOutErrors15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1412 }

    tnTPmonPortHighCapacityPkts15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1413 }

    tnTPmonPortHighCapacityPkts15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1414 }

    tnTPmonPortHighCapacityOctets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1415 }

    tnTPmonPortHighCapacityOctets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1416 }

    tnTPmonPortQueue1PktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1417 }

    tnTPmonPortQueue1PktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1418 }

    tnTPmonPortQueue2PktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1419 }

    tnTPmonPortQueue2PktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1420 }

    tnTPmonPortQueue3PktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1421 }

    tnTPmonPortQueue3PktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1422 }

    tnTPmonPortQueue4PktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1423 }

    tnTPmonPortQueue4PktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1424 }

    tnTPmonPortQueue5PktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1425 }

    tnTPmonPortQueue5PktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1426 }

    tnTPmonPortQueue6PktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1427 }

    tnTPmonPortQueue6PktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1428 }

    tnTPmonPortQueue7PktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1429 }

    tnTPmonPortQueue7PktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1430 }

    tnTPmonPortQueue8PktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1431 }

    tnTPmonPortQueue8PktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1432 }

    tnTPmonPortQueue1OctetsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1433 }

    tnTPmonPortQueue1OctetsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1434 }

    tnTPmonPortQueue2OctetsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1435 }

    tnTPmonPortQueue2OctetsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1436 }

    tnTPmonPortQueue3OctetsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1437 }

    tnTPmonPortQueue3OctetsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1438 }

    tnTPmonPortQueue4OctetsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1439 }

    tnTPmonPortQueue4OctetsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1440 }

    tnTPmonPortQueue5OctetsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1441 }

    tnTPmonPortQueue5OctetsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1442 }

    tnTPmonPortQueue6OctetsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1443 }

    tnTPmonPortQueue6OctetsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1444 }

    tnTPmonPortQueue7OctetsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1445 }

    tnTPmonPortQueue7OctetsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1446 }

    tnTPmonPortQueue8OctetsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1447 }

    tnTPmonPortQueue8OctetsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1448 }

    tnTPmonDmaBfd15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1449 }

    tnTPmonDmaBfd15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1450 }

    tnTPmonDmxBfd15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1451 }

    tnTPmonDmxBfd15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1452 }

    tnTPmonDmanFdv15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1453 }

    tnTPmonDmanFdv15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1454 }

    tnTPmonDmxnFdv15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1455 }

    tnTPmonDmxnFdv15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1456 }

    tnTPmonDmafFdv15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1457 }

    tnTPmonDmafFdv15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1458 }

    tnTPmonDmxfFdv15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1459 }

    tnTPmonDmxfFdv15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1460 }

    tnTPmonSapIngressPktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1461 }

    tnTPmonSapIngressPktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1462 }

    tnTPmonSapIngressOctetsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1463 }

    tnTPmonSapIngressOctetsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1464 }

    tnTPmonPortIfInPackets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1465 }

    tnTPmonPortIfInPackets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1466 }

    tnTPmonPortIfOutPackets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1467 }

    tnTPmonPortIfOutPackets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1468 }

    tnTPmonPortIfInOctets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1469 }

    tnTPmonPortIfInOctets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1470 }

    tnTPmonPortIfOutOctets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1471 }

    tnTPmonPortIfOutOctets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1472 }

    tnTPmonPortIfInDiscards1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1473 }

    tnTPmonPortIfInDiscards1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1474 }

    tnTPmonPortIfOutDiscards1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1475 }

    tnTPmonPortIfOutDiscards1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1476 }

    tnTPmonPortIfInErrors1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1477 }

    tnTPmonPortIfInErrors1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1478 }

    tnTPmonPortIfOutErrors1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1479 }

    tnTPmonPortIfOutErrors1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1480 }

    tnTPmonPortHighCapacityPkts1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1481 }

    tnTPmonPortHighCapacityPkts1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1482 }

    tnTPmonPortHighCapacityOctets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1483 }

    tnTPmonPortHighCapacityOctets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1484 }

    tnTPmonPortQueue1PktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1485 }

    tnTPmonPortQueue1PktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1486 }

    tnTPmonPortQueue2PktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1487 }

    tnTPmonPortQueue2PktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1488 }

    tnTPmonPortQueue3PktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1489 }

    tnTPmonPortQueue3PktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1490 }

    tnTPmonPortQueue4PktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1491 }

    tnTPmonPortQueue4PktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1492 }

    tnTPmonPortQueue5PktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1493 }

    tnTPmonPortQueue5PktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1494 }

    tnTPmonPortQueue6PktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1495 }

    tnTPmonPortQueue6PktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1496 }

    tnTPmonPortQueue7PktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1497 }

    tnTPmonPortQueue7PktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1498 }

    tnTPmonPortQueue8PktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1499 }

    tnTPmonPortQueue8PktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1500 }

    tnTPmonPortQueue1OctetsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1501 }

    tnTPmonPortQueue1OctetsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1502 }

    tnTPmonPortQueue2OctetsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1503 }

    tnTPmonPortQueue2OctetsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1504 }

    tnTPmonPortQueue3OctetsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1505 }

    tnTPmonPortQueue3OctetsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1506 }

    tnTPmonPortQueue4OctetsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1507 }

    tnTPmonPortQueue4OctetsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1508 }

    tnTPmonPortQueue5OctetsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1509 }

    tnTPmonPortQueue5OctetsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1510 }

    tnTPmonPortQueue6OctetsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1511 }

    tnTPmonPortQueue6OctetsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1512 }

    tnTPmonPortQueue7OctetsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1513 }

    tnTPmonPortQueue7OctetsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1514 }

    tnTPmonPortQueue8OctetsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1515 }

    tnTPmonPortQueue8OctetsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1516 }

    tnTPmonSlmanFlr1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1517 }

    tnTPmonSlmanFlr1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1518 }

    tnTPmonSlmxnFlr1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1519 }

    tnTPmonSlmxnFlr1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1520 }

    tnTPmonSlmafFlr1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1521 }

    tnTPmonSlmafFlr1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1522 }

    tnTPmonSlmxfFlr1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1523 }

    tnTPmonSlmxfFlr1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1524 }

    tnTPmonDmaBfd1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1525 }

    tnTPmonDmaBfd1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1526 }

    tnTPmonDmxBfd1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1527 }

    tnTPmonDmxBfd1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1528 }

    tnTPmonDmanFdv1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1529 }

    tnTPmonDmanFdv1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1530 }

    tnTPmonDmxnFdv1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1531 }

    tnTPmonDmxnFdv1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1532 }

    tnTPmonDmafFdv1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1533 }

    tnTPmonDmafFdv1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1534 }

    tnTPmonDmxfFdv1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1535 }

    tnTPmonDmxfFdv1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1536 }

    tnCfmLmTestCompleteRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1537 }

    tnCfmLmTestCompleteClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1538 }

    tnCbr10G3RxLOSRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1539 }

    tnCbr10G3RxLOSClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1540 }

    tnCbr10G3RxLSSRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1541 }

    tnCbr10G3RxLSSClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1542 }

--    obsolete
--    tnLspFailedApeRaisedNotif          NOTIFICATION-TYPE ::= { tnV2AlarmNotificationsRel2 1543 }
--    tnLspFailedApeClearedNotif         NOTIFICATION-TYPE ::= { tnV2AlarmNotificationsRel2 1544 }
--    tnLspFailedXcRaisedNotif           NOTIFICATION-TYPE ::= { tnV2AlarmNotificationsRel2 1545 }
--    tnLspFailedXcClearedNotif          NOTIFICATION-TYPE ::= { tnV2AlarmNotificationsRel2 1546 }
--    tnLspFailedPreRaisedNotif          NOTIFICATION-TYPE ::= { tnV2AlarmNotificationsRel2 1547 }
--    tnLspFailedPreClearedNotif         NOTIFICATION-TYPE ::= { tnV2AlarmNotificationsRel2 1548 }
--    tnLspFailedTpRaisedNotif           NOTIFICATION-TYPE ::= { tnV2AlarmNotificationsRel2 1549 }
--    tnLspFailedTpClearedNotif          NOTIFICATION-TYPE ::= { tnV2AlarmNotificationsRel2 1550 }
--    tnLspFailedUnprotRaisedNotif       NOTIFICATION-TYPE ::= { tnV2AlarmNotificationsRel2 1551 }
--    tnLspFailedUnprotClearedNotif      NOTIFICATION-TYPE ::= { tnV2AlarmNotificationsRel2 1552 }
--    tnApeInProgressRaisedNotif         NOTIFICATION-TYPE ::= { tnV2AlarmNotificationsRel2 1553 }
--    tnApeInProgressClearedNotif        NOTIFICATION-TYPE ::= { tnV2AlarmNotificationsRel2 1554 }
--    tnBackupUnavailRaisedNotif         NOTIFICATION-TYPE ::= { tnV2AlarmNotificationsRel2 1555 }
--    tnBackupUnavailClearedNotif        NOTIFICATION-TYPE ::= { tnV2AlarmNotificationsRel2 1556 }
--    tnChannelViolationRaisedNotif      NOTIFICATION-TYPE ::= { tnV2AlarmNotificationsRel2 1557 }
--    tnChannelViolationClearedNotif     NOTIFICATION-TYPE ::= { tnV2AlarmNotificationsRel2 1558 }
--    tnColorViolationRaisedNotif        NOTIFICATION-TYPE ::= { tnV2AlarmNotificationsRel2 1559 }
--    tnColorViolationClearedNotif       NOTIFICATION-TYPE ::= { tnV2AlarmNotificationsRel2 1560 }
--    tnFeasibilityViolationRaisedNotif  NOTIFICATION-TYPE ::= { tnV2AlarmNotificationsRel2 1561 }
--    tnFeasibilityViolationClearedNotif NOTIFICATION-TYPE ::= { tnV2AlarmNotificationsRel2 1562 }
--    tnSrgDiviersityRaisedNotif         NOTIFICATION-TYPE ::= { tnV2AlarmNotificationsRel2 1563 }
--    tnSrgDiviersityClearedNotif        NOTIFICATION-TYPE ::= { tnV2AlarmNotificationsRel2 1564 }
--    tnLinkDiviersityRaisedNotif        NOTIFICATION-TYPE ::= { tnV2AlarmNotificationsRel2 1565 }
--    tnLinkDiviersityClearedNotif       NOTIFICATION-TYPE ::= { tnV2AlarmNotificationsRel2 1566 }
--    tnNunvCommRaisedNotif              NOTIFICATION-TYPE ::= { tnV2AlarmNotificationsRel2 1567 }
--    tnNunvCommClearedNotif             NOTIFICATION-TYPE ::= { tnV2AlarmNotificationsRel2 1568 }
--    tnNunvConfigRaisedNotif            NOTIFICATION-TYPE ::= { tnV2AlarmNotificationsRel2 1569 }
--    tnNunvConfigClearedNotif           NOTIFICATION-TYPE ::= { tnV2AlarmNotificationsRel2 1570 }
--    tnNunvIndeterminedRaisedNotif      NOTIFICATION-TYPE ::= { tnV2AlarmNotificationsRel2 1571 }
--    tnNunvIndeterminedClearedNotif     NOTIFICATION-TYPE ::= { tnV2AlarmNotificationsRel2 1572 }
--    tnNunvReversionRaisedNotif         NOTIFICATION-TYPE ::= { tnV2AlarmNotificationsRel2 1573 }
--    tnNunvReversionClearedNotif        NOTIFICATION-TYPE ::= { tnV2AlarmNotificationsRel2 1574 }
--    tnNunvTpBlockedRaisedNotif         NOTIFICATION-TYPE ::= { tnV2AlarmNotificationsRel2 1575 }
--    tnNunvTpBlockedClearedNotif        NOTIFICATION-TYPE ::= { tnV2AlarmNotificationsRel2 1576 }
--    tnNunvTransmissionRaisedNotif      NOTIFICATION-TYPE ::= { tnV2AlarmNotificationsRel2 1577 }
--    tnNunvTransmissionClearedNotif     NOTIFICATION-TYPE ::= { tnV2AlarmNotificationsRel2 1578 }
--    tnReadyToRevertRaisedNotif         NOTIFICATION-TYPE ::= { tnV2AlarmNotificationsRel2 1579 }
--    tnReadyToRevertClearedNotif        NOTIFICATION-TYPE ::= { tnV2AlarmNotificationsRel2 1580 }
--    tnRouteNotPossibleRaisedNotif      NOTIFICATION-TYPE ::= { tnV2AlarmNotificationsRel2 1581 }
--    tnRouteNotPossibleClearedNotif     NOTIFICATION-TYPE ::= { tnV2AlarmNotificationsRel2 1582 }
--    tnReRoutedRaisedNotif              NOTIFICATION-TYPE ::= { tnV2AlarmNotificationsRel2 1583 }
--    tnReRoutedClearedNotif             NOTIFICATION-TYPE ::= { tnV2AlarmNotificationsRel2 1584 }
--    tnTestModeRaisedNotif              NOTIFICATION-TYPE ::= { tnV2AlarmNotificationsRel2 1585 }
--    tnTestModeClearedNotif             NOTIFICATION-TYPE ::= { tnV2AlarmNotificationsRel2 1586 }
--    tnRestorationDisabledRaisedNotif   NOTIFICATION-TYPE ::= { tnV2AlarmNotificationsRel2 1587 }
--    tnRestorationDisabledClearedNotif  NOTIFICATION-TYPE ::= { tnV2AlarmNotificationsRel2 1588 }
--    tnNodeDegRaisedNotif               NOTIFICATION-TYPE ::= { tnV2AlarmNotificationsRel2 1589 }
--    tnNodeDegClearedNotif              NOTIFICATION-TYPE ::= { tnV2AlarmNotificationsRel2 1590 }
--    tnInMigrationRaisedNotif           NOTIFICATION-TYPE ::= { tnV2AlarmNotificationsRel2 1591 }
--    tnInMigrationClearedNotif          NOTIFICATION-TYPE ::= { tnV2AlarmNotificationsRel2 1592 }
--    tnSubNodeUnreachableRaisedNotif    NOTIFICATION-TYPE ::= { tnV2AlarmNotificationsRel2 1593 }
--    tnSubNodeUnreachableClearedNotif   NOTIFICATION-TYPE ::= { tnV2AlarmNotificationsRel2 1594 }
--    tnNeUnreachableRaisedNotif         NOTIFICATION-TYPE ::= { tnV2AlarmNotificationsRel2 1595 }
--    tnNeUnreachableClearedNotif        NOTIFICATION-TYPE ::= { tnV2AlarmNotificationsRel2 1596 }
--    tnOpticalParamErrRaisedNotif       NOTIFICATION-TYPE ::= { tnV2AlarmNotificationsRel2 1597 }
--    tnOpticalParamErrClearedNotif      NOTIFICATION-TYPE ::= { tnV2AlarmNotificationsRel2 1598 }
--    tnEptUploadErrRaisedNotif          NOTIFICATION-TYPE ::= { tnV2AlarmNotificationsRel2 1599 }
--    tnEptUploadErrClearedNotif         NOTIFICATION-TYPE ::= { tnV2AlarmNotificationsRel2 1600 }

    tnCommDownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1601 }

    tnCommDownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1602 }

--    obsolete
--    tnCommDegRaisedNotif     NOTIFICATION-TYPE ::= { tnV2AlarmNotificationsRel2 1603 }
--    tnCommDegClearedNotif    NOTIFICATION-TYPE ::= { tnV2AlarmNotificationsRel2 1604 }
--    tnNvMismatchRaisedNotif  NOTIFICATION-TYPE ::= { tnV2AlarmNotificationsRel2 1605 }
--    tnNvMismatchClearedNotif NOTIFICATION-TYPE ::= { tnV2AlarmNotificationsRel2 1606 }

    tnTPmonDmanfd15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1607 }

    tnTPmonDmanfd15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1608 }

    tnTPmonDmxnfd15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1609 }

    tnTPmonDmxnfd15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1610 }

    tnTPmonDmaffd15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1611 }

    tnTPmonDmaffd15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1612 }

    tnTPmonDmxffd15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1613 }

    tnTPmonDmxffd15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1614 }

    tnTPmonSlmanflr15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1615 }

    tnTPmonSlmanflr15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1616 }

    tnTPmonSlmafflr15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1617 }

    tnTPmonSlmafflr15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1618 }

    tnTPmonSlmnhli15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1619 }

    tnTPmonSlmnhli15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1620 }

    tnTPmonSlmfhli15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1621 }

    tnTPmonSlmfhli15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1622 }

    tnTPmonLmanflr15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1623 }

    tnTPmonLmanflr15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1624 }

    tnTPmonLmxnflr15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1625 }

    tnTPmonLmxnflr15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1626 }

    tnTPmonLmafflr15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1627 }

    tnTPmonLmafflr15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1628 }

    tnTPmonLmxfflr15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1629 }

    tnTPmonLmxfflr15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1630 }

    tnTPmonLmnhli15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1631 }

    tnTPmonLmnhli15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1632 }

    tnTPmonLmfhli15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1633 }

    tnTPmonLmfhli15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1634 }

    tnTPmonDmanfd1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1635 }

    tnTPmonDmanfd1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1636 }

    tnTPmonDmxnfd1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1637 }

    tnTPmonDmxnfd1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1638 }

    tnTPmonDmaffd1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1639 }

    tnTPmonDmaffd1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1640 }

    tnTPmonDmxffd1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1641 }

    tnTPmonDmxffd1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1642 }

    tnTPmonSlmnhli1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1643 }

    tnTPmonSlmnhli1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1644 }

    tnTPmonSlmfhli1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1645 }

    tnTPmonSlmfhli1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1646 }

    tnTPmonLmanflr1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1647 }

    tnTPmonLmanflr1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1648 }

    tnTPmonLmxnflr1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1649 }

    tnTPmonLmxnflr1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1650 }

    tnTPmonLmafflr1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1651 }

    tnTPmonLmafflr1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1652 }

    tnTPmonLmxfflr1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1653 }

    tnTPmonLmxfflr1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1654 }

    tnTPmonLmnhli1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1655 }

    tnTPmonLmnhli1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1656 }

    tnTPmonLmfhli1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1657 }

    tnTPmonLmfhli1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1658 }

    tnTPmonSlmfhliContinuousRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1659 }

    tnTPmonSlmfhliContinuousClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1660 }

    tnTPmonSlmnhliContinuousRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1661 }

    tnTPmonSlmnhliContinuousClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1662 }

    tnTPmonSlmxfflrContinuousRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1663 }

    tnTPmonSlmxfflrContinuousClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1664 }

    tnTPmonSlmxnflrContinuousRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1665 }

    tnTPmonSlmxnflrContinuousClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1666 }

    tnTPmonSlmanflrContinuousRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1667 }

    tnTPmonSlmanflrContinuousClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1668 }

    tnTPmonSlmafflrContinuousRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1669 }

    tnTPmonSlmafflrContinuousClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1670 }

    tnTUasOdu15MinOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1671 }

    tnTUasOdu15MinOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1672 }

    tnTSesOdu15MinOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1673 }

    tnTSesOdu15MinOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1674 }

    tnTEsOdu15MinOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1675 }

    tnTEsOdu15MinOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1676 }

    tnTBbeOdu15MinOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1677 }

    tnTBbeOdu15MinOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1678 }

    tnTFeUasOdu15MinOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1679 }

    tnTFeUasOdu15MinOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1680 }

    tnTFeSesOdu15MinOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1681 }

    tnTFeSesOdu15MinOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1682 }

    tnTFeEsOdu15MinOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1683 }

    tnTFeEsOdu15MinOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1684 }

    tnTFeBbeOdu15MinOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1685 }

    tnTFeBbeOdu15MinOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1686 }

    tnTUasOdu1DayOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1687 }

    tnTUasOdu1DayOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1688 }

    tnTSesOdu1DayOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1689 }

    tnTSesOdu1DayOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1690 }

    tnTEsOdu1DayOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1691 }

    tnTEsOdu1DayOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1692 }

    tnTBbeOdu1DayOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1693 }

    tnTBbeOdu1DayOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1694 }

    tnTFeUasOdu1DayOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1695 }

    tnTFeUasOdu1DayOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1696 }

    tnTFeSesOdu1DayOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1697 }

    tnTFeSesOdu1DayOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1698 }

    tnTFeEsOdu1DayOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1699 }

    tnTFeEsOdu1DayOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1700 }

    tnTFeBbeOdu1DayOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1701 }

    tnTFeBbeOdu1DayOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1702 }

    tnUserPayloadMismatchOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1703 }

    tnUserPayloadMismatchOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1704 }

    tnRmdCesChannelNoTdmPlRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1705 }

    tnRmdCesChannelNoTdmPlClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1706 }

    tnRmdCesChannelLPLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1707 }

    tnRmdCesChannelLPLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1708 }

    tnRmdCesChannelRPLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1709 }

    tnRmdCesChannelRPLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1710 }

    tnRmdNimLOFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1711 }

    tnRmdNimLOFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1712 }

    tnRmdIfLOSRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1713 }

    tnRmdIfLOSClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1714 }

    tnPwrSuspRxRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1715 }

    tnPwrSuspRxClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1716 }

    tnTCMAisRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1717 }

    tnTCMAisClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1718 }

    tnTOprhLane1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1719 }

    tnTOprhLane1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1720 }

    tnTOprhLane2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1721 }

    tnTOprhLane2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1722 }

    tnTOprhLane3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1723 }

    tnTOprhLane3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1724 }

    tnTOprhLane4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1725 }

    tnTOprhLane4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1726 }

    tnTOprhLane5RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1727 }

    tnTOprhLane5ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1728 }

    tnTOprhLane6RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1729 }

    tnTOprhLane6ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1730 }

    tnTOprhLane7RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1731 }

    tnTOprhLane7ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1732 }

    tnTOprhLane8RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1733 }

    tnTOprhLane8ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1734 }

    tnTOprhLane9RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1735 }

    tnTOprhLane9ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1736 }

    tnTOprhLane10RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1737 }

    tnTOprhLane10ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1738 }

    tnTOprlLane1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1739 }

    tnTOprlLane1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1740 }

    tnTOprlLane2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1741 }

    tnTOprlLane2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1742 }

    tnTOprlLane3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1743 }

    tnTOprlLane3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1744 }

    tnTOprlLane4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1745 }

    tnTOprlLane4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1746 }

    tnTOprlLane5RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1747 }

    tnTOprlLane5ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1748 }

    tnTOprlLane6RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1749 }

    tnTOprlLane6ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1750 }

    tnTOprlLane7RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1751 }

    tnTOprlLane7ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1752 }

    tnTOprlLane8RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1753 }

    tnTOprlLane8ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1754 }

    tnTOprlLane9RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1755 }

    tnTOprlLane9ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1756 }

    tnTOprlLane10RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1757 }

    tnTOprlLane10ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1758 }

    tnTOpthLane1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1759 }

    tnTOpthLane1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1760 }

    tnTOpthLane2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1761 }

    tnTOpthLane2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1762 }

    tnTOpthLane3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1763 }

    tnTOpthLane3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1764 }

    tnTOpthLane4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1765 }

    tnTOpthLane4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1766 }

    tnTOpthLane5RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1767 }

    tnTOpthLane5ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1768 }

    tnTOpthLane6RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1769 }

    tnTOpthLane6ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1770 }

    tnTOpthLane7RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1771 }

    tnTOpthLane7ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1772 }

    tnTOpthLane8RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1773 }

    tnTOpthLane8ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1774 }

    tnTOpthLane9RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1775 }

    tnTOpthLane9ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1776 }

    tnTOpthLane10RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1777 }

    tnTOpthLane10ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1778 }

    tnTOptlLane1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1779 }

    tnTOptlLane1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1780 }

    tnTOptlLane2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1781 }

    tnTOptlLane2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1782 }

    tnTOptlLane3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1783 }

    tnTOptlLane3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1784 }

    tnTOptlLane4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1785 }

    tnTOptlLane4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1786 }

    tnTOptlLane5RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1787 }

    tnTOptlLane5ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1788 }

    tnTOptlLane6RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1789 }

    tnTOptlLane6ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1790 }

    tnTOptlLane7RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1791 }

    tnTOptlLane7ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1792 }

    tnTOptlLane8RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1793 }

    tnTOptlLane8ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1794 }

    tnTOptlLane9RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1795 }

    tnTOptlLane9ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1796 }

    tnTOptlLane10RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1797 }

    tnTOptlLane10ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1798 }

    tnImageNotReadyRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         deprecated
        DESCRIPTION    "."
        ::= { tnV2AlarmNotificationsRel2 1799 }

    tnImageNotReadyClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         deprecated
        DESCRIPTION    "."
        ::= { tnV2AlarmNotificationsRel2 1800 }

    tnBadClkFreqRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1801 }

    tnBadClkFreqClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1802 }

    tnSuspectClkFreqRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1803 }

    tnSuspectClkFreqClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1804 }

    tnEsCableMismatch1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1805 }

    tnEsCableMismatch1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1806 }

    tnEsCableMismatch2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1807 }

    tnEsCableMismatch2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1808 }

    tnEsCableMismatch3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1809 }

    tnEsCableMismatch3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1810 }

    tnEsCableMismatch4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1811 }

    tnEsCableMismatch4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1812 }

    tnEsCableMismatch5RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1813 }

    tnEsCableMismatch5ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1814 }

    tnEsCableMismatch6RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1815 }

    tnEsCableMismatch6ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1816 }

    tnEsCableMismatch7RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1817 }

    tnEsCableMismatch7ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1818 }

    tnEsCableMismatch8RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1819 }

    tnEsCableMismatch8ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1820 }

    tnEsCableMismatch9RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1821 }

    tnEsCableMismatch9ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1822 }

    tnEsCableMismatch10RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1823 }

    tnEsCableMismatch10ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1824 }

    tnEsCableMismatch11RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1825 }

    tnEsCableMismatch11ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1826 }

    tnEsCableMismatch12RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1827 }

    tnEsCableMismatch12ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1828 }

    tnEsCableMismatch13RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1829 }

    tnEsCableMismatch13ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1830 }

    tnEsCableMismatch14RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1831 }

    tnEsCableMismatch14ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1832 }

    tnEsCableMismatch15RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1833 }

    tnEsCableMismatch15ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1834 }

    tnEsCableMismatch16RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1835 }

    tnEsCableMismatch16ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1836 }

    tnEsCableMismatch17RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1837 }

    tnEsCableMismatch17ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1838 }

    tnEsCableMismatch18RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1839 }

    tnEsCableMismatch18ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1840 }

    tnEsCableMismatch19RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1841 }

    tnEsCableMismatch19ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1842 }

    tnEsCableMismatch20RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1843 }

    tnEsCableMismatch20ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1844 }

    tnEsCableMismatch21RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1845 }

    tnEsCableMismatch21ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1846 }

    tnEsCableMismatch22RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1847 }

    tnEsCableMismatch22ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1848 }

    tnEsCableMismatch23RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1849 }

    tnEsCableMismatch23ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1850 }

    tnEsCableMismatch24RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1851 }

    tnEsCableMismatch24ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1852 }

    tnCardClkOffFreqRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1853 }

    tnCardClkOffFreqClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1854 }

    tnShelfInVoltMaxCurRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1855 }

    tnShelfInVoltMaxCurClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1856 }

    tnFwMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1857 }

    tnFwMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1858 }

    tnFPGAINITNSA1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1859 }

    tnFPGAINITNSA1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1860 }

    tnFPGAINITNSA2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1861 }

    tnFPGAINITNSA2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1862 }

    tnFPGAINITNSA3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1863 }

    tnFPGAINITNSA3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1864 }

    tnFPGAINITNSA4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1865 }

    tnFPGAINITNSA4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1866 }

    tnFPGAINITNSA5RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1867 }

    tnFPGAINITNSA5ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1868 }

    tnFPGAINITNSA6RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1869 }

    tnFPGAINITNSA6ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1870 }

    tnFPGAINITNSA7RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1871 }

    tnFPGAINITNSA7ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1872 }

    tnFPGAINITNSA8RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1873 }

    tnFPGAINITNSA8ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1874 }

    tnFPGAINITNSA9RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1875 }

    tnFPGAINITNSA9ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1876 }

    tnFPGAINITNSA10RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1877 }

    tnFPGAINITNSA10ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1878 }

    tnFPGATIMEOUTNSARaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1879 }

    tnFPGATIMEOUTNSAClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1880 }

    tnFPGAFAILNSARaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1881 }

    tnFPGAFAILNSAClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1882 }

    tnPacketCardInitRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1883 }

    tnPacketCardInitClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1884 }

    tnFRCRFCKSELRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1885 }

    tnFRCRFCKSELClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1886 }

    tnLOLARaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1887 }

    tnLOLAClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1888 }

    tnAPRLIMITEDRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1889 }

    tnAPRLIMITEDClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1890 }

    tnAPRFORCEDRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1891 }

    tnAPRFORCEDClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1892 }

    tnSpiReadErrorRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1893 }

    tnSpiReadErrorClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1894 }

    tnShelfInconRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1895 }

    tnShelfInconClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1896 }

    tnConfigMMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1897 }

    tnConfigMMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1898 }

    tnOpticalTestRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1899 }

    tnOpticalTestClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1900 }

    tnHwAccessFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1901 }

    tnHwAccessFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1902 }

    tnFTDEncrypt15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1903 }

    tnFTDEncrypt15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1904 }

    tnFTDEncrypt1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1905 }

    tnFTDEncrypt1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1906 }

    tnSDKMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1907 }

    tnSDKMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1908 }

    tnLOOMFIRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1909 }

    tnLOOMFIClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1910 }

    tnLOSN1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1911 }

    tnLOSN1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1912 }

    tnLOSN2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1913 }

    tnLOSN2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1914 }

    tnNotAllowPoweredRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1915 }

    tnNotAllowPoweredClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1916 }

    tnShelfLoadWarningRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1917 }

    tnShelfLoadWarningClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1918 }

    tnShelfIdMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1919 }

    tnShelfIdMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1920 }

    tnRestrictedConnectivityRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1921 }

    tnRestrictedConnectivityClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1922 }

    tnVwmIDFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1923 }

    tnVwmIDFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1924 }

    tnGfpExmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1925 }

    tnGfpExmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1926 }

    tnSyncMisc1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1927 }

    tnSyncMisc1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1928 }

    tnIntfcOprDwnRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1929 }

    tnIntfcOprDwnClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1930 }

    tnHiRamanGainRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1931 }

    tnHiRamanGainClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1932 }

    tnLoRamanGainRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1933 }

    tnLoRamanGainClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1934 }

    tnUruORaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1935 }

    tnUruOClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1936 }

    tnUruPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1937 }

    tnUruPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1938 }

    tnMplsLspDownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1939 }

    tnMplsLspDownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1940 }

--    obsolete
--    tnFrequencySlotMismatchRaisedNotif  NOTIFICATION-TYPE ::= { tnV2AlarmNotificationsRel2 1941 }
--    tnFrequencySlotMismatchClearedNotif NOTIFICATION-TYPE ::= { tnV2AlarmNotificationsRel2 1942 }

    tnMJCPFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1943 }

    tnMJCPFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1944 }

    tnEXTIFFAILRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1945 }

    tnEXTIFFAILClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1946 }

    tnSdpOprDwnRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1947 }

    tnSdpOprDwnClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1948 }

    tnSdpSpkOprDwnRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1949 }

    tnSdpSpkOprDwnClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1950 }

    tnEnvInput9ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1951 }

    tnEnvInput9ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1952 }

    tnEnvInput10ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1953 }

    tnEnvInput10ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1954 }

    tnEnvInput11ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1955 }

    tnEnvInput11ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1956 }

    tnEnvInput12ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1957 }

    tnEnvInput12ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1958 }

    tnEnvInput13ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1959 }

    tnEnvInput13ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1960 }

    tnEnvInput14ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1961 }

    tnEnvInput14ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1962 }

    tnEnvInput15ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1963 }

    tnEnvInput15ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1964 }

    tnEnvInput16ActiveRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1965 }

    tnEnvInput16ActiveClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1966 }

    tnMplsMepLocRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1967 }

    tnMplsMepLocClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1968 }

    tnMplsMepMmgRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1969 }

    tnMplsMepMmgClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1970 }

    tnMplsMepUnmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1971 }

    tnMplsMepUnmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1972 }

    tnMplsMepRdiRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1973 }

    tnMplsMepRdiClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1974 }

    tnMplsMepUnpRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1975 }

    tnMplsMepUnpClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1976 }

    tnMplsTpLspPtTypeMsmtchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1977 }

    tnMplsTpLspPtTypeMsmtchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1978 }

    tnMplsTpLspRvrtMsmtchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1979 }

    tnMplsTpLspRvrtMsmtchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1980 }

    tnNoAssociationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1981 }

    tnNoAssociationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1982 }

    tnLanSignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1983 }

    tnLanSignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1984 }

    tnFarEndSignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1985 }

    tnFarEndSignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1986 }

    tnB1SignalDegradeEgressRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1987 }

    tnB1SignalDegradeEgressClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1988 }

    tnClusterUnavailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1989 }

    tnClusterUnavailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1990 }

    tnOCCPCRRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1991 }

    tnOCCPCRClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1992 }

    tnOCCPMJRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1993 }

    tnOCCPMJClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1994 }

    tnOCCPMNRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1995 }

    tnOCCPMNClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1996 }

    tnShelfAirFilterMaintenanceRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1997 }

    tnShelfAirFilterMaintenanceClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1998 }

    tnHwrvUnknownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 1999 }

    tnHwrvUnknownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2000 }

    tnEcTypeMisRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2001 }

    tnEcTypeMisClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2002 }

    tnLatchOpenRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2003 }

    tnLatchOpenClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2004 }

    tnXcMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2005 }

    tnXcMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2006 }

    tnInvalidXcRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2007 }

    tnInvalidXcClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2008 }

    tnCardThermShutdownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2009 }

    tnCardThermShutdownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2010 }

    tnSC1LinkFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2011 }

    tnSC1LinkFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2012 }

    tnSC2LinkFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2013 }

    tnSC2LinkFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2014 }

    tnSC3LinkFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2015 }

    tnSC3LinkFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2016 }

    tnSCLinkFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2017 }

    tnSCLinkFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2018 }

    tnSC1LinkDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2019 }

    tnSC1LinkDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2020 }

    tnSC2LinkDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2021 }

    tnSC2LinkDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2022 }

    tnSC3LinkDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2023 }

    tnSC3LinkDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2024 }

    tnSCLinkDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2025 }

    tnSCLinkDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2026 }

    tnFaceplateMissingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2027 }

    tnFaceplateMissingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2028 }

    tnSoftwareErrorRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2029 }

    tnSoftwareErrorClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2030 }

    tnOAPumpLaserBiasCurrentHighCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2031 }

    tnOAPumpLaserBiasCurrentHighCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2032 }

    tnOAPumpLaserBiasCurrentHighLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2033 }

    tnOAPumpLaserBiasCurrentHighLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2034 }

    tnOAPumpLaserTempHighCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2035 }

    tnOAPumpLaserTempHighCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2036 }

    tnOAPumpLaserTempHighLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2037 }

    tnOAPumpLaserTempHighLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2038 }

    tnLossOfSignalCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2039 }

    tnLossOfSignalCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2040 }

    tnLossOfSignalLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2041 }

    tnLossOfSignalLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2042 }

    tnOprPwrLowCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2043 }

    tnOprPwrLowCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2044 }

    tnOprPwrLowLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2045 }

    tnOprPwrLowLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2046 }

    tnOprPwrHighCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2047 }

    tnOprPwrHighCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2048 }

    tnOprPwrHighLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2049 }

    tnOprPwrHighLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2050 }

    tnAmpDisabledCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2051 }

    tnAmpDisabledCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2052 }

    tnAmpDisabledLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2053 }

    tnAmpDisabledLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2054 }

    tnAmpGainTooHighCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2055 }

    tnAmpGainTooHighCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2056 }

    tnAmpGainTooHighLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2057 }

    tnAmpGainTooHighLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2058 }

    tnAmpGainTooLowCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2059 }

    tnAmpGainTooLowCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2060 }

    tnAmpGainTooLowLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2061 }

    tnAmpGainTooLowLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2062 }

    tnBandLossOfSignalCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2063 }

    tnBandLossOfSignalCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2064 }

    tnBandLossOfSignalLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2065 }

    tnBandLossOfSignalLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2066 }

    tnLotOutCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2067 }

    tnLotOutCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2068 }

    tnLotOutLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2069 }

    tnLotOutLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2070 }

    tnPwrMaxGainCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2071 }

    tnPwrMaxGainCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2072 }

    tnPwrMaxGainLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2073 }

    tnPwrMaxGainLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2074 }

    tnIntOhFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2075 }

    tnIntOhFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2076 }

    tnInvalidModuleRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2077 }

    tnInvalidModuleClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2078 }

    tnIntTsiFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2079 }

    tnIntTsiFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2080 }

    tnEcModeMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2081 }

    tnEcModeMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2082 }

    tnDbCrcTypeMisRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2083 }

    tnDbCrcTypeMisClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2084 }

    tnCardPowerOffRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2085 }

    tnCardPowerOffClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2086 }

    tnCardFailCruRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2087 }

    tnCardFailCruClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2088 }

    tnShelfInventoryErrorRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2089 }

    tnShelfInventoryErrorClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2090 }

    tnShelfInventoryMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2091 }

    tnShelfInventoryMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2092 }

    tnSyncChannelARaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2093 }

    tnSyncChannelAClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2094 }

    tnSyncChannelBRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2095 }

    tnSyncChannelBClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2096 }

    tnSyncChannelBothRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2097 }

    tnSyncChannelBothClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2098 }

    tnCKWKATMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2099 }

    tnCKWKATMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2100 }

    tnInventoryErrModRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2101 }

    tnInventoryErrModClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2102 }

    tnLnkSpdDegRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2103 }

    tnLnkSpdDegClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2104 }

    tnBdLnkSpdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2105 }

    tnBdLnkSpdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2106 }

    tnFopOperationMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2107 }

    tnFopOperationMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2108 }

    tnFopProvisioningMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2109 }

    tnFopProvisioningMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2110 }

    tnFopSwitchMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2111 }

    tnFopSwitchMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2112 }

    tnFopNoResponseRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2113 }

    tnFopNoResponseClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2114 }

    tnFopInconsistentRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2115 }

    tnFopInconsistentClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2116 }

    tnApsWorkingForceSwitchedBackToWorkingFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2117 }

    tnApsWorkingForceSwitchedBackToWorkingFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2118 }

    tnApsWorkingForceSwitchedToProtectFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2119 }

    tnApsWorkingForceSwitchedToProtectFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2120 }

    tnApsLockoutOfProtectionFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2121 }

    tnApsLockoutOfProtectionFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2122 }

    tnApsWorkingManualSwitchedBackToWorkingFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2123 }

    tnApsWorkingManualSwitchedBackToWorkingFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2124 }

    tnApsWorkingManualSwitchedToProtectFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2125 }

    tnApsWorkingManualSwitchedToProtectFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2126 }

    tnApsSwitchedToWorkFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2127 }

    tnApsSwitchedToWorkFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2128 }

    tnApsWorkingSwitchedToProtectFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2129 }

    tnApsWorkingSwitchedToProtectFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2130 }

    tnWtrFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2131 }

    tnWtrFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2132 }

    tnApsExerciseOnWorkingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2133 }

    tnApsExerciseOnWorkingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2134 }

    tnApsExerciseOnProtectionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2135 }

    tnApsExerciseOnProtectionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2136 }

    tnApsExerciseOnWorkingFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2137 }

    tnApsExerciseOnWorkingFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2138 }

    tnApsExerciseOnProtectionFeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2139 }

    tnApsExerciseOnProtectionFeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2140 }

    tnAprBandRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2141 }


    tnAprBandClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2142 }

    tnEqptDgrOchOutCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2143 }

    tnEqptDgrOchOutCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2144 }

    tnEqptDgrOchOutLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2145 }

    tnEqptDgrOchOutLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2146 }

    tnWavelengthTrackerFailureCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2147 }

    tnWavelengthTrackerFailureCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2148 }

    tnWavelengthTrackerFailureLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2149 }

    tnWavelengthTrackerFailureLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2150 }

    tnOchXcWidthNarrowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2151 }

    tnOchXcWidthNarrowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2152 }

    tnConfigCardMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2153 }

    tnConfigCardMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2154 }

    tnFuseFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2155 }

    tnFuseFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2156 }

    tnFilterMissingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2157 }

    tnFilterMissingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2158 }

    tnFilterCloggedCriticalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2159 }

    tnFilterCloggedCriticalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2160 }

    tnFilterCloggedHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2161 }

    tnFilterCloggedHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2162 }

--    obsolete
--    tnLicenseViolationERRaisedNotif  NOTIFICATION-TYPE  ::= { tnV2AlarmNotificationsRel2 2163 }
--    tnLicenseViolationERClearedNotif NOTIFICATION-TYPE ::= { tnV2AlarmNotificationsRel2 2164 }
--    tnLicenseViolationHCRaisedNotif  NOTIFICATION-TYPE  ::= { tnV2AlarmNotificationsRel2 2165 }
--    tnLicenseViolationHCClearedNotif NOTIFICATION-TYPE  ::= { tnV2AlarmNotificationsRel2 2166 }

    tnOmsSSFCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2167 }

    tnOmsSSFCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2168 }

    tnOmsSSFLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2169 }

    tnOmsSSFLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2170 }

    tnCruAlignFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2171 }

    tnCruAlignFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2172 }

    tnOcmMaintRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2173 }

    tnOcmMaintClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2174 }

    tnOcmMaintCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2175 }

    tnOcmMaintCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2176 }

    tnOcmMaintLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2177 }

    tnOcmMaintLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2178 }

    tnOcmMaintAddRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2179 }

    tnOcmMaintAddClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2180 }

    tnOcmMaintDrpRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2181 }

    tnOcmMaintDrpClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2182 }

    tnLossOfPLDCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2183 }

    tnLossOfPLDCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2184 }

    tnLossOfPLDLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2185 }

    tnLossOfPLDLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2186 }

    tnRemVoltageFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2187 }

    tnRemVoltageFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2188 }

    tnBpskFrmtNotSuppRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2189 }

    tnBpskFrmtNotSuppClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2190 }

    tnUnprovChanRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2191 }

    tnUnprovChanClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2192 }

    tnUnprovChanOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2193 }

    tnUnprovChanOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2194 }

    tnUnprovChanOutCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2195 }

    tnUnprovChanOutCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2196 }

    tnUnprovChanOutLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2197 }

    tnUnprovChanOutLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2198 }

--    obsolete
--    tnPwrVOARailedLowCRaisedNotif  NOTIFICATION-TYPE ::= { tnV2AlarmNotificationsRel2 2199 }
--    tnPwrVOARailedLowCClearedNotif NOTIFICATION-TYPE ::= { tnV2AlarmNotificationsRel2 2200 }

    tnPwrVOARailedLowLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2201 }

    tnPwrVOARailedLowLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2202 }

    tnTPmonSlmnuai15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2203 }

    tnTPmonSlmnuai15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2204 }

    tnTPmonSlmfuai15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2205 }

    tnTPmonSlmfuai15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2206 }

    tnTPmonSlmnuai1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2207 }

    tnTPmonSlmnuai1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2208 }

    tnTPmonSlmfuai1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2209 }

    tnTPmonSlmfuai1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2210 }

    tnTPmonSlmnuaiContinuousRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2211 }

    tnTPmonSlmnuaiContinuousClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2212 }

    tnTPmonSlmfuaiContinuousRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2213 }

    tnTPmonSlmfuaiContinuousClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2214 }

    tnNuatRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2215 }

    tnNuatClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2216 }

    tnFuatRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2217 }

    tnFuatClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2218 }

    tnSyncIfTimingRef3AlarmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2219 }

    tnSyncIfTimingRef3AlarmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2220 }

    tnMixedOperationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2221 }

    tnMixedOperationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2222 }

    tnBandwidthExceededRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2223 }

    tnBandwidthExceededClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2224 }

    tnProtectionFrozenRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2225 }

    tnProtectionFrozenClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2226 }

    tnLotRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2227 }

    tnLotClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2228 }

    tnUruOtsRxCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2229 }

    tnUruOtsRxCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2230 }

    tnUruOtsRxLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2231 }

    tnUruOtsRxLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2232 }

    tnUruOtsTxCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2233 }

    tnUruOtsTxCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2234 }

    tnUruOtsTxLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2235 }

    tnUruOtsTxLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2236 }

    tnDbBkupIPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2237 }

    tnDbBkupIPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2238 }

    tnDbRstrIPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2239 }

    tnDbRstrIPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2240 }

    tnCardErrorRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2241 }

    tnCardErrorClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2242 }

    tnMacAllocationPendingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2243 }

    tnMacAllocationPendingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2244 }

    tnHiSerRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2245 }

    tnHiSerClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2246 }

    tnTodNotSupportedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2247 }

    tnTodNotSupportedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2248 }

    tnLTIRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2249 }

    tnLTIClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2250 }

    tnSsmQLDegRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2251 }

    tnSsmQLDegClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2252 }

    tnSyncUnlockRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2253 }

    tnSyncUnlockClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2254 }

    tnLtiT4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2255 }

    tnLtiT4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2256 }

    tnLOEsmCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2257 }

    tnLOEsmCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2258 }

    tnTFreoffHigh15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2259 }

    tnTFreoffHigh15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2260 }

    tnTFreoffHigh1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2261 }

    tnTFreoffHigh1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2262 }

    tnTFreoffLow15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2263 }

    tnTFreoffLow15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2264 }

    tnTFreoffLow1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2265 }

    tnTFreoffLow1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2266 }

    tnOSPFADJv3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2267 }

    tnOSPFADJv3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2268 }

    tnPortProvRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2269 }

    tnPortProvClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2270 }

    tnOchXcTechErrRxRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2271 }

    tnOchXcTechErrRxClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2272 }

    tnOchXcTechErrTxRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2273 }

    tnOchXcTechErrTxClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2274 }

    tnCrdPwrIntFltRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2275 }

    tnCrdPwrIntFltClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2276 }

    tnPTPINPUTDEGRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2277 }

    tnPTPINPUTDEGClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2278 }

    tnTPtoffacump2p15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2279 }

    tnTPtoffacump2p15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2280 }

    tnTPtoffacump2p1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2281 }

    tnTPtoffacump2p1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2282 }

    tnTPterrefl15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2283 }

    tnTPterrefl15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2284 }

    tnTPterrefl1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2285 }

    tnTPterrefl1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2286 }

    tnTPteffefh15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2287 }

    tnTPteffefh15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2288 }

    tnTPteffefh1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2289 }

    tnTPteffefh1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2290 }

    tnMacShortageRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2291 }

    tnMacShortageClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2292 }

    tnFanMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2293 }

    tnFanMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2294 }

    tnDegTransRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2295 }

    tnDegTransClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2296 }

    tnOpsProtFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2297 }

    tnOpsProtFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2298 }

    tnOpsProtRedunLossRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2299 }

    tnOpsProtRedunLossClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2300 }

    tnRAMCAPACITYWARNINGRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2301 }

    tnRAMCAPACITYWARNINGClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2302 }

    tnUsAlsLagRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2303 }

    tnUsAlsLagClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2304 }

    tnLOSN3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2305 }

    tnLOSN3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2306 }

    tnSHELFMODERaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2307 }

    tnSHELFMODEClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2308 }

    tnLicActiveCLMUnavailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2309 }

    tnLicActiveCLMUnavailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2310 }

    tnLicCertNotfoundRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2311 }

    tnLicCertNotfoundClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2312 }

    tnLicClmNotconfigRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2313 }

    tnLicClmNotconfigClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2314 }

    tnLicCLMSyserrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2315 }

    tnLicCLMSyserrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2316 }

    tnLicCLMUnavailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2317 }

    tnLicCLMUnavailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2318 }

    tnLicEntlMissingLine100GLHRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2319 }

    tnLicEntlMissingLine100GLHClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2320 }

    tnLicEntlMissingLine100GMetroRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2321 }

    tnLicEntlMissingLine100GMetroClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2322 }

    tnLicEntlMissingLineAlienRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2323 }

    tnLicEntlMissingLineAlienClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2324 }

    tnLicEntlMissingLineEncryptionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2325 }

    tnLicEntlMissingLineEncryptionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2326 }

    tnLicEntlMissingLineUnkeyedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2327 }

    tnLicEntlMissingLineUnkeyedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2328 }

    tnLicEntlExceededLine100GLHRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2329 }

    tnLicEntlExceededLine100GLHClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2330 }

    tnLicEntlExceededLine100GMetroRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2331 }

    tnLicEntlExceededLine100GMetroClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2332 }

    tnLicEntlExceededLineAlienRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2333 }

    tnLicEntlExceededLineAlienClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2334 }

    tnLicEntlExceededLineEncryptionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2335 }

    tnLicEntlExceededLineEncryptionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2336 }

    tnLicEntlExceededLineUnkeyedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2337 }

    tnLicEntlExceededLineUnkeyedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2338 }

    tnLicJWSErrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2339 }

    tnLicJWSErrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2340 }

    tnLicTimeOosyncRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2341 }

    tnLicTimeOosyncClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2342 }

    tnLicPoolkeyNotfoundRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2343 }

    tnLicPoolkeyNotfoundClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2344 }

    tnLicClientNotRegisteredRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2345 }

    tnLicClientNotRegisteredClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2346 }

    tnUnprovChanLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2347 }

    tnUnprovChanLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2348 }

    tnAllChanMissLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2349 }

    tnAllChanMissLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2350 }

    tnPwrMarginLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2351 }

    tnPwrMarginLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2352 }

    tnTestLaserFailureDeviceRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2353 }

    tnTestLaserFailureDeviceClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2354 }

    tnNoiseLoadingAmpFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2355 }

    tnNoiseLoadingAmpFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2356 }

    tnCPCCOMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2357 }

    tnCPCCOMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2358 }

    tnPTPCOMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2359 }

    tnPTPCOMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2360 }

    tnEQPTCPCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2361 }

    tnEQPTCPCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2362 }

    tnCPCALIGNRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2363 }

    tnCPCALIGNClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2364 }

    tnCPCALIGNFAILRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2365 }

    tnCPCALIGNFAILClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2366 }

    tnPktBkplSC1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2367 }

    tnPktBkplSC1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2368 }

    tnPktBkplSC2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2369 }

    tnPktBkplSC2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2370 }

    tnPktBkplSC3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2371 }

    tnPktBkplSC3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2372 }

    tnPktBkplSC4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2373 }

    tnPktBkplSC4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2374 }

    tnPktBkplSC5RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2375 }

    tnPktBkplSC5ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2376 }

    tnPktBkplSC6RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2377 }

    tnPktBkplSC6ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2378 }

    tnSdpMeshOprDwnRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2379 }

    tnSdpMeshOprDwnClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2380 }

    tnSdpTlsMacAddrLimitAlarmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2381 }

    tnSdpTlsMacAddrLimitAlarmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2382 }

    tnLicClmAddressInvalidRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2383 }

    tnLicClmAddressInvalidClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2384 }

    tnLicClmUrlInvalidRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2385 }

    tnLicClmUrlInvalidClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2386 }

    tnLicJWSErrResponseRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2387 }

    tnLicJWSErrResponseClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2388 }

    tnDegUcbRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2389 }

    tnDegUcbClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2390 }

    tnTSIFreezeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2391 }

    tnTSIFreezeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2392 }

    tnAutoSyncSwT4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2393 }

    tnAutoSyncSwT4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2394 }

    tnContInfraRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2395 }

    tnContInfraClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2396 }

    tnAllChanHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2397 }

    tnAllChanHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2398 }

    tnAllChanLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2399 }

    tnAllChanLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2400 }

    tnAllChanHighOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2401 }

    tnAllChanHighOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2402 }

    tnAllChanLowOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2403 }

    tnAllChanLowOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2404 }

    tnHiEdfaGainRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2405 }

    tnHiEdfaGainClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2406 }

    tnHiEdfaGainOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2407 }

    tnHiEdfaGainOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2408 }

    tnLoEdfaGainRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2409 }

    tnLoEdfaGainClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2410 }

    tnLoEdfaGainOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2411 }

    tnLoEdfaGainOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2412 }

    tnOprHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2413 }

    tnOprHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2414 }

    tnOprLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2415 }

    tnOprLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2416 }

    tnOprHighOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2417 }

    tnOprHighOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2418 }

    tnOprLowOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2419 }

    tnOprLowOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2420 }

    tnBkplLinkInitRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2421 }

    tnBkplLinkInitClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2422 }

    tnRampumpbaseRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2423 }

    tnRampumpbaseClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2424 }

    tnHirampumpbrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2425 }

    tnHirampumpbrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2426 }

    tnPktLOSSRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2427 }

    tnPktLOSSClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2428 }

    tnPktSizeMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2429 }

    tnPktSizeMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2430 }

    tnPtTooLargeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2431 }

    tnPtTooLargeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2432 }

    tnPtTooSmallRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2433 }

    tnPtTooSmallClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2434 }

    tnEncapBufferOverrunRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2435 }

    tnEncapBufferOverrunClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2436 }

    tnDecapBufferOverrunRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2437 }

    tnDecapBufferOverrunClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2438 }

    tnDecapBufferUnderrunRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2439 }

    tnDecapBufferUnderrunClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2440 }

    tnCpriHiberRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2441 }

    tnCpriHiberClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2442 }

    tnCpriHiserRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2443 }

    tnCpriHiserClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2444 }

    tnCPRILOFRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2445 }

    tnCPRILOFClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2446 }

    tnCPRILOSRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2447 }

    tnCPRILOSClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2448 }

    tnCPRIRAIRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2449 }

    tnCPRIRAIClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2450 }

    tnGainOverPlannedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2451 }

    tnGainOverPlannedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2452 }

    tnGainUnderPlannedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2453 }

    tnGainUnderPlannedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2454 }

    tnConfigNotValidRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2455 }

    tnConfigNotValidClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2456 }

    tnDbArRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2457 }

    tnDbArClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2458 }

    tnEqptAccessDgrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2459 }

    tnEqptAccessDgrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2460 }

    tnTopoMissingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2461 }

    tnTopoMissingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2462 }

    tnZtpIpRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2463 }

    tnZtpIpClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2464 }

    tnZtpFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2465 }

    tnZtpFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2466 }

    tnPktBkplMateRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "Packet Backplane Link Down to Mate Card Raise."
        ::= { tnV2AlarmNotificationsRel2 2467 }

    tnPktBkplMateClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "Packet Backplane Link Down to Mate Card Clear."
        ::= { tnV2AlarmNotificationsRel2 2468 }

    tnPcfgdwnlRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2469 }

    tnPcfgdwnlClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2470 }

    tnODNCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2471 }

    tnODNCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2472 }

    tnDecryptionFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2473 }

    tnDecryptionFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2474 }

    tnEncrLoopbackRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2475 }

    tnEncrLoopbackClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2476 }

    tnEncrLinkfailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2477 }

    tnEncrLinkfailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2478 }

    tnPnacPortBasedHWFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2479 }

    tnPnacPortBasedHWFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2480 }

    tnBITSNotSupportedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2481 }

    tnBITSNotSupportedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2482 }

    tnPktBkplComRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2483 }

    tnPktBkplComClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2484 }

    tnRoeLOLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2485 }

    tnRoeLOLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2486 }

    tnDbBuRfsIncRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2487 }

    tnDbBuRfsIncClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2488 }

    tnOchXcInvalidRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2489 }

    tnOchXcInvalidClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2490 }

    tnIntTempOptOORRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2491 }

    tnIntTempOptOORClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2492 }

    tnBGPPEER1NESTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2493 }

    tnBGPPEER1NESTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2494 }

    tnBGPPEER2NESTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2495 }

    tnBGPPEER2NESTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2496 }

    tnBGPPEER3NESTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2497 }

    tnBGPPEER3NESTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2498 }

    tnBGPPEER4NESTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2499 }

    tnBGPPEER4NESTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2500 }

    tnQsfpHeaterFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2501 }

    tnQsfpHeaterFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2502 }

    tnCpcMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2503 }

    tnCpcMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2504 }

    tnAllChanHighLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2505 }

    tnAllChanHighLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2506 }

    tnAllChanLowLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2507 }

    tnAllChanLowLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2508 }

    tnAllChanHighOutLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2509 }

    tnAllChanHighOutLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2510 }

    tnAllChanLowOutLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2511 }

    tnAllChanLowOutLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2512 }

    tnGainOverPlannedLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2513 }

    tnGainOverPlannedLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2514 }

    tnGainUnderPlannedLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2515 }

    tnGainUnderPlannedLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2516 }

    tnPwrVOARailedLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2517 }

    tnPwrVOARailedLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2518 }

    tnNvmLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2519 }

    tnNvmLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2520 }

    tnRamLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2521 }

    tnRamLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2522 }

    tnAprRamPumpOrlRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2523 }

    tnAprRamPumpOrlClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2524 }

    tnDuplicateMainShelfRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2525 }

    tnDuplicateMainShelfClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2526 }

    tnExShelfUnknownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2527 }

    tnExShelfUnknownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2528 }

    tnExShelfMissingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2529 }

    tnExShelfMissingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2530 }

    tnDispShortPushRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2531 }

    tnDispShortPushClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2532 }

    tnDispLongPushRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2533 }

    tnDispLongPushClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2534 }

    tnDispAttentionRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2535 }

    tnDispAttentionClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2536 }

    tnDispDialogRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2537 }

    tnDispDialogClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2538 }

    tnTQmarginL15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2539 }

    tnTQmarginL15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2540 }

    tnTQmarginL1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2541 }

    tnTQmarginL1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2542 }

    tnNETRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2543 }

    tnNETClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2544 }

    tnIfReplUnitMissMODRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2545 }

    tnIfReplUnitMissMODClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2546 }

    tnCardDgrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2547 }

    tnCardDgrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2548 }

    tnLOLCKRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2549 }

    tnLOLCKClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2550 }

    tnFODRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2551 }

    tnFODClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2552 }

    tnFanModFailLeftRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2553 }

    tnFanModFailLeftClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2554 }

    tnFanModFailCenterRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2555 }

    tnFanModFailCenterClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2556 }

    tnFanModFailRightRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2557 }

    tnFanModFailRightClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2558 }

    tnTPmonRoeDecapPktsDropped15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2559 }

    tnTPmonRoeDecapPktsDropped15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2560 }

    tnTPmonRoeDecapPktsDropped1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2561 }

    tnTPmonRoeDecapPktsDropped1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2562 }

    tnTPmonMapperTxRoEPkts15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2563 }

    tnTPmonMapperTxRoEPkts15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2564 }

    tnTPmonMapperTxRoEPkts1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2565 }

    tnTPmonMapperTxRoEPkts1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2566 }

    tnTPmonMapperTxRoEBytes15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2567 }

    tnTPmonMapperTxRoEBytes15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2568 }

    tnTPmonMapperTxRoEBytes1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2569 }

    tnTPmonMapperTxRoEBytes1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2570 }

    tnTPmonMapperTxDropRoEPkts15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2571 }

    tnTPmonMapperTxDropRoEPkts15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2572 }

    tnTPmonMapperTxDropRoEPkts1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2573 }

    tnTPmonMapperTxDropRoEPkts1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2574 }

    tnTPmonMapperEncapQueueOverrun15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2575 }

    tnTPmonMapperEncapQueueOverrun15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2576 }

    tnTPmonMapperEncapQueueOverrun1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2577 }

    tnTPmonMapperEncapQueueOverrun1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2578 }

    tnTPmonMapperGSMTimeSlotMismatch15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2579 }

    tnTPmonMapperGSMTimeSlotMismatch15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2580 }

    tnTPmonMapperGSMTimeSlotMismatch1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2581 }

    tnTPmonMapperGSMTimeSlotMismatch1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2582 }

    tnTPmonDemapperRxRoEPkts15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2583 }

    tnTPmonDemapperRxRoEPkts15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2584 }

    tnTPmonDemapperRxRoEPkts1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2585 }

    tnTPmonDemapperRxRoEPkts1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2586 }

    tnTPmonDemapperRxRoEBytes15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2587 }

    tnTPmonDemapperRxRoEBytes15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2588 }

    tnTPmonDemapperRxRoEBytes1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2589 }

    tnTPmonDemapperRxRoEBytes1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2590 }

    tnTPmonDemapperDecapQueueOverrun15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2591 }

    tnTPmonDemapperDecapQueueOverrun15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2592 }

    tnTPmonDemapperDecapQueueOverrun1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2593 }

    tnTPmonDemapperDecapQueueOverrun1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2594 }

    tnTPmonDemapperDecapQueueUnderrun15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2595 }

    tnTPmonDemapperDecapQueueUnderrun15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2596 }

    tnTPmonDemapperDecapQueueUnderrun1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2597 }

    tnTPmonDemapperDecapQueueUnderrun1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2598 }

    tnTPmonDemapperDecapPktMissing15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2599 }

    tnTPmonDemapperDecapPktMissing15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2600 }

    tnTPmonDemapperDecapPktMissing1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2601 }

    tnTPmonDemapperDecapPktMissing1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2602 }

    tnTPmonDemapperDecapPktSizeMismatch15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2603 }

    tnTPmonDemapperDecapPktSizeMismatch15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2604 }

    tnTPmonDemapperDecapPktSizeMismatch1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2605 }

    tnTPmonDemapperDecapPktSizeMismatch1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2606 }

    tnTPmonFrameAssErrorCount15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2607 }

    tnTPmonFrameAssErrorCount15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2608 }

    tnTPmonFrameAssErrorCount1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2609 }

    tnTPmonFrameAssErrorCount1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2610 }

    tnTPmonFrameSmdErrorCount15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2611 }

    tnTPmonFrameSmdErrorCount15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2612 }

    tnTPmonFrameSmdErrorCount1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2613 }

    tnTPmonFrameSmdErrorCount1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2614 }

    tnTPmonFrameAssOkCount15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2615 }

    tnTPmonFrameAssOkCount15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2616 }

    tnTPmonFrameAssOkCount1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2617 }

    tnTPmonFrameAssOkCount1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2618 }

    tnTPmonFragCountRx15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2619 }

    tnTPmonFragCountRx15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2620 }

    tnTPmonFragCountRx1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2621 }

    tnTPmonFragCountRx1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2622 }

    tnTPmonFragCountTx15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2623 }

    tnTPmonFragCountTx15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2624 }

    tnTPmonFragCountTx1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2625 }

    tnTPmonFragCountTx1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2626 }

    tnTPmonEmacHighCapacityOctets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2627 }

    tnTPmonEmacHighCapacityOctets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2628 }

    tnTPmonEmacHighCapacityOctets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2629 }

    tnTPmonEmacHighCapacityOctets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2630 }

    tnTPmonEmacHighCapacityPkts15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2631 }

    tnTPmonEmacHighCapacityPkts15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2632 }

    tnTPmonEmacHighCapacityPkts1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2633 }

    tnTPmonEmacHighCapacityPkts1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2634 }

    tnTPmonEmacIfInDiscards15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2635 }

    tnTPmonEmacIfInDiscards15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2636 }

    tnTPmonEmacIfInDiscards1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2637 }

    tnTPmonEmacIfInDiscards1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2638 }

    tnTPmonEmacIfInErrors15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2639 }

    tnTPmonEmacIfInErrors15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2640 }

    tnTPmonEmacIfInErrors1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2641 }

    tnTPmonEmacIfInErrors1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2642 }

    tnTPmonEmacIfInOctets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2643 }

    tnTPmonEmacIfInOctets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2644 }

    tnTPmonEmacIfInOctets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2645 }

    tnTPmonEmacIfInOctets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2646 }

    tnTPmonEmacIfInPackets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2647 }

    tnTPmonEmacIfInPackets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2648 }

    tnTPmonEmacIfInPackets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2649 }

    tnTPmonEmacIfInPackets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2650 }

    tnTPmonEmacIfOutDiscards15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2651 }

    tnTPmonEmacIfOutDiscards15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2652 }

    tnTPmonEmacIfOutDiscards1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2653 }

    tnTPmonEmacIfOutDiscards1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2654 }

    tnTPmonEmacIfOutErrors15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2655 }

    tnTPmonEmacIfOutErrors15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2656 }

    tnTPmonEmacIfOutErrors1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2657 }

    tnTPmonEmacIfOutErrors1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2658 }

    tnTPmonEmacIfOutOctets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2659 }

    tnTPmonEmacIfOutOctets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2660 }

    tnTPmonEmacIfOutOctets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2661 }

    tnTPmonEmacIfOutOctets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2662 }

    tnTPmonEmacIfOutPackets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2663 }

    tnTPmonEmacIfOutPackets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2664 }

    tnTPmonEmacIfOutPackets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2665 }

    tnTPmonEmacIfOutPackets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2666 }

    tnTPmonPmacHighCapacityOctets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2667 }

    tnTPmonPmacHighCapacityOctets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2668 }

    tnTPmonPmacHighCapacityOctets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2669 }

    tnTPmonPmacHighCapacityOctets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2670 }

    tnTPmonPmacHighCapacityPkts15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2671 }

    tnTPmonPmacHighCapacityPkts15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2672 }

    tnTPmonPmacHighCapacityPkts1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2673 }

    tnTPmonPmacHighCapacityPkts1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2674 }

    tnTPmonPmacIfInDiscards15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2675 }

    tnTPmonPmacIfInDiscards15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2676 }

    tnTPmonPmacIfInDiscards1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2677 }

    tnTPmonPmacIfInDiscards1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2678 }

    tnTPmonPmacIfInErrors15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2679 }

    tnTPmonPmacIfInErrors15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2680 }

    tnTPmonPmacIfInErrors1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2681 }

    tnTPmonPmacIfInErrors1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2682 }

    tnTPmonPmacIfInOctets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2683 }

    tnTPmonPmacIfInOctets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2684 }

    tnTPmonPmacIfInOctets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2685 }

    tnTPmonPmacIfInOctets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2686 }

    tnTPmonPmacIfInPackets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2687 }

    tnTPmonPmacIfInPackets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2688 }

    tnTPmonPmacIfInPackets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2689 }

    tnTPmonPmacIfInPackets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2690 }

    tnTPmonPmacIfOutDiscards15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2691 }

    tnTPmonPmacIfOutDiscards15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2692 }

    tnTPmonPmacIfOutDiscards1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2693 }

    tnTPmonPmacIfOutDiscards1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2694 }

    tnTPmonPmacIfOutErrors15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2695 }

    tnTPmonPmacIfOutErrors15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2696 }

    tnTPmonPmacIfOutErrors1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2697 }

    tnTPmonPmacIfOutErrors1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2698 }

    tnTPmonPmacIfOutOctets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2699 }

    tnTPmonPmacIfOutOctets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2700 }

    tnTPmonPmacIfOutOctets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2701 }

    tnTPmonPmacIfOutOctets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2702 }

    tnTPmonPmacIfOutPackets15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2703 }

    tnTPmonPmacIfOutPackets15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2704 }

    tnTPmonPmacIfOutPackets1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2705 }

    tnTPmonPmacIfOutPackets1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2706 }

    tnPFFANFAULTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2707 }

    tnPFFANFAULTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2708 }

    tnASEAMPFAILRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2709 }

    tnASEAMPFAILClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2710 }

    tnConfigPortFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2711 }

    tnConfigPortFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2712 }

    tnAdjHiFiberLossRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2713 }

    tnAdjHiFiberLossClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2714 }

    tnAdjMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2715 }

    tnAdjMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2716 }

    tnAdjNotFoundRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2717 }

    tnAdjNotFoundClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2718 }

    tnAdjUnexpRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2719 }

    tnAdjUnexpClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2720 }

    tnCvFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2721 }

    tnCvFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2722 }

    tnLicWaveLengthCapEntlMissingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2723 }

    tnLicWaveLengthCapEntlMissingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2724 }

    tnLicWaveLengthCapEntlExceededRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2725 }

    tnLicWaveLengthCapEntlExceededClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2726 }

    tnLicGenericSpectrumEntlMissingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2727 }

    tnLicGenericSpectrumEntlMissingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2728 }

    tnLicGenericSpectrumEntlExceededRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2729 }

    tnLicGenericSpectrumEntlExceededClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2730 }

    tnLicUnidirRegenEntlMissingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2731 }

    tnLicUnidirRegenEntlMissingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2732 }

    tnLicUnidirRegenEntlExceededRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2733 }

    tnLicUnidirRegenEntlExceededClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2734 }

    tnRmdSlmTableFullRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2735 }

    tnRmdSlmTableFullClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2736 }

    tnRmdHighTempRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2737 }

    tnRmdHighTempClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2738 }

    tnRmdMepUNPRRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2739 }

    tnRmdMepUNPRClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2740 }

    tnCardDgrOmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2741 }

    tnCardDgrOmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2742 }

    tnHiSpanLossRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2743 }

    tnHiSpanLossClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2744 }

    tnPnacPortAuthFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2745 }

    tnPnacPortAuthFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2746 }

    tnRmdDInitRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2747 }

    tnRmdDInitClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2748 }

    tnOchFailedLLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2749 }

    tnOchFailedLLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2750 }

    tnOchFailedLLOutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2751 }

    tnOchFailedLLOutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2752 }

    tnTRNGNoiseSourceFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2753 }

    tnTRNGNoiseSourceFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2754 }

    tnTRNGConditioningFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2755 }

    tnTRNGConditioningFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2756 }

    tnTRNGFipsTestFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2757 }

    tnTRNGFipsTestFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2758 }

    tnTRNGSelfTestFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2759 }

    tnTRNGSelfTestFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2760 }

    tnTRNGHwFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2761 }

    tnTRNGHwFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2762 }

    tnThermShutdModRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2763 }

    tnThermShutdModClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2764 }

    tnTempOorModRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2765 }

    tnTempOorModClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2766 }

    tnPortFPGAInit1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2767 }

    tnPortFPGAInit1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2768 }

    tnPortFPGAInit2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2769 }

    tnPortFPGAInit2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2770 }

    tnPortFPGAInit3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2771 }

    tnPortFPGAInit3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2772 }

    tnPortFPGAInit4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2773 }

    tnPortFPGAInit4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2774 }

    tnPortFPGAInit5RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2775 }

    tnPortFPGAInit5ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2776 }

    tnPortFPGAInit6RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2777 }

    tnPortFPGAInit6ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2778 }

    tnPortFPGAInit7RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2779 }

    tnPortFPGAInit7ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2780 }

    tnPortFPGAInit8RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2781 }

    tnPortFPGAInit8ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2782 }

    tnPortFPGAInit9RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2783 }

    tnPortFPGAInit9ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2784 }

    tnPortFPGAInit10RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2785 }

    tnPortFPGAInit10ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2786 }

    tnPortFPGATimeoutRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2787 }

    tnPortFPGATimeoutClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2788 }

    tnPortFPGAInitNSA1RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2789 }

    tnPortFPGAInitNSA1ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2790 }

    tnPortFPGAInitNSA2RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2791 }

    tnPortFPGAInitNSA2ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2792 }

    tnPortFPGAInitNSA3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2793 }

    tnPortFPGAInitNSA3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2794 }

    tnPortFPGAInitNSA4RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2795 }

    tnPortFPGAInitNSA4ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2796 }

    tnPortFPGAInitNSA5RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2797 }

    tnPortFPGAInitNSA5ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2798 }

    tnPortFPGAInitNSA6RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2799 }

    tnPortFPGAInitNSA6ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2800 }

    tnPortFPGAInitNSA7RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2801 }

    tnPortFPGAInitNSA7ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2802 }

    tnPortFPGAInitNSA8RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2803 }

    tnPortFPGAInitNSA8ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2804 }

    tnPortFPGAInitNSA9RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2805 }

    tnPortFPGAInitNSA9ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2806 }

    tnPortFPGAInitNSA10RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2807 }

    tnPortFPGAInitNSA10ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2808 }

    tnPortFPGATimeoutNSARaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2809 }

    tnPortFPGATimeoutNSAClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2810 }

    tnPortFWVersionNotDefaultRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2811 }

    tnPortFWVersionNotDefaultClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2812 }

    tnPortFWUpgradePendingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2813 }

    tnPortFWUpgradePendingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2814 }

    tnPortFWPendingObsoleteRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2815 }

    tnPortFWPendingObsoleteClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2816 }

    tnPortFPGAFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2817 }

    tnPortFPGAFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2818 }

    tnPortFPGAFailNSARaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2819 }

    tnPortFPGAFailNSAClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2820 }

    tnOadoorRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2821 }

    tnOadoorClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2822 }

    tnCvFailEqptRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2823 }

    tnCvFailEqptClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2824 }

    tnLRCRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2825 }

    tnLRCClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2826 }

    tnTestSignalLineRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2827 }

    tnTestSignalLineClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2828 }

    tnTestSignalTermRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2829 }

    tnTestSignalTermClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2830 }

    tnSyslogTransferFLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2831 }

    tnSyslogTransferFLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2832 }

    tnSyslogTransferFTRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2833 }

    tnSyslogTransferFTClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2834 }

    tnSyslogTransferFMRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2835 }

    tnSyslogTransferFMClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2836 }

    tnSyslogTransferIPRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2837 }

    tnSyslogTransferIPClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2838 }

    tnSwMissingRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2839 }

    tnSwMissingClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2840 }

--    obsolete
--    tnSwUpdateIPRaisedNotif  NOTIFICATION-TYPE ::= { tnV2AlarmNotificationsRel2 2841 }
--    tnSwUpdateIPClearedNotif NOTIFICATION-TYPE ::= { tnV2AlarmNotificationsRel2 2842 }

    tnSwUnAvailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2843 }

    tnSwUnAvailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2844 }

    tnLOARaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2845 }

    tnLOAClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2846 }

    tnComErrModRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2847 }

    tnComErrModClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2848 }

    tnNotifsThrottledRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2849 }

    tnNotifsThrottledClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2850 }

    tnEpsImpairedRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2851 }

    tnEpsImpairedClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2852 }

    tnCardPowerFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2853 }

    tnCardPowerFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2854 }

    tnDelayModeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2855 }

    tnDelayModeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2856 }

    tnCableFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2857 }

    tnCableFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2858 }

    tnSwFeatureUnknownRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2859 }

    tnSwFeatureUnknownClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2860 }

    tnSwRefreshFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2861 }

    tnSwRefreshFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2862 }

    tnTrustCertValidityWarnRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2863 }

    tnTrustCertValidityWarnClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2864 }

    tnTrustCertValidityExpRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2865 }

    tnTrustCertValidityExpClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2866 }

    tnTrustCertRevRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2867 }

    tnTrustCertRevClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2868 }

    tnNeCertValidityWarnRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2869 }

    tnNeCertValidityWarnClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2870 }

    tnNeCertValidityExpRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2871 }

    tnNeCertValidityExpClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2872 }

    tnNeCertRevRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2873 }

    tnNeCertRevClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2874 }

    tnSciLinkInitRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2875 }

    tnSciLinkInitClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2876 }

    tnSciLinkFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2877 }

    tnSciLinkFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2878 }

    tnSciLinkDgrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2879 }

    tnSciLinkDgrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2880 }

    tnSciPeerFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2881 }

    tnSciPeerFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2882 }

    tnRDIFlexORaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2883 }

    tnRDIFlexOClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2884 }

    tnLomDoRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2885 }

    tnLomDoClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2886 }

    tnLomFlexORaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2887 }

    tnLomFlexOClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2888 }

    tnSsfOtsigRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2889 }

    tnSsfOtsigClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2890 }

    tnGidmFlexORaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2891 }

    tnGidmFlexOClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2892 }

    tnFmmFlexORaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2893 }

    tnFmmFlexOClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2894 }

    tnTOchOprh15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2895 }

    tnTOchOprh15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2896 }

    tnTOchOprl15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2897 }

    tnTOchOprl15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2898 }

    tnTOchOprh1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2899 }

    tnTOchOprh1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2900 }

    tnTOchOprl1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2901 }

    tnTOchOprl1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2902 }

    tnLosInferredRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2903 }

    tnLosInferredClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2904 }

    tnPwrLimitHighRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2905 }

    tnPwrLimitHighClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2906 }

    tnPwrLimitLowRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2907 }

    tnPwrLimitLowClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2908 }

    tnPwrAdjGainLimitRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2909 }

    tnPwrAdjGainLimitClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2910 }

    tnPeerComRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2911 }

    tnPeerComClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2912 }

    tnCapUpgInprRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2913 }

    tnCapUpgInprClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2914 }

    tnLofDoRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2915 }

    tnLofDoClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2916 }

    tnOSPFADJV3RaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2917 }

    tnOSPFADJV3ClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2918 }

    tnGnssTimeFrngRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2919 }

    tnGnssTimeFrngClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2920 }

    tnGnssTimeHldoverRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2921 }

    tnGnssTimeHldoverClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2922 }

    tnGnssTimeNotTraceRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2923 }

    tnGnssTimeNotTraceClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2924 }

    tnGnssFreqFrngRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2925 }

    tnGnssFreqFrngClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2926 }

    tnGnssFreqHldoverRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2927 }

    tnGnssFreqHldoverClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2928 }

    tnGnssFreqNotTraceRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2929 }

    tnGnssFreqNotTraceClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2930 }

    tnGnssJamDectRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2931 }

    tnGnssJamDectClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2932 }

    tnGnssSpoofDectRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2933 }

    tnGnssSpoofDectClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2934 }

    tnGnssAntErrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2935 }

    tnGnssAntErrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2936 }

    tnGnssModFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2937 }

    tnGnssModFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2938 }

    tnPtsfLossSyncRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2939 }

    tnPtsfLossSyncClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2940 }

    tnPtsfSyncUncertainRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2941 }

    tnPtsfSyncUncertainClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2942 }

    tnComLosModRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2943 }

    tnComLosModClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2944 }

    tnKeyMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2945 }

    tnKeyMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2946 }

    tnTFcpktCrc15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2947 }

    tnTFcpktCrc15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2948 }

    tnTFcpktCrct15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2949 }

    tnTFcpktCrct15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2950 }

    tnTFcpktCrc1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2951 }

    tnTFcpktCrc1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2952 }

    tnTFcpktCrct1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2953 }

    tnTFcpktCrct1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2954 }

    tnConfigFailOtsigRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2955 }

    tnConfigFailOtsigClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2956 }

    tnMaint1AllowedRemoteRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2957 }

    tnMaint1AllowedRemoteClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2958 }

    tnMaint2AllowedRemoteRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2959 }

    tnMaint2AllowedRemoteClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2960 }

    tnMaintAllowedLocalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2961 }

    tnMaintAllowedLocalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2962 }

    tnTPmonRoeDecapPktMissing15MinRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2963 }

    tnTPmonRoeDecapPktMissing15MinClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2964 }

    tnTPmonRoeDecapPktMissing1DayRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2965 }

    tnTPmonRoeDecapPktMissing1DayClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2966 }

    tnLagDiffLinkIdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2967 }

    tnLagDiffLinkIdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2968 }

    tnLagDiffPortAlgRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2969 }

    tnLagDiffPortAlgClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2970 }

    tnLagDiffPortConvRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2971 }

    tnLagDiffPortConvClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2972 }

    tnLagDiffSvcConvRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2973 }

    tnLagDiffSvcConvClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2974 }

    tnEntropyFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2975 }

    tnEntropyFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2976 }

    tnEntropySelfTestFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2977 }

    tnEntropySelfTestFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2978 }

    tnEntropyNoiseSourceFailRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2979 }

    tnEntropyNoiseSourceFailClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2980 }

    tnDhppCtrlMissRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2981 }

    tnDhppCtrlMissClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2982 }

    tnDhppNodeMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2983 }

    tnDhppNodeMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2984 }

    tnDhppChanMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2985 }

    tnDhppChanMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2986 }

    tnDhppProvMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2987 }

    tnDhppProvMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2988 }

    tnDhppNoResponseRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2989 }

    tnDhppNoResponseClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2990 }

    tnDhppAlsRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2991 }

    tnDhppAlsClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2992 }

    tnLofSdfecRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2993 }

    tnLofSdfecClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2994 }

    tnBgpPeer1IPv4PrefixThresholdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2995 }

    tnBgpPeer1IPv4PrefixThresholdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2996 }

    tnBgpPeer2IPv4PrefixThresholdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2997 }

    tnBgpPeer2IPv4PrefixThresholdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2998 }

    tnBgpPeer3IPv4PrefixThresholdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 2999 }

    tnBgpPeer3IPv4PrefixThresholdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3000 }

    tnBgpPeer4IPv4PrefixThresholdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3001 }

    tnBgpPeer4IPv4PrefixThresholdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3002 }

    tnBgpPeer1IPv6PrefixThresholdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3003 }

    tnBgpPeer1IPv6PrefixThresholdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3004 }

    tnBgpPeer2IPv6PrefixThresholdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3005 }

    tnBgpPeer2IPv6PrefixThresholdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3006 }

    tnBgpPeer3IPv6PrefixThresholdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3007 }

    tnBgpPeer3IPv6PrefixThresholdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3008 }

    tnBgpPeer4IPv6PrefixThresholdRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3009 }

    tnBgpPeer4IPv6PrefixThresholdClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3010 }

    tnShelfTypeMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3011 }

    tnShelfTypeMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsRel2 3012 }

--    obsolete
--    tnCabinAlarm1RaisedNotif                NOTIFICATION-TYPE ::= { tnV2AlarmNotificationsRel2 3109 }
--    tnCabinAlarm1ClearedNotif               NOTIFICATION-TYPE ::= { tnV2AlarmNotificationsRel2 3110 }
--    tnCabinAlarm2RaisedNotif                NOTIFICATION-TYPE ::= { tnV2AlarmNotificationsRel2 3111 }
--    tnCabinAlarm2ClearedNotif               NOTIFICATION-TYPE ::= { tnV2AlarmNotificationsRel2 3112 }
--    tnCabinAlarm3RaisedNotif                NOTIFICATION-TYPE ::= { tnV2AlarmNotificationsRel2 3113 }
--    tnCabinAlarm3ClearedNotif               NOTIFICATION-TYPE ::= { tnV2AlarmNotificationsRel2 3114 }
--    tnCabinAlarm4RaisedNotif                NOTIFICATION-TYPE ::= { tnV2AlarmNotificationsRel2 3115 }
--    tnCabinAlarm4ClearedNotif               NOTIFICATION-TYPE ::= { tnV2AlarmNotificationsRel2 3116 }
--    tnFrameAlarm1RaisedNotif                NOTIFICATION-TYPE ::= { tnV2AlarmNotificationsRel2 3117 }
--    tnFrameAlarm1ClearedNotif               NOTIFICATION-TYPE ::= { tnV2AlarmNotificationsRel2 3118 }
--    tnFrameAlarm2RaisedNotif                NOTIFICATION-TYPE ::= { tnV2AlarmNotificationsRel2 3119 }
--    tnFrameAlarm2ClearedNotif               NOTIFICATION-TYPE ::= { tnV2AlarmNotificationsRel2 3120 }
--    tnFrameAlarm3RaisedNotif                NOTIFICATION-TYPE ::= { tnV2AlarmNotificationsRel2 3121 }
--    tnFrameAlarm3ClearedNotif               NOTIFICATION-TYPE ::= { tnV2AlarmNotificationsRel2 3122 }
--    tnFrameAlarm4RaisedNotif                NOTIFICATION-TYPE ::= { tnV2AlarmNotificationsRel2 3123 }
--    tnFrameAlarm4ClearedNotif               NOTIFICATION-TYPE ::= { tnV2AlarmNotificationsRel2 3124 }
--    tnFrameAlarm5RaisedNotif                NOTIFICATION-TYPE ::= { tnV2AlarmNotificationsRel2 3125 }
--    tnFrameAlarm5ClearedNotif               NOTIFICATION-TYPE ::= { tnV2AlarmNotificationsRel2 3126 }
--    tnFrameAlarm6RaisedNotif                NOTIFICATION-TYPE ::= { tnV2AlarmNotificationsRel2 3127 }
--    tnFrameAlarm6ClearedNotif               NOTIFICATION-TYPE ::= { tnV2AlarmNotificationsRel2 3128 }
--    tnFrameAlarm7RaisedNotif                NOTIFICATION-TYPE ::= { tnV2AlarmNotificationsRel2 3129 }
--    tnFrameAlarm7ClearedNotif               NOTIFICATION-TYPE ::= { tnV2AlarmNotificationsRel2 3130 }
--    tnFrameAlarm8RaisedNotif                NOTIFICATION-TYPE ::= { tnV2AlarmNotificationsRel2 3131 }
--    tnFrameAlarm8ClearedNotif               NOTIFICATION-TYPE ::= { tnV2AlarmNotificationsRel2 3132 }
--    tnFrameAlarm9RaisedNotif                NOTIFICATION-TYPE ::= { tnV2AlarmNotificationsRel2 3133 }
--    tnFrameAlarm9ClearedNotif               NOTIFICATION-TYPE ::= { tnV2AlarmNotificationsRel2 3134 }
--    tnFrameAlarm10RaisedNotif               NOTIFICATION-TYPE ::= { tnV2AlarmNotificationsRel2 3135 }
--    tnFrameAlarm10ClearedNotif              NOTIFICATION-TYPE ::= { tnV2AlarmNotificationsRel2 3136 }
--    tnFrameAlarm11RaisedNotif               NOTIFICATION-TYPE ::= { tnV2AlarmNotificationsRel2 3137 }
--    tnFrameAlarm11ClearedNotif              NOTIFICATION-TYPE ::= { tnV2AlarmNotificationsRel2 3138 }
--    tnFrameAlarm12RaisedNotif               NOTIFICATION-TYPE ::= { tnV2AlarmNotificationsRel2 3139 }
--    tnFrameAlarm12ClearedNotif              NOTIFICATION-TYPE ::= { tnV2AlarmNotificationsRel2 3140 }
--    tnUserAlarm1RaisedNotif                 NOTIFICATION-TYPE ::= { tnV2AlarmNotificationsRel2 3141 }
--    tnUserAlarm1ClearedNotif                NOTIFICATION-TYPE ::= { tnV2AlarmNotificationsRel2 3142 }
--    tnUserAlarm2RaisedNotif                 NOTIFICATION-TYPE ::= { tnV2AlarmNotificationsRel2 3143 }
--    tnUserAlarm2ClearedNotif                NOTIFICATION-TYPE ::= { tnV2AlarmNotificationsRel2 3144 }
--    tnUserAlarm3RaisedNotif                 NOTIFICATION-TYPE ::= { tnV2AlarmNotificationsRel2 3145 }
--    tnUserAlarm3ClearedNotif                NOTIFICATION-TYPE ::= { tnV2AlarmNotificationsRel2 3146 }
--    tnUserAlarm4RaisedNotif                 NOTIFICATION-TYPE ::= { tnV2AlarmNotificationsRel2 3147 }
--    tnUserAlarm4ClearedNotif                NOTIFICATION-TYPE ::= { tnV2AlarmNotificationsRel2 3148 }
--    tnUserAlarm5RaisedNotif                 NOTIFICATION-TYPE ::= { tnV2AlarmNotificationsRel2 3149 }
--    tnUserAlarm5ClearedNotif                NOTIFICATION-TYPE ::= { tnV2AlarmNotificationsRel2 3150 }
--    tnUserAlarm6RaisedNotif                 NOTIFICATION-TYPE ::= { tnV2AlarmNotificationsRel2 3151 }
--    tnUserAlarm6ClearedNotif                NOTIFICATION-TYPE ::= { tnV2AlarmNotificationsRel2 3152 }
--    tnUserAlarm7RaisedNotif                 NOTIFICATION-TYPE ::= { tnV2AlarmNotificationsRel2 3153 }
--    tnUserAlarm7ClearedNotif                NOTIFICATION-TYPE ::= { tnV2AlarmNotificationsRel2 3154 }
--    tnUserAlarm8RaisedNotif                 NOTIFICATION-TYPE ::= { tnV2AlarmNotificationsRel2 3155 }
--    tnUserAlarm8ClearedNotif                NOTIFICATION-TYPE ::= { tnV2AlarmNotificationsRel2 3156 }
--    tnUserAlarm9RaisedNotif                 NOTIFICATION-TYPE ::= { tnV2AlarmNotificationsRel2 3157 }
--    tnUserAlarm9ClearedNotif                NOTIFICATION-TYPE ::= { tnV2AlarmNotificationsRel2 3158 }
--    tnUserAlarm10RaisedNotif                NOTIFICATION-TYPE ::= { tnV2AlarmNotificationsRel2 3159 }
--    tnUserAlarm10ClearedNotif               NOTIFICATION-TYPE ::= { tnV2AlarmNotificationsRel2 3160 }
--    tnUserAlarm11RaisedNotif                NOTIFICATION-TYPE ::= { tnV2AlarmNotificationsRel2 3161 }
--    tnUserAlarm11ClearedNotif               NOTIFICATION-TYPE ::= { tnV2AlarmNotificationsRel2 3162 }
--    tnUserAlarm12RaisedNotif                NOTIFICATION-TYPE ::= { tnV2AlarmNotificationsRel2 3163 }
--    tnUserAlarm12ClearedNotif               NOTIFICATION-TYPE ::= { tnV2AlarmNotificationsRel2 3164 }
--    tnUserAlarm13RaisedNotif                NOTIFICATION-TYPE ::= { tnV2AlarmNotificationsRel2 3165 }
--    tnUserAlarm13ClearedNotif               NOTIFICATION-TYPE ::= { tnV2AlarmNotificationsRel2 3166 }
--    tnUserAlarm14RaisedNotif                NOTIFICATION-TYPE ::= { tnV2AlarmNotificationsRel2 3167 }
--    tnUserAlarm14ClearedNotif               NOTIFICATION-TYPE ::= { tnV2AlarmNotificationsRel2 3168 }
--    tnUserAlarm15RaisedNotif                NOTIFICATION-TYPE ::= { tnV2AlarmNotificationsRel2 3169 }
--    tnUserAlarm15ClearedNotif               NOTIFICATION-TYPE ::= { tnV2AlarmNotificationsRel2 3170 }
--    tnUserAlarm16RaisedNotif                NOTIFICATION-TYPE ::= { tnV2AlarmNotificationsRel2 3171 }
--    tnUserAlarm16ClearedNotif               NOTIFICATION-TYPE ::= { tnV2AlarmNotificationsRel2 3172 }
--    tnUserAlarm17RaisedNotif                NOTIFICATION-TYPE ::= { tnV2AlarmNotificationsRel2 3173 }
--    tnUserAlarm17ClearedNotif               NOTIFICATION-TYPE ::= { tnV2AlarmNotificationsRel2 3174 }
--    tnUserAlarm18RaisedNotif                NOTIFICATION-TYPE ::= { tnV2AlarmNotificationsRel2 3175 }
--    tnUserAlarm18ClearedNotif               NOTIFICATION-TYPE ::= { tnV2AlarmNotificationsRel2 3176 }
--    tnUserAlarm19RaisedNotif                NOTIFICATION-TYPE ::= { tnV2AlarmNotificationsRel2 3177 }
--    tnUserAlarm19ClearedNotif               NOTIFICATION-TYPE ::= { tnV2AlarmNotificationsRel2 3178 }
--    tnUserAlarm20RaisedNotif                NOTIFICATION-TYPE ::= { tnV2AlarmNotificationsRel2 3179 }
--    tnUserAlarm20ClearedNotif               NOTIFICATION-TYPE ::= { tnV2AlarmNotificationsRel2 3180 }
--    tnUserAlarm21RaisedNotif                NOTIFICATION-TYPE ::= { tnV2AlarmNotificationsRel2 3181 }
--    tnUserAlarm21ClearedNotif               NOTIFICATION-TYPE ::= { tnV2AlarmNotificationsRel2 3182 }
--    tnUserAlarm22RaisedNotif                NOTIFICATION-TYPE ::= { tnV2AlarmNotificationsRel2 3183 }
--    tnUserAlarm22ClearedNotif               NOTIFICATION-TYPE ::= { tnV2AlarmNotificationsRel2 3184 }
--    tnUserAlarm23RaisedNotif                NOTIFICATION-TYPE ::= { tnV2AlarmNotificationsRel2 3185 }
--    tnUserAlarm23ClearedNotif               NOTIFICATION-TYPE ::= { tnV2AlarmNotificationsRel2 3186 }
--    tnUserAlarm24RaisedNotif                NOTIFICATION-TYPE ::= { tnV2AlarmNotificationsRel2 3187 }
--    tnUserAlarm24ClearedNotif               NOTIFICATION-TYPE ::= { tnV2AlarmNotificationsRel2 3188 }
--    tnUserAlarm25RaisedNotif                NOTIFICATION-TYPE ::= { tnV2AlarmNotificationsRel2 3189 }
--    tnUserAlarm25ClearedNotif               NOTIFICATION-TYPE ::= { tnV2AlarmNotificationsRel2 3190 }
--    tnUserAlarm26RaisedNotif                NOTIFICATION-TYPE ::= { tnV2AlarmNotificationsRel2 3191 }
--    tnUserAlarm26ClearedNotif               NOTIFICATION-TYPE ::= { tnV2AlarmNotificationsRel2 3192 }
--    tnUserAlarm27RaisedNotif                NOTIFICATION-TYPE ::= { tnV2AlarmNotificationsRel2 3193 }
--    tnUserAlarm27ClearedNotif               NOTIFICATION-TYPE ::= { tnV2AlarmNotificationsRel2 3194 }
--    tnUserAlarm28RaisedNotif                NOTIFICATION-TYPE ::= { tnV2AlarmNotificationsRel2 3195 }
--    tnUserAlarm28ClearedNotif               NOTIFICATION-TYPE ::= { tnV2AlarmNotificationsRel2 3196 }
--    tnUserAlarm29RaisedNotif                NOTIFICATION-TYPE ::= { tnV2AlarmNotificationsRel2 3197 }
--    tnUserAlarm29ClearedNotif               NOTIFICATION-TYPE ::= { tnV2AlarmNotificationsRel2 3198 }
--    tnUserAlarm30RaisedNotif                NOTIFICATION-TYPE ::= { tnV2AlarmNotificationsRel2 3199 }
--    tnUserAlarm30ClearedNotif               NOTIFICATION-TYPE ::= { tnV2AlarmNotificationsRel2 3200 }
--    tnUserAlarm31RaisedNotif                NOTIFICATION-TYPE ::= { tnV2AlarmNotificationsRel2 3201 }
--    tnUserAlarm31ClearedNotif               NOTIFICATION-TYPE ::= { tnV2AlarmNotificationsRel2 3202 }
--    tnUserAlarm32RaisedNotif                NOTIFICATION-TYPE ::= { tnV2AlarmNotificationsRel2 3203 }
--    tnUserAlarm32ClearedNotif               NOTIFICATION-TYPE ::= { tnV2AlarmNotificationsRel2 3204 }
--    tnSoftwareCompatibilityFailRaisedNotif  NOTIFICATION-TYPE ::= { tnV2AlarmNotificationsRel2 3205 }
--    tnSoftwareCompatibilityFailClearedNotif NOTIFICATION-TYPE ::= { tnV2AlarmNotificationsRel2 3206 }
--    tnApsLossOfServiceRaisedNotif           NOTIFICATION-TYPE ::= { tnV2AlarmNotificationsRel2 3207 }
--    tnApsLossOfServiceClearedNotif          NOTIFICATION-TYPE ::= { tnV2AlarmNotificationsRel2 3208 }
--    tnApsBlockRaisedNotif                   NOTIFICATION-TYPE ::= { tnV2AlarmNotificationsRel2 3209 }
--    tnApsBlockClearedNotif                  NOTIFICATION-TYPE ::= { tnV2AlarmNotificationsRel2 3210 }
--    tnApsLOSyncRaisedNotif                  NOTIFICATION-TYPE ::= { tnV2AlarmNotificationsRel2 3211 }
--    tnApsLOSyncClearedNotif                 NOTIFICATION-TYPE ::= { tnV2AlarmNotificationsRel2 3212 }
--    tnAuditBlockRaisedNotif                 NOTIFICATION-TYPE ::= { tnV2AlarmNotificationsRel2 3213 }
--    tnAuditBlockClearedNotif                NOTIFICATION-TYPE ::= { tnV2AlarmNotificationsRel2 3214 }
--    tnTxSquelchRaisedNotif                  NOTIFICATION-TYPE ::= { tnV2AlarmNotificationsRel2 3215 }
--    tnTxSquelchClearedNotif                 NOTIFICATION-TYPE ::= { tnV2AlarmNotificationsRel2 3216 }
--    tnApsSuspendedRaisedNotif               NOTIFICATION-TYPE ::= { tnV2AlarmNotificationsRel2 3217 }
--    tnApsSuspendedClearedNotif              NOTIFICATION-TYPE ::= { tnV2AlarmNotificationsRel2 3218 }

-- -------------------------------------------------------------
-- Event Notifications Release 2
-- -------------------------------------------------------------
    tnEventNotificationsRel2 OBJECT IDENTIFIER ::= { tnNotificationsRel2 2 }
    tnV2EventNotificationsRel2 OBJECT IDENTIFIER ::= { tnEventNotificationsRel2 0 }

    tnLedStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 1 }

    tnSystemTimingCommandChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 2 }

    tnSystemTimingActiveReferenceChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 3 }

    tnSystemTimingSynchClockUnitActiveNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 4 }

    tnPmBinsRolledOverNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 5 }

    tnWorkingSwitchedToProtectNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 6 }

    tnWorkingSwitchedBackToWorkingNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 7 }

    tnMaxFailedLoginAttemptsNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 8 }

    tnSynchronizationStatusMessageChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 9 }

    tnUserLoginNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 10 }

    tnCardConfigCorrectedByAuditNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 11 }

    tnCardAutonomousResetNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 12 }

    tnCardManualResetNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 13 }

    tnOchXcCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 14 }

    tnDbCrcErrorNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 15 }

    tnDbCannotConvertRecordTypeOrVersionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 16 }

    tnDbBadFileHeaderNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 17 }

    tnDbDetectedDiskFailureNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 18 }

    tnSystemReadyNotif NOTIFICATION-TYPE
        OBJECTS {
            tnTrapTime,
            tnTrapObjectIDType,
            tnTrapObjectID,
            tnTrapCategory,
            tnTrapDescr
        }
        STATUS         current
        DESCRIPTION    "."
        ::= { tnV2EventNotificationsRel2 19 }

    tnVtsConnCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 20 }

--    obsolete
--    tnLockedIndicationEgressNotif             NOTIFICATION-TYPE ::= { tnV2EventNotificationsRel2 21 }
--    tnOpenConnectionIndicationEgressNotif     NOTIFICATION-TYPE ::= { tnV2EventNotificationsRel2 22 }
--    tnSignalDegradeEgressNotif                NOTIFICATION-TYPE ::= { tnV2EventNotificationsRel2 23 }
--    tnBackwardDefectIndicationEgressNotif     NOTIFICATION-TYPE ::= { tnV2EventNotificationsRel2 24 }
--    tnTrailTraceIdentifierMismatchEgressNotif NOTIFICATION-TYPE ::= { tnV2EventNotificationsRel2 25 }
--    tnPayloadTypeMismatchEgressNotif          NOTIFICATION-TYPE ::= { tnV2EventNotificationsRel2 26 }
--    tnServerSignalFailureEgressNotif          NOTIFICATION-TYPE ::= { tnV2EventNotificationsRel2 27 }

    tnEcReconnectedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 28 }

    tnOdukXcCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 29 }

    tnNTPClkAdjNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 30 }

    tnSwColdResetRequestNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 31 }

    tnSwWarmResetRequestNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 32 }

    tnFmRa2pGainFailureNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 33 }

    tnOcsAuditSuccessNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 34 }

    tnOcsAuditFailNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 35 }

    tnOcsUplinkDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 36 }

    tnOcsDataRtrvNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 37 }

    tnOcsDataFltNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 38 }

    tnDataErrNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 39 }

    tnEthRingPathFwdStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 40 }

    tnLagSubGroupSelectNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 41 }

    tnLagPortAddFailedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 42 }

    tnLinkOamPeerChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 43 }

    tnLinkOamNonThresholdNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 44 }

    tnSvcStatusChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 45 }

    tnSapStatusChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 46 }

    tnDot1agCfmFaultNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 47 }

    tnDot1agCfmAisStateChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 48 }

    tnDot1agCfmSlmTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 49 }

    tnDot1agCfmDmTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 50 }

    tnDot1agCfmLbmTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 51 }

    tnDot1agCfmLtmTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 52 }

    tnIgmpSnpgSrcLimitExceededNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 53 }

    tnMirrorSourceEnabledNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 54 }

    tnMirrorSourceDisabledNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 55 }

    tnMirrorDestinationEnabledNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 56 }

    tnMirrorDestinationDisabledNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 57 }

    tnDCConfigFailNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 58 }

    tnNtpChkSigNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 59 }

    tnPTPGMDegradeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 60 }

    tnPTPGMSwitchNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 61 }

    tnPTPPathSwitchNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 62 }

    tnAutoSyncSwNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 63 }

    tnAutoSyncSwT4Notif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 64 }

    tnDot1agCfmLmTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 65 }

    tnGmreLspCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 66 }

    tnGmreLspDeletionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 67 }

    tnGmreTelinkCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 68 }

    tnGmreTelinkDeletionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 69 }

    tnGmreDblinkCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 70 }

    tnGmreDblinkDeletionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 71 }

    tnGmreCpneighborCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 72 }

    tnGmreCpneighborDeletionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 73 }

    tnGmreRsvpCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 74 }

    tnGmreRsvpDeletionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 75 }

    tnGmreDprCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 76 }

    tnGmreDprDeletionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 77 }

    tnGmreLmpCreationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 78 }

    tnGmreLmpDeletionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 79 }

    tnSRTCANotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 80 }

    tnRmdDiscoveredDeviceNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 81 }

    tnRmdTypeMismatchNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 82 }

    tnRmdWrongDestMacNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 83 }

    tnRmdUnknownEcidNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 84 }

    tnRmdJbRecenteredNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 85 }

    tnLagStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 86 }

    tnLagMemberPortStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 87 }

    tnOtdrScanStatusSuccessNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 88 }

    tnOtdrScanStatusFailNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 89 }

    tnInsertModNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 90 }

    tnRemoveModNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 91 }

    tnDiscoverModNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 92 }

    tnLagPortAddSuccessNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 93 }

    tnSapPortStateChangeProcessedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 94 }

    tnSapTlsMacMoveExceededNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 95 }

    tnmplsIfStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 96 }

    tnmplsLspUpNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 97 }

    tnmplsTpLspActivePathUpNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 98 }

    tnmplsTpLspActivePathChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 99 }

    tnMplsTpLspPingTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 100 }

    tnMplsTpLspTraceTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 101 }

    tnSdpOprStatChgNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 102 }

    tnTPmonIntfcTransmittedPkts15MinNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 103 }

    tnTPmonIntfcTransmittedPkts1DayNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 104 }

    tnTPmonIntfcTransmittedOctets15MinNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 105 }

    tnTPmonIntfcTransmittedOctets1DayNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 106 }

    tnTPmonIntfcReceivedPkts15MinNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 107 }

    tnTPmonIntfcReceivedPkts1DayNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 108 }

    tnTPmonIntfcReceivedOctets15MinNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 109 }

    tnTPmonIntfcReceivedOctets1DayNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 110 }

    tnTPmonSdpIngressForwardedPkts15MinNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 111 }

    tnTPmonSdpIngressForwardedPkts1DayNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 112 }

    tnTPmonSdpIngressForwardedOctets15MinNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 113 }

    tnTPmonSdpIngressForwardedOctets1DayNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 114 }

    tnTPmonSdpEgressForwardedPkts15MinNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 115 }

    tnTPmonSdpEgressForwardedPkts1DayNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 116 }

    tnTPmonSdpEgressForwardedOctets15MinNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 117 }

    tnTPmonSdpEgressForwardedOctets1DayNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 118 }

    tnSdpSpkStateChgNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 119 }

    tnSdpBindOprStateChgNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 120 }

    tnClusterAuditSuccessNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 121 }

    tnClusterAuditFailNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 122 }

    tnClusterDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 123 }

    tnClusterDataRtrvNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 124 }

    tnClusterDataFltNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 125 }

    tnClusterTrapFailNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 126 }

    tnVRtrBfdSessExtDownNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 127 }

    tnVRtrBfdSessExtDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 128 }

    tnVRtrBfdSessExtProtChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 129 }

    tnVRtrBfdSessExtUpNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 130 }

    tnSdpBindEndPointTxActiveChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 131 }

    tnSdpBindPwLocalStatusBitsChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 132 }

    tnSdpBindPwPeerStatusBitsChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 133 }

    tnSdpBindPingTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 134 }

    tnSdpBindTraceTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 135 }

    tnEthRingStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 136 }

    tnEthRingPortStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 137 }

    tnLldpRemTablesChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 138 }

    tnPmTelemetryCounterNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 139 }

    tnTsbFabSwitchStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 140 }

    tnFmReadyNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 141 }

    tnAbsNodeCreatedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 142 }

    tnAbsNodeDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 143 }

    tnAbsNodeModifiedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 144 }

    tnOamTestHeadTestCompleteNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 145 }

    tnLagPortActStdChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 146 }

    tnLagPortOperChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 147 }

    tnMcLagStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 148 }

    tnMplsTpLspPDUChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 149 }

    tnCardInsertNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 150 }

    tnCardExtractNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 151 }

    tnSyncEStatusChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 152 }

    tnSyncESwitchTimingReferenceNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 153 }

    tnSyncESwitchTimingReferenceT4Notif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 154 }

    tnPTPStatSwitchNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 155 }

    tnDeltaFileRolledOverNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 156 }

    tnLastTrapDeltaFileNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 157 }

    tnSdpMeshStatusChangedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 158 }

    tnSdpTlsMacMoveExceededNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 159 }

    tnPresentationTimeTooLargeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 160 }

    tnPresentationTimeTooSmallNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 161 }

    tnOchXcCreationDataNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 162 }

    tnLicReqRedirectedNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 163 }

    tnLicClmUnknownErrorNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 164 }

    tnErpOperStateChngNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 165 }

    tnPnacPortAuthStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 166 }

    tnNtpChkSigChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 167 }

    tnDiscoverMeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 168 }

    tnAutoTrapRebootNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 169 }

    tnQsfpHeaterEnableNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 170 }

    tnQsfpHeaterDisableNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 171 }

    tnNeColdResetPendingNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 172 }

    tnAutoDownCITStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 173 }

    tnAutoUpCITStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 174 }

    tnAutoNotApplicableCITStateChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 175 }

    tnDhppFrcdWkSwBkChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 176 }

    tnDhppFrcdWkSwPrChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 177 }

    tnDhppManWkSwBkChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 178 }

    tnDhppManWkSwPrChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 179 }

    tnDhppWkSwBkChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 180 }

    tnDhppWkSwPrChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 181 }

    tnDhppWTRChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 182 }

    tnDhppDNRChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 183 }

    tnDhppNRChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 184 }

    tnDhppFrcdWkSwBkFeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 185 }

    tnDhppFrcdWkSwPrFeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 186 }

    tnDhppManWkSwBkFeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 187 }

    tnDhppManWkSwPrFeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 188 }

    tnDhppWkSwBkFeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 189 }

    tnDhppWkSwPrFeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 190 }

    tnDhppWTRFeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 191 }

    tnDhppDNRFeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 192 }

    tnDhppNRFeChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2EventNotificationsRel2 193 }

-- -------------------------------------------------------------
-- Alarm Notifications SDH
-- -------------------------------------------------------------
    tnAlarmNotificationsSdh OBJECT IDENTIFIER ::= { tnNotificationsSdh 1 }
    tnV2AlarmNotificationsSdh OBJECT IDENTIFIER ::= { tnAlarmNotificationsSdh 0 }

    tnSdhLossOfSignalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 1 }

    tnSdhLossOfSignalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 2 }

    tnSdhLossOfClockRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 3 }

    tnSdhLossOfClockClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 4 }

    tnSdhLossOfFrameRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 5 }

    tnSdhLossOfFrameClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 6 }

    tnSdhAlarmIndicationSignalRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 7 }

    tnSdhAlarmIndicationSignalClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 8 }

    tnSdhSignalFailureRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 9 }

    tnSdhSignalFailureClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 10 }

    tnSdhSignalDegradeRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 11 }

    tnSdhSignalDegradeClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 12 }

    tnSdhMultiplexSectionRemoteFailureIndicationRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 13 }

    tnSdhMultiplexSectionRemoteFailureIndicationClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 14 }

    tnSdhRegeneratorSectionTraceMismatchRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 15 }

    tnSdhRegeneratorSectionTraceMismatchClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 16 }

    tnSdhLossOfPointerRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 17 }

    tnSdhLossOfPointerClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsSdh 18 }

-- -------------------------------------------------------------
-- Alarm Notifications E1
-- -------------------------------------------------------------
    tnAlarmNotificationsE1 OBJECT IDENTIFIER ::= { tnNotificationsE1 1 }
    tnV2AlarmNotificationsE1 OBJECT IDENTIFIER ::= { tnAlarmNotificationsE1 0 }

    tnE1LosRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 1 }

    tnE1LosClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 2 }

    tnE1NoCRC4MRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 3 }

    tnE1NoCRC4MClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 4 }

    tnE1LofRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 5 }

    tnE1LofClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 6 }

    tnE1AisLRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 7 }

    tnE1AisLClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 8 }

    tnE1RaiRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 9 }

    tnE1RaiClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 10 }

    tnE1LofEgrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 11 }

    tnE1LofEgrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 12 }

    tnE1AisEgrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 13 }

    tnE1AisEgrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 14 }

    tnE1NoCRC4MEgrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 15 }

    tnE1NoCRC4MEgrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 16 }

    tnE1RaiEgrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 17 }

    tnE1RaiEgrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsE1 18 }

-- -------------------------------------------------------------
-- Alarm Notifications Unregistered
-- -------------------------------------------------------------
    tnAlarmNotificationsUnregistered OBJECT IDENTIFIER ::= { tnNotificationsUnregistered 1 }
    tnV2AlarmNotificationsUnregistered OBJECT IDENTIFIER ::= { tnAlarmNotificationsUnregistered 0 }

    tnUnregisteredAlarmRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsUnregistered 1 }

    tnUnregisteredAlarmClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnV2AlarmNotificationsUnregistered 2 }

-- -------------------------------------------------------------
-- Security Notifications
-- -------------------------------------------------------------
    tnSecurityNotifications OBJECT IDENTIFIER ::= { tnNotificationsSecurity 1 }
    tnV2SecurityNotifications OBJECT IDENTIFIER ::= { tnSecurityNotifications 0 }

    tnSecurityLoginNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 1 }

    tnSecurityLogoutNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 2 }

    tnSecurityUnauthAccessAttemptNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 3 }

    tnSecurityExceededLoginAttemptsNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 4 }

    tnSecurityNodeStartupNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 5 }

    tnSecurityChangeAccountNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 6 }

    tnSecurityChangePasswordNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 7 }

    tnSecurityAddAccountNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 8 }

    tnSecurityDeleteAccountNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 9 }

    tnSecurityLockAccountNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 10 }


    tnSecurityUnlockAccountNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 11 }

    tnSecurityLogViewNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 12 }

    tnSecurityAclVialationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 13 }

    tnSecurityCreateAclNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 14 }

    tnSecurityDeleteAclNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 15 }

    tnSecurityEnableInterfaceNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 16 }

    tnSecurityDisableInterfaceNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 17 }

    tnSecurityConfigSyslogNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 18 }

    tnSecurityConfigLoggingNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 19 }

    tnSecurityFileTransferNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 20 }

    tnSecurityFileNameNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 21 }

    tnSecurityDebugDumpNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 22 }

    tnSecurityChangeMaxFailedLoginsNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 23 }

    tnSecurityChangeAuthTrapNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 24 }

    tnSecurityDatabaseBackupAndRestoreNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 25 }

    tnDormantUserNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 26 }

    tnLogBuf90SecuLogNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 27 }

    tnLogBufOvflSecuLogNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 28 }

    tnSecurityOptIntrusionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 29 }

    tnSecurityChangeUiModeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 30 }

    tnSecurityChangeFipsSquelchModeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 31 }

    tnSecuritySelfTestCompNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 32 }

    tnSecurityChangeEncryptStateNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 33 }

    tnSecurityEncryptActionRejectNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 34 }

    tnSecurityAclVialationIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 35 }

    tnSecurityAddAccountIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 36 }

        tnSecurityDatabaseBackupAndRestoreIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 37 }

    tnSecurityChangeAccountIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 38 }

    tnSecurityChangeAuthTrapIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 39 }

    tnSecurityChangeEncryptStateIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 40 }

    tnSecurityChangeFipsSquelchModeIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 41 }

    tnSecurityChangeMaxFailedLoginsIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 42 }

    tnSecurityChangePasswordIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 43 }

    tnSecurityChangeUiModeIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 44 }

    tnSecurityConfigLoggingIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 45 }

    tnSecurityConfigSyslogIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 46 }

    tnSecurityCreateAclIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 47 }

    tnSecurityDeleteAccountIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 48 }

    tnSecurityDeleteAclIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 49 }

    tnSecurityDisableInterfaceIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 50 }

    tnSecurityEnableInterfaceIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 51 }

    tnSecurityExceededLoginAttemptsIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 52 }

    tnSecurityFileNameIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 53 }

    tnSecurityFileTransferIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 54 }

    tnSecurityLockAccountIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 55 }

    tnSecurityLoginIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 56 }

    tnSecurityLogoutIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 57 }

    tnSecurityLogViewIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 58 }

    tnSecurityNodeStartupIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 59 }

    tnSecurityUnauthAccessAttemptIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 60 }

    tnSecurityUnlockAccountIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 61 }

    tnDormantUserIpv6Notif NOTIFICATION-TYPE
        OBJECTS {
            tnTrapTime,
            tnTrapObjectIDIpV6,
            tnTrapCategory,
            tnTrapDescr,
            tnTrapData
        }
        STATUS         current
        DESCRIPTION    "."
        ::= { tnV2SecurityNotifications 62 }

    tnSwAssistedNonceChangeNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 63 }

    tnSecurityChangeMaxSessionLoginsNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 64 }

    tnSecurityChangeMaxSessionLoginsIpv6Notif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 65 }

    tnSecurityACLLoggingNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 66 }

    tnSecurityACLLoggingIpv6Notif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 67 }

    tnSecurityChangeMinPwdObsIntNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 68 }

    tnSecurityChangeMinPwdLengthNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 69 }

    tnSecuritySysRadiusSrvrAuthportNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 70 }

    tnSecuritySysRadiusRetriesNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 71 }

    tnSecuritySysRadiusServerStatusNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 72 }

    tnSecuritySysRadiusTimeoutNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 73 }

    tnSecuritySysAuthOrderNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 74 }

    tnSecurityRadiusServerNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 75 }

    tnSecurityChangeMinIntInvloginNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 76 }

    tnSecuritySyslogReopenNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 77 }

    tnClmSigningCertNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 78 }

    tnClmHttpsConnectionNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 79 }

    tnZtpTriggerInfoNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 80 }

    tnZtpDhcpIpNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 81 }

    tnSecurityChangeConnectedStateNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 82 }

    tnSecurityCertValidationNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 83 }

    tnSecurityChangeUserMgmtAttrNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 84 }

    tnSecurityChangeRadAttrNotif NOTIFICATION-TYPE
        OBJECTS {
            tnTrapTime,
            tnTrapObjectIDType,
            tnTrapObjectID,
            tnTrapCategory,
            tnTrapDescr,
            tnTrapData
        }
        STATUS         current
        DESCRIPTION    "."
        ::= { tnV2SecurityNotifications 85 }

-- -------------------------------------------------------------
-- Trap Buffering Table
-- -------------------------------------------------------------
    tnTrapBufferTable OBJECT-TYPE
        SYNTAX         SEQUENCE OF TnTrapBufferEntry
        MAX-ACCESS     not-accessible
        STATUS         current
        DESCRIPTION    "Table tnTrapBufferTable serves as a circular
                        trap buffer for all trap notifications destined
                        for a Network Management Station (NMS).  When
                        such a trap event occurs, it is copied into
                        tnTrapBufferTable.  Subsequently, a trap
                        notification is sent to the NMS.  If the NMS
                        temporarily loses its connection with the node
                        agent, any trap notifications missed during the
                        outage may be recovered from this table.  The
                        NMS can do this by referring to the serial
                        number associated with the last received trap
                        before the outage and the serial number associated
                        with the last missed trap sent by the node agent
                        during the outage.  The serial number of the last
                        missed trap can be determined by getting the
                        value of variable tnLastMissedTrap from the node
                        agent."
        ::= { tnTrapBuffering 1 }

    tnTrapBufferEntry OBJECT-TYPE
        SYNTAX         TnTrapBufferEntry
        MAX-ACCESS     not-accessible
        STATUS         current
        DESCRIPTION    "."
        INDEX { tnTrapSerialNumber }
        ::= { tnTrapBufferTable 1 }

    TnTrapBufferEntry ::=
        SEQUENCE {
            tnTrapSerialNumber     Unsigned32,
            tnTrapType             OBJECT IDENTIFIER,
            tnTrapTime             Unsigned32,
            tnTrapObjectIDType     Unsigned32,
            tnTrapObjectID         Unsigned32,
            tnTrapCategory         TnTrapCategory,
            tnTrapDescr            SnmpAdminString,
            tnTrapChangedObject    OBJECT IDENTIFIER,
            tnTrapData             SnmpAdminString,
            tnTrapServiceAffecting TruthValue,
            tnTrapEntityType       TnEntityType,
            tnTrapCondition        TnCondition,
            tnTrapObjectIDIpV6     InetAddress
        }

    tnTrapSerialNumber OBJECT-TYPE
        SYNTAX         Unsigned32
        MAX-ACCESS     not-accessible
        STATUS         current
        DESCRIPTION    "The independently incremented number associated
                        with the sequential ordering of outgoing traps.  A
                        value of zero is invalid for the trap buffer, but
                        may be valid for outgoing traps."
        ::= { tnTrapBufferEntry 1 }

    tnTrapType OBJECT-TYPE
        SYNTAX         OBJECT IDENTIFIER
        MAX-ACCESS     read-only
        STATUS         current
        DESCRIPTION    "The OID of the notification."
        ::= { tnTrapBufferEntry 2 }

    tnTrapTime OBJECT-TYPE
        SYNTAX         Unsigned32
        MAX-ACCESS     read-only
        STATUS         current
        DESCRIPTION    "The time at which the trap occurred, measured in
                        total time ticks (seconds) from the year 1970."
        ::= { tnTrapBufferEntry 3 }

    tnTrapObjectIDType OBJECT-TYPE
        SYNTAX         Unsigned32
        MAX-ACCESS     read-only
        STATUS         current
        DESCRIPTION    "The type of Object ID associated with the trap.

            -----------------------------------------------------------
            | Bit31-Bit23 | Bit22-Bit20 | Bit19-Bit18   | Bit17-Bit16 |
            --------------+-------------+---------------+--------------
            | 9 bits      | 3 bits      | 2 bits        | 2 bits      |
            --------------+-------------+---------------+--------------
            | Lo-ODU ID   | TCM Level   | TCM Direction | Reserved    |
            |             | (1-6)       | (AM=1, BM=2)  |             |
            -----------------------------------------------------------

            -----------------------------------------
            | Bit15-Bit12 | Bit11-Bit6 | Bit5-Bit0  |
            --------------+------------+-------------
            | 4 bits      | 6 bits     | 6 bits     |
            --------------+------------+-------------
            | FacType     | SubFacType | =25        |
            -----------------------------------------

              FacType                 |  Value
            --------------------------+---------
              NULL                    |    0
              ODU1PTF                 |    1
              OPTSG                   |    2
              OTU                     |    3
              Client ODU Transparent  |    4
              HO ODU NIM              |    5
              ODU TP                  |    6
              LOODU NIM               |    7
              FAC_WANIF               |   13

              FacType              |  SubFacType  |  AID
            -----------------------+--------------+-----------------------
              NULL(0)              |  0           |  NULL
            -----------------------+--------------+-----------------------
              ODU1PTF(1)           |  xx          |  ODU1PTF
            -----------------------+--------------+-----------------------
              OTU(3)               |  xx          |  OTU
            -----------------------+--------------+-----------------------
              Client ODU Trans(4)  |  1           |  ODU0
                                   |  2           |  ODU1
                                   |  3           |  ODU2
                                   |  4           |  ODU2e
                                   |  5           |  ODU3
                                   |  6           |  ODU3e (not used)
                                   |  7           |  ODU3E2
                                   |  8           |  ODU4
                                   |  9           |  ODUflex
            -----------------------+--------------+-----------------------
              HO ODU NIM(5)        |  1           |  OTUODU0
                                   |  2           |  OTUODU1
                                   |  3           |  OTUODU2
                                   |  4           |  OTUODU2e
                                   |  5           |  OTUODU3
                                   |  6           |  Not used (OTUODU3e)
                                   |  7           |  OTUODU3E2
                                   |  8           |  OTUODU4
            -----------------------+--------------+-----------------------
              ODU TP(6)            |  1           |  ODU0
                                   |  2           |  ODU1
                                   |  3           |  ODU2
                                   |  4           |  ODU2e
                                   |  5           |  ODU3
                                   |  6           |  ODU3e (not used)
                                   |  7           |  ODU3E2
                                   |  8           |  ODU4
            -----------------------+--------------+-----------------------
              LO-ODU NIM(7)        |   1          |  ODU1ODU0
                                   |   2          |  ODU2ODU0
                                   |   3          |  ODU2ODU1
                                   |   4          |  ODU2ODUF
                                   |   5          |  ODU2eODU0
                                   |   6          |  ODU2eODU1
                                   |   7          |  ODU2eODUf
                                   |   8          |  ODU3ODU0
                                   |   9          |  ODU3ODU1
                                   |  10          |  ODU3ODU2
                                   |  11          |  ODU3ODU2e
                                   |  12          |  ODU3ODUF
                                   |  13          |  ODU3eODU0
                                   |  14          |  ODU3eODU1
                                   |  15          |  ODU3eOU2
                                   |  16          |  ODU3eODU2e
                                   |  17          |  ODU3eODUF
                                   |  18          |  ODU3e2ODU0
                                   |  19          |  ODU3e2ODU1
                                   |  20          |  ODU3e2ODU2
                                   |  21          |  ODU3e2ODU2e
                                   |  22          |  ODU3e2ODUF
                                   |  23          |  ODU4ODU0
                                   |  24          |  ODU4ODU1
                                   |  25          |  ODU4ODU2
                                   |  26          |  ODU4ODU2e
                                   |  27          |  ODU4ODU3
                                   |  28          |  ODU4ODU3e
                                   |  29          |  ODU4ODU3e2
                                   |  30          |  ODU4ODUF
            -----------------------+--------------+-----------------------
              FAC_WANIF            |  1           |  WANIFODU2E
                                   |  2           |  WANIFODU4
                       "
        ::= { tnTrapBufferEntry 4 }

    tnTrapObjectID OBJECT-TYPE
        SYNTAX         Unsigned32
        MAX-ACCESS     read-only
        STATUS         current
        DESCRIPTION    "1) The physical interface or service associated with
                           the trap.

            --------------------------------------------------------------
            | Bit31-Bit24 | Bit23-Bit16 | Bit15 | Bit14-Bit2 | Bit1-Bit0 |
            --------------+-------------+-------+------------+------------
            | 8 bits      | 8 bits      | 1 bit | 13 bits    | 2 bits    |
            --------------+-------------+-------+------------+------------
            | shelf       | slot        | 0     | HO-ODU     | Direction |
            |             |             |       | Number     |           |
            --------------------------------------------------------------

                       2) Manually created ODUPTF WANIF format.
            ------------------------------------------------------------------------------------
            | Bit31-Bit24 | Bit23-Bit16 | Bit15 | Bit14-Bit13 | Bit12-Bit3 | Bit2-Bit1 | Bit0  |
            --------------+-------------+-------+------------+----------------------------------
            | 8 bits      | 8 bits      | 1 bit | 2 bits      | 10 bits    | 2 bits    | 1 bit |
            --------------+-------------+-------+------------+----------------------------------
            | shelf       | slot        | 1     | Pad         | Wanif ID   | Direction | 1     |
            |             |             |       |             |            |           |       |
            ------------------------------------------------------------------------------------
                       "
        ::= { tnTrapBufferEntry 5 }

    tnTrapCategory OBJECT-TYPE
        SYNTAX         TnTrapCategory
        MAX-ACCESS     read-only
        STATUS         current
        DESCRIPTION    "The trap category."
        ::= { tnTrapBufferEntry 6 }

    tnTrapDescr OBJECT-TYPE
        SYNTAX         SnmpAdminString (SIZE(0..255))
        MAX-ACCESS     read-only
        STATUS         current
        DESCRIPTION    "A detailed description of the trap."
        ::= { tnTrapBufferEntry 7 }

    tnTrapChangedObject OBJECT-TYPE
        SYNTAX         OBJECT IDENTIFIER
        MAX-ACCESS     read-only
        STATUS         current
        DESCRIPTION    "The OID of an attribute changed in a tnChangeNotif
                        notification.  This is null for all other
                        notifications."
        ::= { tnTrapBufferEntry 8 }

    tnTrapData OBJECT-TYPE
        SYNTAX         SnmpAdminString (SIZE(0..2048))
        MAX-ACCESS     read-only
        STATUS         current
        DESCRIPTION    "Any application specific data relevant to the trap.
                        This could be the value of a changed attribute or
                        any other formatted information related to a
                        notification."
        ::= { tnTrapBufferEntry 9 }

    tnTrapServiceAffecting OBJECT-TYPE
        SYNTAX         TruthValue
        MAX-ACCESS     read-only
        STATUS         current
        DESCRIPTION    "An indication as to whether or not this trap is
                        service affecting."
        ::= { tnTrapBufferEntry 10 }

    tnTrapEntityType OBJECT-TYPE
        SYNTAX         TnEntityType
        MAX-ACCESS     read-only
        STATUS         current
        DESCRIPTION    "The entity type."
        ::= { tnTrapBufferEntry 11 }

    tnTrapCondition OBJECT-TYPE
        SYNTAX         TnCondition
        MAX-ACCESS     read-only
        STATUS         current
        DESCRIPTION    "The condition."
        ::= { tnTrapBufferEntry 12 }

    tnTrapObjectIDIpV6 OBJECT-TYPE
        SYNTAX         InetAddress
        MAX-ACCESS     read-only
        STATUS         current
        DESCRIPTION    "Denotes a generic Internet address."
        ::= { tnTrapBufferEntry 13 }

-- -------------------------------------------------------------
-- Last Issued Trap Serial Number
-- -------------------------------------------------------------
    tnLastIssuedTrap OBJECT-TYPE
        SYNTAX         Unsigned32
        MAX-ACCESS     read-only
        STATUS         current
        DESCRIPTION    "The serial number of last issued trap."
        ::= { tnTrapBuffering 2 }

    tnTrapSerialNumberResetToBeHandled OBJECT-TYPE
        SYNTAX         TruthValue
        MAX-ACCESS     read-write
        STATUS         current
        DESCRIPTION    "The value is true if the trap serial number was
                        reset to 0 over the last network element restart.
                        It may be set to false if the network element
                        manager determines that this condition no longer
                        needs to be handled.  Sets with a value of true
                        are restricted."
        ::= { tnTrapBuffering 3 }

-- -------------------------------------------------------------
-- Multiple Type Trap Buffer
-- -------------------------------------------------------------

    tnMultipleTypeTrapBufferTable OBJECT-TYPE
        SYNTAX         SEQUENCE OF TnMultipleTypeTrapBufferEntry
        MAX-ACCESS     not-accessible
        STATUS         current
        DESCRIPTION    "Table tnMultipleTypeTrapBufferTable serves as a circular
                        trap buffer for particular trap notifications destined
                        for a Network Management Station (NMS).  When
                        such a trap event occurs, it is copied into
                        tnMultipleTypeTrapBufferTable.  Subsequently, a trap
                        notification is sent to the NMS.  If the NMS
                        temporarily loses its connection with the node
                        agent, any trap notifications missed during the
                        outage may be recovered from this table.  The
                        NMS can do this by referring to the serial
                        number associated with the last received trap
                        before the outage and the serial number associated
                        with the last missed trap sent by the node agent
                        during the outage.  The serial number of the last
                        missed trap can be determined by getting the
                        value of variable tnLastMissedTrap from the node
                        agent."
        ::= { tnTrapBuffering 4 }

    tnMultipleTypeTrapBufferEntry OBJECT-TYPE
        SYNTAX         TnMultipleTypeTrapBufferEntry
        MAX-ACCESS     not-accessible
        STATUS         current
        DESCRIPTION    "."
        INDEX { tnMultipleTypeTrapBufferType,
                tnTrapSerialNumber }
        ::= { tnMultipleTypeTrapBufferTable 1 }

    TnMultipleTypeTrapBufferEntry ::=
        SEQUENCE {
            tnMultipleTypeTrapBufferType       INTEGER,
            tnMultipleTypeTrapType             OBJECT IDENTIFIER,
            tnMultipleTypeTrapTime             Unsigned32,
            tnMultipleTypeTrapObjectIDType     Unsigned32,
            tnMultipleTypeTrapObjectID         Unsigned32,
            tnMultipleTypeTrapCategory         TnTrapCategory,
            tnMultipleTypeTrapDescr            SnmpAdminString,
            tnMultipleTypeTrapChangedObject    OBJECT IDENTIFIER,
            tnMultipleTypeTrapData             SnmpAdminString,
            tnMultipleTypeTrapServiceAffecting TruthValue,
            tnMultipleTypeTrapEntityType       TnEntityType,
            tnMultipleTypeTrapCondition        TnCondition,
            tnMultipleTypeTrapObjectIDIpV6     InetAddress
        }

    tnMultipleTypeTrapBufferType OBJECT-TYPE
        SYNTAX         INTEGER{
                         pmData(1)
                       }
        MAX-ACCESS     not-accessible
        STATUS         current
        DESCRIPTION    "Trap buffer type."
        ::= { tnMultipleTypeTrapBufferEntry 1 }

    tnMultipleTypeTrapType OBJECT-TYPE
        SYNTAX         OBJECT IDENTIFIER
        MAX-ACCESS     read-only
        STATUS         current
        DESCRIPTION    "The OID of the notification."
        ::= { tnMultipleTypeTrapBufferEntry 2 }

    tnMultipleTypeTrapTime OBJECT-TYPE
        SYNTAX         Unsigned32
        MAX-ACCESS     read-only
        STATUS         current
        DESCRIPTION    "The time at which the trap occurred, measured in
                        total time ticks (seconds) from the year 1970."
        ::= { tnMultipleTypeTrapBufferEntry 3 }

    tnMultipleTypeTrapObjectIDType OBJECT-TYPE
        SYNTAX         Unsigned32
        MAX-ACCESS     read-only
        STATUS         current
        DESCRIPTION    "The type of Object ID associated with the trap.

            -----------------------------------------------------------
            | Bit31-Bit23 | Bit22-Bit20 | Bit19-Bit18   | Bit17-Bit16 |
            --------------+-------------+---------------+--------------
            | 9 bits      | 3 bits      | 2 bits        | 2 bits      |
            --------------+-------------+---------------+--------------
            | Lo-ODU ID   | TCM Level   | TCM Direction | Reserved    |
            |             | (1-6)       | (AM=1, BM=2)  |             |
            -----------------------------------------------------------

            -----------------------------------------
            | Bit15-Bit12 | Bit11-Bit6 | Bit5-Bit0  |
            --------------+------------+-------------
            | 4 bits      | 6 bits     | 6 bits     |
            --------------+------------+-------------
            | FacType     | SubFacType | =25        |
            -----------------------------------------

              FacType                 |  Value
            --------------------------+---------
              NULL                    |    0
              ODU1PTF                 |    1
              OPTSG                   |    2
              OTU                     |    3
              Client ODU Transparent  |    4
              HO ODU NIM              |    5
              ODU TP                  |    6
              LOODU NIM               |    7


              FacType              |  SubFacType  |  AID
            -----------------------+--------------+-----------------------
              NULL(0)              |  0           |  NULL
            -----------------------+--------------+-----------------------
              ODU1PTF(1)           |  xx          |  ODU1PTF
            -----------------------+--------------+-----------------------
              OTU(3)               |  xx          |  OTU
            -----------------------+--------------+-----------------------
              Client ODU Trans(4)  |  1           |  ODU0
                                   |  2           |  ODU1
                                   |  3           |  ODU2
                                   |  4           |  ODU2e
                                   |  5           |  ODU3
                                   |  6           |  ODU3e (not used)
                                   |  7           |  ODU3E2
                                   |  8           |  ODU4
                                   |  9           |  ODUflex
            -----------------------+--------------+-----------------------
              HO ODU NIM(5)        |  1           |  OTUODU0
                                   |  2           |  OTUODU1
                                   |  3           |  OTUODU2
                                   |  4           |  OTUODU2e
                                   |  5           |  OTUODU3
                                   |  6           |  Not used (OTUODU3e)
                                   |  7           |  OTUODU3E2
                                   |  8           |  OTUODU4
            -----------------------+--------------+-----------------------
              ODU TP(6)            |  1           |  ODU0
                                   |  2           |  ODU1
                                   |  3           |  ODU2
                                   |  4           |  ODU2e
                                   |  5           |  ODU3
                                   |  6           |  ODU3e (not used)
                                   |  7           |  ODU3E2
                                   |  8           |  ODU4
            -----------------------+--------------+-----------------------
              LO-ODU NIM(7)        |   1          |  ODU1ODU0
                                   |   2          |  ODU2ODU0
                                   |   3          |  ODU2ODU1
                                   |   4          |  ODU2ODUF
                                   |   5          |  ODU2eODU0
                                   |   6          |  ODU2eODU1
                                   |   7          |  ODU2eODUf
                                   |   8          |  ODU3ODU0
                                   |   9          |  ODU3ODU1
                                   |  10          |  ODU3ODU2
                                   |  11          |  ODU3ODU2e
                                   |  12          |  ODU3ODUF
                                   |  13          |  ODU3eODU0
                                   |  14          |  ODU3eODU1
                                   |  15          |  ODU3eOU2
                                   |  16          |  ODU3eODU2e
                                   |  17          |  ODU3eODUF
                                   |  18          |  ODU3e2ODU0
                                   |  19          |  ODU3e2ODU1
                                   |  20          |  ODU3e2ODU2
                                   |  21          |  ODU3e2ODU2e
                                   |  22          |  ODU3e2ODUF
                                   |  23          |  ODU4ODU0
                                   |  24          |  ODU4ODU1
                                   |  25          |  ODU4ODU2
                                   |  26          |  ODU4ODU2e
                                   |  27          |  ODU4ODU3
                                   |  28          |  ODU4ODU3e
                                   |  29          |  ODU4ODU3e2
                                   |  30          |  ODU4ODUF
                       "
        ::= { tnMultipleTypeTrapBufferEntry 4 }

    tnMultipleTypeTrapObjectID OBJECT-TYPE
        SYNTAX         Unsigned32
        MAX-ACCESS     read-only
        STATUS         current
        DESCRIPTION    "The physical interface or service associated with
                        the trap.

            --------------------------------------------------------------
            | Bit31-Bit24 | Bit23-Bit16 | Bit15 | Bit14-Bit2 | Bit1-Bit0 |
            --------------+-------------+-------+------------+------------
            | 8 bits      | 8 bits      | 1 bit | 13 bits    | 2 bits    |
            --------------+-------------+-------+------------+------------
            | shelf       | slot        | 0     | HO-ODU     | Direction |
            |             |             |       | Number     |           |
            --------------------------------------------------------------
                       "
        ::= { tnMultipleTypeTrapBufferEntry 5 }

    tnMultipleTypeTrapCategory OBJECT-TYPE
        SYNTAX         TnTrapCategory
        MAX-ACCESS     read-only
        STATUS         current
        DESCRIPTION    "The trap category."
        ::= { tnMultipleTypeTrapBufferEntry 6 }

    tnMultipleTypeTrapDescr OBJECT-TYPE
        SYNTAX         SnmpAdminString (SIZE(0..255))
        MAX-ACCESS     read-only
        STATUS         current
        DESCRIPTION    "A detailed description of the trap."
        ::= { tnMultipleTypeTrapBufferEntry 7 }

    tnMultipleTypeTrapChangedObject OBJECT-TYPE
        SYNTAX         OBJECT IDENTIFIER
        MAX-ACCESS     read-only
        STATUS         current
        DESCRIPTION    "The OID of an attribute changed in a tnChangeNotif
                        notification.  This is null for all other
                        notifications."
        ::= { tnMultipleTypeTrapBufferEntry 8 }

    tnMultipleTypeTrapData OBJECT-TYPE
        SYNTAX         SnmpAdminString (SIZE(0..255))
        MAX-ACCESS     read-only
        STATUS         current
        DESCRIPTION    "Any application specific data relevant to the trap.
                        This could be the value of a changed attribute or
                        any other formatted information related to a
                        notification."
        ::= { tnMultipleTypeTrapBufferEntry 9 }

    tnMultipleTypeTrapServiceAffecting OBJECT-TYPE
        SYNTAX         TruthValue
        MAX-ACCESS     read-only
        STATUS         current
        DESCRIPTION    "An indication as to whether or not this trap is
                        service affecting."
        ::= { tnMultipleTypeTrapBufferEntry 10 }

    tnMultipleTypeTrapEntityType OBJECT-TYPE
        SYNTAX         TnEntityType
        MAX-ACCESS     read-only
        STATUS         current
        DESCRIPTION    "The entity type."
        ::= { tnMultipleTypeTrapBufferEntry 11 }

    tnMultipleTypeTrapCondition OBJECT-TYPE
        SYNTAX         TnCondition
        MAX-ACCESS     read-only
        STATUS         current
        DESCRIPTION    "The condition."
        ::= { tnMultipleTypeTrapBufferEntry 12 }

    tnMultipleTypeTrapObjectIDIpV6 OBJECT-TYPE
        SYNTAX         InetAddress
        MAX-ACCESS     read-only
        STATUS         current
        DESCRIPTION    "Denotes a generic Internet address."
        ::= { tnMultipleTypeTrapBufferEntry 13 }

-- -------------------------------------------------------------
-- Multiple Type Trap attributes
-- -------------------------------------------------------------

    tnMultipleTypeTrapTable OBJECT-TYPE
        SYNTAX         SEQUENCE OF TnMultipleTypeTrapEntry
        MAX-ACCESS     not-accessible
        STATUS         current
        DESCRIPTION    "Table The serial number of last issued trap."
        ::= { tnTrapBuffering 5 }

    tnMultipleTypeTrapEntry OBJECT-TYPE
        SYNTAX         TnMultipleTypeTrapEntry
        MAX-ACCESS     not-accessible
        STATUS         current
        DESCRIPTION    "."
        INDEX { tnMultipleTypeTrapBufferType }
        ::= { tnMultipleTypeTrapTable 1 }

    TnMultipleTypeTrapEntry ::=
        SEQUENCE {
            tnMultipleTypeLastIssuedTrap       Unsigned32
        }

    tnMultipleTypeLastIssuedTrap OBJECT-TYPE
        SYNTAX         Unsigned32
        MAX-ACCESS     read-only
        STATUS         current
        DESCRIPTION    "The serial number of last issued trap."
        ::= { tnMultipleTypeTrapEntry 1 }

-- -------------------------------------------------------------
-- Trap Serial number
-- -------------------------------------------------------------
    tnTrapResetCount OBJECT-TYPE
        SYNTAX         Unsigned32
        MAX-ACCESS     read-only
        STATUS         current
        DESCRIPTION    "The trap serial number reset count."
        ::= { tnTrapBuffering 6 }

-------------------------------------------------------------------------------
-- Conformance Group Definitions
-------------------------------------------------------------------------------
    tnTrapBufferGroup OBJECT-GROUP
        OBJECTS {
            tnTrapType,
            tnTrapTime,
            tnTrapObjectIDType,
            tnTrapObjectID,
            tnTrapCategory,
            tnTrapDescr,
            tnTrapChangedObject,
            tnTrapData,
            tnTrapServiceAffecting,
            tnTrapEntityType,
            tnTrapCondition,
            tnTrapObjectIDIpV6
        }
        STATUS         current
        DESCRIPTION    "."
        ::= { tnNotificationGroups 1 }

    tnTrapBufferScalarsGroup OBJECT-GROUP
        OBJECTS {
            tnLastIssuedTrap,
            tnTrapSerialNumberResetToBeHandled,
            tnTrapResetCount
        }
        STATUS         current
        DESCRIPTION    "."
        ::= { tnNotificationGroups 2 }

    tnMultipleTypeTrapBufferGroup OBJECT-GROUP
        OBJECTS {
            tnMultipleTypeTrapType,
            tnMultipleTypeTrapTime,
            tnMultipleTypeTrapObjectIDType,
            tnMultipleTypeTrapObjectID,
            tnMultipleTypeTrapCategory,
            tnMultipleTypeTrapDescr,
            tnMultipleTypeTrapChangedObject,
            tnMultipleTypeTrapData,
            tnMultipleTypeTrapServiceAffecting,
            tnMultipleTypeTrapEntityType,
            tnMultipleTypeTrapCondition,
            tnMultipleTypeTrapObjectIDIpV6
        }
        STATUS         current
        DESCRIPTION    "."
        ::= { tnNotificationGroups 3 }

    tnMultipleTypeTrapGroup OBJECT-GROUP
        OBJECTS {
            tnMultipleTypeLastIssuedTrap
        }
        STATUS         current
        DESCRIPTION    "."
        ::= { tnNotificationGroups 4 }

-- -------------------------------------------------------------
-- Compliance Statements
-- -------------------------------------------------------------
    tnNotificationCompliance MODULE-COMPLIANCE
        STATUS         current
        DESCRIPTION    "."
        MODULE
        MANDATORY-GROUPS {
            tnTrapBufferGroup,
            tnTrapBufferScalarsGroup,
            tnMultipleTypeTrapBufferGroup,
            tnMultipleTypeTrapGroup
        }
        ::= { tnNotificationCompliances 1 }

END -- DEFINITION OF TROPIC-NOTIFICATION-MIB
