TROPIC-ASON-MIB DEFINITIONS ::= BEGIN

-- (c) Copyright 2023 Nokia Networks.  All rights reserved.
-- This software is the confidential and proprietary property of
-- Nokia and may only be used in accordance with the terms of the
-- license agreement provided with this software.

IMPORTS
      SnmpAdminString                         FROM SNMP-FRAMEWORK-MIB
      OBJECT-TYPE, MODULE-IDENTITY,
      IpAddress,
      Unsigned32, Integer32                   FROM SNMPv2-SMI
      MODULE-COMPLIANCE, OBJECT-GROUP         FROM SNMPv2-CONF
      TEXTUAL-CONVENTION,
      RowStatus, DisplayString                FROM SNMPv2-TC
      ifIndex, InterfaceIndexOrZero           FROM IF-MIB
      InetAddressType, InetAddress            FROM INET-ADDRESS-MIB
      TnCommand,
      AluWdmTransferProtocol,
      AluWdmNewTransferProtocol,
      AluWdmFecMode                           FROM TROPIC-TC
      tnSystemModules, tnAsonMIB              FROM TROPIC-GLOBAL-REG;

  tnAsonMibModule MODULE-IDENTITY
      LAST-UPDATED    "202303101200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION "ASON MIB types."

      REVISION    "202303101200Z"
      DESCRIPTION "Added the following to TnGmreOptLineImpEncoding:
                   mtCohPm16Sqam(24)."

      REVISION    "202212161200Z"
      DESCRIPTION "Added the following to tnGmreOmsLineImpLFiberType:
                   g652smfull(9)    -- G652 Ultra Low Loss Fiber
                   g654e(10)        -- G654E Ultra Low Loss Fiber."

      REVISION    "202212091200Z"
      DESCRIPTION "Added the following to tnGmreOmsLineImpFiberType:
                   g652smfull(11)   -- G652 Ultra Low Loss Fiber
                   g654e(12)        -- G654E Ultra Low Loss Fiber."

      REVISION    "202209301200Z"
      DESCRIPTION "Added the following to TnGmreOptLineImpEncoding:
                   alien(23)."

      REVISION    "202207291200Z"
      DESCRIPTION "Added the following scalar to tnAsonGlobal:
                   tnGmreCommissioningStatus."

      REVISION    "202207151200Z"
      DESCRIPTION "Added the following to TnGmreOptLineProfileImpSlotWidth:
                   sw-137p5-GHz(11)
                   to
                   sw-162p5-GHz(13)."

      REVISION    "202207081200Z"
      DESCRIPTION "Added the following table:
                   tnGmreOptLineProfileImpLTable."

      REVISION    "202207011200Z"
      DESCRIPTION "1) Added the following TEXTUAL-CONVENTION:
                      TnGmreOptLineProfileImpSlotWidth.
                   2) Added the following to tnGmreOmsLineImpTable:
                      tnGmreOmsLineImpLatency.
                   3) Added the following table:
                      tnGmreOptLineProfileImpTable."

      REVISION    "202205201200Z"
      DESCRIPTION "Updated SYNTAX and DESCRIPTION for the following:
                   tnGmreOmsLineImp1830lxdcm."

      REVISION    "202204011200Z"
      DESCRIPTION "Marked the following as obsolete:
                   tnAsonIorGlobal
                   tnGmreCorbaName
                   tnGmreCorbaHostIpAddress
                   tnGmreCorbaIor
                   tnGmreCorbaIorIPv6."

      REVISION    "202107091200Z"
      DESCRIPTION "Added the following to tnGmreOmsWavelengthEncodingType:
                   slotWidth100g(9)      -- Slot Width 100Ghz
                   to
                   slotWidth125g(11)     -- Slot Width 125Ghz."

      REVISION    "202107021200Z"
      DESCRIPTION "1) Added the following to TnGmreOptLineImpEncoding:
                      optimum90gtc(21)
                      optimum86gtc(22).
                   2) Added the following to TnGmreOptLineImpCompModule:
                      add5u(43)
                      to
                      add4b(45)."

      REVISION    "202105211200Z"
      DESCRIPTION "Added the following to tnAlienOtEntityTable:
                   tnAlienOtEntityXcIdAdd
                   tnAlienOtEntityXcIdDrop."

      REVISION    "202012241200Z"
      DESCRIPTION "1) Added the following to TnGmreOptLineImpCompModule:
                      alien(42).
                   2) Added the following table:
                      tnAlienOtEntityTable."

      REVISION    "202012041200Z"
      DESCRIPTION "1) Added the following to TnGmreOptLineImpEncoding:
                      optimum86g(19)
                      optimum90g(20).
                   2) Added the following to TnGmreOptLineImpCompModule:
                      add4l(39)
                      to
                      add5(41)."

      REVISION    "202010091200Z"
      DESCRIPTION "1) Marked the following in TnGmreOptLineImpEncoding as deprecated:
                      icohpmqpsk(6)
                      cohpm64qam(10)
                      to
                      cohpm16qamAbsDcm(13).
                   2) Marked the following in TnGmreOptLineImpCompModule as deprecated:
                      add3iwe(38)."

      REVISION    "202005011200Z"
      DESCRIPTION "Added the following to tnGmreOptLineImpLBitRate:
                   rate300G(10)
                   to
                   rate500G(12)."

      REVISION    "202004101200Z"
      DESCRIPTION "1) Added the following to TnGmreOptLineImpEncoding:
                      optimum33g(16)
                      to
                      optimum56g(18).
                   2) Added the following to TnGmreOptLineImpCompModule:
                      add3iwe(38).
                   3) Added the following to tnGmreOptLineImpBitRate:
                      rate500G(12)."

      REVISION    "201911221200Z"
      DESCRIPTION "Added the following scalar to tnAsonFeasibility:
                   tnAsonFeasibilityPort."

      REVISION    "201911151200Z"
      DESCRIPTION "Changed SYNTAX of from AluWdmTransferProtocol to
                   AluWdmNewTransferProtocol:
                   tnAsonFeasibilityProtocol."

      REVISION    "201905171200Z"
      DESCRIPTION "1) Added the following to tnGmreOmsLineImpFiberType:
                      lx1830ssmf(9)  -- Interworking with 1830LX using SSMF fiber
                      lx1830g654(10) -- Interworking with 1830LX using G654 fiber.
                   2) Added the following to tnGmreOmsLineImpTable:
                      tnGmreOmsLineImp1830lxdcm."

      REVISION    "201904261200Z"
      DESCRIPTION "Added the following to tnGmreUplinkTable:
                   tnGmreUplinkRowStatus
                   tnGmreUplinkMode."

      REVISION    "201904121200Z"
      DESCRIPTION "Added the following table:
                   tnGmreUplinkTable."

      REVISION    "201904051200Z"
      DESCRIPTION "1) Added the following to TnGmreOptLineImpEncoding:
                      optimum62g(14)
                      optimum67g(15).
                   2) Added the following to tnGmreOptLineImpBitRate:
                      rate300G(10)
                      rate50G(11).
                   3) Added the following to tnGmreOmsWavelengthEncodingType
                      slotWidth75g(7)   -- Slot Width 75Ghz
                      slotWidth87p5g(8) -- Slot Width 87 P 5Ghz."

      REVISION    "201903291200Z"
      DESCRIPTION "Added the following table:
                   tnGmreSubmarineGridModeTable."

      REVISION    "201903151200Z"
      DESCRIPTION "Updated the DEFVAL of following from tftp to ftp:
                   tnAsonFeasibilityProtocol."

      REVISION    "201810191200Z"
      DESCRIPTION "Added the following to TnGmreOptLineImpCompModule:
                   c2aco(34)
                   to
                   s13x100l(37)."

      REVISION    "201808241200Z"
      DESCRIPTION "1) Changed MAX-ACCESS of the following from read-write to read-only
                      and DEFVAL from cBandOnly to cPlusLBand:
                      tnGmreAsonItuBandMode.
                   2) Marked the following in tnGmreAsonItuBandMode as deprecated:
                      lBandOnly(2)
                      cBandOnly(3).
                   3) Added the following to tnAsonIorGlobalGroup:
                      tnGmreCorbaIorIPv6.
                   4) Added the following to tnAsonSnapshotGroup:
                      tnAsonSnapshotRemoteInetAddressType
                      tnAsonSnapshotRemoteInetAddress."

      REVISION    "201807201200Z"
      DESCRIPTION "Added the following table:
                   tnGmreClusterTable."

      REVISION    "201805251200Z"
      DESCRIPTION "Added the following scalar to tnAsonGlobal:
                   tnGmreClusterMode."

      REVISION    "201802231200Z"
      DESCRIPTION "Updated the contact info."

      REVISION    "201801191200Z"
      DESCRIPTION "Added the following to TnGmreOptLineImpCompModule:
                   addxs(32)
                   add4(33)."

      REVISION    "201801121200Z"
      DESCRIPTION "Updated ranges for the following attributes:
                   tnGmreOptLineImpLOSNR    (0..3162277660)
                   tnGmreOptLineImpLOSNRNP  (0..3162277660)
                   tnGmreOptLineImpOSNR     (0..3162277660)
                   tnGmreOptLineImpOSNRNP   (0..3162277660)."

      REVISION    "201710201200Z"
      DESCRIPTION "Added the following to tnGmreOptLineImpLTable:
                   tnGmreOptLineImpLPhaseEncode."

      REVISION    "201710131200Z"
      DESCRIPTION "Added the following to tnGmreOptLineImpTable:
                   tnGmreOptLineImpPhaseEncode."

      REVISION    "201709081200Z"
      DESCRIPTION "Added the following to TnGmreOptLineImpCompModule:
                   cm130sl(31)."

      REVISION    "201708181200Z"
      DESCRIPTION "Added the following scalar to tnAsonGlobal:
                   tnGmreAsonItuBandMode."

      REVISION    "201707071200Z"
      DESCRIPTION "1) Added the following to TnGmreOptLineImpCompModule:
                      tsfpplus(30)
                   2) Added the following to TnGmreOptLineImpEncoding:
                      cohpm16qamDiffFree(12)
                      cohpm16qamAbsDcm(13)
                   3) Added the following to tnGmreOmsLineImpTable:
                      tnGmreOmsLineImpCD1546.
                   4) Fixed MIB compile issues."

      REVISION    "201705121200Z"
      DESCRIPTION "1) Marked the following in TnGmreOptLineImpCompModule as deprecated:
                      variant1(7)
                      to
                      variant10(16).
                   2) Renamed add2lh(24) to cm2ac100h(24) in TnGmreOptLineImpCompModule.
                   3) Changed SYNTAX of the following from INTEGER to TnGmreOptLineImpEncoding.
                      tnGmreOptLineImpEncoding.
                   4) Changed SYNTAX of the following from INTEGER to TnGmreOptLineImpCompModule.
                      tnGmreOptLineImpCompModule."

      REVISION    "201704281200Z"
      DESCRIPTION "1) Added the following to TnGmreOptLineImpCompModule and fixed typos:
                      add3iw(27)
                      s13x100(28)
                      add3l(29).
                   2) Fixed the following typo in tnGmreOptLineImpEncoding and
                      tnGmreOptLineImpLEncoding:
                      from ohpmqpskabs to cohpmqpskabs."

      REVISION    "201704131200Z"
      DESCRIPTION "Added the following to tnGmreOmsLineImpLFiberType:
                   dsf(8)  -- Dispersion Shifted Fiber."

      REVISION    "201704071200Z"
      DESCRIPTION "Added the following to tnGmreOmsLineImpFiberType:
                   dsf(8)  -- Dispersion Shifted Fiber."

      REVISION    "201703171200Z"
      DESCRIPTION "1) Added the following:
                      tnGmreOmsLineImpLTable
                      tnGmreOptLineImpLTable
                      tnGmreOmsWavelengthSetLTable.
                   2) Added the following to tnGmreOptLineImpCompModule and
                      tnGmreOptLineImpLCompModule:
                      s13x100(28)
                      add3l(29)."

      REVISION    "201702171200Z"
      DESCRIPTION "Added the following scalars to tnAsonFeasibility:
                   tnAsonFeasibilityRemoteInetAddressType
                   tnAsonFeasibilityRemoteInetAddress."

      REVISION    "201612071200Z"
      DESCRIPTION "1) Added the following to tnGmreOptLineImpEncoding:
                      cohpmqpskabs(11)  -- Coherent Path Modulation Quad Phase
                                        -- Shift Keying /w absolute phase encoding
                   2) Added the comment for  cohpmqpsk(5) to
                      cohpmqpsk(5)      -- Coherent Path Modulation Quad Phase
                                        -- Shift Keying /w differential phase encoding."

      REVISION    "201611161200Z"
      DESCRIPTION "Updated the contact info."

      REVISION    "201610281200Z"
      DESCRIPTION "1) Added ls(6) to tnGmreOmsLineImpFiberType.
                   2) Added add3iw(27) to tnGmreOptLineImpCompModule.
                   3) Renamed add2lh(24) to cm2ac100h(24) in tnGmreOptLineImpCompModule.
                   4) Marked variant1(7) to variant10(16) as depricated in tnGmreOptLineImpCompModule.
                   5) Added the following to tnGmreOmsWavelengthEncodingType
                      slotWidth50(4)   -- Slot Width 50Ghz
                      lotWidth62p5(5)  -- Slot Width 62 P 5Ghz
                      coherent16qam(6) -- Coherent encoding 16qam."

      REVISION    "201606101200Z"
      DESCRIPTION "1) Added the following scalar to tnAsonGlobal:
                      tnGmreDiscoveryMode.
                   2) Changed the SYNTAX of tnGmreOmsWavelengthEncodingBitMap
                      From OCTET STRING (SIZE(12)) to OCTET STRING (SIZE(11))"

      REVISION    "201605181200Z"
      DESCRIPTION "Added the following to tnGmreOptLineImpCompModule
                   and TnGmreOptLineImpCompModule:
                   cm2ac100(26)."

      REVISION    "201604181200Z"
      DESCRIPTION "Added the following to tnGmreOptLineImpCompModule
                   and TnGmreOptLineImpCompModule:
                   ovclk(25)        -- 200G High Performace OT."

      REVISION    "201603181200Z"
      DESCRIPTION "Added the following to TEXTUAL-CONVENTION:
                   TnGmreOptLineImpEncoding
                   TnGmreOptLineImpCompModule."

      REVISION    "201602241200Z"
      DESCRIPTION "1) Added the following to tnGmreOptLineImpBitRate:
                      rate50G(6)
                      rate200G(7)
                      rate250G(8)
                      rate400G(9).
                   2) Added the following to tnGmreOptLineImpEncoding:
                      cohspqpsk(9)   -- Coherent Set Partial Quad Phase
                                     -- Shift Keying
                      cohpm64qam(10) -- Coherent Polarization Multiplexed 64-state
                                     -- Quadrature Amplitude Modulation.
                   3) Added the following to tnGmreOptLineImpCompModule:
                      add2l(23)      -- >= 100G High Performace OT for metro, 2nd Generation
                      add2lh(24)     -- >= 100G High Performace OT for long haul, 2nd Generation."

      REVISION    "201602191200Z"
      DESCRIPTION "Changed the value of following in tnGmreOptLineImpCompModule:
                   From add(22) to add3(22)."

      REVISION    "201601201200Z"
      DESCRIPTION "1) Added the following to tnGmreOptLineImpEncoding:
                      cohpm8qam(8)   -- Coherent Polarization Multiplexed
                                     -- 8-state Quadrature Amplitude Modulation
                   2) Added the following to tnGmreOptLineImpCompModule:
                      add(22)        -- >= 100G High Performace OT, 3rd Gen."

      REVISION    "201506291200Z"
      DESCRIPTION "Changed the SYNTAX of tnGmreOmsLineImpPDL:
                    Modified the max range from 10000 to 500000"

      REVISION    "201506021200Z"
      DESCRIPTION "Added the following to tnGmreOmsLineImpTable:
                   tnGmreOmsLineImpPDL."

      REVISION    "201503261200Z"
      DESCRIPTION "Changed range values of following in tnGmreOptLineImpTable:
                   tnGmreOptLineImpNLP
                   tnGmreOptLineImpNLPNP."

      REVISION    "201402261200Z"
      DESCRIPTION "Added DEFVAL to attributes."

      REVISION    "201311221200Z"
      DESCRIPTION "1) Added the following to tnGmreOptLineImpBitRate:
                      rate260G(5).
                   2) Added the following to tnGmreOptLineImpEncoding:
                      cohpm16qam(7)  -- Coherent Polarization Multiplexed
                                     -- 16-state Quadrature Amplitude Modulation."

      REVISION    "201311181200Z"
      DESCRIPTION "Added the following to tnAsonSnapshotGroup:
                   tnAsonSnapshotRootRemotePath."

      REVISION    "201309201200Z"
      DESCRIPTION "1) Added the following scalars to tnAsonSnapshot:
                      tnAsonSnapshotRemoteHostIp
                      tnAsonSnapshotProtocol
                      tnAsonSnapshotUserId
                      tnAsonSnapshotPassword.
                   2) Added the following table:
                      tnAsonSnapshotTable.
                   3) Added the following to tnGmreOptLineImpCompModule:
                      hperf2(21)      -- 100G High Performance OT, 2nd Gen."

      REVISION    "201211051200Z"
      DESCRIPTION "Added the following to tnGmreOptLineImpCompModule:
                   sperf2(20)     -- 100G Standard Performance OT, 2nd Gen."

      REVISION    "201210221200Z"
      DESCRIPTION "1) Added the following to tnGmreOptLineImpEncoding:
                      icohpmqpsk(6)  -- Time-interleaved Coherent Path
                                     -- Modulation Quad Phase Shift Keying
                   2) Added the following to tnGmreOptLineImpCompModule:
                      ctxfpwt(19)     -- 0-Chirp Tunable XFP with unused WT capability."

      REVISION    "201208101200Z"
      DESCRIPTION "1) Added the following to tnGmreOmsLineImpTable:
                      tnGmreOmsLineImpCD
                      tnGmreOmsLineImpFiberType.
                   2) Added the following to tnGmreOptLineImpTable:
                      tnGmreOptLineImpPower."

      REVISION    "201206251200Z"
      DESCRIPTION "Added the following MIB table:
                   tnGmreOmsWavelengthSetTable."

      REVISION    "201201241200Z"
      DESCRIPTION "Added the following to tnGmreOptLineImpCompModule:
                   cr(18)          -- Cost Reduced."

      REVISION    "201201171200Z"
      DESCRIPTION "1) Added the following MIB table:
                      tnAsonMgracdTable.
                   2) Added the following define:
                      AluWdmAccessControlDevice."

      REVISION    "201108121200Z"
      DESCRIPTION "Added the following to tnGmreOptLineImpCompModule:
                   tcfp(17)       -- Tunable Compact Form Package."

      REVISION    "201108081200Z"
      DESCRIPTION "Added the following scalars to tnAsonFeasibility:
                   tnAsonFeasibilityCommand
                   tnAsonFeasibilityRemoteHostIp
                   tnAsonFeasibilityRemotePath
                   tnAsonFeasibilityStatus
                   tnAsonFeasibilityLastTransferredVersion
                   tnAsonFeasibilityProtocol
                   tnAsonFeasibilityUserId
                   tnAsonFeasibilityPassword."

      REVISION    "201108031200Z"
      DESCRIPTION "Updated ranges for the following attributes:
                   tnGmreOptLineImpOSNR, (0..1000000000)
                   tnGmreOptLineImpOSNRNP, (0..1000000000)."

      REVISION    "201107251200Z"
      DESCRIPTION "Added the following to tnGmreOptLineImpCompModule:
                   hperf1(6)       -- 100G High Performance OT
                   to
                   variant10(16)   -- Variant 10."

      REVISION    "201106301200Z"
      DESCRIPTION "Added ranges to the SYNTAX of the following attributes:
                   tnGmreOmsLineImpMaxAlwCh, (1..96)
                   tnGmreOmsLineImpPMD, (0..10000)
                   tnGmreOptLineImpOSNR, (0..100000000)
                   tnGmreOptLineImpOSNRNP, (0..100000000)."

      REVISION    "201105311200Z"
      DESCRIPTION "Added the following to tnGmreOptLineImpCompModule:
                   txfp(5)   -- Tunable 10G Small Form Factor Pluggable."

      REVISION    "201105051200Z"
      DESCRIPTION "Added the following table:
                   tnAsonTopoAlarmTable."

      REVISION    "201103041200Z"
      DESCRIPTION "Added the following tables:
                   tnGmreOmsLineImpTable
                   tnGmreOptLineImpTable."

      REVISION    "201010121200Z"
      DESCRIPTION "Created MIB file for GMRE IP and CORBA IOR parameters."

      ::= { tnSystemModules 10 }

  tnAsonConf               OBJECT IDENTIFIER ::= { tnAsonMIB 1 }
  tnAsonGroups             OBJECT IDENTIFIER ::= { tnAsonConf 1 }
  tnAsonCompliances        OBJECT IDENTIFIER ::= { tnAsonConf 2 }
  tnAsonObjs               OBJECT IDENTIFIER ::= { tnAsonMIB 2 }
  tnAsonGlobal             OBJECT IDENTIFIER ::= { tnAsonObjs 1 }
--  obsolete
--  tnAsonIorGlobal          OBJECT IDENTIFIER ::= { tnAsonObjs 2 }
  tnAsonOmsLineImp         OBJECT IDENTIFIER ::= { tnAsonObjs 3 }
  tnAsonOptLineImp         OBJECT IDENTIFIER ::= { tnAsonObjs 4 }
  tnAsonTopoAlarm          OBJECT IDENTIFIER ::= { tnAsonObjs 5 }
  tnAsonFeasibility        OBJECT IDENTIFIER ::= { tnAsonObjs 6 }
  tnAsonMgracdInfo         OBJECT IDENTIFIER ::= { tnAsonObjs 7 }
  tnAsonOmsWavelengthSet   OBJECT IDENTIFIER ::= { tnAsonObjs 8 }
  tnAsonSnapshot           OBJECT IDENTIFIER ::= { tnAsonObjs 9 }
  tnAsonOmsLineImpL        OBJECT IDENTIFIER ::= { tnAsonObjs 10 }
  tnAsonOptLineImpL        OBJECT IDENTIFIER ::= { tnAsonObjs 11 }
  tnAsonOmsWavelengthSetL  OBJECT IDENTIFIER ::= { tnAsonObjs 12 }
  tnAsonClusterObjs        OBJECT IDENTIFIER ::= { tnAsonObjs 13 }
  tnAsonSubmarineGridMode  OBJECT IDENTIFIER ::= { tnAsonObjs 14 }
  tnAsonUpLink             OBJECT IDENTIFIER ::= { tnAsonObjs 15 }
  tnAlienOtEntity          OBJECT IDENTIFIER ::= { tnAsonObjs 16 }

--------------------------------------------------------------------------------
-- Type Definitions
--------------------------------------------------------------------------------
    AluWdmAccessControlDevice ::= TEXTUAL-CONVENTION
        STATUS         current
        DESCRIPTION    "Indicates if an entity is managed by control
                        plane, management plane, shared by both, or free."
        SYNTAX         INTEGER {
                         null(1), -- Entity is free
                         cp(2),   -- Entity is owned by control plane
                         mp(3),   -- Entity is owned by management plane
                         cpMp(4)  -- Entity is shared by control and management planes
                       }

    TnGmreOptLineImpEncoding ::= TEXTUAL-CONVENTION
        STATUS         current
        DESCRIPTION    "GMRE optical line encoding or modulation."
        SYNTAX         INTEGER {
                         nrz(1),                 -- Non-Return-to-Zero encoding
                         pdpsk(2),               -- Partial Differential Phase
                                                 -- Shift Keying
                         dpsk(3),                -- Differential Phase-Shift Keying
                         cohpmbpsk(4),           -- Coherent Path Modulation Binary
                                                 -- Phase Shift Keying
                         cohpmqpsk(5),           -- Coherent Path Modulation Quad
                                                 -- Phase
                                                 -- Shift Keying /w differential
                                                 -- phase encoding
                         icohpmqpsk(6),          --deprecated
                                                 -- Time-interleaved Coherent Path
                                                 -- Modulation Quad Phase Shift Keying
                         cohpm16qam(7),          -- Coherent Polarization Multiplexed
                                                 -- 16-state Quadrature Amplitude
                                                 -- Modulation
                         cohpm8qam(8),           -- Coherent Polarization Multiplexed
                                                 -- 8-state Quadrature Amplitude
                                                 -- Modulation
                         cohspqpsk(9),           -- Coherent Set Partial Quad Phase
                                                 -- Shift Keying
                         cohpm64qam(10),         --deprecated
                                                 -- Coherent Polarization Multiplexed
                                                 -- 64-state
                                                 -- Quadrature Amplitude Modulation
                         cohpmqpskabs(11),       --deprecated
                                                 -- Coherent Path Modulation Quad Phase
                                                 -- Shift Keying /w absolute phase
                                                 -- encoding
                         cohpm16qamDiffFree(12), --deprecated
                                                 -- Coherent Polarization Multiplexed
                                                 -- 16-state Quadrature Amplitude
                                                 -- Modulation /w differential phase
                                                 -- encoding in DCM free NW
                         cohpm16qamAbsDcm(13),   --deprecated
                                                 -- Coherent Polarization Multiplexed
                                                 -- 16-state Quadrature Amplitude
                                                 -- Modulation /w absolute phase
                                                 -- encoding in DCM NW
                         optimum62g(14),         -- optimum line encoding for ADD4 with
                                                 -- 62 Gbaud rate
                         optimum67g(15),         -- optimum line encoding for ADD4 with
                                                 -- 67 Gbaud rate
                         optimum33g(16),         -- optimum line encoding for ADD4 with
                                                 -- 33 Gbaud rate
                         optimum45g(17),         -- optimum line encoding for ADD4 with
                                                 -- 45 Gbaud rate
                         optimum56g(18),         -- optimum line encoding for ADD4 with
                                                 -- 56 Gbaud rate
                         optimum86g(19),         -- optimum line encoding for ADD5 with
                                                 -- 86 Gbaud rate
                         optimum90g(20),         -- optimum line encoding for ADD5 with
                                                 -- 90 Gbaud rate
                         optimum90gtc(21),       -- optimum line encoding for ADD5u with
                                                 -- Transcoded  mapping 90 Gbaud rate
                         optimum86gtc(22),       -- optimum line encoding for ADD5u with
                                                 -- Transcoded  mapping 86 Gbaud rate
                         alien(23),              -- Line encoding for Alien Transponders
                         mtCohPm16Sqam(24)       -- Line encoding for BFP Subsea 2.0 Transponders
                       }

    TnGmreOptLineImpCompModule ::= TEXTUAL-CONVENTION
        STATUS         current
        DESCRIPTION    "GMRE Optical Line Compensation Module (on the OCH
                        transponder line side)."
        SYNTAX         INTEGER {
                         null(1),
                         pmdc(2),        -- Polarization Mode Dispersion Compensation
                         mlse(3),        -- Maximum-Likelihood Sequence
                         tdcm(4),        -- Tunable Dispersion Compensation Module
                         txfp(5),        -- Tunable 10G Small Form Factor Pluggable
                         hperf1(6),      -- 100G High Performance OT
--                         deprecated
--                         variant1(7),
--                         variant2(8),
--                         variant3(9),
--                         variant4(10),
--                         variant5(11),
--                         variant6(12),
--                         variant7(13),
--                         variant8(14),
--                         variant9(15),
--                         variant10(16),
                         tcfp(17),       -- Tunable Compact Form Package
                         cr(18),         -- Cost Reduced
                         ctxfpwt(19),    -- 0-Chirp Tunable XFP with unused WT
                                         -- capability
                         sperf2(20),     -- 100G Standard Performance OT, 2nd Gen
                         hperf2(21),     -- 100G High Performance OT, 2nd Gen
                         add3(22),       -- >= 100G High Performace OT, 3rd Gen
                         add2l(23),      -- >= 100G High Performace OT for metro,
                                         -- 2nd Generation
                         cm2ac100h(24),  -- >= 100G High Performace OT for long
                                         -- haul, 2nd Generation
                         ovclk(25),      -- 200G High Performance OT
                         cm2ac100(26),   -- 100G High Performace OT for metro,
                                         -- 2nd Generation, pluggable
                         add3iw(27),     -- interworking compensation module of
                                         -- new D5X500 variant w/ 4UC400
                         s13x100(28),    -- special comp module for S13X100R/E
                         add3l(29),      -- >= 100G High Performace OT, 3rd Gen
                                         -- for L Band
                         tsfpplus(30),   -- Tunable 10G pluggable module with
                                         -- Wavetracker support
                         cm130sl(31),    -- 100G standard performance L band, 2nd
                                         -- generation for 130SLX10 and 130SCA1
                         addxs(32),      -- >= 100G High Performace OT, 4th Generation
                         add4(33),       -- >= 100G High Performace OT, 4th Generation
                         c2aco(34),
                         c4aco(35),
                         ctxfpiwton(36),
                         s13x100l(37),   -- L band version of S13X100E
                         add3iwe(38),    --deprecated
                                         -- interworking compensation module of
                                         -- new variant 4UC400E
                         add4l(39),      -- >= 100G High Performance OT, 4th
                                         -- Generation for L Band
                         add4m(40),      -- >= 100G High Performance OT, 5th
                                         -- Generation for C Band
                         add5(41),       -- >= 100G High Performance OT, 6th
                                         -- Generation for C Band
                         alien(42),      -- Alien OT Entity
                         add5u(43),      -- >= 100G High Performance OT, 6th
                                         -- Generation for C Band
                         add5ul(44),     -- >= 100G High Performance OT, 6th
                                         -- Generation for L Band
                         add4b(45)       -- >= 100G High Performance OT, 4th
                                         -- Generation for DFC12
                       }

    TnGmreOptLineImpPhaseEncode ::= TEXTUAL-CONVENTION
        STATUS         current
        DESCRIPTION    "GMRE optical line phase encoding."
        SYNTAX         INTEGER {
                         notAppl(0),         -- not applicable for this type
                         absolute(1),        -- absolute phase encoding
                         differential(2)     -- differential phase encoding
                       }

    TnGmreOptLineProfileImpSlotWidth ::= TEXTUAL-CONVENTION
        STATUS       current
        DESCRIPTION  "Slot Width."
        SYNTAX       INTEGER {
                       invalid(0),
                       sw-12p5-GHz(1),
                       sw-25-GHz(2),
                       sw-37p5-GHz(3),
                       sw-50-GHz(4),
                       sw-62p5-GHz(5),
                       sw-75-GHz(6),
                       sw-87p5-GHz(7),
                       sw-100-GHz(8),
                       sw-112p5-GHz(9),
                       sw-125-GHz(10),
                       sw-137p5-GHz(11),
                       sw-150-GHz(12),
                       sw-162p5-GHz(13)
                     }

--------------------------------------------------------------------------------
-- GMRE IP parameters
--------------------------------------------------------------------------------
    tnGmreNodeIpAddr OBJECT-TYPE
        SYNTAX         IpAddress
        MAX-ACCESS     read-write
        STATUS         current
        DESCRIPTION    "This address is used for all GMPLS communication
                        protocols across the network."
        DEFVAL         { '00000000'H }
        ::= { tnAsonGlobal 1 }

    tnGmreNodeSubMask OBJECT-TYPE
        SYNTAX         IpAddress
        MAX-ACCESS     read-write
        STATUS         current
        DESCRIPTION    "Subnet mask for tnGmreNodeIpAddr."
        DEFVAL         { '00000000'H }
        ::= { tnAsonGlobal 2 }

    tnGmreNotifyIpAddr OBJECT-TYPE
        SYNTAX         IpAddress
        MAX-ACCESS     read-write
        STATUS         current
        DESCRIPTION    "This address is used by RSVP-TE for fast failure
                        notify message within the network."
        DEFVAL         { '00000000'H }
        ::= { tnAsonGlobal 3 }

    tnGmreNotifySubMask OBJECT-TYPE
        SYNTAX         IpAddress
        MAX-ACCESS     read-write
        STATUS         current
        DESCRIPTION    "Subnet mask for tnGmreNotifyIpAddr."
        DEFVAL         { '00000000'H }
        ::= { tnAsonGlobal 4 }

    tnGmreDiscoveryMode OBJECT-TYPE
        SYNTAX         INTEGER {
                         yes(1),
                         no(2)
                       }
        MAX-ACCESS     read-write
        STATUS         current
        DESCRIPTION    "Enable or disable the eGLUE discovery mode."
        DEFVAL         { no }
        ::= { tnAsonGlobal 5 }

    tnGmreAsonItuBandMode OBJECT-TYPE
        SYNTAX         INTEGER {
                         unknown(1),
                         lBandOnly(2),     --deprecated
                         cBandOnly(3),     --deprecated
                         cPlusLBand(4)
                       }
        MAX-ACCESS     read-only
        STATUS         current
        DESCRIPTION    "Ason ITU Band mode."
        DEFVAL         { cPlusLBand }
        ::= { tnAsonGlobal 6 }

    tnGmreClusterMode OBJECT-TYPE
        SYNTAX         INTEGER {
                         yes(1),
                         no(2)
                       }
        MAX-ACCESS     read-write
        STATUS         current
        DESCRIPTION    "Enable or disable the GLUE cluster mode."
        DEFVAL         { no }
        ::= { tnAsonGlobal 7 }

    tnGmreCommissioningStatus OBJECT-TYPE
        SYNTAX         INTEGER {
                         up(1),
                         down(2)
                       }
        MAX-ACCESS     read-only
        STATUS         current
        DESCRIPTION    "Display the status of GMRE node commissioning."
        ::= { tnAsonGlobal 8 }

--------------------------------------------------------------------------------
-- GMRE CORBA IOR parameters
--------------------------------------------------------------------------------
--    obsolete
--    tnGmreCorbaName OBJECT-TYPE          ::= { tnAsonIorGlobal 1 }
--    tnGmreCorbaHostIpAddress OBJECT-TYPE ::= { tnAsonIorGlobal 2 }
--    tnGmreCorbaIor OBJECT-TYPE           ::= { tnAsonIorGlobal 3 }
--    tnGmreCorbaIorIPv6 OBJECT-TYPE       ::= { tnAsonIorGlobal 4 }

--------------------------------------------------------------------------------
-- GMRE OMS Line Optical Impairment Scalar
--------------------------------------------------------------------------------
    tnGmreOmsLineImpAttributeTotal OBJECT-TYPE
        SYNTAX         Integer32
        MAX-ACCESS     read-only
        STATUS         current
        DESCRIPTION    "."
        ::= { tnAsonOmsLineImp 1 }

--------------------------------------------------------------------------------
-- GMRE OMS Line Optical Impairment parameters
--------------------------------------------------------------------------------
    tnGmreOmsLineImpTable OBJECT-TYPE
        SYNTAX         SEQUENCE OF TnGmreOmsLineImpEntry
        MAX-ACCESS     not-accessible
        STATUS         current
        DESCRIPTION    "."
        ::= { tnAsonOmsLineImp 2 }

    tnGmreOmsLineImpEntry OBJECT-TYPE
        SYNTAX         TnGmreOmsLineImpEntry
        MAX-ACCESS     not-accessible
        STATUS         current
        DESCRIPTION    "."
        INDEX { ifIndex }
        ::= { tnGmreOmsLineImpTable 1 }

    TnGmreOmsLineImpEntry ::=
        SEQUENCE {
            tnGmreOmsLineImpMaxAlwCh      Unsigned32,
            tnGmreOmsLineImpPMD           Unsigned32,
            tnGmreOmsLineImpAlcMode       INTEGER,
            tnGmreOmsLineImpDcuFree       INTEGER,
            tnGmreOmsLineImpCD            Integer32,
            tnGmreOmsLineImpFiberType     INTEGER,
            tnGmreOmsLineImpPDL           Unsigned32,
            tnGmreOmsLineImpCD1546        Integer32,
            tnGmreOmsLineImp1830lxdcm     Integer32,
            tnGmreOmsLineImpLatency       Integer32
        }

    tnGmreOmsLineImpMaxAlwCh OBJECT-TYPE
        SYNTAX         Unsigned32 (1..96)
        MAX-ACCESS     read-create
        STATUS         current
        DESCRIPTION    "GMRE OMS maximum allowed channels (MAXALCH).

                        Current configurable range: 1 to 96."
        DEFVAL         { 88 }
        ::= { tnGmreOmsLineImpEntry 1 }

    tnGmreOmsLineImpPMD OBJECT-TYPE
        SYNTAX         Unsigned32 (0..10000)
        UNITS          "1/10 picoSecond"
        MAX-ACCESS     read-create
        STATUS         current
        DESCRIPTION    "GMRE OMS polarization mode dispersion (PMD).  The
                        valid value is 0.0 to 1000.0 pico-seconds with
                        precision of one decimal digit.

                        Current configurable range: 0 to 10000."
        DEFVAL         { 0 }
        ::= { tnGmreOmsLineImpEntry 2 }

    tnGmreOmsLineImpAlcMode OBJECT-TYPE
        SYNTAX         INTEGER {
                         on(1),
                         off(2)
                       }
        MAX-ACCESS     read-create
        STATUS         current
        DESCRIPTION    "An indication as to whether or not the GMRE OMS
                        Automatic Level Control (ALC) Mode is on or not.
                        Equivalent to LNS (Laser Network Stabilization)
                        Mode."
        DEFVAL         { on }
        ::= { tnGmreOmsLineImpEntry 3 }

    tnGmreOmsLineImpDcuFree OBJECT-TYPE
        SYNTAX         INTEGER {
                         yes(1),
                         no(2)
                       }
        MAX-ACCESS     read-create
        STATUS         current
        DESCRIPTION    "GMRE OMS Dispersion Compensation Unit (DCU) is DCM
                        Free or not."
        DEFVAL         { yes }
        ::= { tnGmreOmsLineImpEntry 4 }

    tnGmreOmsLineImpCD OBJECT-TYPE
        SYNTAX         Integer32 (-40000..78000)
        UNITS          "1/10 ps/nm"
        MAX-ACCESS     read-create
        STATUS         current
        DESCRIPTION    "GMRE OMS chromatic dispersion (CD).  The new
                        coherent feasibility model is in units of 1/10
                        ps/nm (picoseconds/nanometer) because it needs
                        to have precision of one decimal digit.  The valid
                        values are -4000.0 to 7800.0 ps/nm.

                        Current configurable range: -40000 to 78000."
        DEFVAL         { 17000 }
        ::= { tnGmreOmsLineImpEntry 5 }

    tnGmreOmsLineImpFiberType OBJECT-TYPE
        SYNTAX         INTEGER {
                         ssmf(1),         -- Standard Single-Mode Fiber (SSMF)
                         eleaf(2),        -- Enhanced Large Effective Area Fiber (ELEAF)
                         twrs(3),         -- True Wave Reduced Slope (TWRS)
                         twc(4),          -- True Wave Classic (TWC)
                         twp(5),          -- True Wave Plus (TW+)
                         mixed(6),        -- Mixed fiber type
                         ls(7),           -- Corning SMF-LS, LEAF Submarine
                         dsf(8),          -- Dispersion Shifted Fiber
                         lx1830ssmf(9),   -- Interworking with 1830LX using SSMF fiber
                         lx1830g654(10),  -- Interworking with 1830LX using G654 fiber
                         g652smfull(11),  -- G652 Ultra Low Loss Fiber
                         g654e(12)        -- G654E Ultra Low Loss Fiber
                       }
        MAX-ACCESS     read-create
        STATUS         current
        DESCRIPTION    "GMRE OMS span fiber type."
        DEFVAL         { ssmf }
        ::= { tnGmreOmsLineImpEntry 6 }

    tnGmreOmsLineImpPDL OBJECT-TYPE
        SYNTAX         Unsigned32 (0..500000)
        UNITS          "1 dB"
        MAX-ACCESS     read-create
        STATUS         current
        DESCRIPTION    "GMRE OMS polarization dependent loss (PDL).  The
                        valid value is 0.00000 to 5.00000 dB  with
                        precision of five decimal digit.
                        Current configurable range: 0 to 500000."
        DEFVAL         { 0 }
        ::= { tnGmreOmsLineImpEntry 7 }

    tnGmreOmsLineImpCD1546 OBJECT-TYPE
        SYNTAX         Integer32 (-40000..78000)
        UNITS          "1/10 ps/nm"
        MAX-ACCESS     read-create
        STATUS         current
        DESCRIPTION    "GMRE OMS chromatic dispersion (CD)at 1546 nm [ps/nm].
                        The new coherent feasibility model is in units of 1/10
                        ps/nm (picoseconds/nanometer) because it needs to have
                        precision of one decimal digit.  The valid values are
                        -4000.0 to 7800.0 ps/nm.

                        Current configurable range: -40000 to 78000."
        DEFVAL         { 17000 }
        ::= { tnGmreOmsLineImpEntry 8 }

    tnGmreOmsLineImp1830lxdcm OBJECT-TYPE
        SYNTAX         Integer32
        UNITS          "1/10 ps/nm"
        MAX-ACCESS     read-create
        STATUS         current
        DESCRIPTION    "GMRE OMS accumulated chromatic dispersion (CD) for
                        1830LX Submarine link.  The new coherent feasibility
                        model is in units of 1/10 ps/nm (picoseconds/nanometer)
                        because it needs to have precision of one decimal digit.
                        The valid values are -10000.0 to 0.0 ps/nm.

                        Current configurable range: -1000000.0..0."
        DEFVAL         { 0 }
        ::= { tnGmreOmsLineImpEntry 9 }

    tnGmreOmsLineImpLatency OBJECT-TYPE
        SYNTAX         Integer32
        MAX-ACCESS     read-create
        STATUS         current
        DESCRIPTION    "Current configurable range: 0..1000000000."
        DEFVAL         { 0 }
        ::= { tnGmreOmsLineImpEntry 10 }

--------------------------------------------------------------------------------
-- GMRE OMS Line Optical Impairment Scalar for L Band
--------------------------------------------------------------------------------
    tnGmreOmsLineImpLAttributeTotal OBJECT-TYPE
        SYNTAX         Integer32
        MAX-ACCESS     read-only
        STATUS         current
        DESCRIPTION    "."
        ::= { tnAsonOmsLineImpL 1 }

--------------------------------------------------------------------------------
-- GMRE OMS Line Optical Impairment parameters for L Band
--------------------------------------------------------------------------------
    tnGmreOmsLineImpLTable OBJECT-TYPE
        SYNTAX         SEQUENCE OF TnGmreOmsLineImpLEntry
        MAX-ACCESS     not-accessible
        STATUS         current
        DESCRIPTION    "."
        ::= { tnAsonOmsLineImpL 2 }

    tnGmreOmsLineImpLEntry OBJECT-TYPE
        SYNTAX         TnGmreOmsLineImpLEntry
        MAX-ACCESS     not-accessible
        STATUS         current
        DESCRIPTION    "."
        INDEX { ifIndex }
        ::= { tnGmreOmsLineImpLTable 1 }

    TnGmreOmsLineImpLEntry ::=
        SEQUENCE {
            tnGmreOmsLineImpLMaxAlwCh   Unsigned32,
            tnGmreOmsLineImpLPMD        Unsigned32,
            tnGmreOmsLineImpLAlcMode    INTEGER,
            tnGmreOmsLineImpLDcuFree    INTEGER,
            tnGmreOmsLineImpLCD         Integer32,
            tnGmreOmsLineImpLFiberType  INTEGER,
            tnGmreOmsLineImpLPDL        Unsigned32
        }

    tnGmreOmsLineImpLMaxAlwCh OBJECT-TYPE
        SYNTAX         Unsigned32 (1..96)
        MAX-ACCESS     read-create
        STATUS         current
        DESCRIPTION    "GMRE OMS maximum allowed channels (MAXALCH) for L Band.

                        Current configurable range: 1 to 96."
        DEFVAL         { 88 }
        ::= { tnGmreOmsLineImpLEntry 1 }

    tnGmreOmsLineImpLPMD OBJECT-TYPE
        SYNTAX         Unsigned32 (0..10000)
        UNITS          "1/10 picoSecond"
        MAX-ACCESS     read-create
        STATUS         current
        DESCRIPTION    "GMRE OMS polarization mode dispersion (PMD).  The
                        valid value is 0.0 to 1000.0 pico-seconds with
                        precision of one decimal digit for L Band.

                        Current configurable range: 0 to 10000."
        DEFVAL         { 0 }
        ::= { tnGmreOmsLineImpLEntry 2 }

    tnGmreOmsLineImpLAlcMode OBJECT-TYPE
        SYNTAX         INTEGER {
                         on(1),
                         off(2)
                       }
        MAX-ACCESS     read-create
        STATUS         current
        DESCRIPTION    "An indication as to whether or not the GMRE OMS
                        Automatic Level Control (ALC) Mode is on or not.
                        Equivalent to LNS (Laser Network Stabilization)
                        Mode for L Band."
        DEFVAL         { on }
        ::= { tnGmreOmsLineImpLEntry 3 }

    tnGmreOmsLineImpLDcuFree OBJECT-TYPE
        SYNTAX         INTEGER {
                         yes(1),
                         no(2)
                       }
        MAX-ACCESS     read-create
        STATUS         current
        DESCRIPTION    "GMRE OMS Dispersion Compensation Unit (DCU) is DCM
                        Free or not for L Band."
        DEFVAL         { yes }
        ::= { tnGmreOmsLineImpLEntry 4 }

    tnGmreOmsLineImpLCD OBJECT-TYPE
        SYNTAX         Integer32 (-40000..78000)
        UNITS          "1/10 ps/nm"
        MAX-ACCESS     read-create
        STATUS         current
        DESCRIPTION    "GMRE OMS chromatic dispersion (CD).  The new
                        coherent feasibility model is in units of 1/10
                        ps/nm (picoseconds/nanometer) because it needs
                        to have precision of one decimal digit.  The valid
                        values are -4000.0 to 7800.0 ps/nm for L Band.

                        Current configurable range: -40000 to 78000."
        DEFVAL         { 17000 }
        ::= { tnGmreOmsLineImpLEntry 5 }

    tnGmreOmsLineImpLFiberType OBJECT-TYPE
        SYNTAX         INTEGER {
                         ssmf(1),         -- Standard Single-Mode Fiber (SSMF)
                         eleaf(2),        -- Enhanced Large Effective Area Fiber (ELEAF)
                         twrs(3),         -- True Wave Reduced Slope (TWRS)
                         twc(4),          -- True Wave Classic (TWC)
                         twp(5),          -- True Wave Plus (TW+)
                         mixed(6),        -- Mixed fiber type
                         ls(7),           -- Corning SMF-LS, LEAF Submarine
                         dsf(8),          -- Dispersion Shifted Fiber
                         g652smfull(9),   -- G652 Ultra Low Loss Fiber
                         g654e(10)        -- G654E Ultra Low Loss Fiber
                       }
        MAX-ACCESS     read-create
        STATUS         current
        DESCRIPTION    "GMRE OMS span fiber type for L Band."
        DEFVAL         { ssmf }
        ::= { tnGmreOmsLineImpLEntry 6 }

    tnGmreOmsLineImpLPDL OBJECT-TYPE
        SYNTAX         Unsigned32 (0..500000)
        UNITS          "1 dB"
        MAX-ACCESS     read-create
        STATUS         current
        DESCRIPTION    "GMRE OMS polarization dependent loss (PDL).  The
                        valid value is 0.00000 to 5.00000 dB  with
                        precision of five decimal digit for L Band.
                        Current configurable range: 0 to 500000."
        DEFVAL         { 0 }
        ::= { tnGmreOmsLineImpLEntry 7 }

--------------------------------------------------------------------------------
-- GMRE Optical Line Impairment Scalar
--------------------------------------------------------------------------------
    tnGmreOptLineImpAttributeTotal OBJECT-TYPE
        SYNTAX         Integer32
        MAX-ACCESS     read-only
        STATUS         current
        DESCRIPTION    "."
        ::= { tnAsonOptLineImp 1 }

--------------------------------------------------------------------------------
-- GMRE Optical Line Impairment parameters
--------------------------------------------------------------------------------
    tnGmreOptLineImpTable OBJECT-TYPE
        SYNTAX         SEQUENCE OF TnGmreOptLineImpEntry
        MAX-ACCESS     not-accessible
        STATUS         current
        DESCRIPTION    "."
        ::= { tnAsonOptLineImp 2 }

    tnGmreOptLineImpEntry OBJECT-TYPE
        SYNTAX         TnGmreOptLineImpEntry
        MAX-ACCESS     not-accessible
        STATUS         current
        DESCRIPTION    "On creation of TnGmreOptLineImpEntry, the user
                        must fully specify all members before entry will
                        be processed."
        INDEX { ifIndex,
                tnGmreOptLineImpIndex }
        ::= { tnGmreOptLineImpTable 1 }

    TnGmreOptLineImpEntry ::=
        SEQUENCE {
            tnGmreOptLineImpIndex        Unsigned32,
            tnGmreOptLineImpBitRate      INTEGER,
            tnGmreOptLineImpEncoding     TnGmreOptLineImpEncoding,
            tnGmreOptLineImpCompModule   TnGmreOptLineImpCompModule,
            tnGmreOptLineImpFecMode      AluWdmFecMode,
            tnGmreOptLineImpNLP          Unsigned32,
            tnGmreOptLineImpOSNR         Unsigned32,
            tnGmreOptLineImpNLPNP        Unsigned32,
            tnGmreOptLineImpOSNRNP       Unsigned32,
            tnGmreOptLineImpRowStatus    RowStatus,
            tnGmreOptLineImpPower        Unsigned32,
            tnGmreOptLineImpPhaseEncode  TnGmreOptLineImpPhaseEncode
        }

    tnGmreOptLineImpIndex OBJECT-TYPE
        SYNTAX         Unsigned32
        MAX-ACCESS     not-accessible
        STATUS         current
        DESCRIPTION    "GMRE Optical Line Impairment table entry index.
                        Each index must identify a unique combination
                        of BitRate, Encoding, CompModule, and FecMode and phase encode.

                        Current configurable range: 1 to 255."
        ::= { tnGmreOptLineImpEntry 1 }

    tnGmreOptLineImpBitRate OBJECT-TYPE
        SYNTAX         INTEGER {
                         rate2G5(1),
                         rate10G(2),
                         rate40G(3),
                         rate100G(4),
                         rate260G(5),
                         rate50G(6),
                         rate200G(7),
                         rate250G(8),
                         rate400G(9),
                         rate300G(10),
                         rate600G(11),
                         rate500G(12)
                       }
        MAX-ACCESS     read-create
        STATUS         current
        DESCRIPTION    "GMRE Optical Line transmitted signal bit rate."
        ::= { tnGmreOptLineImpEntry 2 }

    tnGmreOptLineImpEncoding OBJECT-TYPE
        SYNTAX         TnGmreOptLineImpEncoding
        MAX-ACCESS     read-create
        STATUS         current
        DESCRIPTION    "GMRE optical line encoding or modulation."
        ::= { tnGmreOptLineImpEntry 3 }

    tnGmreOptLineImpCompModule OBJECT-TYPE
        SYNTAX         TnGmreOptLineImpCompModule
        MAX-ACCESS     read-create
        STATUS         current
        DESCRIPTION    "GMRE Optical Line Compensation Module (on the OCH
                        transponder line side)."
        ::= { tnGmreOptLineImpEntry 4 }

    tnGmreOptLineImpFecMode OBJECT-TYPE
        SYNTAX         AluWdmFecMode
        MAX-ACCESS     read-create
        STATUS         current
        DESCRIPTION    "GMRE Optical Line Forward Error Correction (FEC)
                        mode."
        ::= { tnGmreOptLineImpEntry 5 }

    tnGmreOptLineImpNLP OBJECT-TYPE
        SYNTAX         Unsigned32 (0..99900000)
        UNITS          "percentage"
        MAX-ACCESS     read-create
        STATUS         current
        DESCRIPTION    "GMRE OPTLINE Non-Linear Phase (NLP).
                        The valid value
                        is 0.00000 to 999.00000 with precision of 5
                        decimal digits.

                        Current configurable range: 0 to 99900000."
        ::= { tnGmreOptLineImpEntry 6 }

    tnGmreOptLineImpOSNR OBJECT-TYPE
        SYNTAX         Unsigned32 (0..3162277660)
        MAX-ACCESS     read-create
        STATUS         current
        DESCRIPTION    "GMRE OPTLINE Optical Signal-To-Noise (OSNR)
                        Power Ratio.  The valid value is 0.00000 to
                        31622.77660 with precision of 5 decimal digits.

                        Current configurable range: 0 to 3162277660.

                        Note:  The OSNR value derived from the MIB value
                        (after dividing by 100000) is the linear inverse
                        of the real value in dB.  To convert the MIB value
                        to a value in dB, use 10 * log(MIBvalue/100000),
                        e.g., 10 * log(100000000/100000 ) = 30 dB."
        ::= { tnGmreOptLineImpEntry 7 }

    tnGmreOptLineImpNLPNP OBJECT-TYPE
        SYNTAX         Unsigned32 (0..99900000)
        UNITS          "percentage"
        MAX-ACCESS     read-create
        STATUS         current
        DESCRIPTION    "GMRE OPTLINE Non-Linear Phase Negative-Positive
                        (NLPNP).
                        The valid value
                        is 0.00000 to 999.00000 with precision of 5
                        decimal digits.

                        Current configurable range: 0 to 99900000."
        ::= { tnGmreOptLineImpEntry 8 }

    tnGmreOptLineImpOSNRNP OBJECT-TYPE
        SYNTAX         Unsigned32 (0..3162277660)
        MAX-ACCESS     read-create
        STATUS         current
        DESCRIPTION    "GMRE OPTLINE Optical Signal-To-Noise Negative-
                        Positive (OSNRNP) Power Ratio.  The valid value
                        is 0.00000 to 31622.77660 with precision of 5
                        decimal digits.

                        Current configurable range: 0 to 3162277660.

                        Note:  The OSNR value derived from the MIB value
                        (after dividing by 100000) is the linear inverse
                        of the real value in dB.  To convert the MIB value
                        to a value in dB, use 10 * log(MIBvalue/100000),
                        e.g., 10 * log(100000000/100000) = 30 dB."
        ::= { tnGmreOptLineImpEntry 9 }

    tnGmreOptLineImpRowStatus OBJECT-TYPE
        SYNTAX         RowStatus
        MAX-ACCESS     read-create
        STATUS         current
        DESCRIPTION    "Row Status of Optical Line Impairment entry.
                        Supported values are active, createAndGo, and
                        destroy."
        ::= { tnGmreOptLineImpEntry 10 }

    tnGmreOptLineImpPower OBJECT-TYPE
        SYNTAX         Unsigned32 (0..40500)
        UNITS          "micro-Watts"
        MAX-ACCESS     read-create
        STATUS         current
        DESCRIPTION    "GMRE OPTLINE Power.  The valid values are 0 to
                        40.50 milli-Watts and the default is 0.79
                        milli-Watt.

                        Current configurable range: 0 to 40500."
        DEFVAL         { 790 }
        ::= { tnGmreOptLineImpEntry 11 }

    tnGmreOptLineImpPhaseEncode OBJECT-TYPE
        SYNTAX         TnGmreOptLineImpPhaseEncode
        MAX-ACCESS     read-create
        STATUS         current
        DESCRIPTION    "GMRE Optical Line phase encoding mode."
        ::= { tnGmreOptLineImpEntry 12 }

--------------------------------------------------------------------------------
-- GMRE Optical Line Profile Impairment Scalar
--------------------------------------------------------------------------------
    tnGmreOptLineProfileImpAttributeTotal OBJECT-TYPE
        SYNTAX         Integer32
        MAX-ACCESS     read-only
        STATUS         current
        DESCRIPTION    "."
        ::= { tnAsonOptLineImp 3 }

--------------------------------------------------------------------------------
-- GMRE Optical Line Profile Impairment parameters
--------------------------------------------------------------------------------
    tnGmreOptLineProfileImpTable OBJECT-TYPE
        SYNTAX         SEQUENCE OF TnGmreOptLineProfileImpEntry
        MAX-ACCESS     not-accessible
        STATUS         current
        DESCRIPTION    "."
        ::= { tnAsonOptLineImp 4 }

    tnGmreOptLineProfileImpEntry OBJECT-TYPE
        SYNTAX         TnGmreOptLineProfileImpEntry
        MAX-ACCESS     not-accessible
        STATUS         current
        DESCRIPTION    "On creation of TnGmreOptLineProfileImpEntry, the user
                        must fully specify all members before entry will be
                        processed."
        INDEX { ifIndex,
                tnGmreOptLineProfileImpIndex }
        ::= { tnGmreOptLineProfileImpTable 1 }

    TnGmreOptLineProfileImpEntry ::=
        SEQUENCE {
            tnGmreOptLineProfileImpIndex        Unsigned32,
            tnGmreOptLineProfileImpCompModule   TnGmreOptLineImpCompModule,
            tnGmreOptLineProfileImpNLP          Unsigned32,
            tnGmreOptLineProfileImpOSNR         Unsigned32,
            tnGmreOptLineProfileImpNLPNP        Unsigned32,
            tnGmreOptLineProfileImpOSNRNP       Unsigned32,
            tnGmreOptLineProfileImpRowStatus    RowStatus,
            tnGmreOptLineProfileImpPower        Unsigned32,
            tnGmreOptLineProfileImpProfileID    Unsigned32,
            tnGmreOptLineProfileImpSlotWidth    TnGmreOptLineProfileImpSlotWidth
        }

    tnGmreOptLineProfileImpIndex OBJECT-TYPE
        SYNTAX         Unsigned32
        MAX-ACCESS     not-accessible
        STATUS         current
        DESCRIPTION    "GMRE Optical Line Impairment table entry index.  Each
                        index must identify a unique combination of BitRate,
                        Encoding, CompModule, and FecMode and phase encode.

                        Current configurable range: 1 to 255."
        ::= { tnGmreOptLineProfileImpEntry 1 }

    tnGmreOptLineProfileImpCompModule OBJECT-TYPE
        SYNTAX         TnGmreOptLineImpCompModule
        MAX-ACCESS     read-create
        STATUS         current
        DESCRIPTION    "GMRE Optical Line Compensation Module (on the OCH
                        transponder line side)."
        ::= { tnGmreOptLineProfileImpEntry 2 }

    tnGmreOptLineProfileImpNLP OBJECT-TYPE
        SYNTAX         Unsigned32 (0..99900000)
        UNITS          "percentage"
        MAX-ACCESS     read-create
        STATUS         current
        DESCRIPTION    "GMRE OPTLINE Non-Linear Phase (NLP).  The valid value
                        is 0.00000 to 999.00000 with precision of 5 decimal
                        digits.

                        Current configurable range: 0 to 99900000."
        ::= { tnGmreOptLineProfileImpEntry 3 }

    tnGmreOptLineProfileImpOSNR OBJECT-TYPE
        SYNTAX         Unsigned32 (0..3162277660)
        MAX-ACCESS     read-create
        STATUS         current
        DESCRIPTION    "GMRE OPTLINE Optical Signal-To-Noise (OSNR) Power Ratio.
                        The valid value is 0.00000 to 31622.77660 with precision
                        of 5 decimal digits.

                        Current configurable range: 0 to 3162277660.

                        Note:  The OSNR value derived from the MIB value (after
                        dividing by 100000) is the linear inverse of the real
                        value in dB.  To convert the MIB value to a value in dB,
                        use 10 * log(MIBvalue/100000), e.g.,
                        10 * log(100000000/100000 ) = 30 dB."
        ::= { tnGmreOptLineProfileImpEntry 4 }

    tnGmreOptLineProfileImpNLPNP OBJECT-TYPE
        SYNTAX         Unsigned32 (0..99900000)
        UNITS          "percentage"
        MAX-ACCESS     read-create
        STATUS         current
        DESCRIPTION    "GMRE OPTLINE Non-Linear Phase Negative-Positive (NLPNP).
                        The valid value is 0.00000 to 999.00000 with precision
                        of 5 decimal digits.

                        Current configurable range: 0 to 99900000."
        ::= { tnGmreOptLineProfileImpEntry 5 }

    tnGmreOptLineProfileImpOSNRNP OBJECT-TYPE
        SYNTAX         Unsigned32 (0..3162277660)
        MAX-ACCESS     read-create
        STATUS         current
        DESCRIPTION    "GMRE OPTLINE Optical Signal-To-Noise Negative-Positive
                        (OSNRNP) Power Ratio.  The valid value is 0.00000 to
                        31622.77660 with precision of 5 decimal digits.

                        Current configurable range: 0 to 3162277660.

                        Note:  The OSNR value derived from the MIB value (after
                        dividing by 100000) is the linear inverse of the real
                        value in dB.  To convert the MIB value to a value in dB,
                        use 10 * log(MIBvalue/100000), e.g.,
                        10 * log(100000000/100000) = 30 dB."
        ::= { tnGmreOptLineProfileImpEntry 6 }

    tnGmreOptLineProfileImpRowStatus OBJECT-TYPE
        SYNTAX         RowStatus
        MAX-ACCESS     read-create
        STATUS         current
        DESCRIPTION    "Row Status of Optical Line Impairment entry.  Supported
                        values are active, createAndGo, and destroy."
        ::= { tnGmreOptLineProfileImpEntry 7 }

    tnGmreOptLineProfileImpPower OBJECT-TYPE
        SYNTAX         Unsigned32 (0..40500)
        UNITS          "micro-Watts"
        MAX-ACCESS     read-create
        STATUS         current
        DESCRIPTION    "GMRE OPTLINE Power.  The valid values are 0 to 40.50
                        milli-Watts and the default is 0.79 milli-Watt.

                        Current configurable range: 0 to 40500."
        DEFVAL         { 790 }
        ::= { tnGmreOptLineProfileImpEntry 8 }

    tnGmreOptLineProfileImpProfileID OBJECT-TYPE
        SYNTAX         Unsigned32
        MAX-ACCESS     read-create
        STATUS         current
        DESCRIPTION    "."
        ::= { tnGmreOptLineProfileImpEntry 9 }

    tnGmreOptLineProfileImpSlotWidth OBJECT-TYPE
        SYNTAX         TnGmreOptLineProfileImpSlotWidth
        MAX-ACCESS     read-create
        STATUS         current
        DESCRIPTION    "The slot width granularity."
        ::= { tnGmreOptLineProfileImpEntry 10 }

--------------------------------------------------------------------------------
-- GMRE Optical Line Impairment Scalar for L Band
--------------------------------------------------------------------------------
    tnGmreOptLineImpLAttributeTotal OBJECT-TYPE
        SYNTAX         Integer32
        MAX-ACCESS     read-only
        STATUS         current
        DESCRIPTION    "."
        ::= { tnAsonOptLineImpL 1 }

--------------------------------------------------------------------------------
-- GMRE Optical Line Impairment parameters for L Band
--------------------------------------------------------------------------------
    tnGmreOptLineImpLTable OBJECT-TYPE
        SYNTAX         SEQUENCE OF TnGmreOptLineImpLEntry
        MAX-ACCESS     not-accessible
        STATUS         current
        DESCRIPTION    "."
        ::= { tnAsonOptLineImpL 2 }

    tnGmreOptLineImpLEntry OBJECT-TYPE
        SYNTAX         TnGmreOptLineImpLEntry
        MAX-ACCESS     not-accessible
        STATUS         current
        DESCRIPTION    "On creation of TnGmreOptLineImpLEntry, the user
                        must fully specify all members before entry will
                        be processed."
        INDEX { ifIndex,
                tnGmreOptLineImpLIndex }
        ::= { tnGmreOptLineImpLTable 1 }

    TnGmreOptLineImpLEntry ::=
        SEQUENCE {
            tnGmreOptLineImpLIndex        Unsigned32,
            tnGmreOptLineImpLBitRate      INTEGER,
            tnGmreOptLineImpLEncoding     TnGmreOptLineImpEncoding,
            tnGmreOptLineImpLCompModule   TnGmreOptLineImpCompModule,
            tnGmreOptLineImpLFecMode      AluWdmFecMode,
            tnGmreOptLineImpLNLP          Unsigned32,
            tnGmreOptLineImpLOSNR         Unsigned32,
            tnGmreOptLineImpLNLPNP        Unsigned32,
            tnGmreOptLineImpLOSNRNP       Unsigned32,
            tnGmreOptLineImpLRowStatus    RowStatus,
            tnGmreOptLineImpLPower        Unsigned32,
            tnGmreOptLineImpLPhaseEncode  TnGmreOptLineImpPhaseEncode
        }

    tnGmreOptLineImpLIndex OBJECT-TYPE
        SYNTAX         Unsigned32
        MAX-ACCESS     not-accessible
        STATUS         current
        DESCRIPTION    "GMRE Optical Line Impairment table entry index.
                        Each index must identify a unique combination
                        of BitRate, Encoding, CompModule, and FecMode
                        for L Band.

                        Current configurable range: 1 to 255."
        ::= { tnGmreOptLineImpLEntry 1 }

    tnGmreOptLineImpLBitRate OBJECT-TYPE
        SYNTAX         INTEGER {
                         rate2G5(1),
                         rate10G(2),
                         rate40G(3),
                         rate100G(4),
                         rate260G(5),
                         rate50G(6),
                         rate200G(7),
                         rate250G(8),
                         rate400G(9),
                         rate300G(10),
                         rate600G(11),
                         rate500G(12)
                       }
        MAX-ACCESS     read-create
        STATUS         current
        DESCRIPTION    "GMRE Optical Line transmitted signal bit rate for L Band."
        ::= { tnGmreOptLineImpLEntry 2 }

    tnGmreOptLineImpLEncoding OBJECT-TYPE
        SYNTAX         TnGmreOptLineImpEncoding
        MAX-ACCESS     read-create
        STATUS         current
        DESCRIPTION    "GMRE optical line encoding or modulation for L Band."
        ::= { tnGmreOptLineImpLEntry 3 }

    tnGmreOptLineImpLCompModule OBJECT-TYPE
        SYNTAX         TnGmreOptLineImpCompModule
        MAX-ACCESS     read-create
        STATUS         current
        DESCRIPTION    "GMRE Optical Line Compensation Module (on the OCH
                        transponder line side) for L Band."
        ::= { tnGmreOptLineImpLEntry 4 }

    tnGmreOptLineImpLFecMode OBJECT-TYPE
        SYNTAX         AluWdmFecMode
        MAX-ACCESS     read-create
        STATUS         current
        DESCRIPTION    "GMRE Optical Line Forward Error Correction (FEC)
                        mode for L Band."
        ::= { tnGmreOptLineImpLEntry 5 }

    tnGmreOptLineImpLNLP OBJECT-TYPE
        SYNTAX         Unsigned32 (0..99900000)
        UNITS          "percentage"
        MAX-ACCESS     read-create
        STATUS         current
        DESCRIPTION    "GMRE OPTLINE Non-Linear Phase (NLP).
                        The valid value
                        is 0.00000 to 999.00000 with precision of 5
                        decimal digits.

                        Current configurable range: 0 to 99900000 for L Band."
        ::= { tnGmreOptLineImpLEntry 6 }

    tnGmreOptLineImpLOSNR OBJECT-TYPE
        SYNTAX         Unsigned32 (0..3162277660)
        MAX-ACCESS     read-create
        STATUS         current
        DESCRIPTION    "GMRE OPTLINE Optical Signal-To-Noise (OSNR)
                        Power Ratio.  The valid value is 0.00000 to
                        31622.77660 with precision of 5 decimal digits
                        for L Band.

                        Current configurable range: 0 to 3162277660.

                        Note:  The OSNR value derived from the MIB value
                        (after dividing by 100000) is the linear inverse
                        of the real value in dB.  To convert the MIB value
                        to a value in dB, use 10 * log(MIBvalue/100000),
                        e.g., 10 * log(100000000/100000 ) = 30 dB."
        ::= { tnGmreOptLineImpLEntry 7 }

    tnGmreOptLineImpLNLPNP OBJECT-TYPE
        SYNTAX         Unsigned32 (0..99900000)
        UNITS          "percentage"
        MAX-ACCESS     read-create
        STATUS         current
        DESCRIPTION    "GMRE OPTLINE Non-Linear Phase Negative-Positive
                        (NLPNP).
                        The valid value
                        is 0.00000 to 999.00000 with precision of 5
                        decimal digits for L Band.

                        Current configurable range: 0 to 99900000."
        ::= { tnGmreOptLineImpLEntry 8 }

    tnGmreOptLineImpLOSNRNP OBJECT-TYPE
        SYNTAX         Unsigned32 (0..3162277660)
        MAX-ACCESS     read-create
        STATUS         current
        DESCRIPTION    "GMRE OPTLINE Optical Signal-To-Noise Negative-
                        Positive (OSNRNP) Power Ratio.  The valid value
                        is 0.00000 to 31622.77660 with precision of 5
                        decimal digits for L Band.

                        Current configurable range: 0 to 3162277660.

                        Note:  The OSNR value derived from the MIB value
                        (after dividing by 100000) is the linear inverse
                        of the real value in dB.  To convert the MIB value
                        to a value in dB, use 10 * log(MIBvalue/100000),
                        e.g., 10 * log(100000000/100000) = 30 dB."
        ::= { tnGmreOptLineImpLEntry 9 }

    tnGmreOptLineImpLRowStatus OBJECT-TYPE
        SYNTAX         RowStatus
        MAX-ACCESS     read-create
        STATUS         current
        DESCRIPTION    "Row Status of Optical Line Impairment entry.
                        Supported values are active, createAndGo, and
                        destroy for L Band ."
        ::= { tnGmreOptLineImpLEntry 10 }

    tnGmreOptLineImpLPower OBJECT-TYPE
        SYNTAX         Unsigned32 (0..40500)
        UNITS          "micro-Watts"
        MAX-ACCESS     read-create
        STATUS         current
        DESCRIPTION    "GMRE OPTLINE Power.  The valid values are 0 to
                        40.50 milli-Watts and the default is 0.79
                        milli-Watt for L Band.

                        Current configurable range: 0 to 40500."
        DEFVAL         { 790 }
        ::= { tnGmreOptLineImpLEntry 11 }

    tnGmreOptLineImpLPhaseEncode OBJECT-TYPE
        SYNTAX         TnGmreOptLineImpPhaseEncode
        MAX-ACCESS     read-create
        STATUS         current
        DESCRIPTION    "GMRE Optical Line phase encoding mode for L Band."
        ::= { tnGmreOptLineImpLEntry 12 }

--------------------------------------------------------------------------------
-- GMRE Optical Line Profile Impairment Scalar for L Band
--------------------------------------------------------------------------------
    tnGmreOptLineProfileImpLAttributeTotal OBJECT-TYPE
        SYNTAX         Integer32
        MAX-ACCESS     read-only
        STATUS         current
        DESCRIPTION    "."
        ::= { tnAsonOptLineImpL 3 }

--------------------------------------------------------------------------------
-- GMRE Optical Line Profile Impairment parameters for L Band
--------------------------------------------------------------------------------
    tnGmreOptLineProfileImpLTable OBJECT-TYPE
        SYNTAX         SEQUENCE OF TnGmreOptLineProfileImpLEntry
        MAX-ACCESS     not-accessible
        STATUS         current
        DESCRIPTION    "."
        ::= { tnAsonOptLineImpL 4 }

    tnGmreOptLineProfileImpLEntry OBJECT-TYPE
        SYNTAX         TnGmreOptLineProfileImpLEntry
        MAX-ACCESS     not-accessible
        STATUS         current
        DESCRIPTION    "On creation of TnGmreOptLineProfileImpLEntry, the user
                        must fully specify all members before entry will be
                        processed."
        INDEX { ifIndex,
                tnGmreOptLineProfileImpLIndex }
        ::= { tnGmreOptLineProfileImpLTable 1 }

    TnGmreOptLineProfileImpLEntry ::=
        SEQUENCE {
            tnGmreOptLineProfileImpLIndex        Unsigned32,
            tnGmreOptLineProfileImpLCompModule   TnGmreOptLineImpCompModule,
            tnGmreOptLineProfileImpLNLP          Unsigned32,
            tnGmreOptLineProfileImpLOSNR         Unsigned32,
            tnGmreOptLineProfileImpLNLPNP        Unsigned32,
            tnGmreOptLineProfileImpLOSNRNP       Unsigned32,
            tnGmreOptLineProfileImpLRowStatus    RowStatus,
            tnGmreOptLineProfileImpLPower        Unsigned32,
            tnGmreOptLineProfileImpLProfileID    Unsigned32,
            tnGmreOptLineProfileImpLSlotWidth    TnGmreOptLineProfileImpSlotWidth
        }

    tnGmreOptLineProfileImpLIndex OBJECT-TYPE
        SYNTAX         Unsigned32
        MAX-ACCESS     not-accessible
        STATUS         current
        DESCRIPTION    "GMRE Optical Line Impairment table entry index.  Each
                        index must identify a unique combination of BitRate,
                        Encoding, CompModule, and FecMode and phase encode for
                        L Band.

                        Current configurable range: 1 to 255."
        ::= { tnGmreOptLineProfileImpLEntry 1 }

    tnGmreOptLineProfileImpLCompModule OBJECT-TYPE
        SYNTAX         TnGmreOptLineImpCompModule
        MAX-ACCESS     read-create
        STATUS         current
        DESCRIPTION    "GMRE Optical Line Compensation Module (on the OCH
                        transponder line side) for L Band."
        ::= { tnGmreOptLineProfileImpLEntry 2 }

    tnGmreOptLineProfileImpLNLP OBJECT-TYPE
        SYNTAX         Unsigned32 (0..99900000)
        UNITS          "percentage"
        MAX-ACCESS     read-create
        STATUS         current
        DESCRIPTION    "GMRE OPTLINE Non-Linear Phase (NLP).  The valid value is
                        0.00000 to 999.00000 with precision of 5 decimal digits
                        for L Band.

                        Current configurable range: 0 to 99900000."
        ::= { tnGmreOptLineProfileImpLEntry 3 }

    tnGmreOptLineProfileImpLOSNR OBJECT-TYPE
        SYNTAX         Unsigned32 (0..3162277660)
        MAX-ACCESS     read-create
        STATUS         current
        DESCRIPTION    "GMRE OPTLINE Optical Signal-To-Noise (OSNR) Power Ratio.
                        The valid value is 0.00000 to 31622.77660 with precision
                        of 5 decimal digits for L Band.

                        Current configurable range: 0 to 3162277660.

                        Note:  The OSNR value derived from the MIB value (after
                        dividing by 100000) is the linear inverse of the real
                        value in dB.  To convert the MIB value to a value in dB,
                        use 10 * log(MIBvalue/100000), e.g.,
                        10 * log(100000000/100000 ) = 30 dB."
        ::= { tnGmreOptLineProfileImpLEntry 4 }

    tnGmreOptLineProfileImpLNLPNP OBJECT-TYPE
        SYNTAX         Unsigned32 (0..99900000)
        UNITS          "percentage"
        MAX-ACCESS     read-create
        STATUS         current
        DESCRIPTION    "GMRE OPTLINE Non-Linear Phase Negative-Positive (NLPNP).
                        The valid value is 0.00000 to 999.00000 with precision
                        of 5 decimal digits for L Band.

                        Current configurable range: 0 to 99900000."
        ::= { tnGmreOptLineProfileImpLEntry 5 }

    tnGmreOptLineProfileImpLOSNRNP OBJECT-TYPE
        SYNTAX         Unsigned32 (0..3162277660)
        MAX-ACCESS     read-create
        STATUS         current
        DESCRIPTION    "GMRE OPTLINE Optical Signal-To-Noise Negative-Positive
                        (OSNRNP) Power Ratio.  The valid value is 0.00000 to
                        31622.77660 with precision of 5 decimal digits for L
                        Band.

                        Current configurable range: 0 to 3162277660.

                        Note:  The OSNR value derived from the MIB value (after
                        dividing by 100000) is the linear inverse of the real
                        value in dB.  To convert the MIB value to a value in dB,
                        use 10 * log(MIBvalue/100000), e.g.,
                        10 * log(100000000/100000) = 30 dB."
        ::= { tnGmreOptLineProfileImpLEntry 6 }

    tnGmreOptLineProfileImpLRowStatus OBJECT-TYPE
        SYNTAX         RowStatus
        MAX-ACCESS     read-create
        STATUS         current
        DESCRIPTION    "Row Status of Optical Line Impairment entry.  Supported
                        values are active, createAndGo, and destroy for L Band."
        ::= { tnGmreOptLineProfileImpLEntry 7 }

    tnGmreOptLineProfileImpLPower OBJECT-TYPE
        SYNTAX         Unsigned32 (0..40500)
        UNITS          "micro-Watts"
        MAX-ACCESS     read-create
        STATUS         current
        DESCRIPTION    "GMRE OPTLINE Power.  The valid values are 0 to 40.50
                        milli-Watts and the default is 0.79 milli-Watt for L Band.

                        Current configurable range: 0 to 40500."
        DEFVAL         { 790 }
        ::= { tnGmreOptLineProfileImpLEntry 8 }

    tnGmreOptLineProfileImpLProfileID OBJECT-TYPE
        SYNTAX         Unsigned32
        MAX-ACCESS     read-create
        STATUS         current
        DESCRIPTION    "."
        ::= { tnGmreOptLineProfileImpLEntry 9 }

    tnGmreOptLineProfileImpLSlotWidth OBJECT-TYPE
        SYNTAX         TnGmreOptLineProfileImpSlotWidth
        MAX-ACCESS     read-create
        STATUS         current
        DESCRIPTION    "The slot width granularity for L Band."
        ::= { tnGmreOptLineProfileImpLEntry 10 }

--------------------------------------------------------------------------------
-- ASON Topology Connectivity Alarm Scalar
--------------------------------------------------------------------------------
    tnAsonTopoAlarmAttributeTotal OBJECT-TYPE
        SYNTAX         Integer32
        MAX-ACCESS     read-only
        STATUS         current
        DESCRIPTION    "."
        ::= { tnAsonTopoAlarm 1 }

--------------------------------------------------------------------------------
-- ASON Topology Connectivity Alarm Table
--------------------------------------------------------------------------------
    tnAsonTopoAlarmTable OBJECT-TYPE
        SYNTAX         SEQUENCE OF TnAsonTopoAlarmEntry
        MAX-ACCESS     not-accessible
        STATUS         current
        DESCRIPTION    "."
        ::= { tnAsonTopoAlarm 2 }

    tnAsonTopoAlarmEntry OBJECT-TYPE
        SYNTAX         TnAsonTopoAlarmEntry
        MAX-ACCESS     not-accessible
        STATUS         current
        DESCRIPTION    "."
        INDEX { ifIndex }
        ::= { tnAsonTopoAlarmTable 1 }

    TnAsonTopoAlarmEntry ::=
        SEQUENCE {
            tnAsonTopoClearAlarm    TnCommand
        }

    tnAsonTopoClearAlarm OBJECT-TYPE
        SYNTAX         TnCommand
        MAX-ACCESS     read-create
        STATUS         current
        DESCRIPTION    "Clears ASON topology connectivity alarm."
        DEFVAL         { noCmd }
        ::= { tnAsonTopoAlarmEntry 1 }

--------------------------------------------------------------------------------
--  ASON Feasibility File Transfer Parameters
--------------------------------------------------------------------------------
    tnAsonFeasibilityCommand OBJECT-TYPE
        SYNTAX         INTEGER {
                         noCmd(1),
                         transferFromRemote(2)
                       }
        MAX-ACCESS     read-write
        STATUS         current
        DESCRIPTION    "This attribute is used to start the feasibility
                        file transfer."
        DEFVAL         { noCmd }
        ::= { tnAsonFeasibility 1 }

    tnAsonFeasibilityRemoteHostIp OBJECT-TYPE
        SYNTAX         IpAddress
        MAX-ACCESS     read-write
        STATUS         current
        DESCRIPTION    "This attribute is used for the ip address of the
                        remote server where the feasibility file resides."

        DEFVAL         { '00000000'H }
        ::= { tnAsonFeasibility 2 }

    tnAsonFeasibilityRemotePath OBJECT-TYPE
        SYNTAX         SnmpAdminString (SIZE(0..255))
        MAX-ACCESS     read-write
        STATUS         current
        DESCRIPTION    "This attribute is used for the path and filename
                        on the remote server to indicate which feasibility
                        file to transfer."
        DEFVAL         { "" }
        ::= { tnAsonFeasibility 3 }

    tnAsonFeasibilityStatus OBJECT-TYPE
        SYNTAX         SnmpAdminString (SIZE(0..255))
        MAX-ACCESS     read-only
        STATUS         current
        DESCRIPTION    "This attribute indicates the status of the
                        previously executed tnAsonFeasibilityCommand
                        operation.  Here are the status strings:

                        * Success
                        * Remote transfer in progress
                        * Failed - Remote path exceeds the max length
                                   of 127 characters
                        * Failed - The remote path must specify a file
                        * Failed - Cannot transfer file while operation
                                   already in progress
                        * Failed - Invalid protocol (only tftp or sftp is
                                   allowed)
                        * Failed - Local error
                        * Failed - Network error
                        * Failed - Remote server error
                        * Failed - Invalid remote server IP address
                        * Failed - Unknown Error
                        * Failed - Authorization failed
                        * Failed - File permission(s) failed
                        * Failed - <Unknown error code>."
        DEFVAL         { "" }
        ::= { tnAsonFeasibility 4 }

    tnAsonFeasibilityLastTransferredVersion OBJECT-TYPE
        SYNTAX         SnmpAdminString (SIZE(0..255))
        MAX-ACCESS     read-only
        STATUS         current
        DESCRIPTION    "This attribute indicates the version of the
                        feasibility file that was last transferred
                        successfully."
        DEFVAL         { "" }
        ::= { tnAsonFeasibility 5 }

    tnAsonFeasibilityProtocol OBJECT-TYPE
        SYNTAX         AluWdmNewTransferProtocol
        MAX-ACCESS     read-write
        STATUS         current
        DESCRIPTION    "This attributes indicates the feasibility file
                        transfer protocol."
        DEFVAL         { ftp }
        ::= { tnAsonFeasibility 6 }

    tnAsonFeasibilityUserId OBJECT-TYPE
        SYNTAX         SnmpAdminString (SIZE(0..128))
        MAX-ACCESS     read-write
        STATUS         current
        DESCRIPTION    "The userId used to access the feasibility file
                        transfer server."
        DEFVAL         { "" }
        ::= { tnAsonFeasibility 7 }

    tnAsonFeasibilityPassword OBJECT-TYPE
        SYNTAX         SnmpAdminString (SIZE(0..128))
        MAX-ACCESS     read-write
        STATUS         current
        DESCRIPTION    "The password used to access the feasibility file
                        transfer server.

                        When read, this attribute will return an empty
                        string if the password has not been set and
                        '********' if it has been set."
        DEFVAL         { "" }
        ::= { tnAsonFeasibility 8 }

    tnAsonFeasibilityRemoteInetAddressType OBJECT-TYPE
        SYNTAX         InetAddressType
        MAX-ACCESS     read-write
        STATUS         current
        DESCRIPTION    "The value specifies the type of Internet address
                        stored tnAsonFeasibilityRemoteInetAddress"
        DEFVAL         { unknown }
        ::= { tnAsonFeasibility 9 }

    tnAsonFeasibilityRemoteInetAddress OBJECT-TYPE
        SYNTAX         InetAddress
        MAX-ACCESS     read-write
        STATUS         current
        DESCRIPTION    "Indicates the IPv6 address"
        DEFVAL         { ''H }
        ::= { tnAsonFeasibility 10 }

    tnAsonFeasibilityPort OBJECT-TYPE
        SYNTAX         Unsigned32 (1..65535)
        MAX-ACCESS     read-write
        STATUS         current
        DESCRIPTION    "This attributes indicates the ason port."
        DEFVAL         { 21 }
        ::= { tnAsonFeasibility 11 }

--------------------------------------------------------------------------------
-- ASON Manager Access Control Device Scalar
--------------------------------------------------------------------------------
    tnAsonMgracdAttributeTotal OBJECT-TYPE
        SYNTAX         Integer32
        MAX-ACCESS     read-only
        STATUS         current
        DESCRIPTION    "."
        ::= { tnAsonMgracdInfo 1 }

--------------------------------------------------------------------------------
-- ASON Manager Access Control Device
--------------------------------------------------------------------------------
    tnAsonMgracdTable OBJECT-TYPE
        SYNTAX         SEQUENCE OF TnAsonMgracdEntry
        MAX-ACCESS     not-accessible
        STATUS         current
        DESCRIPTION    "."
        ::= { tnAsonMgracdInfo 2 }

    tnAsonMgracdEntry OBJECT-TYPE
        SYNTAX         TnAsonMgracdEntry
        MAX-ACCESS     not-accessible
        STATUS         current
        DESCRIPTION    "."
        INDEX { ifIndex }
        ::= { tnAsonMgracdTable 1 }

    TnAsonMgracdEntry ::=
        SEQUENCE {
            tnAsonOchMgracd       AluWdmAccessControlDevice,
            tnAsonOmsochifMgracd  AluWdmAccessControlDevice,
            tnAsonOtsMgracd       AluWdmAccessControlDevice
        }

    tnAsonOchMgracd OBJECT-TYPE
        SYNTAX         AluWdmAccessControlDevice
        MAX-ACCESS     read-create
        STATUS         current
        DESCRIPTION    "This attribute indicates ownership of the OCH
                        entity."
        DEFVAL         { null }
        ::= { tnAsonMgracdEntry 1 }

    tnAsonOmsochifMgracd OBJECT-TYPE
        SYNTAX         AluWdmAccessControlDevice
        MAX-ACCESS     read-create
        STATUS         current
        DESCRIPTION    "This attribute indicates ownership of the
                        OMSOCHIF entity."
        DEFVAL         { null }
        ::= { tnAsonMgracdEntry 2 }

    tnAsonOtsMgracd OBJECT-TYPE
        SYNTAX         AluWdmAccessControlDevice
        MAX-ACCESS     read-create
        STATUS         current
        DESCRIPTION    "This attribute indicates ownership of the OTS
                        entity."
        DEFVAL         { null }
        ::= { tnAsonMgracdEntry 3 }

--------------------------------------------------------------------------------
-- GMRE OMS WavelengthSet Encoding Scalar
--------------------------------------------------------------------------------
    tnGmreOmsWavelengthSetAttributeTotal OBJECT-TYPE
        SYNTAX         Integer32
        MAX-ACCESS     read-only
        STATUS         current
        DESCRIPTION    "."
        ::= { tnAsonOmsWavelengthSet 1 }

--------------------------------------------------------------------------------
-- GMRE OMS WavelengthSet Encoding parameters
--------------------------------------------------------------------------------
    tnGmreOmsWavelengthSetTable OBJECT-TYPE
        SYNTAX         SEQUENCE OF TnGmreOmsWavelengthSetEntry
        MAX-ACCESS     not-accessible
        STATUS         current
        DESCRIPTION    "."
        ::= { tnAsonOmsWavelengthSet 2 }

    tnGmreOmsWavelengthSetEntry OBJECT-TYPE
        SYNTAX         TnGmreOmsWavelengthSetEntry
        MAX-ACCESS     not-accessible
        STATUS         current
        DESCRIPTION    "."
        INDEX { ifIndex,
                tnGmreOmsWavelengthEncodingType }
        ::= { tnGmreOmsWavelengthSetTable 1 }

    TnGmreOmsWavelengthSetEntry ::=
        SEQUENCE {
          tnGmreOmsWavelengthEncodingType    INTEGER,
          tnGmreOmsWavelengthEncodingBitMap  OCTET STRING
        }

    tnGmreOmsWavelengthEncodingType OBJECT-TYPE
        SYNTAX         INTEGER {
                         nrz(1),               -- Non-Return-to-Zero encoding
                         pdpsk(2),             -- Partial Differential Phase
                                               -- Shift Keying
                         coherent(3),          -- Coherent encoding
                         slotWidth50(4),       -- Slot Width 50Ghz
                         slotWidth62p5(5),     -- Slot Width 62 P 5Ghz
                         coherent16qam(6),     -- Coherent encoding 16qam
                         slotWidth75g(7),      -- Slot Width 75Ghz
                         slotWidth87p5g(8),    -- Slot Width 87 P 5Ghz
                         slotWidth100g(9),     -- Slot Width 100Ghz
                         slotWidth112p5g(10),  -- Slot Width 112.5Ghz
                         slotWidth125g(11)     -- Slot Width 125Ghz
                       }
        MAX-ACCESS     not-accessible
        STATUS         current
        DESCRIPTION    "GMRE OMS line encoding type for Wavelengths/channels."
        ::= { tnGmreOmsWavelengthSetEntry 1 }

    tnGmreOmsWavelengthEncodingBitMap OBJECT-TYPE
        SYNTAX         OCTET STRING (SIZE(12))
        MAX-ACCESS     read-create
        STATUS         current
        DESCRIPTION    "This attribute provides the wavelengths/channels
                        for encoding types on an OMS line.  It is a fixed
                        size octet string.  Each bit represents an ITU
                        channel.  The ITU channel numbers decrement from
                        the MSB of the first octet, 60.5, 60, 59.5, ...,
                        18, 17.5, 17.  Currently we support 96 channels,
                        requiring 96 bits, or 12 characters, to represent
                        the ITU channels.

                        0 = ITU channel is not part of specified encoding type
                        1 = ITU channel is part of the specified encoding type."
        ::= { tnGmreOmsWavelengthSetEntry 2 }

--------------------------------------------------------------------------------
-- GMRE OMS WavelengthSet Encoding Scalar for L Band
--------------------------------------------------------------------------------
    tnGmreOmsWavelengthSetLAttributeTotal OBJECT-TYPE
        SYNTAX         Integer32
        MAX-ACCESS     read-only
        STATUS         current
        DESCRIPTION    "."
        ::= { tnAsonOmsWavelengthSetL 1 }

--------------------------------------------------------------------------------
-- GMRE OMS WavelengthSet Encoding parameters for L Band
--------------------------------------------------------------------------------
    tnGmreOmsWavelengthSetLTable OBJECT-TYPE
        SYNTAX         SEQUENCE OF TnGmreOmsWavelengthSetLEntry
        MAX-ACCESS     not-accessible
        STATUS         current
        DESCRIPTION    "."
        ::= { tnAsonOmsWavelengthSetL 2 }

    tnGmreOmsWavelengthSetLEntry OBJECT-TYPE
        SYNTAX         TnGmreOmsWavelengthSetLEntry
        MAX-ACCESS     not-accessible
        STATUS         current
        DESCRIPTION    "."
        INDEX { ifIndex,
                tnGmreOmsWavelengthLEncodingType }
        ::= { tnGmreOmsWavelengthSetLTable 1 }

    TnGmreOmsWavelengthSetLEntry ::=
        SEQUENCE {
          tnGmreOmsWavelengthLEncodingType    INTEGER,
          tnGmreOmsWavelengthLEncodingBitMap  OCTET STRING
        }

    tnGmreOmsWavelengthLEncodingType OBJECT-TYPE
        SYNTAX         INTEGER {
                         nrz(1),           -- Non-Return-to-Zero encoding
                         pdpsk(2),         -- Partial Differential Phase Shift Keying
                         coherent(3),      -- Coherent encoding
                         slotWidth50(4),   -- Slot Width 50Ghz
                         slotWidth62p5(5), -- Slot Width 62 P 5Ghz
                         coherent16qam(6)  -- Coherent encoding 16qam
                       }
        MAX-ACCESS     not-accessible
        STATUS         current
        DESCRIPTION    "GMRE OMS line encoding type for Wavelengths/channels
                        for L Band."
        ::= { tnGmreOmsWavelengthSetLEntry 1 }

    tnGmreOmsWavelengthLEncodingBitMap OBJECT-TYPE
        SYNTAX         OCTET STRING (SIZE(12))
        MAX-ACCESS     read-create
        STATUS         current
        DESCRIPTION    "This attribute provides the wavelengths/channels
                        for encoding types on an OMS line.  It is a fixed
                        size octet string.  Each bit represents an ITU
                        channel.  The ITU channel numbers decrement from
                        the MSB of the first octet, 60.5, 60, 59.5, ...,
                        18, 17.5, 17.  Currently we support 96 channels,
                        requiring 96 bits, or 12 characters, to represent
                        the ITU channels for L Band.

                        0 = ITU channel is not part of specified encoding type
                        1 = ITU channel is part of the specified encoding type."
        ::= { tnGmreOmsWavelengthSetLEntry 2 }

--------------------------------------------------------------------------------
-- GMRE Cluster Scalar
--------------------------------------------------------------------------------
    tnGmreClusterAttributeTotal OBJECT-TYPE
        SYNTAX         Integer32
        MAX-ACCESS     read-only
        STATUS         current
        DESCRIPTION    "."
        ::= { tnAsonClusterObjs 1 }

--------------------------------------------------------------------------------
-- GMRE Cluster Table
--------------------------------------------------------------------------------
    tnGmreClusterTable OBJECT-TYPE
        SYNTAX         SEQUENCE OF TnGmreClusterEntry
        MAX-ACCESS     not-accessible
        STATUS         current
        DESCRIPTION    "."
        ::= { tnAsonClusterObjs 2 }

    tnGmreClusterEntry OBJECT-TYPE
        SYNTAX         TnGmreClusterEntry
        MAX-ACCESS     not-accessible
        STATUS         current
        DESCRIPTION    "."
        INDEX { tnGmreClusterFarEndNode }
        ::= { tnGmreClusterTable 1 }

    TnGmreClusterEntry ::= SEQUENCE {
        tnGmreClusterFarEndNode             OCTET STRING,
        tnGmreClusterRowStatus              RowStatus,
        tnGmreClusterIpAddress              IpAddress,
        tnGmreClusterlinkStatus             INTEGER,
        tnGmreClusterInetAddressType        InetAddressType,
        tnGmreClusterInetAddress            InetAddress
    }

    tnGmreClusterFarEndNode OBJECT-TYPE
        SYNTAX         OCTET STRING
        MAX-ACCESS     not-accessible
        STATUS         current
        DESCRIPTION    "."
        ::= { tnGmreClusterEntry 1 }

    tnGmreClusterRowStatus OBJECT-TYPE
        SYNTAX         RowStatus
        MAX-ACCESS     read-create
        STATUS         current
        DESCRIPTION    "."
        ::= { tnGmreClusterEntry 2 }

    tnGmreClusterIpAddress OBJECT-TYPE
        SYNTAX         IpAddress
        MAX-ACCESS     read-create
        STATUS         current
        DESCRIPTION    "."
        DEFVAL         { '00000000'H }
        ::= { tnGmreClusterEntry 3 }

    tnGmreClusterlinkStatus OBJECT-TYPE
        SYNTAX         INTEGER {
                         up(1),
                         down(2),
                         unknown(3)
                       }
        MAX-ACCESS     read-create
        STATUS         current
        DESCRIPTION    "GMRE Cluster link status"
        DEFVAL         { unknown }
        ::= { tnGmreClusterEntry 4 }

    tnGmreClusterInetAddressType OBJECT-TYPE
        SYNTAX         InetAddressType
        MAX-ACCESS     read-create
        STATUS         current
        DESCRIPTION    "The value specifies the type of Internet address
                        stored in GMRE Cluster"
        DEFVAL         { unknown }
        ::= { tnGmreClusterEntry 5 }

    tnGmreClusterInetAddress OBJECT-TYPE
        SYNTAX         InetAddress
        MAX-ACCESS     read-create
        STATUS         current
        DESCRIPTION    "Indicates the IPv6 address of the GMRE Cluster"
        DEFVAL         { ''H }
        ::= { tnGmreClusterEntry 6 }

--------------------------------------------------------------------------------
-- Snapshot of Generic Part for Server Access
--------------------------------------------------------------------------------
    tnAsonSnapshotRemoteHostIp OBJECT-TYPE
        SYNTAX         IpAddress
        MAX-ACCESS     read-write
        STATUS         current
        DESCRIPTION    "."
        DEFVAL         { '00000000'H }
        ::= { tnAsonSnapshot 1 }

    tnAsonSnapshotProtocol OBJECT-TYPE
        SYNTAX         AluWdmTransferProtocol
        MAX-ACCESS     read-write
        STATUS         current
        DESCRIPTION    "This attributes indicates the snapshot protocol."
        ::= { tnAsonSnapshot 2 }

    tnAsonSnapshotUserId OBJECT-TYPE
        SYNTAX         SnmpAdminString
        MAX-ACCESS     read-write
        STATUS         current
        DESCRIPTION    "The userId used to access the snapshot server."
        ::= { tnAsonSnapshot 3 }

    tnAsonSnapshotPassword OBJECT-TYPE
        SYNTAX         SnmpAdminString
        MAX-ACCESS     read-write
        STATUS         current
        DESCRIPTION    "The password used to access the snapshot server.
                        When read, this attribute will return an empty
                        string if the password has not been set and
                        '********' if it has been set."
        ::= { tnAsonSnapshot 4 }

    tnAsonSnapshotRootRemotePath OBJECT-TYPE
        SYNTAX         SnmpAdminString (SIZE(0..255))
        MAX-ACCESS     read-write
        STATUS         current
        DESCRIPTION    "Defines the root directory on the server the
                        snapshot shall be stored.  Must be present when
                        row status of snapshot entries is created.
                        Default is empty string."
        DEFVAL         { "" }
        ::= { tnAsonSnapshot 5 }

    tnAsonSnapshotRemoteInetAddressType OBJECT-TYPE
        SYNTAX         InetAddressType
        MAX-ACCESS     read-write
        STATUS         current
        DESCRIPTION    "The value specifies the type of Internet address
                        stored tnAsonSnapshotRemoteInetAddress."
        DEFVAL         { unknown }
        ::= { tnAsonSnapshot 8 }

    tnAsonSnapshotRemoteInetAddress OBJECT-TYPE
        SYNTAX         InetAddress
        MAX-ACCESS     read-write
        STATUS         current
        DESCRIPTION    "Indicates the IPv6 address."
        DEFVAL         { ''H }
        ::= { tnAsonSnapshot 9 }

--------------------------------------------------------------------------------
-- GMPLS Snapshot Requests Scalars
--------------------------------------------------------------------------------
    tnAsonSnapshotAttributeTotal OBJECT-TYPE
        SYNTAX         Integer32
        MAX-ACCESS     read-only
        STATUS         current
        DESCRIPTION    "."
        ::= { tnAsonSnapshot 6 }

--------------------------------------------------------------------------------
-- GMPLS Snapshot Requests Table
--------------------------------------------------------------------------------
    tnAsonSnapshotTable OBJECT-TYPE
        SYNTAX         SEQUENCE OF TnAsonSnapshotEntry
        MAX-ACCESS     not-accessible
        STATUS         current
        DESCRIPTION    "."
        ::= { tnAsonSnapshot 7 }

    tnAsonSnapshotEntry OBJECT-TYPE
        SYNTAX         TnAsonSnapshotEntry
        MAX-ACCESS     not-accessible
        STATUS         current
        DESCRIPTION    "."
        INDEX { tnAsonSnapshotTime }
        ::= { tnAsonSnapshotTable 1 }

    TnAsonSnapshotEntry ::=
        SEQUENCE {
            tnAsonSnapshotTime           Unsigned32,
            tnAsonSnapshotStatus         SnmpAdminString,
            tnAsonSnapshotRemotePath     SnmpAdminString,
            tnAsonSnapshotRowStatus      RowStatus,
            tnAsonSnapshotFilename       SnmpAdminString
        }

    tnAsonSnapshotTime OBJECT-TYPE
        SYNTAX         Unsigned32
        MAX-ACCESS     not-accessible
        STATUS         current
        DESCRIPTION    "The date and time when the snapshot is scheduled."
        ::= { tnAsonSnapshotEntry 1 }

    tnAsonSnapshotStatus OBJECT-TYPE
        SYNTAX         SnmpAdminString (SIZE(0..255))
        MAX-ACCESS     read-only
        STATUS         current
        DESCRIPTION    "This attribute indicates the status of the
                        schedule snapshot operation. Here are the status
                        strings:

                        * Success
                        * Pending - waiting for scheduled time
                        * Snapshot in progress
                        * failed - timed out - e.g. due to node reset at scheduled time.
                        * failed - remote path exceeds the max length of 127 characters
                        * Failed - local error
                        * Failed - network error
                        * Failed - Remote server error.

                        default at creation time is pending."
        ::= { tnAsonSnapshotEntry 2 }

    tnAsonSnapshotRemotePath OBJECT-TYPE
        SYNTAX         SnmpAdminString (SIZE(0..255))
        MAX-ACCESS     read-create
        STATUS         current
        DESCRIPTION    "Defines the directory on the server the snapshot
                        shall be stored.  Must be present when row status
                        is active. Default is empty string."
        DEFVAL         { "" }
        ::= { tnAsonSnapshotEntry 3 }

    tnAsonSnapshotRowStatus OBJECT-TYPE
        SYNTAX         RowStatus
        MAX-ACCESS     read-create
        STATUS         current
        DESCRIPTION    "The following two values are states, which may be
                        may be read or written:
                        - active(1),        - set only used in combination
                                            - with createAndWait.
                        - notInService(2),  - set should not be used, use a destroy.

                        The following value is a state, which may be read only:
                        - notReady(3),      - never used as cannot be incomplete.

                        The following three values are actions, which may
                        be written but are never read:
                        - createAndGo(4),   - recommended way to use.
                        - createAndWait(5), - not recommended way to use.
                        - destroy(6)        - used to delete the row entry
                                            - after completion."
        ::= { tnAsonSnapshotEntry 4 }

    tnAsonSnapshotFilename OBJECT-TYPE
        SYNTAX         SnmpAdminString (SIZE(0..255))
        MAX-ACCESS     read-only
        STATUS         current
        DESCRIPTION    "This attribute indicates the filename for the
                        snapshot performed on the node.  If none exists,
                        this attribute will return an empty string.  If
                        a snapshot is in progress, this attribute will
                        return an empty string."
        ::= { tnAsonSnapshotEntry 5 }

--------------------------------------------------------------------------------
-- GMRE Submarine Grid Mode Scalar
--------------------------------------------------------------------------------
    tnGmreSubmarineGridModeTotal OBJECT-TYPE
        SYNTAX         Integer32
        MAX-ACCESS     read-only
        STATUS         current
        DESCRIPTION    "."
        ::= { tnAsonSubmarineGridMode 1 }

--------------------------------------------------------------------------------
-- GMRE Submarine Grid Mode Table
--------------------------------------------------------------------------------
    tnGmreSubmarineGridModeTable OBJECT-TYPE
        SYNTAX         SEQUENCE OF TnGmreSubmarineGridModeEntry
        MAX-ACCESS     not-accessible
        STATUS         current
        DESCRIPTION    "."
        ::= { tnAsonSubmarineGridMode 2 }

    tnGmreSubmarineGridModeEntry OBJECT-TYPE
        SYNTAX         TnGmreSubmarineGridModeEntry
        MAX-ACCESS     not-accessible
        STATUS         current
        DESCRIPTION    "On creation of tnGmreSubmarineGridModeEntry, the user
                        must fully specify center frequency channel spacing
                        before entry will be processed."

        INDEX { ifIndex }
        ::= { tnGmreSubmarineGridModeTable 1 }

    TnGmreSubmarineGridModeEntry ::= SEQUENCE {
        tnGmreSubmarineGridModeType         INTEGER
    }

    tnGmreSubmarineGridModeType OBJECT-TYPE
        SYNTAX         INTEGER {
                         chSpacingNC(1),   -- channel spacing not configured
                         chSpacing6p25(2), -- channel spacing 6.25 GHz
                         chSpacing50(3),   -- channel spacing 50.0 GHz
                         chSpacing100(4),  -- channel spacing 100.0 GHz
                         chSpacing150(5),  -- channel spacing 150.0 GHz
                         chSpacing200(6)   -- channel spacing 200.0 GHz
                       }
        MAX-ACCESS     read-create
        STATUS         current
        DESCRIPTION    "GMRE allowed center frequency channel spacing."
        ::= { tnGmreSubmarineGridModeEntry 1 }

--------------------------------------------------------------------------------
-- GMRE Uplink Scalar
--------------------------------------------------------------------------------
    tnGmreUplinkAttributeTotal OBJECT-TYPE
        SYNTAX         Integer32
        MAX-ACCESS     read-only
        STATUS         current
        DESCRIPTION    "."
        ::= { tnAsonUpLink 1 }

--------------------------------------------------------------------------------
-- GMRE Uplink parameters
--------------------------------------------------------------------------------
    tnGmreUplinkTable OBJECT-TYPE
        SYNTAX         SEQUENCE OF TnGmreUplinkEntry
        MAX-ACCESS     not-accessible
        STATUS         current
        DESCRIPTION    "."
        ::= { tnAsonUpLink 2 }

    tnGmreUplinkEntry OBJECT-TYPE
        SYNTAX         TnGmreUplinkEntry
        MAX-ACCESS     not-accessible
        STATUS         current
        DESCRIPTION    "On creation of TnGmreUplinkEntry, the user must fully
                        specify all members before entry will be processed."
        INDEX { tnGmreUplinkIndex }
        ::= { tnGmreUplinkTable 1 }

    TnGmreUplinkEntry ::=
        SEQUENCE {
        tnGmreUplinkIndex         Unsigned32,
        tnGmreUplink1             InterfaceIndexOrZero,
        tnGmreUplink2             InterfaceIndexOrZero,
        tnGmreUplinkRowStatus     RowStatus,
        tnGmreUplinkMode          INTEGER
    }

    tnGmreUplinkIndex OBJECT-TYPE
        SYNTAX         Unsigned32
        MAX-ACCESS     not-accessible
        STATUS         current
        DESCRIPTION    "GMRE UpLink group index."
        ::= { tnGmreUplinkEntry 1 }

    tnGmreUplink1 OBJECT-TYPE
        SYNTAX         InterfaceIndexOrZero
        MAX-ACCESS     read-create
        STATUS         current
        DESCRIPTION    "GMRE UpLink interface 1."
        ::= { tnGmreUplinkEntry 2 }

    tnGmreUplink2 OBJECT-TYPE
        SYNTAX         InterfaceIndexOrZero
        MAX-ACCESS     read-create
        STATUS         current
        DESCRIPTION    "GMRE UpLink interface 2."
        ::= { tnGmreUplinkEntry 3 }

    tnGmreUplinkRowStatus OBJECT-TYPE
        SYNTAX         RowStatus
        MAX-ACCESS     read-create
        STATUS         current
        DESCRIPTION    "GMRE UpLink Row Status."
        ::= { tnGmreUplinkEntry 4 }

    tnGmreUplinkMode OBJECT-TYPE
        SYNTAX         INTEGER {
                         protected(1),
                         unprotected(2)
                       }
        MAX-ACCESS     read-only
        STATUS         current
        DESCRIPTION    "GMRE UpLink Mode."
        ::= { tnGmreUplinkEntry 5 }

--------------------------------------------------------------------------------
-- Alien OT Entity Scalar
--------------------------------------------------------------------------------
    tnAlienOtEntityAttributeTotal OBJECT-TYPE
        SYNTAX         Integer32
        MAX-ACCESS     read-only
        STATUS         current
        DESCRIPTION    "."
        ::= { tnAlienOtEntity 1 }

--------------------------------------------------------------------------------
-- Alien OT Entity parameters
--------------------------------------------------------------------------------
    tnAlienOtEntityTable OBJECT-TYPE
        SYNTAX         SEQUENCE OF TnAlienOtEntityEntry
        MAX-ACCESS     not-accessible
        STATUS         current
        DESCRIPTION    "."
        ::= { tnAlienOtEntity 2 }

    tnAlienOtEntityEntry OBJECT-TYPE
        SYNTAX         TnAlienOtEntityEntry
        MAX-ACCESS     not-accessible
        STATUS         current
        DESCRIPTION    "On creation of TnAlienOtEntityEntry, the user must fully
                        specify mandatory members before entry will be processed."
        INDEX { ifIndex,
                tnAlienOtEntityIndex }
        ::= { tnAlienOtEntityTable 1 }

    TnAlienOtEntityEntry ::=
        SEQUENCE {
            tnAlienOtEntityIndex            Unsigned32,
            tnAlienOtEntityRowStatus        RowStatus,
            tnAlienOtEntityDescription      DisplayString,
            tnAlienOtEntityFrequencyMHz     Unsigned32,
            tnAlienOtEntitySlotWidthMHz     Unsigned32,
            tnAlienOtEntityCompModule       TnGmreOptLineImpCompModule,
            tnAlienOtEntityProfileId        Unsigned32,
            tnAlienOtEntityXcId             Unsigned32,
            tnAlienOtEntityXcIdAdd          Unsigned32,
            tnAlienOtEntityXcIdDrop         Unsigned32
        }

    tnAlienOtEntityIndex OBJECT-TYPE
        SYNTAX         Unsigned32
        MAX-ACCESS     not-accessible
        STATUS         current
        DESCRIPTION    "Alien OT Entity table entry index.  Each index must
                        identify a unique combination of Frequency (in MHz)
                        and SlotWidth (center frequency channel spacing).

                        Current configurable range: 1 to 255."
        ::= { tnAlienOtEntityEntry 1 }

    tnAlienOtEntityRowStatus OBJECT-TYPE
        SYNTAX         RowStatus
        MAX-ACCESS     read-create
        STATUS         current
        DESCRIPTION    "Row Status of Alien OT Entity Supported values are
                        active, createAndGo, and destroy."
        ::= { tnAlienOtEntityEntry 2 }

    tnAlienOtEntityDescription OBJECT-TYPE
        SYNTAX         DisplayString (SIZE (0..255))
        MAX-ACCESS     read-create
        STATUS         current
        DESCRIPTION    "A description for Alien OT Entity."
        ::= { tnAlienOtEntityEntry 3 }

    tnAlienOtEntityFrequencyMHz OBJECT-TYPE
        SYNTAX         Unsigned32 (0 | 8610000..9085000 | 9130000..9605000)
        UNITS          "MHz"
        MAX-ACCESS     read-create
        STATUS         current
        DESCRIPTION    "Frequency."
        DEFVAL         { 0 }
        ::= { tnAlienOtEntityEntry 4 }

    tnAlienOtEntitySlotWidthMHz OBJECT-TYPE
        SYNTAX         Unsigned32 (37500..125000)
        UNITS          "MHz"
        MAX-ACCESS     read-create
        STATUS         current
        DESCRIPTION    "Slot-Width (center frequency channel spacing).

                        Current configurable in multiple of 12500 MHz"
        DEFVAL         { 50000 }
        ::= { tnAlienOtEntityEntry 5 }

    tnAlienOtEntityCompModule OBJECT-TYPE
        SYNTAX         TnGmreOptLineImpCompModule
        MAX-ACCESS     read-create
        STATUS         current
        DESCRIPTION    "Compensation Module of Alien OT Entity."
        DEFVAL         { alien }
        ::= { tnAlienOtEntityEntry 6 }

    tnAlienOtEntityProfileId OBJECT-TYPE
        SYNTAX         Unsigned32
        MAX-ACCESS     read-create
        STATUS         current
        DESCRIPTION    "Profile identifier for Alien OT Entity."
        DEFVAL         { 99999 }
        ::= { tnAlienOtEntityEntry 7 }

    tnAlienOtEntityXcId OBJECT-TYPE
        SYNTAX         Unsigned32
        MAX-ACCESS     read-only
        STATUS         current
        DESCRIPTION    "XC identifier for Alien OT Entity; value 0 if no XC
                        is present."
        DEFVAL         { 0 }
        ::= { tnAlienOtEntityEntry 8 }

    tnAlienOtEntityXcIdAdd OBJECT-TYPE
        SYNTAX         Unsigned32
        MAX-ACCESS     read-only
        STATUS         current
        DESCRIPTION    "XC identifier for Alien OT Entity in Add direction;
                        value 0 if no XC is present."
        DEFVAL         { 0 }
        ::= { tnAlienOtEntityEntry 9 }

    tnAlienOtEntityXcIdDrop OBJECT-TYPE
        SYNTAX         Unsigned32
        MAX-ACCESS     read-only
        STATUS         current
        DESCRIPTION    "XC identifier for Alien OT Entity in Drop direction;
                        value 0 if no XC is present."
        DEFVAL         { 0 }
        ::= { tnAlienOtEntityEntry 10 }

--------------------------------------------------------------------------------
-- Conformance Group Definitions
--------------------------------------------------------------------------------
    tnAsonGlobalGroup OBJECT-GROUP
        OBJECTS {
            tnGmreNodeIpAddr,
            tnGmreNodeSubMask,
            tnGmreNotifyIpAddr,
            tnGmreNotifySubMask,
            tnGmreDiscoveryMode,
            tnGmreAsonItuBandMode,
            tnGmreClusterMode,
            tnGmreCommissioningStatus
        }
        STATUS         current
        DESCRIPTION    "."
        ::= { tnAsonGroups 1 }

--    obsolete
--    tnAsonIorGlobalGroup OBJECT-GROUP ::= { tnAsonGroups 2 }

    tnAsonOmsLineImpScalarsGroup OBJECT-GROUP
        OBJECTS {
            tnGmreOmsLineImpAttributeTotal
        }
        STATUS         current
        DESCRIPTION    "."
        ::= { tnAsonGroups 3 }

    tnAsonOmsLineImpGroup OBJECT-GROUP
        OBJECTS {
            tnGmreOmsLineImpMaxAlwCh,
            tnGmreOmsLineImpPMD,
            tnGmreOmsLineImpAlcMode,
            tnGmreOmsLineImpDcuFree,
            tnGmreOmsLineImpCD,
            tnGmreOmsLineImpFiberType,
            tnGmreOmsLineImpPDL,
            tnGmreOmsLineImpCD1546,
            tnGmreOmsLineImp1830lxdcm,
            tnGmreOmsLineImpLatency
        }
        STATUS         current
        DESCRIPTION    "."
        ::= { tnAsonGroups 4 }

    tnAsonOptLineImpScalarsGroup OBJECT-GROUP
        OBJECTS {
            tnGmreOptLineImpAttributeTotal
        }
        STATUS         current
        DESCRIPTION    "."
        ::= { tnAsonGroups 5 }

    tnAsonOptLineImpGroup OBJECT-GROUP
        OBJECTS {
            tnGmreOptLineImpBitRate,
            tnGmreOptLineImpEncoding,
            tnGmreOptLineImpCompModule,
            tnGmreOptLineImpFecMode,
            tnGmreOptLineImpNLP,
            tnGmreOptLineImpOSNR,
            tnGmreOptLineImpNLPNP,
            tnGmreOptLineImpOSNRNP,
            tnGmreOptLineImpRowStatus,
            tnGmreOptLineImpPower,
            tnGmreOptLineImpPhaseEncode
        }
        STATUS         current
        DESCRIPTION    "."
        ::= { tnAsonGroups 6 }

    tnAsonTopoAlarmScalarsGroup OBJECT-GROUP
        OBJECTS {
            tnAsonTopoAlarmAttributeTotal
        }
        STATUS         current
        DESCRIPTION    "."
        ::= { tnAsonGroups 7 }

    tnAsonTopoAlarmGroup OBJECT-GROUP
        OBJECTS {
            tnAsonTopoClearAlarm
        }
        STATUS         current
        DESCRIPTION    "."
        ::= { tnAsonGroups 8 }

    tnAsonFeasibilityGroup OBJECT-GROUP
        OBJECTS {
            tnAsonFeasibilityCommand,
            tnAsonFeasibilityRemoteHostIp,
            tnAsonFeasibilityRemotePath,
            tnAsonFeasibilityStatus,
            tnAsonFeasibilityLastTransferredVersion,
            tnAsonFeasibilityProtocol,
            tnAsonFeasibilityUserId,
            tnAsonFeasibilityPassword,
            tnAsonFeasibilityRemoteInetAddressType,
            tnAsonFeasibilityRemoteInetAddress,
            tnAsonFeasibilityPort
        }
        STATUS         current
        DESCRIPTION    "."
        ::= { tnAsonGroups 9 }

    tnAsonMgracdScalarsGroup OBJECT-GROUP
        OBJECTS {
            tnAsonMgracdAttributeTotal
        }
        STATUS         current
        DESCRIPTION    "."
        ::= { tnAsonGroups 10 }

    tnAsonMgracdGroup OBJECT-GROUP
        OBJECTS {
            tnAsonOchMgracd,
            tnAsonOmsochifMgracd,
            tnAsonOtsMgracd
        }
        STATUS         current
        DESCRIPTION    "."
        ::= { tnAsonGroups 11 }

    tnAsonOmsWavelengthSetScalarsGroup OBJECT-GROUP
        OBJECTS {
            tnGmreOmsWavelengthSetAttributeTotal
        }
        STATUS         current
        DESCRIPTION    "."
        ::= { tnAsonGroups 12 }

    tnAsonOmsWavelengthSetGroup OBJECT-GROUP
        OBJECTS {
            tnGmreOmsWavelengthEncodingBitMap
        }
        STATUS         current
        DESCRIPTION    "."
        ::= { tnAsonGroups 13 }

    tnAsonSnapshotScalarsGroup OBJECT-GROUP
        OBJECTS {
            tnAsonSnapshotRemoteHostIp,
            tnAsonSnapshotProtocol,
            tnAsonSnapshotUserId,
            tnAsonSnapshotPassword,
            tnAsonSnapshotRootRemotePath,
            tnAsonSnapshotAttributeTotal,
            tnAsonSnapshotRemoteInetAddressType,
            tnAsonSnapshotRemoteInetAddress
        }
        STATUS         current
        DESCRIPTION    "."
        ::= { tnAsonGroups 14 }

    tnAsonSnapshotGroup OBJECT-GROUP
        OBJECTS {
            tnAsonSnapshotStatus,
            tnAsonSnapshotRemotePath,
            tnAsonSnapshotRowStatus,
            tnAsonSnapshotFilename
        }
        STATUS         current
        DESCRIPTION    "."
        ::= { tnAsonGroups 15 }

    tnAsonOmsLineImpLScalarsGroup OBJECT-GROUP
        OBJECTS {
            tnGmreOmsLineImpLAttributeTotal
        }
        STATUS         current
        DESCRIPTION    "."
        ::= { tnAsonGroups 16 }

    tnAsonOmsLineImpLGroup OBJECT-GROUP
        OBJECTS {
            tnGmreOmsLineImpLMaxAlwCh,
            tnGmreOmsLineImpLPMD,
            tnGmreOmsLineImpLAlcMode,
            tnGmreOmsLineImpLDcuFree,
            tnGmreOmsLineImpLCD,
            tnGmreOmsLineImpLFiberType,
            tnGmreOmsLineImpLPDL
        }
        STATUS         current
        DESCRIPTION    "."
        ::= { tnAsonGroups 17 }

    tnAsonOptLineImpLScalarsGroup OBJECT-GROUP
        OBJECTS {
            tnGmreOptLineImpLAttributeTotal
        }
        STATUS         current
        DESCRIPTION    "."
        ::= { tnAsonGroups 18 }

    tnAsonOptLineImpLGroup OBJECT-GROUP
        OBJECTS {
            tnGmreOptLineImpLBitRate,
            tnGmreOptLineImpLEncoding,
            tnGmreOptLineImpLCompModule,
            tnGmreOptLineImpLFecMode,
            tnGmreOptLineImpLNLP,
            tnGmreOptLineImpLOSNR,
            tnGmreOptLineImpLNLPNP,
            tnGmreOptLineImpLOSNRNP,
            tnGmreOptLineImpLRowStatus,
            tnGmreOptLineImpLPower,
            tnGmreOptLineImpLPhaseEncode
        }
        STATUS         current
        DESCRIPTION    "."
        ::= { tnAsonGroups 19 }

    tnAsonOmsWavelengthSetLScalarsGroup OBJECT-GROUP
        OBJECTS {
            tnGmreOmsWavelengthSetLAttributeTotal
        }
        STATUS         current
        DESCRIPTION    "."
        ::= { tnAsonGroups 20 }

    tnAsonOmsWavelengthSetLGroup OBJECT-GROUP
        OBJECTS {
            tnGmreOmsWavelengthLEncodingBitMap
        }
        STATUS         current
        DESCRIPTION    "."
        ::= { tnAsonGroups 21 }

    tnAsonClusterScalarsGroup OBJECT-GROUP
        OBJECTS {
            tnGmreClusterAttributeTotal
        }
        STATUS         current
        DESCRIPTION    "."
        ::= { tnAsonGroups 22 }

    tnAsonClusterGroup OBJECT-GROUP
        OBJECTS {
            tnGmreClusterRowStatus,
            tnGmreClusterIpAddress,
            tnGmreClusterlinkStatus,
            tnGmreClusterInetAddressType,
            tnGmreClusterInetAddress
        }
        STATUS         current
        DESCRIPTION    "."
        ::= { tnAsonGroups 23 }

    tnGmreSubmarineGridModeScalarsGroup OBJECT-GROUP
        OBJECTS {
            tnGmreSubmarineGridModeTotal
        }
        STATUS         current
        DESCRIPTION    "."
        ::= { tnAsonGroups 24 }

    tnGmreSubmarineGridModeGroup OBJECT-GROUP
        OBJECTS {
            tnGmreSubmarineGridModeType
        }
        STATUS         current
        DESCRIPTION    "."
        ::= { tnAsonGroups 25 }

    tnGmreUplinkAttributeScalarsGroup OBJECT-GROUP
        OBJECTS {
            tnGmreUplinkAttributeTotal
        }
        STATUS         current
        DESCRIPTION    "."
        ::= { tnAsonGroups 26 }

    tnGmreUplinkGroup OBJECT-GROUP
        OBJECTS {
            tnGmreUplink1,
            tnGmreUplink2,
            tnGmreUplinkRowStatus,
            tnGmreUplinkMode
        }
        STATUS         current
        DESCRIPTION    "."
        ::= { tnAsonGroups 27 }

    tnAlienOtEntityScalarsGroup OBJECT-GROUP
        OBJECTS {
            tnAlienOtEntityAttributeTotal
        }
        STATUS         current
        DESCRIPTION    "."
        ::= { tnAsonGroups 28 }

    tnAlienOtEntityGroup OBJECT-GROUP
        OBJECTS {
            tnAlienOtEntityRowStatus,
            tnAlienOtEntityDescription,
            tnAlienOtEntityFrequencyMHz,
            tnAlienOtEntitySlotWidthMHz,
            tnAlienOtEntityCompModule,
            tnAlienOtEntityProfileId,
            tnAlienOtEntityXcId,
            tnAlienOtEntityXcIdAdd,
            tnAlienOtEntityXcIdDrop
        }
        STATUS         current
        DESCRIPTION    "."
        ::= { tnAsonGroups 29 }

    tnAsonOptLineProfileImpScalarsGroup OBJECT-GROUP
        OBJECTS {
            tnGmreOptLineProfileImpAttributeTotal
        }
        STATUS         current
        DESCRIPTION    "."
        ::= { tnAsonGroups 30 }

    tnAsonOptLineProfileImpGroup OBJECT-GROUP
        OBJECTS {
            tnGmreOptLineProfileImpCompModule,
            tnGmreOptLineProfileImpNLP,
            tnGmreOptLineProfileImpOSNR,
            tnGmreOptLineProfileImpNLPNP,
            tnGmreOptLineProfileImpOSNRNP,
            tnGmreOptLineProfileImpRowStatus,
            tnGmreOptLineProfileImpPower,
            tnGmreOptLineProfileImpProfileID,
            tnGmreOptLineProfileImpSlotWidth
        }
        STATUS         current
        DESCRIPTION    "."
        ::= { tnAsonGroups 31 }

    tnAsonOptLineProfileImpLScalarsGroup OBJECT-GROUP
        OBJECTS {
            tnGmreOptLineProfileImpLAttributeTotal
        }
        STATUS         current
        DESCRIPTION    "."
        ::= { tnAsonGroups 32 }

    tnAsonOptLineProfileImpLGroup OBJECT-GROUP
        OBJECTS {
            tnGmreOptLineProfileImpLCompModule,
            tnGmreOptLineProfileImpLNLP,
            tnGmreOptLineProfileImpLOSNR,
            tnGmreOptLineProfileImpLNLPNP,
            tnGmreOptLineProfileImpLOSNRNP,
            tnGmreOptLineProfileImpLRowStatus,
            tnGmreOptLineProfileImpLPower,
            tnGmreOptLineProfileImpLProfileID,
            tnGmreOptLineProfileImpLSlotWidth
        }
        STATUS         current
        DESCRIPTION    "."
        ::= { tnAsonGroups 33 }

--------------------------------------------------------------------------------
-- Compliance Statements (mandatory)
--------------------------------------------------------------------------------
    tnAsonCompliance MODULE-COMPLIANCE
        STATUS         current
        DESCRIPTION    "."
        MODULE
        MANDATORY-GROUPS {
            tnAsonGlobalGroup,
--            obsolete
--            tnAsonIorGlobalGroup,
            tnAsonOmsLineImpScalarsGroup,
            tnAsonOmsLineImpGroup,
            tnAsonOptLineImpScalarsGroup,
            tnAsonOptLineImpGroup,
            tnAsonTopoAlarmScalarsGroup,
            tnAsonTopoAlarmGroup,
            tnAsonFeasibilityGroup,
            tnAsonMgracdScalarsGroup,
            tnAsonMgracdGroup,
            tnAsonOmsWavelengthSetScalarsGroup,
            tnAsonOmsWavelengthSetGroup,
            tnAsonSnapshotScalarsGroup,
            tnAsonSnapshotGroup,
            tnAsonOmsLineImpLScalarsGroup,
            tnAsonOmsLineImpLGroup,
            tnAsonOptLineImpLScalarsGroup,
            tnAsonOptLineImpLGroup,
            tnAsonOmsWavelengthSetLScalarsGroup,
            tnAsonOmsWavelengthSetLGroup,
            tnAsonClusterScalarsGroup,
            tnAsonClusterGroup,
            tnGmreSubmarineGridModeScalarsGroup,
            tnGmreSubmarineGridModeGroup,
            tnGmreUplinkAttributeScalarsGroup,
            tnGmreUplinkGroup,
            tnAlienOtEntityScalarsGroup,
            tnAlienOtEntityGroup,
            tnAsonOptLineProfileImpScalarsGroup,
            tnAsonOptLineProfileImpGroup,
            tnAsonOptLineProfileImpLScalarsGroup,
            tnAsonOptLineProfileImpLGroup
        }
        ::= { tnAsonCompliances 1 }

END -- DEFINITION OF TROPIC-ASON-MIB
