TROPIC-1830PSD-CAPABILITY-MIB DEFINITIONS ::= BEGIN

-- (c) Copyright 2023 Nokia Networks. All rights reserved.
-- This software is the confidential and proprietary property of
-- Nokia and may only be used in accordance with the terms of the
-- license agreement provided with this software.

IMPORTS
    MODULE-IDENTITY, Unsigned32,
    Integer32                       FROM SNMPv2-SMI
    AGENT-CAPABILITIES              FROM SNMPv2-CONF
    tnPsdAgentCapability            FROM TROPIC-PSD-MIB;

tn1830PsdCapability MODULE-IDENTITY
    LAST-UPDATED    "202212240000Z"
    ORGANIZATION    "Nokia"
    CONTACT-INFO    "Nokia
                     Attn: Jeff Donnelly
                     600 Mountain Avenue
                     New Providence, NJ 07974

                     Phone: +1 732 221 6408
                     Email: jeff.donnelly@nokia.com"

    DESCRIPTION "The Agent Capabilities for the 1830 PSD."

    REVISION    "202212240000Z"
    DESCRIPTION "Added VARIATION clause for tnPsdSystemMode.

                 Added VARIATION clause for tnSysDiscoveryTransferTraps.

                 Enhanced the VARIATION clause of tnUserRowStatus,
                 describing the rejecting in case of setting it to
                 value notInService(2) or destroy(6).
                 Added not-implemented VARIATION clauses for

                 tnOthOdukStatsTcmConfigIntervalLength.

                 Removed TnCondition values tBerPreFec15min(687),
                 tBerPreFec1day(688), tBerPostFec15min(689) and
                 tBerPostFec1day(690) from, and added values
                 neCertValidityWarn(1807) and neCertValidityExp(1808)
                 to :
                  - tnGenericTrapCondition
                  - tnGenericActiveAlarmCondition
                  - tnGenericCriticalAlarmLogCondition
                  - tnGenericMajorAlarmLogCondition
                  - tnGenericMinorAlarmLogCondition
                  - tnGenericNotAlarmedLogCondition
                  - tnGenericWarningAlarmLogCondition
                  - tnPsdAsapFaultProfileCondition"

    REVISION    "202211070000Z"
    DESCRIPTION "Based on MIB version R15.0-LatestMIBs-221105.

                 Added not-implemented VARIATION clause for
                 tnDwdmCmnClientPortSSFOnOCIAction.

                 Added TnCondition values uruS(574), tBerPreFec15min(687),
                 tBerPreFec1day(688), tBerPostFec15min(689) and
                 tBerPostFec1day(690) to :
                  - tnGenericTrapCondition
                  - tnGenericActiveAlarmCondition
                  - tnGenericCriticalAlarmLogCondition
                  - tnGenericMajorAlarmLogCondition
                  - tnGenericMinorAlarmLogCondition
                  - tnGenericNotAlarmedLogCondition
                  - tnGenericWarningAlarmLogCondition
                  - tnPsdAsapFaultProfileCondition"

    REVISION    "202210290000Z"
    DESCRIPTION "Added support for tnPsdAlsGroup (TROPIC-PSD-MIB)
                 and tnTransferPMDiscoveryGroup (TROPIC-SYSTEM-MIB),
                 and added VARIATION clauses for subsets of the
                 objects from these groups."

    REVISION    "202210180000Z"
    DESCRIPTION "Added not-implemented VARIATION clauses for
                  - tnCNLinkDHCPBootFileName
                  - tnCNLinkDHCPClassName
                  - tnSysOtcWaitTimeAfterPowerChange
                  - tnSysDHCPClassName
                  - tnSysDHCPMatchString
                  - tnSysKeyLicense
                  - tnSysHwIfMode
                  - tnSysIpAclNextIndex
                  - tnSysIpv6AclNextIndex
                  - tnSysDHCPClass
                  - tnSysProtocolIpMode
                  - tnSysMultiShelfAvailableList
                  - tnSysPerformanceMemoryTotal
                  - tnSysPerformanceMemoryUsed
                  - tnSysPerformanceMemoryUsedPercentage
                  - tnSysPerformanceTime
                  - tnSysPerformanceCPUStatsPercentages
                  - tnSysPower
                  - tnUserPasswordForce"

    REVISION    "202209080000Z"
    DESCRIPTION "Added support for tnSysNtpDriftString and
                 tnSysNtpTimeOffsetString.
                 Added support for tnSysNtpServerIdStatsGroup,
                 except for object tnSysNtpServerIdStatsKeyIndex.
                 Removed support for tnPsdNtpStatus, tnPsdNtpStratum,
                 tnPsdNtpAccuracy, tnPsdNtpServerSystemServer,
                 tnPsdNtpServerReachable, tnPsdNtpServerReachabilityData,
                 tnPsdNtpServerPollTime."

    REVISION    "202207280000Z"
    DESCRIPTION "Added VARIATION clauses for tnUserToolsLinux
                 and tnUserMaxSession."

    REVISION    "202207230000Z"
    DESCRIPTION "Added VARIATION clause for tnUserName."

    REVISION    "202207130000Z"
    DESCRIPTION "Added support for a subset of the objects from
                 the tnUserGroup."

    REVISION    "202207110000Z"
    DESCRIPTION "Based on MIB version R14.1-LatestMIBs-220709.
                 Added not-implemented VARIATION clauses for
                  - tnLagPortLinkId
                  - tnAccessPortFacilityDesCustLifeCycleState
                  - tnAccessPortSummaryStatusLEDColor
                  - tnAccessPortSummaryStatusLEDState
                  - tnSysRadiusServerType
                  - tnSysRadiusServerDomain
                  - tnSysRadiusSecState
                  - tnNwPortRxFineOffSet
                  - tnNwPortTxFineOffSet
                  - tnOtuFacilityDescriptorConnPtId
                  - tnOtuFacilityDescCustLifeCycleState
                  - tnOtuFacilityDescAdminState
                  - tnSwNodeUrlLoadType
                  - tnSwNodeMigrateFileName
                  - tnSysCustomerLifeCycleState
                  - tnSysUSBInstall
                  - tnSysNmsIpVerifyState
                  - tnSysOcspSourceIpMode
                  - tnSysDnsSourceIpMode
                  - tnSyslogServerType
                  - tnSyslogServerDomain
                  - tnUserMgmtSysChangePasswordOnFirstLogin
                  - tnUserMgmtSysHistorySize"

    REVISION    "202207070000Z"
    DESCRIPTION "Added value adjusted(7) for objects
                  - tnOthOtukStatsBinStatus
                  - tnOthOdukStatsTcmBinStatus
                  - tnOthOdukStatsRxBinStatus
                  - tnEthPortStatsBinStatus
                  - tnEthCfmTWSlmStatsBinStatus
                  - tnEthCfmTWDmStatsBinStatus"

    REVISION    "202207050000Z"
    DESCRIPTION "Updated AGENT-CAPABILITIES PRODUCT-RELEASE to
                 indicate R5.0.0."

    REVISION    "202111220000Z"
    DESCRIPTION "Added not-implemented VARIATION clauses for
                  - tnDot1agCfmMepOndemandLmSessionStatus
                  - tnDot1agCfmMepOndemandLmRemoteMacAddr
                  - tnSysVersionPatchId
                  - tnSysVersionPatchDescr
                  - tnOthOdutc1StatRxNeBIP8ErrCnt15MinTr
                  - tnOthOdutc1StatRxNeBIP8ErrCnt15MinRtr
                  - tnOthOdutc1StatRxNeBIP8ErrCnt1DayTr
                  - tnOthOdutc1StatRxFeBIP8ErrCnt15MinTr
                  - tnOthOdutc1StatRxFeBIP8ErrCnt15MinRtr
                  - tnOthOdutc1StatRxFeBIP8ErrCnt1DayTr
                  - tnOthOdutc4StatRxNeBIP8ErrCnt15MinTr
                  - tnOthOdutc4StatRxNeBIP8ErrCnt15MinRtr
                  - tnOthOdutc4StatRxNeBIP8ErrCnt1DayTr
                  - tnOthOdutc4StatRxFeBIP8ErrCnt15MinTr
                  - tnOthOdutc4StatRxFeBIP8ErrCnt15MinRtr
                  - tnOthOdutc4StatRxFeBIP8ErrCnt1DayTr
                  - tnOthOtutc1StatRxNeSMBIP8ErrCnt15MinTr
                  - tnOthOtutc1StatRxNeSMBIP8ErrCnt15MinRtr
                  - tnOthOtutc1StatRxNeSMBIP8ErrCnt1DayTr
                  - tnOthOtutc1StatRxFeSMBIP8ErrCnt15MinTr
                  - tnOthOtutc1StatRxFeSMBIP8ErrCnt15MinRtr
                  - tnOthOtutc1StatRxFeSMBIP8ErrCnt1DayTr
                  - tnOthOtutc4StatRxNeSMBIP8ErrCnt15MinTr
                  - tnOthOtutc4StatRxNeSMBIP8ErrCnt15MinRtr
                  - tnOthOtutc4StatRxNeSMBIP8ErrCnt1DayTr
                  - tnOthOtutc4StatRxFeSMBIP8ErrCnt15MinTr
                  - tnOthOtutc4StatRxFeSMBIP8ErrCnt15MinRtr
                  - tnOthOtutc4StatRxFeSMBIP8ErrCnt1DayTr"

    REVISION    "202111150000Z"
    DESCRIPTION "Added VARIATION for tnStatsTCAProfileDescr.
                 Added applicability, depending on the value of object
                 tnSysDiscoveryTransferTraps, for objects :
                  - tnSysDiscoveryFilename
                  - tnSysDiscoveryControl
                  - tnSysDiscoveryBinnedStatsInterval
                  - tnSysDiscoveryBinnedStatsBin
                  - tnSysDiscoveryPrevious15minBinFilesTransfer
                  - tnSysDiscoveryPrevious1dayBinFilesTransfer
                  - tnSysDiscoveryTransferTimeOffset"

    REVISION    "202110210000Z"
    DESCRIPTION "Added back support for the space character for objects :
                  - sysContact
                  - sysLocation
                  - tnAccessPortDescr
                  - tnOthOdukApsDescr
                  - tnOthOdukXcName
                  - tnPmonPolicyDescription
                  - tnPsdShelfName
                  - tnPsdShelfDescr
                  - tnPsdShelfLocation
                  - tnPsdShelfLatitude
                  - tnPsdShelfLongitude
                  - tnPsdShelfAltitude
                 Corrected ASCII value of single quote from 0x39 to 0x27."

    REVISION    "202110130000Z"
    DESCRIPTION "Updated the description of the support of the types
                 and numbers of characters for objects tnSysName and
                 tnSysUserlabel.
                 Added support for :
                  - tnSysDiscoveryPrevious15minBinFilesTransfer
                  - tnSysDiscoveryPrevious1dayBinFilesTransfer
                  - tnSysDiscoveryTransferTimeOffset
                  - tnSysDiscoveryTransferTraps
                 Limited value ranges for :
                  - tnSysDiscoveryPrevious15minBinFilesTransfer
                  - tnSysDiscoveryPrevious1dayBinFilesTransfer"

    REVISION    "202109130000Z"
    DESCRIPTION "Added support for tnSysTimeOffsetTimeZone.
                 Added not-implemented VARIATION clauses for :
                  - tnCNLinkOspfOscRoutingState
                  - tnCNLinkOspfv6OscRoutingState
                  - tnOthOdukTtpMsimResp
                  - tnSysDelayReboot
                  - tnSysNmsUserName
                  - tnSysDiscoveryTransferTraps"

    REVISION    "202108160000Z"
    DESCRIPTION "Added fixed GET reply value for tnSysTransferLogType.
                 Added not-implemented VARIATION clauses for :
                  - tnCNLinkOspfv3HelloInterval
                  - tnCNLinkOspfv3TeMetric
                  - tnCNLinkOspfv3Retransint
                  - tnCNLinkOspfv3RtrDeadInterval
                  - tnCNLinkOspfv3ConfigRtrPriority
                  - tnCNLinkOspfv3RoutingState
                  - tnNetIfOspfv3AreaNumberId
                  - tnNetIfOspfv3HelloInterval
                  - tnNetIfOspfv3Metric
                  - tnNetIfOspfv3Retransint
                  - tnNetIfOspfv3RtrDeadInterval
                  - tnNetIfOspfv3ConfigRtrPriority
                  - tnNetIfOspfv3Status
                  - tnOthOduflexFC3200RxNeBIP8ErrCnt15MinTr
                  - tnOthOduflexFC3200RxNeBIP8ErrCnt15MinRtr
                  - tnOthOduflexFC3200RxNeBIP8ErrCnt1DayTr
                  - tnOthOduflexFC3200RxFeBIP8ErrCnt15MinTr
                  - tnOthOduflexFC3200RxFeBIP8ErrCnt15MinRtr
                  - tnOthOduflexFC3200RxFeBIP8ErrCnt1DayTr
                  - tnSysFeatureAutoTurnUp
                  - tnSysDelayResetNE"

    REVISION    "202108110000Z"
    DESCRIPTION "Added value range VARIATION for tnCNLinkDHCPRange.
                 Added VARIATION clauses for objects :
                  - tnPsdNetIfRemoteIpAddrType
                  - tnPsdNetIfIp6AddrType
                  - tnPsdNetIfIp6Addr
                  - tnPsdNetIfIp6PrefixLen
                  - tnPsdNetIfRemoteIp6AddrType
                  - tnPsdNetIfMonitoring6"

    REVISION    "202107010000Z"
    DESCRIPTION "Based on MIB version R14.0-Latest-MIBs-210626.
                 Added not-implemented VARIATION clauses for object
                 tnSwNodeLoadType.
                 Added support for the tnControlNetworkLinkGroup
                 (TROPIC-L1SERVICE-MIB, and added not-implemented
                 VARIATION clauses for all objects from that group
                 except the supported objects :
                  - tnCNLinkCitAutoStateCtrl
                  - tnCNLinkSourceLossCount
                  - tnCNLinkSourceIPCheckInterval
                  - tnCNLinkAutoStateSourceIP
                  - tnCNLinkAutoStateType
                  - tnCNLinkAutoStateStatus
                  - tnCNLinkAutoStateSourceInetAddressType
                  - tnCNLinkAutoStateSourceInetAddress
                 Added VARIATION clauses for objects :
                  - tnCNLinkAutoStateSourceIP
                  - tnCNLinkAutoStateSourceInetAddressType
                  - tnCNLinkAutoStateSourceInetAddress
                 Added support for objects :
                  - tnCNLinkDHCPServer
                  - tnCNLinkDHCPRange
                  - tnCNLinkDHCPDfltGtwy"

    REVISION    "202106170000Z"
    DESCRIPTION "Updated AGENT-CAPABILITIES PRODUCT-RELEASE to
                 indicate R4.0.0. Renamed tn1830CapabilityR400
                 into tn1830Capability.
                 Added support for tnLoopbackPortLLEB.
                 Updates to reflect support for Service OAM in mode
                 otnNid1GbEor10GbEClientOtu2OduFlexNetworkMode(10).
                 Removed VARIATION clause for tnSysAuthDenyMode.
                 Added non-implemented VARIATION clauses for :
                  - tnSysDiscoveryPrevious15minBinFilesTransfer
                  - tnSysDiscoveryPrevious1dayBinFilesTransfer
                  - tnSysDiscoveryTransferTimeOffset
                 Added support for conditions intrusion(121) and
                 ntpOoSync(265).
                 Updated tnSysBackupAndRestoreRemotePath VARIATION
                 clause for modified file name.
                 Added support for object tnSysNtpClockMode from
                 the tnSysNtpGroup. All other objects from this
                 group are specified to be not-implemented.
                 Added support for the tnSysTransferLogGroup.
                 Added support for tnPsdPmEthStatsGroup and
                 tnPsdPmEthStatsConfigChangeNotifGroup.
                 Removed support for sysName (SNMPv2-MIB) added
                 support for tnSysName and tnSysUserlabel
                 (TROPIC-SYSTEM-MIB).
                 Based on MIB version R14.0-Latest-MIBs-210612.
                 Added not-implemented VARIATION clauses for the
                 integration of Nokia MIB R14.0-Latest-MIBs-210612 :
                   - tnDot1agCfmMepOndemandLmTimeout
                   - tnPmonPolicyFramesPerDeltaT
                   - tnSysAutoTurnUpActiveTemplateForce
                   - tnSysNtpSourceIpMode
                Added supported character set description for:
                   - sysContact
                   - sysLocation
                   - tnOthOdukApsDescr
                   - tnOthOdukXcName"

    REVISION    "202101281200Z"
    DESCRIPTION "Removed dependencies between tnPortEtherSpeed and
                 tnIfType values."

    REVISION    "202101241200Z"
    DESCRIPTION "Updated timestamps for modified files from the
                 R13.1-Latest-MIBs-210123 delivery."

    REVISION    "202101141200Z"
    DESCRIPTION "Updated the VARIATION clause of tnPortEtherSpeed,
                 specifying a limited set of supported values.

                 Updated the VARIATION clauses of tnIfType and
                 tnPortEtherSpeed, specification a relation between the
                 values of these objects."

    REVISION    "202012141200Z"
    DESCRIPTION "Updated timestamps for modified files from the
                 R13.1-Latest-MIBs-201114 delivery.

                 Added not-implemented VARIATION clause for object
                 tnAccessPortModuleReset."

    REVISION    "202012091200Z"
    DESCRIPTION "Enhanced VARIATION clauses for changed degraded threshold
                 values changed by the system :
                  - tnOthOdukTxOduStruct
                  - tnOthOdukTtpDegThr
                  - tnOthOdukNimDegThr

                 Updated VARIATION clauses to refer to tnOthIfIndexLo :
                  - tnOthOdukApsFromedIfIndexLo
                  - tnOthOdukApsFromingIfIndexLo

                 Updated VARIATION clause of tnNetIfFacilityIfIndexLo to :
                  - Indicate that only HO ODU data are used
                  - For otnNid1GbEor10GbEClientOtu2OduFlexNetworkMode(10)
                    it refers to an ODUkP (Odu2P), and for other system
                    modes to an ODUkPm (NIM)."

    REVISION    "202012031200Z"
    DESCRIPTION "Added support for tnSyslogServerGroup.
                 Added VARIATION clauses for tnSyslogServerTable objects."

    REVISION    "202011181200Z"
    DESCRIPTION "Updated timestamps for modified files from the
                 R13.1-Latest-MIBs-201114 delivery."

    REVISION    "202010261200Z"
    DESCRIPTION "Removed VARIATION clause for tnSysBackupAndRestoreType,
                 following its removal from the TROPIC-SYSTEM-MIB.

                 Added non-implemented VARIATION clauses for :
                  - tnOamSaaCtlAlmProfName  (comment style text only)
                  - tnSysAuthDenyMode
                  - tnDwdmCmnClientPortCSFHoldOff
                  - tnDwdmCmnClientPortSSFHoldOff
                  - tnDwdmCmnClientPortSignalMode
                  - tnDwdmCmnClientPortCSFDelayTimer
                  - tnLoopbackPortFacTwo
                  - tnOthOdukTtpDegPeriod
                  - tnOthOdukNimDegPeriod
                  - tnOthOdukTDegPeriod
                  - tnOthOdukApsReSize
                  - tnOthOdukApsNewFromedTsList
                  - tnOthOdukApsNewFromingTsList
                  - tnOthOdukXcResize
                  - tnOthOdukXcNewFromTsList
                  - tnOthOdukXcNewToTsList
                  - tnOthOdukXcYangConnectionName
                  - tnOthOducStatTxNeBIP8ErrCnt15MinTr
                  - tnOthOducStatTxNeBIP8ErrCnt15MinRtr
                  - tnOthOducStatTxNeBIP8ErrCnt1DayTr
                  - tnOthOducStatTxFeBIP8ErrCnt15MinTr
                  - tnOthOducStatTxFeBIP8ErrCnt15MinRtr
                  - tnOthOducStatTxFeBIP8ErrCnt1DayTr
                  - tnOthOduflex400GBETxNeBIP8ErrCnt15MinTr
                  - tnOthOduflex400GBETxNeBIP8ErrCnt15MinRtr
                  - tnOthOduflex400GBETxNeBIP8ErrCnt1DayTr
                  - tnOthOduflex400GBETxFeBIP8ErrCnt15MinTr
                  - tnOthOtucStatRxNeSMBIP8ErrCnt15MinTr
                  - tnOthOtucStatRxNeSMBIP8ErrCnt15MinRtr
                  - tnOthOtucStatRxNeSMBIP8ErrCnt1DayTr
                  - tnOthOtucStatRxFeSMBIP8ErrCnt15MinTr
                  - tnOthOtucStatRxFeSMBIP8ErrCnt15MinRtr
                  - tnOthOtucStatRxFeSMBIP8ErrCnt1DayTr
                  - tnOthOducStatsTcmNeRxBIP8ErrCnt15MinTr,
                  - tnOthOducStatsTcmNeRxBIP8ErrCnt15MinRtr,
                  - tnOthOducStatsTcmNeRxBIP8ErrCnt1DayTr,
                  - tnOthOducStatsTcmFeRxBIP8ErrCnt15MinTr,
                  - tnOthOducStatsTcmFeRxBIP8ErrCnt15MinRtr,
                  - tnOthOducStatsTcmFeRxBIP8ErrCnt1DayTr,
                  - tnOthOduflex400GBEStatsTcmNeRxBIP8ErrCnt15MinTr,
                  - tnOthOduflex400GBEStatsTcmNeRxBIP8ErrCnt15MinRtr,
                  - tnOthOduflex400GBEStatsTcmNeRxBIP8ErrCnt1DayTr,
                  - tnOthOduflex400GBEStatsTcmFeRxBIP8ErrCnt15MinTr,
                  - tnOthOduflex400GBEStatsTcmFeRxBIP8ErrCnt15MinRtr,
                  - tnOthOduflex400GBEStatsTcmFeRxBIP8ErrCnt1DayTr"

    REVISION    "202010231200Z"
    DESCRIPTION "Updated AGENT-CAPABILITIES to indicate R3.0.0.

                 Added support for tnPsdSnmpTrapDest2Group.

                 Added TnCondition values gfpLof(140), plm(151), msim(602),
                 lofLom(691), csfGfp(889), gfpUpm(890) and gfpExm(1182) to :
                  - tnGenericTrapCondition
                  - tnGenericActiveAlarmCondition
                  - tnGenericCriticalAlarmLogCondition
                  - tnGenericMajorAlarmLogCondition
                  - tnGenericMinorAlarmLogCondition
                  - tnGenericNotAlarmedLogCondition
                  - tnGenericWarningAlarmLogCondition
                  - tnPsdAsapFaultProfileCondition

                 Added TnEntityType values oduf(52) and odu2Oduf(76) to :
                  - tnGenericTrapEntityType
                  - tnGenericActiveAlarmEntityType
                  - tnGenericCriticalAlarmLogEntityType
                  - tnGenericMajorAlarmLogEntityType
                  - tnGenericMinorAlarmLogEntityType
                  - tnGenericNotAlarmedLogEntityType
                  - tnGenericWarningAlarmLogEntityType

                 Updated VARIATION of tnIfType, to state that this object
                 can also be modified for system mode
                 otnNid1GbEor10GbEClientOtu2OduFlexNetworkMode.

                 The VARIATIONs of the following objects have been enhanced
                 for the otnNid1GbEor10GbEClientOtu2OduFlexNetworkMode :
                  - tnDwdmCmnClientPortLosProp
                  - tnOtukDegThr
                  - tnOthIfIndex
                  - tnOthOdukPayloadType
                  - tnOthOdukTxOduStruct
                  - tnOthOdukNimDirectionality
                  - tnOthOdukNimDegThr
                  - tnOthOdukTDegThr
                  - tnOthOdukApsToIfIndex
                  - tnOthOdukApsAction
                  - tnOthOdukXcSrcIfIndex
                  - tnNetIfStatus
                  - tnNetIfFacilityIfIndex
                  - tnPortEtherAcctPolicyId (comment style text only)
                  - tnPortEtherCollectStats (comment style text only)
                  - tnPsdSystemMode
                  - tnPsdStaticRouteGatewayType
                  - tnPsdStaticRouteGateway
                  - tnPsdPmTcaReportingMethod

                 Added value oduflex(5) to tnDwdmCmnClientPortContainer
                 VARIATION.

                 Enhanced the tnOthIfIndexLo VARIATION for system mode
                 otnNid1GbEor10GbEClientOtu2OduFlexNetworkMode(10),
                 describing the use of LO-ODUID and LO-ODU type for
                 this mode.

                 Enhanced the tnOthOdukTtpDegThr VARIATION with values for
                 the 2 types (ODU2 and ODUflex) of ODUkP which exists for
                 the otnNid1GbEor10GbEClientOtu2OduFlexNetworkMode.

                 Enhanced the set of supported values for object
                 tnOthOdukApsOduXcRate with the oduFlex(13) value, for the
                 otnNid1GbEor10GbEClientOtu2OduFlexNetworkMode system mode.

                 Enhanced the set of supported values for object
                 tnOthOdukXcRate with the oduFlex(13) value, for the
                 otnNid1GbEor10GbEClientOtu2OduFlexNetworkMode system mode."

    REVISION    "202006151200Z"
    DESCRIPTION "Added not-implemented VARIATION clauses for objects added
                 in the June 13th 2020 MIB Nokia delivery to object
                 groups partly supported by PSD.
                  - TROPIC-ACCESSPORT-MIB
                     - tnAccessPortAseMode
                     - tnAccessPortRole
                     - tnAccessPortFacilityDescriptorName
                     - tnAccessPortFacilityDescriptorDesc
                     - tnAccessPortFacilityDescriptorCirId
                     - tnAccessPortAlienWavebank

                 Removed not-implemented VARIATION clauses for objects
                 removed in the June 13th 2020 MIB Nokia delivery.
                  - TROPIC-OTH-MIB
                     - tnOthOdukFacilityDescriptorName
                     - tnOthOdukFacilityDescriptorDesc
                     - tnOthOdukFacilityDescriptorCirId"

    REVISION    "202006091200Z"
    DESCRIPTION "Combined VARIATION clauses of tnSysRadiusServerRowStatus
                 into one clause."

    REVISION    "202004151200Z"
    DESCRIPTION "Updated VARIATION of tnOthOdukPayloadType for relation
                 with PRBS enabling, and depending on system mode."

    REVISION    "202004061200Z"
    DESCRIPTION "Added support for tnExprSysRadiusServersGroup and
                 tnExprSysRadiusGroup from TROPIC-EXPRSCALARS, and added
                 VARIATION clauses for several of their objects.
                 Updated VARIATION of tnOthOdukPayloadType for relation
                 with PRBS enabling.
                 Added VARIATION clauses for tnExprSysRadiusServersGroup
                 objects, specifying inclusion in SET PDUs.
                 Removed the remarks on non-persistent storage from the
                 VARIATION clauses of objects tnPsdOdukTtpPrbsGenerator,
                 tnPsdOdukTtpPrbsGeneratorInvert, tnPsdOdukTtpPrbsMonitor,
                 tnPsdOdukTtpPrbsMonitorInvert and
                 tnPsdOdukTtpPrbsErrorPropagation."

    REVISION    "202003111200Z"
    DESCRIPTION "Added description for tnDwdmCmnClientPortLosProp.

                 Added support for TnCondition values csf(739) and prbsLSS(1623).

                 Added not-implemented VARIATION for tnSysDiscoveryPort
                 from tnSystemDiscoveryGroup.

                 Added not-implemented VARIATION clauses for objects added
                 in the February 29th 2020 MIB Nokia delivery to object
                 groups partly supported by PSD.
                  - TROPIC-SYSTEM-MIB
                     - tnSysBackupAndRestoreLocalInfo
                     - tnSysBackupAndRestoreType
                     - tnSysBackupAndRestoreLocalDelete
                     - tnSysBackupAndRestorePort
                     - tnSysBackupAndRestoreFallBackTimeStamp
                  - TROPIC-SOFTWARE-MIB
                     - tnSwNodeControlStatus
                     - tnSwNodePort
                     - tnSwNodeUrl
                  - TROPIC-ACCESS-PORT-MIB
                     - tnAccessPortCpriMappingType
                     - tnAccessPortFecType
                     - tnAccessPortFecBypassInd
                     - tnAccessPortCpriRole
                     - tnIfAlmProfName
                  - TROPIC-OPTICALPORT-MIB
                     - tnNwPortLaserOffRequest
                     - tnNwPortForcedLaserState
                     - tnNwPortProgrammedITUNumOffsetTx
                     - tnNwPortProgrammedITUNumOffsetRx
                     - tnNwPortProgrammedITUNumOffsetGridStepSize
                     - tnNwPortCalculatedRxFreq
                     - tnNwPortCalculatedTxFreq
                     - tnNwPortLinkSpan
                     - tnNwPortChannelTxLane
                     - tnNwPortChannelRxLane
                     - tnDwdmCmnClientPortSdiRate
                     - tnDwdmCmnClientPortGfpFcs
                  - TROPIC-OTUODU-MIB
                     - tnOtuOtsigId
                     - tnOtuChanPoolIfIndex
                     - tnOtuFacilityDescriptorName
                     - tnOtuFacilityDescriptorDesc
                     - tnOtuFacilityDescriptorCirId
                  - TROPIC-OTH-MIB
                     - tnOthOdukOduChanPools
                     - tnOthOdukMaxTribNumber
                     - tnOthOdukActualTribNumber
                     - tnOthOdukOduCTypeNMValue
                     - tnOthOdukFacilityDescriptorName
                     - tnOthOdukFacilityDescriptorDesc
                     - tnOthOdukFacilityDescriptorCirId
                     - tnOthOdukTcmDMInvoke
                     - tnOthOdukTcmDMTimeStamp
                     - tnOthOdukTcmDMCMEPMode
                     - tnOthOdukTcmDMStatus
                     - tnOthOdukTcmDMTime
                  - TROPIC-L1SERVICE-MIB
                     - tnNetIfOspfNeighborRouterIp
                     - tnNetIfOspfv3NeighborRouterIp
                     - tnNetIfOspfNeighborIp
                     - tnNetIfOspfv3NeighborInetAddress
                     - tnNetIfIPv6LinkLocalInetAddress
                     - tnNetIfLcpEchoInterval
                     - tnNetIfLcpEchoFailure
                     - tnNetIfOspfStatus
                  - TN-PORT-MIB
                     - tnPortEtherOperEgressRate           (comment style)
                  - TN-IEEE8021-CFM-MIB
                     - tnDot1agCfmMepOWDTDataSize          (comment style)
                     - tnDot1agCfmMepAlmProfName           (comment style)
                     - tnDot1agCfmMepDelayNearEndTestDelay (comment style)
                     - tnDot1agCfmMepDelayNearEndVariation (comment style)
                     - tnDot1agCfmMepDelayFarEndTestDelay  (comment style)
                     - tnDot1agCfmMepDelayFarEndVariation  (comment style)

                 Removed comment style not-implemented VARIATION clauses
                 for objects, following the obsoletion of these objects
                 in the February 29th 2020 MIB Nokia delivery.
                  - TN-PMON-MIB
                    - tnEthPortDot3StatsAlignmentErrors
                    - tnEthPortDot3StatsFCSErrors
                    - tnEthPortDot3StatsSingleCollisionFrames
                    - tnEthPortDot3StatsMultipleCollisionFrames
                    - tnEthPortDot3StatsSQETestErrors
                    - tnEthPortDot3StatsDeferredTransmissions
                    - tnEthPortDot3StatsLateCollisions
                    - tnEthPortDot3StatsExcessiveCollisions
                    - tnEthPortDot3StatsInternalMacTransmitErrors
                    - tnEthPortDot3StatsCarrierSenseErrors
                    - tnEthPortDot3StatsFrameTooLongs
                    - tnEthPortDot3StatsInternalMacReceiveErrors
                    - tnEthPortDot3StatsSymbolErrors

                 Added support for OBJECT-GROUP tnSysDiscoverMeGroup from
                 the TROPIC-SYSTEM-MIB."

    REVISION    "202002251200Z"
    DESCRIPTION "Added support for tnPsdOtn3Group and
                 tnPsdOtnConfigChangeNotif3Group.
                 Added variation for tnPsdOdukTtpPrbsGenerator,
                 tnPsdOdukTtpPrbsGeneratorInvert, tnPsdOdukTtpPrbsMonitor,
                 tnPsdOdukTtpPrbsMonitorInvert and
                 tnPsdOdukTtpPrbsErrorPropagation.
                 Added support for tnPsdIp3Group and
                 tnPsdIpConfigChangeNotif3Group."

    REVISION    "202001131200Z"
    DESCRIPTION "Updated AGENT-CAPABILITIES to indicate R2.0.0."

    REVISION    "201909161200Z"
    DESCRIPTION "Added R1.2.0. conformance groups to the
                 supported conformance groups of TROPIC-PSD-MIB.
                 Add support for tnDwdmCmnClientPortLosProp."

    REVISION    "201805251200Z"
    DESCRIPTION "Enhanced description ifAdminStatus and ifOperStatus.
                 Modified description dot1agCfmMdName.
                 Added variations for TROPIC-OPTICALPORT-MIB:
                 - tnDwdmCmnClientPortSsdca (not-implemented).
                 - tnDwdmCmnClientPortFlexGfpSize (not-implemented).
                 Added variations for TROPIC-L1SERVICE-MIB:
                 - tnNetIfOspfRetransint (not-implemented).
                 - tnNetIfOspfv3AdjStateId (not-implemented).
                 Added variation for tnGenericUserActionLogUserID.
                 Enhanced description of variation
                 tnPsdCfmTransportIdentifier."

    REVISION    "201804301200Z"
    DESCRIPTION "Enhanced variation dot1agCfmMaCompPrimaryVlanId.
                 Added variation for tnOtukOsTransmitted,
                 tnOthOdukTtpOsTransmitted and tnOthOdukTOsTransmitted.
                 Added support and variation for tnUserMgmtSysSessionTimeOut.
                 Removed support for tnPsdInterfaceConfigChangeNotif2Group and
                 added support for tnPsdInterfaceStateChangeNotifGroup and
                 tnPsdInterfaceEventNotifGroup."

    REVISION    "201803191200Z"
    DESCRIPTION "Added support for the TnCondition lanLfi(230) and
                 lanRfi(231).
                 Added variations for tnPsdSoamEnable.
                 Added variations for TROPIC-ACCESSPORT-MIB:
                 - tnIfnumofTimeSlots (not-implemented).
                 Added variations for TROPIC-OPTICALPORT-MIB:
                 - tnDwdmCmnClientPortSSFDelayCa (not-implemented)."

    REVISION    "201802231200Z"
    DESCRIPTION "Updated the contact info."

    REVISION    "201802141200Z"
    DESCRIPTION "Modified variations for IF-MIB:
                 - Added propVirtual(53) to ifType variation.
                 - Enhanced description of ifIndex.
                 Added variations for TROPIC-PSD-MIB:
                 - support and variations for tunable SFP objects
                   tnPsdSfp2Group and tnPsdInterfaceConfigChangeNotif2Group.
                 Modified variations for TROPIC-PSD-MIB:
                 - Enhanced description of tnPsdPmTcaReportingMethod.
                 Added R1.1.0. conformance groups to the
                 supported conformance groups of TROPIC-PSD-MIB.
                 Modified variations for TN-PORT-MIB:
                 - tnPortEtherAcctPolicyId
                 - tnPortEtherCollectStats
                 Added variations for TROPIC-USERMGMT-MIB:
                 - tnUserMgmtSysMaxSession
                 Added variations for IEEE8021-CFM-MIB:
                 - dot1agCfmMaComponentId
                 Modified variations for IEEE8021-CFM-MIB:
                 - dot1agCfmMepRowStatus
                 Added variations TROPIC-STATISTICS-MIB:
                 - Removed supported for tnDwStatsThresholdScalarsGroup."

    REVISION    "201712071200Z"
    DESCRIPTION "Modified variations for TN-IEEE8021-CFM-MIB:
                 - tnDot1agCfmMepOndemandLmSendCount
                 - Enhanced descriptions of tnDot1agCfmMepDelayTestDelay
                   and tnDot1agCfmMepDelayVariation stating that the
                   result values are in expressed in micro seconds.
                 Added variations for TROPIC-USERMGMT-MIB:
                 - tnUserMgmtSysSessionFailedMaxLogins
                 - tnUserMgmtSysPasswordAging
                 - tnUserMgmtSysPasswordObsolescenceInterval
                 Added variations for TROPIC-OPTICALPORT-MIB
                 - tnNwPortProgrammedChannel
                 - tnDwdmCmnClientPortFecBypassInd
                 Added variations TN-IEEE8021-CFM-MIB:
                 - tnDot1agCfmMepDelaySrcMacAddr
                 Added variations in TROPIC-SYSTEM-MIB:
                 - tnSysBackupAndRestoreRemotePath
                 Added support in TROPIC-SOFTWARE-MIB:
                 - tnSwNodeControlAbort
                 Modified variations in TROPIC-PSD-MIB:
                 - tnPsdSnmpTrapDestPort: added range limitation.
                 - tnPsdFaultAlarmRaiseTime, tnPsdFaultAlarmClearTime
                 - tnPsdStaticRouteGatewayType
                 - tnPsdStaticRouteGateway
                 Modified variations in TROPIC-GENERIC-NOTIFICATION-MIB:
                 - tnGenericTrapNumber
                 Modified variations in TROPIC-OTUODU-MIB:
                 - tnOtukDegThr, tnOtukDegM
                 Added variations for TROPIC-STATISTICS-MIB:
                 - tnOtuStatsPortProfileId
                 - tnOthOdukStatsRxProfileid
                 - tnOthOdukStatsTcmConfigProfileId
                 Modified descriptions TN-PMON-MIB:
                 - Enhanced descriptions of counters in tnEthCfmTWDmStatsTable
                   stating that DM results are in expressed in micro seconds.
                 - Added TCA value ranges to the description of
                   tnPmonTcaValue.
                 Added variations in TROPIC-OTH-MIB:
                 - tnOthOdukNimDirectionality
                 Modified variations in TROPIC-OTH-MIB:
                 - tnOthOdukTtpDegThr,tnOthOdukNimDegThr, tnOthOdukTDegThr
                 - tnOthOdukTtpDegM,tnOthOdukNimDegM, tnOthOdukTDegM
                 - tnOthOdukPayloadType
                 - tnOthOdukPlmConsequenceAction
                 - tnOthIfIndex
                 - tnOthOdukApsToIfIndex, tnOthOdukApsToIfIndexLo
                 - tnOthOdukApsAction
                 - tnOthOdukXcSrcIfIndex, tnOthOdukXcSrcIfIndexLo
                 - tnOthOdukXcDestIfIndex, tnOthOdukXcDestIfIndexLo
                 - tnOthOdukXcRowStatus
                 - tnOthOdukXcRate, tnOthOdukXcBidirectional
                 Modified variations in TROPIC-L1SERVICE-MIB:
                 - tnNetIfIndex, tnNetIfStatus, tnNetIfMtu
                 - tnNetIfFacilityIfIndex
                 - tnNetIfFacilityIfIndexLo
                 - tnNetIfFacilityTypeOfOperation
                 Removed descriptions IEEE8023-LAG-MIB:
                 - dot3adAggPortPartnerOperSystemPriority
                 - dot3adAggPortPartnerOperSystemID
                 Added variations  TROPIC-ACCESSPORT-MIB:
                 - tnIfSupportedTypes
                 Added not-implemented variations in TROPIC-ACCESSPORT-MIB:
                 - tnAccessPortDirectionCapability"

    REVISION    "201709251200Z"
    DESCRIPTION "Support for TnCondition crdInit(91) is removed and
                 replaced by unitInit(1479).
                 Modified description for TROPIC-GENERIC-NOTIFICATION-MIB:
                 - tnGenericTrapNumber
                 - tnGenericTrapCondition
                 Added description for TROPIC-GENERIC-NOTIFICATION-MIB:
                 - tnGenericSecurityEnableInterfaceNotif
                 - tnGenericSecurityDisableInterfaceNotif
                 - tnGenericPmBinsRolledOverNotif
                 Modified description for TROPIC-GENERIC-LOG-MIB:
                 - tnGenericSecurityLogSerialNumber
                 Added description for TROPIC-GENERIC-LOG-MIB:
                 - tnGenericActiveAlarmCondition
                 - tnGenericCriticalAlarmLogCondition
                 - tnGenericMajorAlarmLogCondition
                 - tnGenericMinorAlarmLogCondition
                 - tnGenericNotAlarmedLogCondition
                 - tnGenericWarningAlarmLogCondition
                 Added support for tnPsdSoftwareEventGroup (TROPIC-PSD-MIB).
                 Modified variations for TROPIC-OTUODU-MIB:
                 - tnOtukFecMode
                 Added variations for TROPIC-USERMGMT-MIB:
                 - tnUserMgmtGlobalGroup
                 Modified description for TN-OAM-TEST-MIB:
                 - tnOamPingCtlRowStatus
                 - tnOamPingCtlSize
                 Modified descriptions for TN-PMON-MIB:
                 - tnPmonPolicyAvailFlrThreshold
                 - tnPmonPolicyAvailFlrNumOfIntervals
                 - tnEthCfmTWSlmStatsNearEndFrameLossRatioMin
                 - tnEthCfmTWSlmStatsNearEndFrameLossRatioAverage
                 - tnEthCfmTWSlmStatsNearEndFrameLossRatioMax
                 - tnEthCfmTWSlmStatsFarEndFrameLossRatioMin
                 - tnEthCfmTWSlmStatsFarEndFrameLossRatioAverage
                 - tnEthCfmTWSlmStatsFarEndFrameLossRatioMax
                 Removed support of tnPsdAlarmNotifsGroup (TROPIC-PSD-MIB).
                 Modified descriptions for TROPIC-PSD-MIB:
                 - tnPsdOamEthCfmPingCtlPriority
                 - tnPsdAsapFaultProfileCondition
                 - tnPsdPmTcaReportingMethod
                 Added descriptions for TROPIC-PSD-MIB:
                 - tnPsdCfmTransportIdentifier
                 - tnPsdOamEthCfmPingCtlAvailFlrThreshold
                 - tnPsdOamEthCfmPingCtlAvailFlrNumOfIntervals
                 - tnPsdOamEthCfmPingCtlAvailFlrInterval15Min
                 - tnPsdOamEthCfmPingCtlAvailFlrInterval1Day
                 - tnPsdActualIpAddressAddr
                 Modified descriptions for IEEE8021-CFM-MIB:
                 - dot1agCfmMepRowStatus
                 - dot1agCfmMaNetName
                 Added support for dot1agCfmMepDbInterfaceStatusTlv.
                 Added not-implemented variations in IEEE8023-LAG-MIB for:
                 - dot3adAggPortPartnerAdminSystemPriority
                 - dot3adAggPortPartnerAdminSystemID
                 Modified descriptions for TN-LAG-MIB:
                 - tnLagCommand
                 Added not-implemented variations in TROPIC-OPTICALPORT-MIB
                 for:
                 - tnDwdmCmnClientPortInOpsbAction
                 - tnDwdmCmnClientPortSSFDelayTimer"

    REVISION    "201708181200Z"
    DESCRIPTION "Added variations in TN-PMON-MIB for:
                 - tnPmonPolicyType
                 - tnPmonPolicyId
                 - tnPmonPolicyAvailFlrThreshold
                 - tnPmonPolicyAvailFlrNumOfIntervals
                 - tnPmonTcaId
                 - tnPmonTcaVariable
                 - tnEthCfmTWSlmStatsTable
                 - tnEthCfmTWDmStatsTable
                 Added variations in TN-IEEE8021-CFM-MIB for:
                 - tnDot1agCfmMepTWDTMacAddress
                 - tnDot1agCfmMepTWDTPriority
                 - tnDot1agCfmMepTWDTDataSize
                 - tnDot1agCfmMepDelayRsltTable
                 - tnDot1agCfmMepSlmTWTestTable
                 - tnDot1agCfmMepSlmTestRsltTable
                 - tnDot1agCfmMepOndemandLmTestTable
                 - tnDot1agCfmMepOndemandLmTestRsltTable
                 Added support in TROPIC-GENERIC-NOTIFICATION-MIB for
                 - tnGenericTnDot1agCfmConfigChangeNotifGroup
                 - tnGenericTnOamTestConfigChangeNotifGroup
                 - tnGenericTnOamTestCreDelNotifGroup
                 Added variations in TN-OAM-TEST-MIB for:
                 - tnOamPingCtlTable
                 - tnOamEthCfmPingCtlTable
                 - tnOamSaaCtlTable
                 Removed support of notInService(2) for:
                 - dot1agCfmMdRowStatus,
                 - dot1agCfmMaNetRowStatus
                 - dot1agCfmMaCompRowStatus and
                 - dot1agCfmMepRowStatus
                 Modified description of:
                 - dot1agCfmMepActive
                 - tnNetIfIndex
                 - tnNetIfStatus
                 - tnNetIfFacilityIfIndex and tnNetIfFacilityIfIndexLo
                 - tnNetIfFacilityTypeOfOperation
                 - tnPsdSnmpTrapDestDyingGasp
                 - tnPsdStaticRouteDestType
                 - tnPsdStaticRouteGatewayType
                 - tnPsdStaticRouteGateway
                 - tnPsdStaticRouteIfIndex
                 Added variations in tnPsdNetIfTable for:
                 - tnPsdNetIfIpAddrType
                 - tnPsdNetIfIpAddr
                 - tnPsdNetIfIpPrefixLen
                 - tnPsdNetIfMonitoring
                 Added variation for tnPsdDot1agCfmMepDmTWTestStatus.
                 Added variations for tnPsdNetIfEthFacilityTable.
                 Added variations for tnPsdOamEthCfmPingCtlTable.
                 Added variations for tnPsdDot1agCfmMepSlmTWTestTable.
                 Added variations in tnOthOdukApsGroupTable for:
                 - tnOthOdukApsSwitchCmd
                 - tnOthOdukApsCascadedUse."

    REVISION    "201707071200Z"
    DESCRIPTION "Updated variations of tnSystemDiscoveryGroup, tnOtukGroup,
                 tnNetIfGroup for non supported objects.
                 Updated variations of ifType, ifAdminStatus, ifOperStatus,
                 tnIfType, tnOtukDegThr, tnOthOdukNimDegThr,
                 tnOthOdukTDegThr, tnOthOdukApsOduXcRate, tnOthOdukXcRate.
                 Added variations for IEEE8023-LAG-MIB and
                 IEEE8021-CFM-MIB support.
                 Updated variations with support for far-end TCA thresholds.
                 Added variations in comment style to describe the support
                 of MIB objects that are not part of conformance groups for
                 the following MIBs:TN-PMON-MIB, TN-PORT-MIB, TN-LAG-MIB,
                 TN-IEEE8021-CFM-MIB.
                 Added support for following notification groups:
                 - tnGenericTnStatisticsConfigChangeNotifGroup,
                 - tnGenericTnLagConfigChangeNotifGroup,
                 - tnGenericTnPmonConfigChangeNotifGroup,
                 - tnGenericTnPortConfigChangeNotifGroup,
                 - tnGenericDot1agCfmConfigChangeNotifGroup,
                 - tnGenericDot1agCfmCreDelNotifGroup,
                 tnGenericTnDot1agCfmConfigChangeNotifGroup.
                 Added variations for TnCondition and TnEntityType objects.
                 Added variations for added objects of tnGenericTrapEntry
                 and tnGenericLog entries.
                 Added support and variations for:
                 - tnPsdLagGroup,
                 - tnPsdAlarmNotifsGroup
                 - tnPsdCfmGroup
                 - tnPsdPmGroup.
                 Updated variation tnPsdSystemMode.
                 Added variation for tnPsdOdukTtpDmSessionType and
                 tnPsdPmTcaReportingMethod."

    REVISION    "201705051200Z"
    DESCRIPTION "Added variations of not supported ODUflex threshold objects
                 from tnTcmStatsThresholdScalarsGroup.
                 Removed read-only variation tnIfType,
                 tnSysBackupAndRestoreLastBackupFileTimeStamp.
                 Added variation for ifAdminStatus,
                 tnPsdSysDiscoveryServerAddrType.
                 Modified variation tnSysBackupAndRestoreProtocol,
                 tnSysDiscoveryServerProtocol, tnSwNodeSwdlServerProtocol,
                 tnOtukFecMode, tnOthOdukPayloadType,
                 tnOthOdukPlmConsequenceAction, tnOthOdukTxOduStruct,
                 tnOthOdukTTcmMode, tnOthOdukTPosSeq, tnOthOdukXcRowStatus,
                 tnOthOdukXcId, tnOthOdukXcRate, tnOthOdukXcBidirectional.
                 tnOthOdukXcProtectionState, tnNetIfPacketType, tnNetIfMtu,
                 tnNetIfFacilityIfIndex, tnNetIfFacilityTypeOfOperation,
                 tnOtuStatsPortIntervalLength, tnOtuStatsPortNumberOfBins,
                 tnOthOdukStatsTcmConfigNumberOfBins,
                 tnOthOdukStatsRxNumberofBins, tnOthOdukStatsRxIntervalLength,
                 tnOthIfIndex, tnOthOdukApsToIfIndex,
                 tnOthOdukXcSrcIfIndex, tnOthOdukTcmIfIndex, tnOthOdukXcId,
                 tnOthOdukXcRate.
                 Added value none(0) to variation of tnGenericTrapCondition.
                 Added variation for tnPsdShelfTime.
                 Added description for tnSwNodeWorkingReleaseDir."

    REVISION    "201703131200Z"
    DESCRIPTION "Added description for tnSysBackupAndRestoreUserId,
                 tnSysBackupAndRestorePassword, tnSysDiscoveryServerUserId,
                 tnSysDiscoveryServerPassword, tnSwNodeSwdlServerUserId,
                 tnSwNodeSwdlServerPassword.
                 Updated description of variation for tnOthOdukPayloadType.
                 Added support and variation for tnOtuStatsPortEnable.
                 Added support and variations for
                 tnOthOdukStatsTcmEnableGroup, tnOthOdukStatsControlGroup.
                 Added support for tnOthOdukTLtcResp.
                 Added support and variations for tnNetworkPortConfigGroup.
                 Added variation for tnOtukDegThr, tnOthOdukTtpDegThr,
                 tnOthOdukNimDegThr, tnOthOdukTDegThr.
                 Updated variation for tnPsdSnmpTrapDestDyingGasp,
                 tnPsdManualIpv4AddressAddr, tnPsdManualIpv6AddressAddr,
                 tnGenericTrapCondition, tnGenericActiveAlarmCondition,
                 tnPsdAsapFaultProfileCondition.
                 Added variation for tnPsdEnforceSrcIpV4ToLoopbackIpV4
                 and tnPsdEnforceSrcIpV6ToLoopbackIpV6.
                 Added support for following TnConditions:
                 tSesOtu15Min, tUasOtu15Min, tSesOdu15Min, tUasOdu15Min,
                 tSesOtu1Day, tUasOtu1Day, tSesOdu1Day, tUasOdu1Day,
                 tSesTcm15Min, tUasTcm15Min, tSesTcm1Day, tUasTcm1Day.
                 Updated variation of ifOperStatus.
                 Added support for following TCA variable objects:
                 tnOthOdukStatsTcmNeRxSES15MinTr,
                 tnOthOdukStatsTcmNeRxSES1DayTr,
                 tnOthOdukStatsTcmNeRxUAS15MinTr,
                 tnOthOdukStatsTcmNeRxUAS1DayTr, tnOthOdukStatRxNeSES15MinTr,
                 tnOthOdukStatRxNeSES1DayTr, tnOthOdukStatRxNeUAS15MinTr,
                 tnOthOdukStatRxNeUAS1DayTr, tnOthOtukStatRxNeSMSES15MinTr,
                 tnOthOtukStatRxNeSMSES1DayTr, tnOthOtukStatRxNeSMUAS15MinTr,
                 tnOthOtukStatRxNeSMUAS1DayTr.
                 Added support for following counters:
                 tnOthOtukStatNeRxSMUAS, tnOthOtukStatNeRxSMSES,
                 tnOthOtukStatFeRxSMUAS, tnOthOtukStatFeRxSMSES,
                 tnOthOdukStatsTcmNeRxUAS, tnOthOdukStatsTcmNeRxSES,
                 tnOthOdukStatsTcmFeRxUAS, tnOthOdukStatsTcmFeRxSES,
                 tnOthOdukStatsRxNeUAS, tnOthOdukStatsRxNeSES,
                 tnOthOdukStatsRxFeUAS, tnOthOdukStatsRxFeSES."

    REVISION    "201702061200Z"
    DESCRIPTION "Updated description tnOthOdukTRowStatus, tnNetIfStatus,
                 tnPsdSnmpTrapDestPort, tnPsdSnmpTrapDestDyingGasp,
                 tnPsdStaticRouteIfIndex, tnPsdStaticRouteRowStatus,
                 tnPsdNtpServerAddr.
                 Added description tnLoopbackPortDLEB, tnGenericTrapNumber,
                 tnPsdSystemMode, tnPsdSnmpTrapDestAddr,
                 tnPsdManualIpv4AddressAddr, tnPsdManualIpv6AddressAddr,
                 tnPsdStaticRouteDestType, tnPsdStaticRouteGatewayType,
                 tnPsdStaticRouteGateway, tnPsdFaultAlarmRaiseTime,
                 tnPsdFaultAlarmClearTime.
                 Added support and variations for tnOthOdukApsGroup and
                 tnOthOdukXcGroup.
                 Removed support of tnNetworkPortConfigGroup.
                 Added support and variations for tnGenericCriticalAlarmGroup,
                 tnGenericMajorAlarmGroup, tnGenericMinorAlarmGroup,
                 tnGenericStateChangeGroup, tnGenericUserActionGroup,
                 tnGenericGeneralEventGroup, tnGenericNotAlarmedGroup,
                 tnGenericSecurityGroup, tnGenericWarningAlarmGroup.
                 Incoperated MIB changes in tnAccessPortGroup,
                 tnSwNodeGroup, tnSystemBackupAndRestoreGroup,
                 tnDwdmCmnClientPortConfigGroup.
                 Updated descriptions tnPsdStaticRoute objects.
                 Added support for tnPsdIpStateChangeNotifGroup.
                 Added variation for tnOtukFecMode."

    REVISION    "201612211200Z"
    DESCRIPTION "Added support for tnPsdEquipmentEventGroup,
                 tnPsdEquipmentChangeGroup,
                 tnPsdInterfaceConfigChangeNotifGroup,
                 tnPsdSnmpConfigChangeNotifGroup, tnPsdSnmpCreDelNotifGroup,
                 tnPsdTimeConfigChangeNotifGroup,
                 tnPsdIpConfigChangeNotifGroup, tnPsdIpCreDelNotifGroup,
                 tnPsdFaultGroup, tnPsdFaultChangeNotifGroup,
                 tnPsdSysDiscoveryGroup, tnPsdOtnGroup,
                 tnPsdOtnConfigChangeNotifGroup.
                 Added support for tnSystemDiscoveryGroup,
                 tnDwdmCmnClientPortConfigGroup.
                 Added support for optIfOTUkSinkGroup, tnOtukGroup,
                 tnOthOdukTtpGroup, tnOthOdukNimGroup, tnOthOdukTGroup,
                 tnNetIfGroup, tnNetIfFacilityGroup.
                 Added support for tnOtuStatsPortGroup,
                 tnOthOtukStatsGroup, tnOthOdukStatsTcmConfigGroup,
                 tnOthOdukStatsTcmGroup, tnOthOdukStatsRxConfigGroup,
                 tnOthOdukStatsRxGroup, tnStatsTCAProfileGroup,
                 tnStatsTCAGroup, tnOthOtukStatsThresholdScalarsGroup,
                 tnDwStatsThresholdScalarsGroup,
                 tnTcmStatsThresholdScalarsGroup,
                 tnOthOdukStatsRxThresholdScalarsGroup.
                 Added support for tnGenericTrapBufferGroup,
                 tnGenericAlarmNotifsGroup, tnGenericEventNotifsGroup,
                 tnGenericScalarConfigChangeNotifGroup,
                 tnGenericInterfaceConfigChangeNotifGroup,
                 tnGenericInterfaceStateChangeNotifGroup,
                 tnGenericOptIfConfigChangeNotifGroup,
                 tnGenericTnAccessPortConfigChangeNotifGroup,
                 tnGenericTnOpticalPortConfigChangeNotifGroup,
                 tnGenericTnOtuOduConfigChangeNotifGroup,
                 tnGenericTnOthConfigChangeNotifGroup,
                 tnGenericTnOthCreDelNotifGroup,
                 tnGenericTnL1ServiceConfigChangeNotifGroup,
                 tnGenericTnL1ServiceCreDelNotifGroup,
                 tnGenericTnStatisticsConfigChangeNotifGroup.
                 Added support for tnGenericActiveAlarmGroup.
                 Modified supported character set for
                 tnPsdSnmpTrapDestServerId."

    REVISION    "201610281200Z"
    DESCRIPTION "Initial version of this MIB module."

    ::= { tnPsdAgentCapability 1 }

tn1830Capability AGENT-CAPABILITIES
    PRODUCT-RELEASE "Release 5.0.0."
    STATUS          current
    DESCRIPTION     "Agent Capabilities for the 1830 PSD product."

--
-- Capabilities for SNMPv2-MIB
--

    SUPPORTS            SNMPv2-MIB
        INCLUDES        { systemGroup,
                          snmpBasicNotificationsGroup,
                          snmpWarmStartNotificationGroup }

        VARIATION       sysContact
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       sysName
            ACCESS      not-implemented
            DESCRIPTION "This object is not supported. It is superseded by
                         tnSysName of the TROPIC-SYSTEM-MIB."

        VARIATION       sysLocation
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

--
-- Capabilities for IF-MIB
--

    SUPPORTS            IF-MIB
        INCLUDES        { ifGeneralInformationGroup,
                          ifVHCPacketGroup }

        VARIATION       ifIndex
            DESCRIPTION "In the value of this object, the shelf, slot and port
                         values are encoded as follows:
                         shelf           = (value & 0x7F000000) >> 24
                         slot            = (value & 0x00FF0000) >> 16
                         port            = (value & 0x0000FF00) >>  8
                         is logical port = (value & 0x00008000) >> 15
                         The logical port becomes functionally a LAG aggregator
                         in case the ifType equals ieee8023adLag(161) and as
                         soon as LAG is enabled for this port.
                         See description tnLagPortSubgroup."

        VARIATION       ifDescr
            ACCESS      not-implemented
            DESCRIPTION "This object is not supported."

        VARIATION       ifType
            SYNTAX      INTEGER { other(1),
                                  ethernetCsmacd(6),
                                  softwareLoopback(24),
                                  propVirtual(53),
                                  ieee8023adLag(161),
                                  opticalChannel(195) }
            DESCRIPTION "Limited set of values."

        VARIATION       ifAdminStatus
            DESCRIPTION "The only permitted value for interfaces of ifType
                         propVirtual(53) and ieee8023adLag(161) is up(1).
                         For the OTN NID system modes:
                         - value testing(3) is only supported for CLIENT1.
                         - CLIENT1, NETWORK1 and NETWORK2 can be set
                           to up(1) or down(2), the only permitted value for
                           CLIENT2 is down(2).
                         For the ETH NID system mode:
                         - value testing(3) is only supported for CLIENT1 and
                           CLIENT2.
                         - CLIENT1, CLIENT2, NETWORK1 and NETWORK2 can be set
                           to up(1) or down(2)."

        VARIATION       ifOperStatus
            SYNTAX      INTEGER { up(1), down(2), unknown(4) }
            DESCRIPTION "Limited set of values.

                         For the OTN NID system modes:
                         Interfaces of ifType propVirtual(53):
                         - ifOperStatus.CLIENT  = ifOperStatus.CLIENT1

                         For the ETH NID system mode:
                         Interfaces of ifType ieee8023adLag(161) in case
                         LAG is functionally disabled (see tnLagPortSubgroup):
                         - ifOperStatus.CLIENT  = ifOperStatus.CLIENT1
                         - ifOperStatus.NETWORK = ifOperStatus.NETWORK1
                         For interfaces of ifType ieee8023adLag(161) in case
                         LAG is functionally enabled (see tnLagPortSubgroup):
                         - down(2) in case lagLos(742) defect is active and
                           up(1) otherwise."

        VARIATION       ifLinkUpDownTrapEnable
            ACCESS      not-implemented
            DESCRIPTION "This object is not supported."

        VARIATION       ifConnectorPresent
            ACCESS      not-implemented
            DESCRIPTION "This object is not supported."

        VARIATION       ifAlias
            ACCESS      not-implemented
            DESCRIPTION "This object is not supported."

        VARIATION       ifHCInUcastPkts
            ACCESS      not-implemented
            DESCRIPTION "This object is not supported."

        VARIATION       ifHCInMulticastPkts
            ACCESS      not-implemented
            DESCRIPTION "This object is not supported."

        VARIATION       ifHCInBroadcastPkts
            ACCESS      not-implemented
            DESCRIPTION "This object is not supported."

        VARIATION       ifHCOutUcastPkts
            ACCESS      not-implemented
            DESCRIPTION "This object is not supported."

        VARIATION       ifHCOutMulticastPkts
            ACCESS      not-implemented
            DESCRIPTION "This object is not supported."

        VARIATION       ifHCOutBroadcastPkts
            ACCESS      not-implemented
            DESCRIPTION "This object is not supported."

        VARIATION       ifHCInOctets
            ACCESS      not-implemented
            DESCRIPTION "This object is not supported."

        VARIATION       ifHCOutOctets
            ACCESS      not-implemented
            DESCRIPTION "This object is not supported."

        VARIATION       ifInOctets
            ACCESS      not-implemented
            DESCRIPTION "This object is not supported."

        VARIATION       ifOutOctets
            ACCESS      not-implemented
            DESCRIPTION "This object is not supported."

        VARIATION       ifInUnknownProtos
            ACCESS      not-implemented
            DESCRIPTION "This object is not supported."

        VARIATION       ifInErrors
            ACCESS      not-implemented
            DESCRIPTION "This object is not supported."

        VARIATION       ifOutErrors
            ACCESS      not-implemented
            DESCRIPTION "This object is not supported."

        VARIATION       ifInUcastPkts
            ACCESS      not-implemented
            DESCRIPTION "This object is not supported."

        VARIATION       ifInMulticastPkts
            ACCESS      not-implemented
            DESCRIPTION "This object is not supported."

        VARIATION       ifInBroadcastPkts
            ACCESS      not-implemented
            DESCRIPTION "This object is not supported."

        VARIATION       ifInDiscards
            ACCESS      not-implemented
            DESCRIPTION "This object is not supported."

        VARIATION       ifOutUcastPkts
            ACCESS      not-implemented
            DESCRIPTION "This object is not supported."

        VARIATION       ifOutMulticastPkts
            ACCESS      not-implemented
            DESCRIPTION "This object is not supported."

        VARIATION       ifOutBroadcastPkts
            ACCESS      not-implemented
            DESCRIPTION "This object is not supported."

        VARIATION       ifOutDiscards
            ACCESS      not-implemented
            DESCRIPTION "This object is not supported."

        VARIATION       ifPromiscuousMode
            ACCESS      not-implemented
            DESCRIPTION "This object is not supported."

--
-- Capabilities for TROPIC-SYSTEM-MIB
-- Based on MIB version:  R15.0-LatestMIBs-221105
--

    SUPPORTS            TROPIC-SYSTEM-MIB
        INCLUDES        { tnSystemBasicsGroup,
                          tnSystemBackupAndRestoreGroup,
                          tnSystemDiscoveryGroup,
                          tnSysDiscoverMeGroup,
                          tnSyslogServerGroup,
                          tnSysTransferLogGroup,
                          tnSysNtpGroup,
                          tnSysNtpServerIdStatsGroup,
                          tnTransferPMDiscoveryGroup }

        VARIATION       tnSysDescr
            ACCESS      not-implemented
            DESCRIPTION "This object is not supported."

        VARIATION       tnSysTelnetPort
            ACCESS      not-implemented
            DESCRIPTION "This object is not supported."

        VARIATION       tnSysHttpPort
            ACCESS      not-implemented
            DESCRIPTION "This object is not supported."

        VARIATION       tnSysDateAndTime
            ACCESS      not-implemented
            DESCRIPTION "This object is not supported."

        VARIATION       tnSysReset
            ACCESS      not-implemented
            DESCRIPTION "This object is not supported."

        VARIATION       tnSysMIBVersion
            ACCESS      not-implemented
            DESCRIPTION "This object is not supported."

        VARIATION       tnSysRingID
            ACCESS      not-implemented
            DESCRIPTION "This object is not supported."

        VARIATION       tnSysNetworkElementID
            ACCESS      not-implemented
            DESCRIPTION "This object is not supported."

        VARIATION       tnSysAINSDebounceTime
            ACCESS      not-implemented
            DESCRIPTION "This object is not supported."

        VARIATION       tnSysSonetSdhMode
            ACCESS      not-implemented
            DESCRIPTION "This object is not supported."

        VARIATION       tnSysAlarmReportingControl
            ACCESS      not-implemented
            DESCRIPTION "This object is not supported."

        VARIATION       tnSysWavelengthTrackerWaveKeySpace
            ACCESS      not-implemented
            DESCRIPTION "This object is not supported."

        VARIATION       tnSysSecureMode
            ACCESS      not-implemented
            DESCRIPTION "This object is not supported."

        VARIATION       tnSysExtendedTemperatureRange
            ACCESS      not-implemented
            DESCRIPTION "This object is not supported."

        VARIATION       tnSysTemperatureInCelsius
            ACCESS      not-implemented
            DESCRIPTION "This object is not supported."

        VARIATION       tnSysName
            DESCRIPTION "The maximum length is 20 octets.
                         The allowed UTF-8 character set complies to the
                         UTF-8 character set as specified in RFC 3629
                         with the following limitations:
                         - Only 1 or 2 octet UTF-8 characters are supported.
                         - From the 1 octet UTF-8 characters only the
                           following characters are supported:
                           {a-z},{A-Z}{0-9}_./-#%+
                         - Control characters (C0 and C1) are not supported:
                           C0: 0x00 - 0x0f and 0x7f
                           C1: 0x80 - 0x9f
                         - From the 2 octet UTF-8 characters only the
                           printable character codes between 128-255
                           are supported."

        VARIATION       tnSysEquipmentControllerCapacity
            ACCESS      not-implemented
            DESCRIPTION "This object is not supported."

        VARIATION       tnSysFirstLevelControllerCapacity
            ACCESS      not-implemented
            DESCRIPTION "This object is not supported."

        VARIATION       tnSysMatrix0CompactCapacity
            ACCESS      not-implemented
            DESCRIPTION "This object is not supported."

        VARIATION       tnSysUniversalMatrixFirstLevelControllerCapacity
            ACCESS      not-implemented
            DESCRIPTION "This object is not supported."

        VARIATION       tnSysTimeOffsetTimeZone
            DESCRIPTION "The following strings can be configured :
                          - UTC
                          - UTC+HH:MM  (HH: hours, MM: minutes)
                          - UTC-HH:MM  (HH: hours, MM: minutes)"

        VARIATION       tnSysSwitchId
            DESCRIPTION "The value of this object is fixed to 272695296
                         (0x10410000)
                         This is constructed as:
                         - type   (4  bits): 1
                         - shelf  (6  bits): 1
                         - slot   (6  bits): 1
                         - unused (16 bits): 0
                         See TnSwitchID (TN-TC-MIB) for details."

        VARIATION       tnSysFipsSquelchMode
            ACCESS      not-implemented
            DESCRIPTION "This object is not supported."

        VARIATION       tnSysOtdrListOfFileNames
            ACCESS      not-implemented
            DESCRIPTION "This object is not supported."

        VARIATION       tnSysOtdrFileCounts
            ACCESS      not-implemented
            DESCRIPTION "This object is not supported."

        VARIATION       tnSysAltitude
            ACCESS      not-implemented
            DESCRIPTION "This object is not supported."

        VARIATION       tnSysThermalShutdownAutotimer
            ACCESS      not-implemented
            DESCRIPTION "This object is not supported."

        VARIATION       tnSysDisplayShelfLabel
            ACCESS      not-implemented
            DESCRIPTION "This object is not supported."

        VARIATION       tnSysPMFineGranularityControl
            ACCESS      not-implemented
            DESCRIPTION "This object is not supported."

        VARIATION       tnSysFmRead
            ACCESS      not-implemented
            DESCRIPTION "This object is not supported."

        VARIATION       tnSysPMStreamingServerControl
            ACCESS      not-implemented
            DESCRIPTION "This object is not supported."

        VARIATION       tnSysSlotMigrationControl
            ACCESS      not-implemented
            DESCRIPTION "This object is not supported."

        VARIATION       tnSysFlexGridClusterOcsAddDropEnabled
            ACCESS      not-implemented
            DESCRIPTION "This object is not supported."

        VARIATION       tnSysFilterCheckTime
            ACCESS      not-implemented
            DESCRIPTION "This object is not supported."

        VARIATION       tnSysCNLinkPhysicalIfIndex
            ACCESS      not-implemented
            DESCRIPTION "This object is not supported."

        VARIATION       tnSysUserlabel
            DESCRIPTION "The maximum length is 128 octets.
                         1, 2, 3 and 4 octet UTF-8 characters are supported.
                         A maximum of 32 UTF-8 characters can be configured.
                         The allowed UTF-8 character set complies to the
                         UTF-8 character set as specified in RFC 3629
                         with the following limitations:
                         - Control characters (C0 and C1) are not supported:
                           C0: 0x00 - 0x0f and 0x7f
                           C1: 0x80 - 0x9f"

        VARIATION       tnSysOpenAgentControl
            ACCESS      not-implemented
            DESCRIPTION "This object is not supported."

        VARIATION       tnSysUnkeyedDanglingOchAddDropEnabled
            ACCESS      not-implemented
            DESCRIPTION "This object is not supported."

        VARIATION       tnSysNetWorkTraceV3SecurityUser
            ACCESS      not-implemented
            DESCRIPTION "This object is not supported."

        VARIATION       tnSysScotV3SecurityUser
            ACCESS      not-implemented
            DESCRIPTION "This object is not supported."

        VARIATION       tnSysTL1Enable
            ACCESS      not-implemented
            DESCRIPTION "This object is not supported."

        VARIATION       tnSysLMEnabled
            ACCESS      not-implemented
            DESCRIPTION "This object is not supported."

        VARIATION       tnSysAlienChannelLicensingEnabled
            ACCESS      not-implemented
            DESCRIPTION "This object is not supported."

        VARIATION       tnSysDebug
            ACCESS      not-implemented
            DESCRIPTION "This object is not supported."

        VARIATION       tnSysClusterV3SecurityUser
            ACCESS      not-implemented
            DESCRIPTION "This object is not supported."

        VARIATION       tnSysSyncMode
            ACCESS      not-implemented
            DESCRIPTION "This object is not supported."

        VARIATION       tnSysPMMode
            ACCESS      not-implemented
            DESCRIPTION "This object is not supported."

        VARIATION       tnSysShelfLatitude
            ACCESS      not-implemented
            DESCRIPTION "This object is not supported."

        VARIATION       tnSysShelfLongitude
            ACCESS      not-implemented
            DESCRIPTION "This object is not supported."

        VARIATION       tnSysAlmProfName
            ACCESS      not-implemented
            DESCRIPTION "This object is not supported."

        VARIATION       tnSysBgpAsn
            ACCESS      not-implemented
            DESCRIPTION "This object is not supported."

        VARIATION       tnSysBgpLocalRouterId
            ACCESS      not-implemented
            DESCRIPTION "This object is not supported."

        VARIATION       tnSysNodeIdLabel
            ACCESS      not-implemented
            DESCRIPTION "This object is not supported."

        VARIATION       tnSysNodeNumber
            ACCESS      not-implemented
            DESCRIPTION "This object is not supported."

        VARIATION       tnSysNodeCLLI
            ACCESS      not-implemented
            DESCRIPTION "This object is not supported."

        VARIATION       tnSysNodeTemplate
            ACCESS      not-implemented
            DESCRIPTION "This object is not supported."

        VARIATION       tnSysCustomerApplicationMode
            ACCESS      not-implemented
            DESCRIPTION "This object is not supported."

        VARIATION       tnSysMDCli
            ACCESS      not-implemented
            DESCRIPTION "This object is not supported."

        VARIATION       tnSysMultiShelfMode
            ACCESS      not-implemented
            DESCRIPTION "This object is not supported."

        VARIATION       tnSysMultiShelfConfigList
            ACCESS      not-implemented
            DESCRIPTION "This object is not supported."

        VARIATION       tnSysMultiShelfUnknownList
            ACCESS      not-implemented
            DESCRIPTION "This object is not supported."

        VARIATION       tnSysMultiShelfMissingList
            ACCESS      not-implemented
            DESCRIPTION "This object is not supported."

        VARIATION       tnSysPrompt
            ACCESS      not-implemented
            DESCRIPTION "This object is not supported."

        VARIATION       tnSysPromptType
            ACCESS      not-implemented
            DESCRIPTION "This object is not supported."

        VARIATION       tnSysShelfAltitude
            ACCESS      not-implemented
            DESCRIPTION "This object is not supported."

        VARIATION       tnSysTacacsSourceIpMode
            ACCESS      not-implemented
            DESCRIPTION "This object is not supported."

        VARIATION       tnSysRadiusSourceIpMode
            ACCESS      not-implemented
            DESCRIPTION "This object is not supported."

        VARIATION       tnSysFtpSourceIpMode
            ACCESS      not-implemented
            DESCRIPTION "This object is not supported."

        VARIATION       tnSysSftpSourceIpMode
            ACCESS      not-implemented
            DESCRIPTION "This object is not supported."

        VARIATION       tnSysHttpSourceIpMode
            ACCESS      not-implemented
            DESCRIPTION "This object is not supported."

        VARIATION       tnSysHttpsSourceIpMode
            ACCESS      not-implemented
            DESCRIPTION "This object is not supported."

        VARIATION       tnSysSnmpSourceIpMode
            ACCESS      not-implemented
            DESCRIPTION "This object is not supported."

        VARIATION       tnSysSyslogSourceIpMode
            ACCESS      not-implemented
            DESCRIPTION "This object is not supported."

        VARIATION       tnSysSshSourceIpMode
            ACCESS      not-implemented
            DESCRIPTION "This object is not supported."

        VARIATION       tnSysAutoTurnUpActiveTemplate
            ACCESS      not-implemented
            DESCRIPTION "This object is not supported."

        VARIATION       tnSysAuthenticationOrder
            ACCESS      not-implemented
            DESCRIPTION "This object is not supported."

        VARIATION       tnSysAuthRejectOption
            ACCESS      not-implemented
            DESCRIPTION "This object is not supported."

        VARIATION       tnSysAutoTurnUpActiveTemplateForce
            ACCESS      not-implemented
            DESCRIPTION "This object is not supported."

        VARIATION       tnSysNtpSourceIpMode
            ACCESS      not-implemented
            DESCRIPTION "This object is not supported."

        VARIATION       tnSysFeatureAutoTurnUp
            ACCESS      not-implemented
            DESCRIPTION "This object is not supported."

        VARIATION       tnSysDelayResetNE
            ACCESS      not-implemented
            DESCRIPTION "This object is not supported."

        VARIATION       tnSysDelayReboot
            ACCESS      not-implemented
            DESCRIPTION "This object is not supported."

        VARIATION       tnSysNmsUserName
            ACCESS      not-implemented
            DESCRIPTION "This object is not supported."

        VARIATION       tnSysVersionPatchId
            ACCESS      not-implemented
            DESCRIPTION "This object is not supported."

        VARIATION       tnSysVersionPatchDescr
            ACCESS      not-implemented
            DESCRIPTION "This object is not supported."

        VARIATION       tnSysCustomerLifeCycleState
            ACCESS      not-implemented
            DESCRIPTION "This object is not supported."

        VARIATION       tnSysUSBInstall
            ACCESS      not-implemented
            DESCRIPTION "This object is not supported."

        VARIATION       tnSysNmsIpVerifyState
            ACCESS      not-implemented
            DESCRIPTION "This object is not supported."

        VARIATION       tnSysOcspSourceIpMode
            ACCESS      not-implemented
            DESCRIPTION "This object is not supported."

        VARIATION       tnSysDnsSourceIpMode
            ACCESS      not-implemented
            DESCRIPTION "This object is not supported."

        VARIATION       tnSysOtcWaitTimeAfterPowerChange
            ACCESS      not-implemented
            DESCRIPTION "This object is not supported."

        VARIATION       tnSysDHCPClassName
            ACCESS      not-implemented
            DESCRIPTION "This object is not supported."

        VARIATION       tnSysDHCPMatchString
            ACCESS      not-implemented
            DESCRIPTION "This object is not supported."

        VARIATION       tnSysKeyLicense
            ACCESS      not-implemented
            DESCRIPTION "This object is not supported."

        VARIATION       tnSysHwIfMode
            ACCESS      not-implemented
            DESCRIPTION "This object is not supported."

        VARIATION       tnSysIpAclNextIndex
            ACCESS      not-implemented
            DESCRIPTION "This object is not supported."

        VARIATION       tnSysIpv6AclNextIndex
            ACCESS      not-implemented
            DESCRIPTION "This object is not supported."

        VARIATION       tnSysDHCPClass
            ACCESS      not-implemented
            DESCRIPTION "This object is not supported."

        VARIATION       tnSysProtocolIpMode
            ACCESS      not-implemented
            DESCRIPTION "This object is not supported."

        VARIATION       tnSysMultiShelfAvailableList
            ACCESS      not-implemented
            DESCRIPTION "This object is not supported."

        VARIATION       tnSysPerformanceMemoryTotal
            ACCESS      not-implemented
            DESCRIPTION "This object is not supported."

        VARIATION       tnSysPerformanceMemoryUsed
            ACCESS      not-implemented
            DESCRIPTION "This object is not supported."

        VARIATION       tnSysPerformanceMemoryUsedPercentage
            ACCESS      not-implemented
            DESCRIPTION "This object is not supported."

        VARIATION       tnSysPerformanceTime
            ACCESS      not-implemented
            DESCRIPTION "This object is not supported."

        VARIATION       tnSysPerformanceCPUStatsPercentages
            ACCESS      not-implemented
            DESCRIPTION "This object is not supported."

        VARIATION       tnSysPower
            ACCESS      not-implemented
            DESCRIPTION "This object is not supported."

        VARIATION       tnSysBackupAndRestoreRemoteHostIp
            ACCESS      not-implemented
            DESCRIPTION "This object is not supported. It is superseded by
                         objects
                         tnPsdDatabaseBackupAndRestoreRemoteHostAddrType
                         and tnPsdDatabaseBackupAndRestoreRemoteHostAddr."

        VARIATION       tnSysBackupAndRestoreRemotePath
            DESCRIPTION "For a backup operation in case the value of this
                         object ends with a '/' character, i.e. it is a
                         directory, the system will generate the file name
                         for the database file.
                         This file name contains:
                         - 1830PSD
                         - The software release version
                         - A date and time indication
                         An example of a generated filename:
                           1830PSD-R04.00.00-20210512-16-19-18.bak
                         In case the value of this object does not end with a
                         '/',i.e. it is a file, then this value will be used
                         by the system and no file name is generated.
                         For a restore operation the file name must be
                         included in the value of this object."

        VARIATION       tnSysBackupAndRestoreProtocol
            SYNTAX      INTEGER { sftp(2) }
            DEFVAL       { sftp }
            DESCRIPTION "Limited set of values."

        VARIATION       tnSysBackupAndRestoreUserId
            DESCRIPTION "The length must have a minimal length of 1 character
                         and a maximum length of 128 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnSysBackupAndRestorePassword
            DESCRIPTION "The length must have a minimal length of 1 character
                         and a maximum length of 128 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnSysBackupAndRestoreLastBackupFileCrc
            ACCESS      not-implemented
            DESCRIPTION "This object is not supported."

        VARIATION       tnSysBackupAndRestoreRemoteHostInetAddressType
            ACCESS      not-implemented
            DESCRIPTION "This object is not supported."

        VARIATION       tnSysBackupAndRestoreRemoteHostInetAddress
            ACCESS      not-implemented
            DESCRIPTION "This object is not supported."

        VARIATION       tnSysBackupAndRestoreLocalInfo
            ACCESS      not-implemented
            DESCRIPTION "This object is not supported."

        VARIATION       tnSysBackupAndRestoreLocalDelete
            ACCESS      not-implemented
            DESCRIPTION "This object is not supported."

        VARIATION       tnSysBackupAndRestorePort
            ACCESS      not-implemented
            DESCRIPTION "This object is not supported."

        VARIATION       tnSysBackupAndRestoreFallBackTimeStamp
            ACCESS      not-implemented
            DESCRIPTION "This object is not supported."

        VARIATION       tnSysDiscoveryFilename
            DESCRIPTION "When object tnSysDiscoveryTransferTraps
                         has value true(1), this object can contain
                         a file name (not ending with a slash) or a
                         directory name (must end with a slash).
                         When object tnSysDiscoveryTransferTraps
                         has value false(2), this object can only
                         contain a directory name (must end with a
                         slash)."

        VARIATION       tnSysDiscoveryMask
            ACCESS      not-implemented
            DESCRIPTION "This object is not supported."

        VARIATION       tnSysDiscoveryControl
            DESCRIPTION "This object is only applicable when object
                         tnSysDiscoveryTransferTraps has value
                         true(1)"

        VARIATION       tnSysDiscoveryErrorCode
            ACCESS      not-implemented
            DESCRIPTION "This object is not supported."

        VARIATION       tnSysDiscoveryBinnedStatsInterval
            SYNTAX      Unsigned32 (0..1)
            DESCRIPTION "Limited value range. Value 0 corresponds
                         with a 15 minute interval.
                         Value 1 corresponds with a 1 day interval.
                         This object is only applicable when object
                         tnSysDiscoveryTransferTraps has value
                         true(1)."

        VARIATION       tnSysDiscoveryBinnedStatsBin
            SYNTAX      Unsigned32 (1..96)
            DESCRIPTION "Limited value range.
                         Value 1 indicates the most recent history bin
                         for all PM points. Value 2 indicates the second
                         most recent history bin etc.
                         When tnSysDiscoveryBinnedStatsInterval is set to
                         value 0 (which corresponds to a 15 minute interval)
                         bin numbers in the range of 1..96 can be requested.
                         When tnSysDiscoveryBinnedStatsInterval is set to
                         value 1 (which corresponds to a 1 day interval)
                         only bin number 1 can be requested.
                         This object is only applicable when object
                         tnSysDiscoveryTransferTraps has value
                         true(1)."

        VARIATION       tnSysDiscoveryServerProtocol
            SYNTAX      INTEGER { sftp(2) }
            DEFVAL       { sftp }
            DESCRIPTION "Limited set of values."

        VARIATION       tnSysDiscoveryServerIp
            ACCESS      not-implemented
            DESCRIPTION "This object is not supported. It is superseded by
                         objects tnPsdSysDiscoveryServerAddrType and
                         tnPsdSysDiscoveryServerAddr."

        VARIATION       tnSysDiscoveryServerUserId
            DESCRIPTION "The length must have a minimal length of 1 character
                         and a maximum length of 128 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnSysDiscoveryServerPassword
            DESCRIPTION "The length must have a minimal length of 1 character
                         and a maximum length of 128 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnSysDiscoveryServerInetAddressType
            ACCESS      not-implemented
            DESCRIPTION "This object is not supported."

        VARIATION       tnSysDiscoveryServerInetAddress
            ACCESS      not-implemented
            DESCRIPTION "This object is not supported."

        VARIATION       tnSysDiscoveryPort
            ACCESS      not-implemented
            DESCRIPTION "This object is not supported."

        VARIATION       tnSysDiscoveryPrevious15minBinFilesTransfer
            SYNTAX      Unsigned32 (0..8)
            DESCRIPTION "Limited value range.
                         This object is only applicable when object
                         tnSysDiscoveryTransferTraps has value
                         false(2)"

        VARIATION       tnSysDiscoveryPrevious1dayBinFilesTransfer
            SYNTAX      Unsigned32 (0..7)
            DESCRIPTION "Limited value range.
                         This object is only applicable when object
                         tnSysDiscoveryTransferTraps has value
                         false(2)"

        VARIATION       tnSysDiscoveryTransferTimeOffset
            DESCRIPTION "This object is only applicable when object
                         tnSysDiscoveryTransferTraps has value
                         false(2)"

        VARIATION       tnSysDiscoveryTransferTraps
            DESCRIPTION "This object can only be changed from true(1) to
                         false(2). A change from false(2) to true(1) is
                         rejected and an error is returned."

        VARIATION       tnSyslogServerIpAddress
            ACCESS      not-implemented
            DESCRIPTION "This object is not supported."

        VARIATION       tnSyslogServerFacility
            ACCESS      not-implemented
            DESCRIPTION "This object is not supported."

        VARIATION       tnSyslogServerPort
            DESCRIPTION "This object can be included in an SNMP SET PDU
                         together with objects tnSyslogServerInetAddress
                         and tnSyslogServerInetAddress."

        VARIATION       tnSyslogServerInetAddressType
            DESCRIPTION "This object must always be included in an SNMP SET
                         PDU together with object tnSyslogServerInetAddress,
                         otherwise error 'inconsistent value' is returned.

                         This object can be included in an SNMP SET PDU
                         together with object tnSyslogServerPort. See the
                         VARIATION text for tnSyslogServerInetAddress below."

        VARIATION       tnSyslogServerInetAddress
            DESCRIPTION "This object must always be included in an SNMP SET
                         PDU together with object tnSyslogServerInetAddressType,
                         otherwise error 'inconsistent value' is returned.

                         Setting this object to a value different from the
                         null IPv4 address and different from the null IPv6
                         address, creates an entry in the tnSyslogServerTable.

                         Setting this object to a value equal to the null
                         IPv4 address or equal to the null IPv6 address,
                         deletes an entry from the tnSyslogServerTable.

                         This object can be included in an SNMP SET PDU
                         together with object tnSyslogServerPort. If object
                         tnSyslogServerPort is not included, port number 514
                         is used in case a tnSyslogServerTable entry is to
                         be created."

        VARIATION       tnSyslogServerType
            ACCESS      not-implemented
            DESCRIPTION "This object is not supported."

        VARIATION       tnSyslogServerDomain
            ACCESS      not-implemented
            DESCRIPTION "This object is not supported."

        VARIATION       tnSysTransferLogCommand
            DESCRIPTION "An SNMP GET action always returns noCmd(1).
                         This object must always be included in an SNMP SET
                         PDU together with object tnSysTransferLogType.
                         When in this PDU the value of tnSysTransferLogType
                         is set to ualPartial(8), this object must also be
                         included in this PDU with objects
                         tnSysTransferLogWindowStart and
                         tnSysTransferLogWindowStop. Otherwise error
                        'inconsistent value' is returned."

        VARIATION       tnSysTransferLogRemoteHostIp
            DESCRIPTION "This object must always be included in an SNMP SET
                         PDU together with object
                         tnSysTransferLogRemoteHostInetAddressType, of which
                         the value is set to ipv4(1). Otherwise error
                         'inconsistent value' is returned."

        VARIATION       tnSysTransferLogRemotePath
            DESCRIPTION "The value of this object is always assummed to be a
                         directory. In case the path does not end with a '/'
                         character the system will append a / automatically."

        VARIATION       tnSysTransferLogType
            SYNTAX      INTEGER { none(1),
                                  ual(3),
                                  ualPartial(8) }
            DESCRIPTION "Limited set of values.
                         An SNMP GET action always returns value none(1).
                         For a SNMP SET PDU request only the value ual(3) or
                         ualPartial(8) is allowed.
                         This object must always be included in an SNMP SET
                         PDU together with object tnSysTransferLogCommand.
                         When the value is set to ualPartial(8), this object
                         must also be included with objects
                         tnSysTransferLogWindowStart and
                         tnSysTransferLogWindowStop in this same PDU.
                         Otherwise error 'inconsistent value' is returned."

        VARIATION       tnSysTransferLogLastCommand
            SYNTAX      INTEGER { noCommand(1),
                                  ual(3),
                                  ualPartial(5) }
            DESCRIPTION "Limited set of values."

        VARIATION       tnSysTransferLogLastFileTimeStamp
            DESCRIPTION "Only the time stamp of the last successful file transfer
                         is recorded in this object."

        VARIATION       tnSysTransferLogProtocol
            SYNTAX      INTEGER { sftp(2) }
            DEFVAL       { sftp }
            DESCRIPTION "Limited set of values."

        VARIATION        tnSysTransferLogUserId
            DESCRIPTION "The length must have a minimal length of 1 character
                         and a maximum length of 32 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnSysTransferLogPassword
            DESCRIPTION "The length must have a minimal length of 1 character
                         and a maximum length of 32 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnSysTransferLogWindowStart
            DESCRIPTION "An SNMP GET action always returns value 0.
                         This object must always be included in an SNMP SET
                         PDU with objects tnSysTransferLogCommand,
                         tnSysTransferLogType and tnSysTransferLogWindowStop.
                         Also in this PDU, tnSysTransferLogType must be set to
                         value ualPartial(8). Otherwise, error 'inconsistent
                         value' is returned."

        VARIATION       tnSysTransferLogWindowStop
            DESCRIPTION "An SNMP GET action always returns value 0.
                         This object must always be included in an SNMP SET
                         PDU with objects tnSysTransferLogCommand,
                         tnSysTransferLogType and tnSysTransferLogWindowStart.
                         Also in this PDU, tnSysTransferLogType must be set to
                         value ualPartial(8). Otherwise, error 'inconsistent
                         value' is returned."

        VARIATION       tnSysTransferLogRemoteHostInetAddressType
            DESCRIPTION "When this object is set to value ipv4(1), this object
                         must always be included in an SNMP SET PDU with object
                         tnSysTransferLogRemoteHostIp, otherwise error
                         'inconsistent value' is returned.
                         When this object is set to value ipv6(2), this object
                         must always be included in an SNMP SET PDU with object
                         tnSysTransferLogRemoteHostInetAddress, otherwise
                         error 'inconsistent value' is returned."

        VARIATION       tnSysTransferLogRemoteHostInetAddress
            DESCRIPTION "This object must always be included in an SNMP SET
                         PDU together with object
                         tnSysTransferLogRemoteHostInetAddressType, of which
                         the value is set to ipv6(2). Otherwise error
                         'inconsistent value' is returned."

        VARIATION       tnSysTransferLogPort
            ACCESS      not-implemented
            DESCRIPTION "This object is not supported."

        VARIATION       tnSysNtpEnable
            ACCESS      not-implemented
            DESCRIPTION "This object is not supported."

        VARIATION       tnSysNtpSynched
            ACCESS      not-implemented
            DESCRIPTION "This object is not supported."

        VARIATION       tnSysNtpServerCurrentIpAddress
            ACCESS      not-implemented
            DESCRIPTION "This object is not supported."

        VARIATION       tnSysNtpServerCurrentInetAddressType
            ACCESS      not-implemented
            DESCRIPTION "This object is not supported."

        VARIATION       tnSysNtpServerCurrentInetAddress
            ACCESS      not-implemented
            DESCRIPTION "This object is not supported."

        VARIATION       tnSysNtpServerIdStatsKeyIndex
            ACCESS      not-implemented
            DESCRIPTION "This object is not supported."

        VARIATION       tnTransferPMDiscoveryRowStatus
            SYNTAX      INTEGER { active(1),
                                  createAndGo(4),
                                  destroy(6) }
            DESCRIPTION "Limited set of values."

        VARIATION       tnTransferPMDiscoveryFilename
            DESCRIPTION "This object can only contain a directory
                         name (must end with a slash)."

        VARIATION       tnTransferPMDiscoveryErrorCode
            ACCESS      not-implemented
            DESCRIPTION "This object is not supported."

        VARIATION       tnTransferPMDiscoveryServerProtocol
            SYNTAX      INTEGER { sftp(2) }
            DEFVAL       { sftp }
            DESCRIPTION "Limited set of values."

        VARIATION       tnTransferPMDiscoveryServerIp
            DESCRIPTION "This object must always be included in an SNMP
                         SET PDU together with object
                         tnTransferPMDiscoveryServerInetAddressType, otherwise
                         error 'inconsistent value' is returned."

        VARIATION       tnTransferPMDiscoveryServerUserId
            DESCRIPTION "The length must have a minimal length of 1 character
                         and a maximum length of 128 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnTransferPMDiscoveryServerPassword
            DESCRIPTION "The length must have a minimal length of 1 character
                         and a maximum length of 128 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnTransferPMDiscoveryServerInetAddressType
            DESCRIPTION "This object must always be included in an SNMP SET
                         PDU together with object tnTransferPMDiscoveryServerIp
                         when it is set to value ipv4(1), otherwise error
                         'inconsistent value' is returned.
                         This object must always be included in an SNMP SET PDU
                         together with object tnTransferPMDiscoveryServerInetAddress
                         when it is set to value ipv6(2), otherwise error
                         'inconsistent value' is returned."

        VARIATION       tnTransferPMDiscoveryServerInetAddress
            DESCRIPTION "This object must always be included in an SNMP
                         SET PDU together with object
                         tnTransferPMDiscoveryServerInetAddressType, otherwise
                         error 'inconsistent value' is returned."

        VARIATION       tnTransferPMDiscoveryPort
            ACCESS      not-implemented
            DESCRIPTION "This object is not supported."

        VARIATION       tnTransferPMDiscoveryPrevious15minBinFilesTransfer
            SYNTAX      Unsigned32 (0..8)
            DESCRIPTION "Limited value range."

        VARIATION       tnTransferPMDiscoveryPrevious1dayBinFilesTransfer
            SYNTAX      Unsigned32 (0..7)
            DESCRIPTION "Limited value range."

        VARIATION       tnTransferPMDiscoveryTransferTimeOffset
            SYNTAX      Unsigned32 (0..600)
            DESCRIPTION "Limited value range."

        VARIATION       tnTransferPMDiscovery15minBinFileTransferCount
            ACCESS      not-implemented
            DESCRIPTION "This object is not supported."

        VARIATION       tnTransferPMDiscovery1dayBinFileTransferCount
            ACCESS      not-implemented
            DESCRIPTION "This object is not supported."

        VARIATION       tnTransferPMDiscovery15minBinFileTransferFailureCount
            ACCESS      not-implemented
            DESCRIPTION "This object is not supported."

        VARIATION       tnTransferPMDiscovery1dayBinFileTransferFailureCount
            ACCESS      not-implemented
            DESCRIPTION "This object is not supported."

--
-- Capabilities for TROPIC-SOFTWARE-MIB
-- Based on MIB version:  R15.0-LatestMIBs-221105
--

    SUPPORTS            TROPIC-SOFTWARE-MIB
        INCLUDES        { tnSwNodeGroup }

        VARIATION       tnSwNodeControl
            SYNTAX      INTEGER { noCmd(1),
                                  audit(3),
                                  activate(4),
                                  commit(6),
                                  backout(7),
                                  load(8) }
            DESCRIPTION "Limited set of values."

        VARIATION       tnSwNodeForce
            ACCESS      not-implemented
            DESCRIPTION "This object is not supported."

        VARIATION       tnSwNodeNoBackup
            ACCESS      not-implemented
            DESCRIPTION "This object is not supported."

        VARIATION       tnSwNodeLastControlOperation
            SYNTAX      INTEGER { noCmd(1),
                                  audit(3),
                                  activate(4),
                                  commit(6),
                                  backout(7),
                                  load(8) }
            DESCRIPTION "Limited set of values."

        VARIATION       tnSwNodeLastControlOperationIntegerResult
            ACCESS      not-implemented
            DESCRIPTION "This object is not supported."

        VARIATION       tnSwNodeLastAuditTimeStamp
            DESCRIPTION "The value can only be set by the agent. An SNMP set
                         command is allowed but the value is ignored."

        VARIATION       tnSwNodeWorkingReleaseDir
            DESCRIPTION "Only the relative path is returned. This is equal to
                         the value that was used in an SNMP set request of
                         this object."

        VARIATION       tnSwNodeSwdlServerProtocol
            SYNTAX      INTEGER { sftp(2) }
            DEFVAL       { sftp }
            DESCRIPTION "Limited set of values."

        VARIATION       tnSwNodeSwdlServerIp
            ACCESS      not-implemented
            DESCRIPTION "This object is not supported. It is superseded
                         by objects tnPsdSoftwareRemoteHostAddrType and
                         tnPsdSoftwareRemoteHostAddr."

        VARIATION       tnSwNodeSwdlServerUserId
            DESCRIPTION "The length must have a minimal length of 1 character
                         and a maximum length of 128 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnSwNodeSwdlServerPassword
            DESCRIPTION "The length must have a minimal length of 1 character
                         and a maximum length of 128 characters.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnSwNodePartialLoadCommand
            ACCESS      not-implemented
            DESCRIPTION "This object is not supported."

        VARIATION       tnSwNodePartialLoadSupportedCardTypes
            ACCESS      not-implemented
            DESCRIPTION "This object is not supported."

        VARIATION       tnSwNodePartialLoadImgInstalledCardTypes
            ACCESS      not-implemented
            DESCRIPTION "This object is not supported."

        VARIATION       tnSwNodePartialLoadImgToBeInstalledCardTypes
            ACCESS      not-implemented
            DESCRIPTION "This object is not supported."

        VARIATION       tnSwNodePartialLoadActionResult
            ACCESS      not-implemented
            DESCRIPTION "This object is not supported."

        VARIATION       tnSwNodePartialLoadActionPercentCompleted
            ACCESS      not-implemented
            DESCRIPTION "This object is not supported."

        VARIATION       tnSwNodeSwdlServerInetAddressType
            ACCESS      not-implemented
            DESCRIPTION "This object is not supported."

        VARIATION       tnSwNodeSwdlServerInetAddress
            ACCESS      not-implemented
            DESCRIPTION "This object is not supported."

        VARIATION       tnSwNodeControlStatus
            ACCESS      not-implemented
            DESCRIPTION "This object is not supported."

        VARIATION       tnSwNodePort
            ACCESS      not-implemented
            DESCRIPTION "This object is not supported."

        VARIATION       tnSwNodeUrl
            ACCESS      not-implemented
            DESCRIPTION "This object is not supported."

        VARIATION       tnSwNodeLoadType
            ACCESS      not-implemented
            DESCRIPTION "This object is not supported."

        VARIATION       tnSwNodeUrlLoadType
            ACCESS      not-implemented
            DESCRIPTION "This object is not supported."

        VARIATION       tnSwNodeMigrateFileName
            ACCESS      not-implemented
            DESCRIPTION "This object is not supported."

--
-- Capabilities for TROPIC-USERMGMT-MIB
-- Based on MIB version:  R15.0-LatestMIBs-221105
--

    SUPPORTS            TROPIC-USERMGMT-MIB
        INCLUDES        { tnUserGroup,
                          tnUserMgmtGlobalGroup }

        VARIATION       tnUserName
            DESCRIPTION "The length has a minimum of 1 character and a maximum
                         of 32 characters. From ITU Recommendation T.50 the G0
                         character set (values 0x21 - 0x7E) is supported with
                         the following exceptions:
                          - value 0x22: double quotes
                          - value 0x27: single quote
                          - value 0x3f: question mark
                          - value 0x5c: backslash
                         The reason of these exceptions is that those
                         characters conflict with the Command Line Interface
                         (CLI)."

        VARIATION       tnUserRowStatus
            SYNTAX      INTEGER { active(1),
                                  notInService(2),
                                  createAndGo(4),
                                  destroy(6) }
            DESCRIPTION "Limited set of values.
                         When set to value createAndGo(4), this object must
                         always be included in an SNMP SET PDU together with
                         objects tnUserAccessLevel and tnUserPassword,
                         otherwise error 'inconsistent value' is returned.

                         Setting the value to notInService(2) or destroy(6) is
                         rejected in case this would lead to the removal of the
                         last active user with administrator access rights, i.e.
                         with tnUserAccessLevel equal to value administrator(2).
                         User 'factorydefaultuser', who has administrator access
                         rights, is excluded from this check as it is not
                         capable of managing user accounts."

        VARIATION       tnUserAccessLevel
            SYNTAX      INTEGER { administrator(2),
                                  provisioner(3),
                                  observer(4) }
            DESCRIPTION "Limited set of values.
                         This object must always be included in an SNMP SET PDU
                         together with objects tnUserPassword and tnRowStatus,
                         of which the latter must be set to value createAndGo(4),
                         otherwise error 'inconsistent value' is returned."

        VARIATION       tnUserPassword
            DESCRIPTION "The password must have a minimal length of 12 characters
                         and a maximum length of 32 characters. A valid password
                         must contain at least one lowercase alphabetic, one
                         uppercase alphabetic, one numeric, and one special
                         character.
                        The first character of the password can be any alphabetic,
                         numeric, or a valid special character. Only exception is
                         that the first character # (pound sign) of the password
                         is not allowed.
                         The password shall not have more than 3 consecutive
                         identical characters.
                         The password shall not be the same as, nor the reverse
                         of, the associated user name.
                         The following ASCII characters from ITU Recommendation
                         T.50 are supported:
                         The G0 character set - values 0x21 - 0x7E, with the
                         following exceptions:
                         - value 0x22: double quotes
                         - value 0x27: single quote
                         - value 0x3f: question mark
                         - value 0x5c: backslash
                         The reason of these exceptions is that those
                         characters conflict with the Command Line Interface
                         (CLI).
                         When set, this object must be either :
                          - the only object in an SNMP SET PDU
                          - be included in an SNMP SET PDU together with objects
                            tnUserAccessLevel and tnRowStatus, of which the
                            latter must be set to value createAndGo(4),
                            otherwise error 'inconsistent value' is returned."

        VARIATION       tnUserLastLoginDateAndTime
            ACCESS      not-implemented
            DESCRIPTION "This object is not supported."

        VARIATION       tnUserLastLoginTerminalIP
            ACCESS      not-implemented
            DESCRIPTION "This object is not supported."

        VARIATION       tnUserSessionTimeout
            ACCESS      not-implemented
            DESCRIPTION "This object is not supported."

        VARIATION       tnUserPasswordAge
            ACCESS      not-implemented
            DESCRIPTION "This object is not supported."

        VARIATION       tnUserPasswordGraceInterval
            ACCESS      not-implemented
            DESCRIPTION "This object is not supported."

        VARIATION       tnUserPasswordGraceLogins
            ACCESS      not-implemented
            DESCRIPTION "This object is not supported."

        VARIATION       tnUserPasswordAging
            ACCESS      not-implemented
            DESCRIPTION "This object is not supported."

        VARIATION       tnUserToolsLinux
            ACCESS      not-implemented
            DESCRIPTION "This object is not supported."

        VARIATION       tnUserMaxSession
            SYNTAX      Unsigned32 ( 0..10 )
            DESCRIPTION "Limited value range."

        VARIATION       tnUserPasswordForce
            ACCESS      not-implemented
            DESCRIPTION "This object is not supported."

        VARIATION       tnUserMgmtSysMinPasswordLength
            ACCESS      not-implemented
            DESCRIPTION "This object is not supported."

        VARIATION       tnUserMgmtSysMaxPasswordLength
            ACCESS      not-implemented
            DESCRIPTION "This object is not supported."

        VARIATION       tnUserMgmtSysSessionTimeOut
            SYNTAX      Unsigned32 (1..999)
            DESCRIPTION "Limited set of values, range 1 - 999."

        VARIATION       tnUserMgmtSysSessionFailedMaxLogins
            SYNTAX      Unsigned32 (0..15)
            DESCRIPTION "Limited set of values, range 0 - 15."

        VARIATION       tnUserMgmtSysLoginInactivityTimeOut
            ACCESS      not-implemented
            DESCRIPTION "This object is not supported."

        VARIATION       tnUserMgmtSysMinIntervalInvalidLogin
            ACCESS      not-implemented
            DESCRIPTION "This object is not supported."

        VARIATION       tnUserMgmtSysSessionLogoff
            ACCESS      not-implemented
            DESCRIPTION "This object is not supported."

        VARIATION       tnUserMgmtSysPasswordAging
            SYNTAX      Unsigned32 (0..999)
            DESCRIPTION "Limited set of values, range 0 - 999."

        VARIATION       tnUserMgmtSysPasswordAgingGraceInterval
            ACCESS      not-implemented
            DESCRIPTION "This object is not supported."

        VARIATION       tnUserMgmtSysPasswordAgingGraceLogins
            ACCESS      not-implemented
            DESCRIPTION "This object is not supported."

        VARIATION       tnUserMgmtSysPasswordObsolescenceInterval
            SYNTAX      Unsigned32 (0..999)
            DESCRIPTION "Limited set of values, range 0 - 999."

        VARIATION       tnUserMgmtSysMaxSession
            ACCESS      not-implemented
            DESCRIPTION "This object is not supported."

        VARIATION       tnUserMgmtSysChangePasswordOnFirstLogin
            ACCESS      not-implemented
            DESCRIPTION "This object is not supported."

        VARIATION       tnUserMgmtSysHistorySize
            ACCESS      not-implemented
            DESCRIPTION "This object is not supported."

--
-- Capabilities for TROPIC-ACCESSPORT-MIB
-- Based on MIB version:  R15.0-LatestMIBs-221105
--

    SUPPORTS            TROPIC-ACCESSPORT-MIB
        INCLUDES        { tnAccessPortGroup,
                          tnIfGroup }

        VARIATION       tnAccessPortDescr
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnAccessPortStatusLEDColor
            ACCESS      not-implemented
            DESCRIPTION "This object is not supported."

        VARIATION       tnAccessPortStatusLEDState
            ACCESS      not-implemented
            DESCRIPTION "This object is not supported."

        VARIATION       tnAccessPortOperationalCapability
            ACCESS      not-implemented
            DESCRIPTION "This object is not supported."

        VARIATION       tnAccessPortStateQualifier
            ACCESS      not-implemented
            DESCRIPTION "This object is not supported."

        VARIATION       tnAccessPortFarEndAddress
            ACCESS      not-implemented
            DESCRIPTION "This object is not supported."

        VARIATION       tnAccessPortFarEndIfIndex
            ACCESS      not-implemented
            DESCRIPTION "This object is not supported."

        VARIATION       tnAccessPortFarEndType
            ACCESS      not-implemented
            DESCRIPTION "This object is not supported."

        VARIATION       tnAccessPortDirection
            ACCESS      not-implemented
            DESCRIPTION "This object is not supported."

        VARIATION       tnAccessPortAINS
            ACCESS      not-implemented
            DESCRIPTION "This object is not supported."

        VARIATION       tnAccessPortAINSDebounceTime
            ACCESS      not-implemented
            DESCRIPTION "This object is not supported."

        VARIATION       tnAccessPortUsingSysAINSDebounceTime
            ACCESS      not-implemented
            DESCRIPTION "This object is not supported."

        VARIATION       tnAccessPortAINSDebounceTimeRemaining
            ACCESS      not-implemented
            DESCRIPTION "This object is not supported."

        VARIATION       tnAccessPortIsDomainEdgePort
            ACCESS      not-implemented
            DESCRIPTION "This object is not supported."

        VARIATION       tnAccessPortFarEndAddressConnFrom
            ACCESS      not-implemented
            DESCRIPTION "This object is not supported."

        VARIATION       tnAccessPortFarEndIfIndexConnFrom
            ACCESS      not-implemented
            DESCRIPTION "This object is not supported."

        VARIATION       tnAccessPortFarEndTypeConnFrom
            ACCESS      not-implemented
            DESCRIPTION "This object is not supported."

        VARIATION       tnAccessPortExtAmpIpAddressIn
            ACCESS      not-implemented
            DESCRIPTION "This object is not supported."

        VARIATION       tnAccessPortExtAmpIpAddressOut
            ACCESS      not-implemented
            DESCRIPTION "This object is not supported."

        VARIATION       tnAccessPortWtocmConnLoss
            ACCESS      not-implemented
            DESCRIPTION "This object is not supported."

        VARIATION       tnAccessPortWtocmConnAddress
            ACCESS      not-implemented
            DESCRIPTION "This object is not supported."

        VARIATION       tnAccessPortOppDirectionPortAddress
            ACCESS      not-implemented
            DESCRIPTION "This object is not supported."

        VARIATION       tnAccessPortIsValidInternalOTSXcEndpoint
            ACCESS      not-implemented
            DESCRIPTION "This object is not supported."

        VARIATION       tnAccessPortWtDomainNumber
            ACCESS      not-implemented
            DESCRIPTION "This object is not supported."

        VARIATION       tnAccessPortHasMpoConnector
            ACCESS      not-implemented
            DESCRIPTION "This object is not supported."

        VARIATION       tnAccessPortMpoConnectorPortOutIfIndex
            ACCESS      not-implemented
            DESCRIPTION "This object is not supported."

        VARIATION       tnAccessPortMpoConnectorPortInIfIndex
            ACCESS      not-implemented
            DESCRIPTION "This object is not supported."

        VARIATION       tnAccessPortIsMpo
            ACCESS      not-implemented
            DESCRIPTION "This object is not supported."

        VARIATION       tnAccessPortMonOcmConnAddress
            ACCESS      not-implemented
            DESCRIPTION "This object is not supported."

        VARIATION       tnAccessPortAlmProfName
            ACCESS      not-implemented
            DESCRIPTION "This object is not supported. The PSD ASAP Fault
                         Profile implementation is used."

        VARIATION       tnAccessPortmfcTemperature
            ACCESS      not-implemented
            DESCRIPTION "This object is not supported."

        VARIATION       tnAccessPortmfcNominalPressure
            ACCESS      not-implemented
            DESCRIPTION "This object is not supported."

        VARIATION       tnAccessPortmfcDifferentialPressure
            ACCESS      not-implemented
            DESCRIPTION "This object is not supported."

        VARIATION       tnAccessFilterAmbientTemperature
            ACCESS      not-implemented
            DESCRIPTION "This object is not supported."

        VARIATION       tnAccessFilterPressure
            ACCESS      not-implemented
            DESCRIPTION "This object is not supported."

        VARIATION       tnAccessFilterRecorded
            ACCESS      not-implemented
            DESCRIPTION "This object is not supported."

        VARIATION       tnAccessFilterCalibrated
            ACCESS      not-implemented
            DESCRIPTION "This object is not supported."

        VARIATION       tnAccessFilterAltitude
            ACCESS      not-implemented
            DESCRIPTION "This object is not supported."

        VARIATION       tnAccessFilterRecordTime
            ACCESS      not-implemented
            DESCRIPTION "This object is not supported."

        VARIATION       tnAccessFilterCalibrateTime
            ACCESS      not-implemented
            DESCRIPTION "This object is not supported."

        VARIATION       tnAccessFilterScheduledTime
            ACCESS      not-implemented
            DESCRIPTION "This object is not supported."

        VARIATION       tnAccessPortL2FarEndIfIndex
            ACCESS      not-implemented
            DESCRIPTION "This object is not supported."

        VARIATION       tnAccessPortL2FarEndMacAddress
            ACCESS      not-implemented
            DESCRIPTION "This object is not supported."

        VARIATION       tnAccessPortDirectionCapability
            ACCESS      not-implemented
            DESCRIPTION "This object is not supported."

        VARIATION       tnAccessPortCpriMappingType
            ACCESS      not-implemented
            DESCRIPTION "This object is not supported."

        VARIATION       tnAccessPortFecType
            ACCESS      not-implemented
            DESCRIPTION "This object is not supported."

        VARIATION       tnAccessPortFecBypassInd
            ACCESS      not-implemented
            DESCRIPTION "This object is not supported."

        VARIATION       tnAccessPortCpriRole
            ACCESS      not-implemented
            DESCRIPTION "This object is not supported."

        VARIATION       tnAccessPortAseMode
            ACCESS      not-implemented
            DESCRIPTION "This object is not supported."

        VARIATION       tnAccessPortRole
            ACCESS      not-implemented
            DESCRIPTION "This object is not supported."

        VARIATION       tnAccessPortFacilityDescriptorName
            ACCESS      not-implemented
            DESCRIPTION "This object is not supported."

        VARIATION       tnAccessPortFacilityDescriptorDesc
            ACCESS      not-implemented
            DESCRIPTION "This object is not supported."

        VARIATION       tnAccessPortFacilityDescriptorCirId
            ACCESS      not-implemented
            DESCRIPTION "This object is not supported."

        VARIATION       tnAccessPortAlienWavebank
            ACCESS      not-implemented
            DESCRIPTION "This object is not supported."

        VARIATION       tnAccessPortModuleReset
            ACCESS      not-implemented
            DESCRIPTION "This object is not supported."

        VARIATION       tnAccessPortFacilityDesCustLifeCycleState
            ACCESS      not-implemented
            DESCRIPTION "This object is not supported."

        VARIATION       tnAccessPortSummaryStatusLEDColor
            ACCESS      not-implemented
            DESCRIPTION "This object is not supported."

        VARIATION       tnAccessPortSummaryStatusLEDState
            ACCESS      not-implemented
            DESCRIPTION "This object is not supported."

        VARIATION       tnIfType
            SYNTAX      INTEGER { unknown(3),
                                  otu1(10),
                                  otu2(11),
                                  gige(12),
                                  tenGige(13),
                                  dcn(40),
                                  otu2e(46),
                                  lagGroup(51) }
            DESCRIPTION "Limited set of values.
                         The value is fixed and determined by the system.

                         There is an exception for system modes
                         ethNid1GbEor10GbEClient10GbENetworkMode and
                         otnNid1GbEor10GbEClientOtu2OduFlexNetworkMode.
                         In these system modes it is possible to modify the
                         value of this object for the logical CLIENT port to
                         either value gige(12) or tenGige(13). CLIENT1 and
                         CLIENT2 will derive their value from the logical
                         CLIENT port."

        VARIATION       tnIfSupportedTypes
            DESCRIPTION "Limited set of values. The following bits may be set:
                         otu1(6)
                         otu2(7)
                         gige(8)
                         tenGige(9)
                         dcn(36)
                         otu2e(42)
                         lagGroup(47)"

        VARIATION       tnIfForceAdminStatus
            ACCESS      not-implemented
            DESCRIPTION "This object is not supported."

        VARIATION       tnIfnumofTimeSlots
            ACCESS      not-implemented
            DESCRIPTION "This object is not supported."

        VARIATION       tnIfAlmProfName
            ACCESS      not-implemented
            DESCRIPTION "This object is not supported."

--
-- Capabilities for TROPIC-OPTICALPORT-MIB
-- Based on MIB version:  R15.0-LatestMIBs-221105
--

    SUPPORTS            TROPIC-OPTICALPORT-MIB
        INCLUDES        { tnNetworkPortConfigGroup,
                          tnLoopbackPortGroup,
                          tnDwdmCmnClientPortConfigGroup }

        VARIATION       tnNwPortProgrammedChannel
            ACCESS      read-only
            DESCRIPTION "Setting of this object is not allowed.
                         The value represents the actual by the SFP applied
                         channel number. Object tnPsdSfpProgrammedChannel
                         (TROPIC-PSD-MIB) must be used to configure the SFP
                         channel number."

        VARIATION       tnNwPortChannelRx
            ACCESS      not-implemented
            DESCRIPTION "This object is not supported."

        VARIATION       tnNwPortChannelSpacing
            ACCESS      not-implemented
            DESCRIPTION "This object is not supported."

        VARIATION       tnNwPortLaserOffRequest
            ACCESS      not-implemented
            DESCRIPTION "This object is not supported."

        VARIATION       tnNwPortForcedLaserState
            ACCESS      not-implemented
            DESCRIPTION "This object is not supported."

        VARIATION       tnNwPortProgrammedITUNumOffsetTx
            ACCESS      not-implemented
            DESCRIPTION "This object is not supported."

        VARIATION       tnNwPortProgrammedITUNumOffsetRx
            ACCESS      not-implemented
            DESCRIPTION "This object is not supported."

        VARIATION       tnNwPortProgrammedITUNumOffsetGridStepSize
            ACCESS      not-implemented
            DESCRIPTION "This object is not supported."

        VARIATION       tnNwPortCalculatedRxFreq
            ACCESS      not-implemented
            DESCRIPTION "This object is not supported."

        VARIATION       tnNwPortCalculatedTxFreq
            ACCESS      not-implemented
            DESCRIPTION "This object is not supported."

        VARIATION       tnNwPortLinkSpan
            ACCESS      not-implemented
            DESCRIPTION "This object is not supported."

        VARIATION       tnNwPortChannelTxLane
            ACCESS      not-implemented
            DESCRIPTION "This object is not supported."

        VARIATION       tnNwPortChannelRxLane
            ACCESS      not-implemented
            DESCRIPTION "This object is not supported."

        VARIATION       tnNwPortRxFineOffSet
            ACCESS      not-implemented
            DESCRIPTION "This object is not supported."

        VARIATION       tnNwPortTxFineOffSet
            ACCESS      not-implemented
            DESCRIPTION "This object is not supported."

        VARIATION       tnLoopbackPortDLEB
            DESCRIPTION "The interface must first be put in maintenance (i.e.
                         ifAdminStatus must be set to the value testing(3))
                         before this loopback can be applied.
                         In case the ifAdminStatus does not have the value
                         testing, and this loopback is attempted to be
                         applied, an error is returned.
                         A diagnostic/terminal loopback can not be enabled
                         when a line/facility loopback is currently enabled
                         for the same interface."

        VARIATION       tnLoopbackPortLLEB
            DESCRIPTION "The interface must first be put in maintenance (i.e.
                         ifAdminStatus must be set to the value testing(3))
                         before this loopback can be applied.
                         In case the ifAdminStatus does not have the value
                         testing, and this loopback is attempted to be
                         applied, an error is returned.
                         A line/facility loopback can not be enabled when a
                         diagnostic/terminal loopback is currently enabled
                         for the same interface."

        VARIATION       tnLoopbackPortTSEB
            ACCESS      not-implemented
            DESCRIPTION "This object is not supported."

        VARIATION       tnLoopbackPortFacTwo
            ACCESS      not-implemented
            DESCRIPTION "This object is not supported."

        VARIATION       tnDwdmCmnClientPortLosProp
            DESCRIPTION "Changing the value of this object is only allowed for
                         the logical CLIENT interface and is only supported
                         in the following system modes:
                         - otnNid1GbeClientOtu1NetworkMode
                         - otnNid1GbeClientOtu2NetworkMode
                         - otnNid10GbeClientOtu2NetworkMode
                         - otnNid10GbeClientOtu2eNetworkMode
                         - otnNid1GbEor10GbEClientOtu2OduFlexNetworkMode"

        VARIATION       tnDwdmCmnClientPortTs1
            ACCESS      not-implemented
            DESCRIPTION "This object is not supported."

        VARIATION       tnDwdmCmnClientPortTs2
            ACCESS      not-implemented
            DESCRIPTION "This object is not supported."

        VARIATION       tnDwdmCmnClientPortOchOtu2FecMode
            ACCESS      not-implemented
            DESCRIPTION "This object is not supported."

        VARIATION       tnDwdmCmnClientPortOchOtu2Rate
            ACCESS      not-implemented
            DESCRIPTION "This object is not supported."

        VARIATION       tnDwdmCmnClientPortOtu2TransmittedTti
            ACCESS      not-implemented
            DESCRIPTION "This object is not supported."

        VARIATION       tnDwdmCmnClientPortOtu2ExpectedTti
            ACCESS      not-implemented
            DESCRIPTION "This object is not supported."

        VARIATION       tnDwdmCmnClientPortOtu2TimConsequenceAction
            ACCESS      not-implemented
            DESCRIPTION "This object is not supported."

        VARIATION       tnDwdmCmnClientPortOtu2TimDetectionMode
            ACCESS      not-implemented
            DESCRIPTION "This object is not supported."

        VARIATION       tnDwdmCmnClientPortOdu2TransmittedTti
            ACCESS      not-implemented
            DESCRIPTION "This object is not supported."

        VARIATION       tnDwdmCmnClientPortOdu2ExpectedTti
            ACCESS      not-implemented
            DESCRIPTION "This object is not supported."

        VARIATION       tnDwdmCmnClientPortOdu2TimDetectionMode
            ACCESS      not-implemented
            DESCRIPTION "This object is not supported."

        VARIATION       tnDwdmCmnClientPortProtectionTs1
            ACCESS      not-implemented
            DESCRIPTION "This object is not supported."

        VARIATION       tnDwdmCmnClientPortProtectionTs2
            ACCESS      not-implemented
            DESCRIPTION "This object is not supported."

        VARIATION       tnDwdmCmnClientPortTsMap
            ACCESS      not-implemented
            DESCRIPTION "This object is not supported."

        VARIATION       tnDwdmCmnClientPortContainer
            SYNTAX      INTEGER { none(1),
                                  oduflex(5),
                                  odu2(6),
                                  odu2e(7) }
            DESCRIPTION "Limited set of values.
                         This object is only instantiated for 10Gbe clients
                         and is used to indicate whether an ODUFlex, ODU2
                         or ODU2e is used."

        VARIATION       tnDwdmCmnClientPortCSF
            ACCESS      not-implemented
            DESCRIPTION "This object is not supported."

        VARIATION       tnDwdmCmnClientPortSSF
            ACCESS      not-implemented
            DESCRIPTION "This object is not supported."

        VARIATION       tnDwdmCmnClientPortScramMode
            ACCESS      not-implemented
            DESCRIPTION "This object is not supported."

        VARIATION       tnDwdmCmnClientPortDegInterval
            ACCESS      not-implemented
            DESCRIPTION "This object is not supported."

        VARIATION       tnDwdmCmnClientPortDegThreshold
            ACCESS      not-implemented
            DESCRIPTION "This object is not supported."

        VARIATION       tnDwdmCmnClientPortHoldOffTimer
            ACCESS      not-implemented
            DESCRIPTION "This object is not supported."

        VARIATION       tnDwdmCmnClientPortYcableMode
            ACCESS      not-implemented
            DESCRIPTION "This object is not supported."

        VARIATION       tnDwdmCmnClientPortEthFecMode
            ACCESS      not-implemented
            DESCRIPTION "This object is not supported."

        VARIATION       tnDwdmCmnClientPortHoldOffTimerValue
            ACCESS      not-implemented
            DESCRIPTION "This object is not supported."

        VARIATION       tnDwdmCmnClientPortFlsState
            ACCESS      not-implemented
            DESCRIPTION "This object is not supported."

        VARIATION       tnDwdmCmnClientPortServerPort
            ACCESS      not-implemented
            DESCRIPTION "This object is not supported."

        VARIATION       tnDwdmCmnClientPortInOpsbAction
            ACCESS      not-implemented
            DESCRIPTION "This object is not supported."

        VARIATION       tnDwdmCmnClientPortSSFDelayTimer
            ACCESS      not-implemented
            DESCRIPTION "This object is not supported."

        VARIATION       tnDwdmCmnClientPortFecBypassInd
            ACCESS      not-implemented
            DESCRIPTION "This object is not supported."

        VARIATION       tnDwdmCmnClientPortSSFDelayCa
            ACCESS      not-implemented
            DESCRIPTION "This object is not supported."

        VARIATION       tnDwdmCmnClientPortSsdca
            ACCESS      not-implemented
            DESCRIPTION "This object is not supported."

        VARIATION       tnDwdmCmnClientPortFlexGfpSize
            ACCESS      not-implemented
            DESCRIPTION "This object is not supported."

        VARIATION       tnDwdmCmnClientPortSdiRate
            ACCESS      not-implemented
            DESCRIPTION "This object is not supported."

        VARIATION       tnDwdmCmnClientPortGfpFcs
            ACCESS      not-implemented
            DESCRIPTION "This object is not supported."

        VARIATION       tnDwdmCmnClientPortCSFHoldOff
            ACCESS      not-implemented
            DESCRIPTION "This object is not supported."

        VARIATION       tnDwdmCmnClientPortSSFHoldOff
            ACCESS      not-implemented
            DESCRIPTION "This object is not supported."

        VARIATION       tnDwdmCmnClientPortSignalMode
            ACCESS      not-implemented
            DESCRIPTION "This object is not supported."

        VARIATION       tnDwdmCmnClientPortCSFDelayTimer
            ACCESS      not-implemented
            DESCRIPTION "This object is not supported."

        VARIATION       tnDwdmCmnClientPortSSFOnOCIAction
            ACCESS      not-implemented
            DESCRIPTION "This object is not supported."

--
-- Capabilities for OPT-IF-MIB
-- Based on MIB version:  R15.0-LatestMIBs-221105
--

    SUPPORTS            OPT-IF-MIB
        INCLUDES        { optIfOTUkSinkGroup }

        VARIATION       optIfOTUkSAPIExpected
            ACCESS      not-implemented
            DESCRIPTION "This object is not supported. It is superseded by
                         tnPsdOtukSapiExpected."

        VARIATION       optIfOTUkTraceIdentifierAccepted
            ACCESS      not-implemented
            DESCRIPTION "This object is not supported."

--
-- Capabilities for TROPIC-OTUODU-MIB
-- Based on MIB version:  R15.0-LatestMIBs-221105
--

    SUPPORTS            TROPIC-OTUODU-MIB
        INCLUDES        { tnOtukGroup }

        VARIATION       tnOtukFecMode
            SYNTAX      INTEGER { noFec(1), g709Fec(2) }
            DEFVAL      { g709Fec }
            DESCRIPTION "Limited set of values."

        VARIATION       tnOtukIncRes
            ACCESS      not-implemented
            DESCRIPTION "This object is not supported."

        VARIATION       tnOtukAdminStatus
            ACCESS      not-implemented
            DESCRIPTION "This object is not supported."

        VARIATION       tnOtukStateAINS
            ACCESS      not-implemented
            DESCRIPTION "This object is not supported."

        VARIATION       tnOtukOperStatus
            ACCESS      not-implemented
            DESCRIPTION "This object is not supported."

        VARIATION       tnOtukStateQualifier
            ACCESS      not-implemented
            DESCRIPTION "This object is not supported."

        VARIATION       tnOtukOperationalCapability
            ACCESS      not-implemented
            DESCRIPTION "This object is not supported."

        VARIATION       tnOtukAINSDebounceTime
            ACCESS      not-implemented
            DESCRIPTION "This object is not supported."

        VARIATION       tnOtukUsingSysAINSDebounceTime
            ACCESS      not-implemented
            DESCRIPTION "This object is not supported."

        VARIATION       tnOtukAINSDebounceTimeRemaining
            ACCESS      not-implemented
            DESCRIPTION "This object is not supported."

        VARIATION       tnOtukPreFec
            ACCESS      not-implemented
            DESCRIPTION "This object is not supported."

        VARIATION       tnOtukPostFec
            ACCESS      not-implemented
            DESCRIPTION "This object is not supported."

        VARIATION       tnOtukAsymInterworking
            ACCESS      not-implemented
            DESCRIPTION "This object is not supported."

        VARIATION       tnOtukDegThr
            SYNTAX      Unsigned32 (1..82300)
            DESCRIPTION "Depending on the system mode (tnPsdSystemMode) the
                         following ranges are allowed:
                         - otnNid1GbeClientOtu1NetworkMode(2)   : [1..20420]
                         - otnNid1GbeClientOtu2NetworkMode(3)   : [1..82026]
                         - otnNid10GbeClientOtu2NetworkMode(4)  : [1..82026]
                         - otnNid10GbeClientOtu2eNetworkMode(5) : [1..82300]
                         - otnNidOtu1ClientOtu1NetworkMode(6)   : [1..20420]
                         - otnNidOtu2ClientOtu2NetworkMode(7)   : [1..82026]
                         - otnNidOtu2eClientOtu2eNetworkMode(8) : [1..82300]
                         - otnNid1GbEor10GbEClientOtu2OduFlexNetworkMode(10) : [1..82026]."

        VARIATION       tnOtukDegM
            SYNTAX      Unsigned32 (2..10)
            DESCRIPTION "Limited set of values."

        VARIATION       tnOtukDapiAccepted
            ACCESS      not-implemented
            DESCRIPTION "This object is not supported. It is superseded by
                         tnPsdOtukDapiAccepted."

        VARIATION       tnOtukDapiExpected
            ACCESS      not-implemented
            DESCRIPTION "This object is not supported. It is superseded by
                         tnPsdOtukDapiExpected."

        VARIATION       tnOtukDapiTransmitted
            ACCESS      not-implemented
            DESCRIPTION "This object is not supported. It is superseded by
                         tnPsdOtukDapiTransmitted."

        VARIATION       tnOtukOsTransmitted
            DESCRIPTION "32 octets must be provided, otherwise the request is
                         rejected and an error is returned."

        VARIATION       tnOtuAlmProfName
            ACCESS      not-implemented
            DESCRIPTION "This object is not supported. The PSD ASAP Fault
                         Profile implementation is used."

        VARIATION       tnOtuServerPort
            ACCESS      not-implemented
            DESCRIPTION "This object is not supported."

        VARIATION       tnOtukMgracd
            ACCESS      not-implemented
            DESCRIPTION "This object is not supported."

        VARIATION       tnOtukType
            ACCESS      not-implemented
            DESCRIPTION "This object is not supported."

        VARIATION       tnOtuOtsigId
            ACCESS      not-implemented
            DESCRIPTION "This object is not supported."

        VARIATION       tnOtuChanPoolIfIndex
            ACCESS      not-implemented
            DESCRIPTION "This object is not supported."

        VARIATION       tnOtuFacilityDescriptorName
            ACCESS      not-implemented
            DESCRIPTION "This object is not supported."

        VARIATION       tnOtuFacilityDescriptorDesc
            ACCESS      not-implemented
            DESCRIPTION "This object is not supported."

        VARIATION       tnOtuFacilityDescriptorCirId
            ACCESS      not-implemented
            DESCRIPTION "This object is not supported."

        VARIATION       tnOtuFacilityDescriptorConnPtId
            ACCESS      not-implemented
            DESCRIPTION "This object is not supported."

        VARIATION       tnOtuFacilityDescCustLifeCycleState
            ACCESS      not-implemented
            DESCRIPTION "This object is not supported."

        VARIATION       tnOtuFacilityDescAdminState
            ACCESS      not-implemented
            DESCRIPTION "This object is not supported."

--
-- Capabilities for TROPIC-OTH-MIB
-- Based on MIB version:  R15.0-LatestMIBs-221105
--

    SUPPORTS            TROPIC-OTH-MIB
        INCLUDES        { tnOthOdukTtpGroup,
                          tnOthOdukNimGroup,
                          tnOthOdukTGroup,
                          tnOthOdukApsGroup,
                          tnOthOdukXcGroup }

        VARIATION       tnOthIfIndex
            DESCRIPTION "In the value of this object, the shelf, slot and
                         HO-ODU number values are encoded as follows:
                         shelf         = (value & 0xFF000000) >> 24
                         slot          = (value & 0x00FF0000) >> 16
                         HO-ODU number = (value & 0x0000FF00) >>  8

                         Shelf:
                         The value of shelf is fixed set to 1.

                         Slot:
                         The value of slot is set fixed to 1 except for
                         the virtual objects of ODUkP (path) and ODUkPm (NIM).
                         The following Ethernet Client OTN Network system modes
                         have a VIRTUAL(71) ODUkP (path) object defined
                         (i.e. entry in tnOthOdukTtpTable) and have the slot
                         value set to 71:
                         - otnNid1GbeClientOtu1NetworkMode(2)
                         - otnNid1GbeClientOtu2NetworkMode(3)
                         - otnNid10GbeClientOtu2NetworkMode(4)
                         - otnNid10GbeClientOtu2eNetworkMode(5)
                         Ethernet Client OTN Network system mode
                         otnNid1GbEor10GbEClientOtu2OduFlexNetworkMode(10)
                         has a VIRTUAL(71) ODUkP (path) object, as well as
                         ODUkP (path) and ODUkPm (NIM) objects related to
                         the Network ports.
                         OTN Client OTN Network system modes do not have a
                         ODUkP (path) object defined (i.e. no entries in
                         tnOthOdukTtpTable) instead there is a VIRTUAL(71)
                         ODUkPm (NIM) object defined (tnOthOdukNimTable).
                         For this object the slot value is set to 71.
                         This applies to the following system modes:
                         - otnNidOtu1ClientOtu1NetworkMode(6)
                         - otnNidOtu2ClientOtu2NetworkMode(7)
                         - otnNidOtu2eClientOtu2eNetworkMode(8)

                         HO-ODU number:
                         For HO-ODU number only the portID part is supported.
                         The portID value contains the value of the port
                         numbers e.g.: NETWORK1(1), NETWORK2(2), CLIENT1(3)."

        VARIATION       tnOthIfIndexLo
            DESCRIPTION "For system modes
                         - otnNid1GbeClientOtu1NetworkMode(2)
                         - otnNid1GbeClientOtu2NetworkMode(3)
                         - otnNid10GbeClientOtu2NetworkMode(4)
                         - otnNid10GbeClientOtu2eNetworkMode(5)
                         - otnNid1GbEor10GbEClientOtu2OduFlexNetworkMode(10)
                         - otnNidOtu1ClientOtu1NetworkMode(6)
                         - otnNidOtu2ClientOtu2NetworkMode(7)
                         - otnNidOtu2eClientOtu2eNetworkMode(8):
                           For the encoded bit fields in this object only
                           ContainerType and HO-ODU type fields are used.
                           All other fields are set to value 0.
                           These values are encoded as follows:
                             Container type = (value & 0x0000FC00) >> 10
                             HO-ODU type    = (value & 0x000003E0) >>  5

                         For system mode
                         - otnNid1GbEor10GbEClientOtu2OduFlexNetworkMode(10):
                           For the encoded bit fields in this object fields
                           LO-ODUID, ContainerType, HO-ODU type and LO-ODU
                           type fields are used.
                           All other fields are set to value 0.
                           These values are encoded as follows:
                             LO-ODUID       = (value & 0x01FF0000) >> 16
                             Container type = (value & 0x0000FC00) >> 10
                             HO-ODU type    = (value & 0x000003E0) >>  5
                             LO-ODU type    = (value & 0x0000001F)."

        VARIATION       tnOthOdukTtpSapiTransmitted
            ACCESS      not-implemented
            DESCRIPTION "This object is not supported. It is superseded by
                         tnPsdOdukTtpSapiTransmitted."

        VARIATION       tnOthOdukTtpDapiExpected
            ACCESS      not-implemented
            DESCRIPTION "This object is not supported. It is superseded by
                         tnPsdOdukTtpDapiExpected."

        VARIATION       tnOthOdukTtpSapiExpected
            ACCESS      not-implemented
            DESCRIPTION "This object is not supported. It is superseded by
                         tnPsdOdukTtpSapiExpected."

        VARIATION       tnOthOdukTtpTraceIdentifierAccepted
            ACCESS      not-implemented
            DESCRIPTION "This object is not supported."

        VARIATION       tnOthOdukTtpDegThr
            SYNTAX      Unsigned32 (1..82300)
            DESCRIPTION "Depending on the system mode (tnPsdSystemMode) the
                         following ranges are allowed:
                         - otnNid1GbeClientOtu1NetworkMode(2)   : [1..20420]
                         - otnNid1GbeClientOtu2NetworkMode(3)   : [1..82026]
                         - otnNid10GbeClientOtu2NetworkMode(4)  : [1..82026]
                         - otnNid10GbeClientOtu2eNetworkMode(5) : [1..82300]

                         For the otnNid1GbEor10GbEClientOtu2OduFlexNetworkMode(10)
                         system mode, an ODUkP exists for :
                          - Each NETWORK port (Odu2P)
                            Allowed range : [1..82026]
                          - VIRTUAL slot (OduFlexP)
                            The value of this object changes when the number of
                            assigned ODUFlex timeslots, configured via object
                            tnOthOdukTxOduStruct, changes. The current value
                            is multiplied by NTS/CTS, where NTS is the new
                            number of assigned timeslots and CTS is the current
                            number of assigned timeslots. When no timeslots are
                            assigned, the value corresponding to 8 assigned
                            timeslots applies.
                            Allowed range : [1..CTS*10209], where CTS is the
                            current number of assigned timeslots."

        VARIATION       tnOthOdukTtpDegM
            SYNTAX      Unsigned32 (2..10)
            DESCRIPTION "Limited set of values."

        VARIATION       tnOthOdukPayloadType
            SYNTAX      Unsigned32 (3|5|32|33|254)
            DESCRIPTION "The value of this object can not be configured.

                         Its value is determined by the system mode
                         (tnPsdSystemMode) as follows:
                         - otnNid1GbeClientOtu1NetworkMode(2)   : 0x20
                         - otnNid1GbeClientOtu2NetworkMode(3)   : 0x21
                         - otnNid10GbeClientOtu2NetworkMode(4)  : 0x05
                         - otnNid10GbeClientOtu2eNetworkMode(5) : 0x03
                         - otnNid1GbEor10GbEClientOtu2OduFlexNetworkMode(10) : 0x21

                        The value is changed autonomously by the system, only
                        for system modes otnNid10GbeClientOtu2NetworkMode(4)
                        and otnNid10GbeClientOtu2eNetworkMode(5) :
                         - to 0xFE (PRBS) when the ODUk PRBS generator
                           (tnPsdOdukTtpPrbsGenerator) is enabled
                         - to the system mode specific value when the ODUk
                           PRBS generator is disabled."

        VARIATION       tnOthOdukPlmConsequenceAction
            SYNTAX      INTEGER { true(1) }
            DESCRIPTION "The value is fixed and set to true."

        VARIATION       tnOthOdukTxOduStruct
            DESCRIPTION "For below four system modes the value is fixed and
                         is determined by the system mode (tnPsdSystemMode),
                         as follows:
                         OtnNid1GbEClientOTU1NetworkMode(2)   : odu0#1-1
                         OtnNid1GbEClientOTU2NetworkMode(3)   : odu0#1-1
                         OtnNid10GbEClientOTU2NetworkMode(4)  : odu2#1-1
                         OtnNid10GbEClientOTU2eNetworkMode(5) : odu2e#1-1

                         For otnNid1GbEor10GbEClientOtu2OduFlexNetworkMode(10) :
                         This object is configurable, but only for the ODUkP
                         related to the NETWORK1 port. The configured value is
                         applied to both NETWORK ports identically, and change
                         notifications are sent for both NETWORK ports.
                         For the ODUkP's related to the NETWORK ports, the
                         default value is string : uas#0-1,2,3,4,5,6,7,8
                         Examples of strings used for configuration are:
                          - odufgfp#1-1,3       (assign timeslots 1 and 3)
                          - odufgfp#1-1&uas#0-3 (unassign timeslot 3, keep 1)
                         Only value 1 can be used for the tributary slot number,
                         i.e. odufgfp#1.
                         For the ODUkP related to the VIRTUAL slot, this object
                         has no meaning, and its value is fixed to an empty
                         string.
                         A GET on this object always contains all assigned and
                         unassigned time slots, e.g.:
                          - odufgfp#1-1,3&uas#0-2,4,5,6,7,8
                         When the number of assigned ODUFlex timeslots changes,
                         also the value of object tnOthOdukTtpDegThr of the
                         ODUkP related to the VIRTUAL slot, as well as the
                         value of object tnOthOdukNimDegThr of the ODUkPm's
                         (NIMs) related to the NETWORK ports, change."

        VARIATION       tnOthOdukTtpCurrentStatus
            ACCESS      not-implemented
            DESCRIPTION "This object is not supported."

        VARIATION       tnOthOdukOdu0Interwk
            ACCESS      not-implemented
            DESCRIPTION "This object is not supported."

        VARIATION       tnOthOdukTtpDapiAccepted
            ACCESS      not-implemented
            DESCRIPTION "This object is not supported. It is superseded by
                         tnPsdOdukTtpDapiAccepted."

        VARIATION       tnOthOdukTtpDapiTransmitted
            ACCESS      not-implemented
            DESCRIPTION "This object is not supported. It is superseded by
                         tnPsdOdukTtpDapiTransmitted."

        VARIATION       tnOthOdukTtpOsTransmitted
            DESCRIPTION "32 octets must be provided, otherwise the request is
                         rejected and an error is returned."

        VARIATION       tnOthOdukRxMSI
            ACCESS      not-implemented
            DESCRIPTION "This object is not supported."

        VARIATION       tnOthOdukTtpCndRes
            ACCESS      not-implemented
            DESCRIPTION "This object is not supported."

        VARIATION       tnOthOdukTtpCmEmphasis
            ACCESS      not-implemented
            DESCRIPTION "This object is not supported."

        VARIATION       tnOthOdukTtpManualOduPtf
            ACCESS      not-implemented
            DESCRIPTION "This object is not supported."

        VARIATION       tnOthOdukTtpCsfType
            ACCESS      not-implemented
            DESCRIPTION "This object is not supported."

        VARIATION       tnOthOdukOduChanPools
            ACCESS      not-implemented
            DESCRIPTION "This object is not supported."

        VARIATION       tnOthOdukMaxTribNumber
            ACCESS      not-implemented
            DESCRIPTION "This object is not supported."

        VARIATION       tnOthOdukActualTribNumber
            ACCESS      not-implemented
            DESCRIPTION "This object is not supported."

        VARIATION       tnOthOdukOduCTypeNMValue
            ACCESS      not-implemented
            DESCRIPTION "This object is not supported."

        VARIATION       tnOthOdukTtpDegPeriod
            ACCESS      not-implemented
            DESCRIPTION "This object is not supported."

       VARIATION       tnOthOdukTtpMsimResp
            ACCESS      not-implemented
            DESCRIPTION "This object is not supported."

        VARIATION       tnOthOdukNimDirectionality
            SYNTAX      INTEGER { sink(1) }
            DESCRIPTION "Limited set of values.
                        All NIMs have directionality set to sink.
                        For the Ethernet Client OTN Network system modes:
                         - otnNid1GbeClientOtu1NetworkMode(2)
                         - otnNid1GbeClientOtu2NetworkMode(3)
                         - otnNid10GbeClientOtu2NetworkMode(4)
                         - otnNid10GbeClientOtu2eNetworkMode(5)
                         - otnNid1GbEor10GbEClientOtu2OduFlexNetworkMode(10)
                        the traffic is monitored in the following direction:
                        NETWORK1 NIM: NETWORK1 ---(virtual ODUkP)--> CLIENT1
                        NETWORK2 NIM: NETWORK2 ---(virtual ODUkP)--> CLIENT1
                        For the OTN Client OTN Network system modes:
                         - otnNidOtu1ClientOtu1NetworkMode(6)
                         - otnNidOtu2ClientOtu2NetworkMode(7)
                         - otnNidOtu2eClientOtu2eNetworkMode(8)
                        the traffic is monitored in the following direction:
                        NETWORK1 NIM: NETWORK1 ---(virtual ODUkPm) --> CLIENT1
                        NETWORK2 NIM: NETWORK2 ---(virtual ODUkPm) --> CLIENT1
                        CLIENT1  NIM: CLIENT1  --> NETWORK1,2
                        Please refer to the description of tnOthOdukApsAction
                        to see which NIM objects are present depending on the
                        protection state."

        VARIATION       tnOthOdukNimDapiExpected
            ACCESS      not-implemented
            DESCRIPTION "This object is not supported. It is superseded by
                         tnPsdOdukNimDapiExpected."

        VARIATION       tnOthOdukNimSapiExpected
            ACCESS      not-implemented
            DESCRIPTION "This object is not supported. It is superseded by
                         tnPsdOdukNimSapiExpected."

        VARIATION       tnOthOdukNimTraceIdentifierAccepted
            ACCESS      not-implemented
            DESCRIPTION "This object is not supported."

        VARIATION       tnOthOdukNimDegThr
            SYNTAX      Unsigned32 (1..82300)
            DESCRIPTION "Depending on the system mode (tnPsdSystemMode) the
                         following ranges are allowed:
                         - otnNid1GbeClientOtu1NetworkMode(2)   : [1..20420]
                         - otnNid1GbeClientOtu2NetworkMode(3)   : [1..82026]
                         - otnNid10GbeClientOtu2NetworkMode(4)  : [1..82026]
                         - otnNid10GbeClientOtu2eNetworkMode(5) : [1..82300]
                         - otnNidOtu1ClientOtu1NetworkMode(6)   : [1..20420]
                         - otnNidOtu2ClientOtu2NetworkMode(7)   : [1..82026]
                         - otnNidOtu2eClientOtu2eNetworkMode(8) : [1..82300].

                         For the otnNid1GbEor10GbEClientOtu2OduFlexNetworkMode(10)
                         system mode, an ODUkPm (Odu2OduFlexPm) exists for each
                         NETWORK port.
                         The value of this object changes when the number of
                         assigned ODUFlex timeslots, configured via object
                         tnOthOdukTxOduStruct, changes. The current value is
                         multiplied by NTS/CTS, where NTS is the new number
                         of assigned timeslots and CTS is the current number
                         of assigned timeslots. When no timeslots are assigned,
                         the value corresponding to 8 assigned timeslots applies.
                         Allowed range : [1..CTS*10209], where CTS is the
                         current number of assigned timeslots."

        VARIATION       tnOthOdukNimDegM
            SYNTAX      Unsigned32 (2..10)
            DESCRIPTION "Limited set of values."

        VARIATION       tnOthOdukNimPom
            ACCESS      not-implemented
            DESCRIPTION "This object is not supported."

        VARIATION       tnOthOdukNimDapiAccepted
            ACCESS      not-implemented
            DESCRIPTION "This object is not supported. It is superseded by
                         tnPsdOdukNimDapiAccepted."

        VARIATION       tnOthOdukNimDegPeriod
            ACCESS      not-implemented
            DESCRIPTION "This object is not supported."

        VARIATION       tnOthOdukTcmIfIndex
            DESCRIPTION "In the value of this object, the shelf, slot and
                         HO-ODU number values are encoded as follows:

                         shelf         = (value & 0xFF000000) >> 24
                         slot          = (value & 0x00FF0000) >> 16
                         HO-ODU number = (value & 0x0000FF00) >>  8

                         The value of shelf and slot are fixed set to 1.
                         For HO-ODU number only the portID part is supported.
                         The portID value contains the value of the port
                         numbers e.g.: NETWORK1(1), NETWORK2(2)."

        VARIATION        tnOthOdukTcmIfIndexLo
            DESCRIPTION "For the encoded bit fields in this object only
                         Container type, HO-ODU type, TCM level and
                         TCM direction fields are used, where TCM
                         direction is always set to fixed value BM=2.
                         All other fields are set to value 0.
                         These values are encoded as follows:

                         HO-ODU type    = (value & 0x007C0000) >> 18
                         Container type = (value & 0x0000FC00) >> 10
                         TCM level      = (value & 0x00000380) >>  7
                         TCM direction  = (value & 0x00000060) >>  5"

        VARIATION       tnOthOdukTRowStatus
            SYNTAX      INTEGER { active(1),
                                  notInService(2),
                                  createAndWait(5),
                                  destroy(6) }
            DESCRIPTION "Limited set of values.
                         In case the value is set to active the system creates
                         a corresponding ODUkT performance monitoring (PM)
                         point in the tnOthOdukStatsTcmConfigTable.
                         In case the value is set to notInService the system
                         deletes the corresponding ODUkT performance monitoring
                         point from the tnOthOdukStatsTcmConfigTable and also
                         all corresponding PM history data is removed."

        VARIATION       tnOthOdukTTcmMode
            SYNTAX      INTEGER { termination(1) }
            DESCRIPTION "Limited set of values."

        VARIATION       tnOthOdukTPosSeq
            SYNTAX      Unsigned32 (1)
            DESCRIPTION "The value is fixed and set to 1."

        VARIATION       tnOthOdukTAdminStatus
            ACCESS      not-implemented
            DESCRIPTION "This object is not supported."

        VARIATION       tnOthOdukTSapiTransmitted
            ACCESS      not-implemented
            DESCRIPTION "This object is not supported. It is superseded by
                         tnPsdOdukTSapiTransmitted."

        VARIATION       tnOthOdukTSapiExpected
            ACCESS      not-implemented
            DESCRIPTION "This object is not supported. It is superseded by
                         tnPsdOdukTSapiExpected."

        VARIATION       tnOthOdukTTraceIdentifierAccepted
            ACCESS      not-implemented
            DESCRIPTION "This object is not supported."

        VARIATION       tnOthOdukTAisOnDef
            ACCESS      not-implemented
            DESCRIPTION "This object is not supported."

        VARIATION       tnOthOdukTLtcResp
            DESCRIPTION "The default value of this object is disable(2).
                         This means that the LTC defect does not contribute
                         to the consequent action.
                         The value of this object can only be set to enable(1)
                         when the tnOthOdukTRowStatus is active(1), otherwise
                         an error is returned.
                         The user should not set the value of this object to
                         enable(1) and tnOthOdukTRowStatus to active(1)
                         in the same varbind."

        VARIATION       tnOthOdukTOhAdd
            ACCESS      not-implemented
            DESCRIPTION "This object is not supported."

        VARIATION       tnOthOdukTOhRmv
            ACCESS      not-implemented
            DESCRIPTION "This object is not supported."

        VARIATION       tnOthOdukTDegThr
            SYNTAX      Unsigned32 (1..82300)
            DESCRIPTION "Depending on the system mode (tnPsdSystemMode) the
                         following ranges are allowed:
                         - otnNid1GbeClientOtu1NetworkMode(2)   : [1..20420]
                         - otnNid1GbeClientOtu2NetworkMode(3)   : [1..82026]
                         - otnNid10GbeClientOtu2NetworkMode(4)  : [1..82026]
                         - otnNid10GbeClientOtu2eNetworkMode(5) : [1..82300]
                         - otnNidOtu1ClientOtu1NetworkMode(6)   : [1..20420]
                         - otnNidOtu2ClientOtu2NetworkMode(7)   : [1..82026]
                         - otnNidOtu2eClientOtu2eNetworkMode(8) : [1..82300].
                         - otnNid1GbEor10GbEClientOtu2OduFlexNetworkMode(10) : [1..82026]."

        VARIATION       tnOthOdukTDegM
            SYNTAX      Unsigned32 (2..10)
            DESCRIPTION "Limited set of values."

        VARIATION       tnOthOdukTDapiAccepted
            ACCESS      not-implemented
            DESCRIPTION "This object is not supported. It is superseded by
                         tnPsdOdukTDapiAccepted."

        VARIATION       tnOthOdukTDapiExpected
            ACCESS      not-implemented
            DESCRIPTION "This object is not supported. It is superseded by
                         tnPsdOdukTDapiExpected."

        VARIATION       tnOthOdukTDapiTransmitted
            ACCESS      not-implemented
            DESCRIPTION "This object is not supported. It is superseded by
                         tnPsdOdukTDapiTransmitted."

        VARIATION       tnOthOdukTOsTransmitted
            DESCRIPTION "32 octets must be provided, otherwise the request is
                         rejected and an error is returned."

        VARIATION       tnOthOdukTTcmAlmProfName
            ACCESS      not-implemented
            DESCRIPTION "This object is not supported. The PSD ASAP Fault
                         Profile implementation is used."

        VARIATION       tnOthOdukTcmOperStatus
            ACCESS      not-implemented
            DESCRIPTION "This object is not supported."

        VARIATION       tnOthOdukTcmMgracd
            ACCESS      not-implemented
            DESCRIPTION "This object is not supported."

        VARIATION       tnOthOdukTcmincstat
            ACCESS      not-implemented
            DESCRIPTION "This object is not supported."

        VARIATION       tnOthOdukTcmOperationalCapability
            ACCESS      not-implemented
            DESCRIPTION "This object is not supported."

        VARIATION       tnOthOdukTcmStateQualifier
            ACCESS      not-implemented
            DESCRIPTION "This object is not supported."

        VARIATION       tnOthOdukTcmDMInvoke
            ACCESS      not-implemented
            DESCRIPTION "This object is not supported."

        VARIATION       tnOthOdukTcmDMTimeStamp
            ACCESS      not-implemented
            DESCRIPTION "This object is not supported."

        VARIATION       tnOthOdukTcmDMCMEPMode
            ACCESS      not-implemented
            DESCRIPTION "This object is not supported."

        VARIATION       tnOthOdukTcmDMStatus
            ACCESS      not-implemented
            DESCRIPTION "This object is not supported."

        VARIATION       tnOthOdukTcmDMTime
            ACCESS      not-implemented
            DESCRIPTION "This object is not supported."

        VARIATION       tnOthOdukTDegPeriod
            ACCESS      not-implemented
            DESCRIPTION "This object is not supported."

        VARIATION       tnOthOdukApsToIfIndex
            DESCRIPTION "See description tnOthIfIndex for the encoding rules.
                         The value of this object contains the value that
                         corresponds with the virtual ODUkP  (path) index or
                         the virtual ODUkPm (NIM), dependent on the system
                         mode.
                         The virtual ODUkP (path), i.e. the entry in the
                         tnOthOdukTtpTable with a slot value that equals 71,
                         is referenced in following system modes:
                         - otnNid1GbeClientOtu1NetworkMode(2)
                         - otnNid1GbeClientOtu2NetworkMode(3)
                         - otnNid10GbeClientOtu2NetworkMode(4)
                         - otnNid10GbeClientOtu2eNetworkMode(5)
                         - otnNid1GbEor10GbEClientOtu2OduFlexNetworkMode(10)
                         The virtual ODUkPm (NIM), i.e. the entry in the
                         tnOthOdukNimTable with a slot value that equals 71,
                         is referenced in the following system
                         modes:
                         - otnNidOtu1ClientOtu1NetworkMode(6)
                         - otnNidOtu2ClientOtu2NetworkMode(7)
                         - otnNidOtu2eClientOtu2eNetworkMode(8)"

        VARIATION        tnOthOdukApsToIfIndexLo
            DESCRIPTION "See description tnOthIfIndexLo for the encoding rules.
                         The value of this object contains the value that
                         corresponds with the virtual ODUkP (path) index or
                         virtual ODUkPm (NIM) depending on the system mode.
                         For more information, see description of
                         tnOthOdukApsToIfIndex."

        VARIATION       tnOthOdukApsAction
            SYNTAX      INTEGER { convertToProt(4),
                                  convertToUnprot(5),
                                  noCommand(6) }
            DESCRIPTION "Limited set of values.
                         When the tnPsdSystemMode is unequal to
                         factoryDefault(1) the tnOthOdukApsGroupTable contains
                         a by the system created single row entry.
                         In case the tnPsdSystemMode is equal to
                         factoryDefault(1) no entry is present in this table
                         and any other OTN related table.
                         This object supports the following operations:
                         - convertToProt(4)   -> Conversion from an unprotected
                                                 to an protected connection.
                         - convertToUnprot(5) -> Conversion from a protected to
                                                 an unprotected connection.
                         Only SNC/Ne protection is supported. The value
                         noCommand(6) is returned on get and ignored if used
                         on set.
                         Attributes can be changed regardless if protection is
                         enabled or not.

                         For Ethernet Client OTN Network system modes:
                           - otnNid1GbeClientOtu1NetworkMode(2)
                           - otnNid1GbeClientOtu2NetworkMode(3)
                           - otnNid10GbeClientOtu2NetworkMode(4)
                           - otnNid10GbeClientOtu2eNetworkMode(5)
                           - otnNid1GbEor10GbEClientOtu2OduFlexNetworkMode(10)
                         in case protection is enabled, the following applies:
                         - tnOthOdukXcTable: contains the following
                           bi-directional cross-connect entries:
                           For Ethernet Client OTN Network system modes:
                           1) src=path (virtual ODUkP),
                              dest=worker (NETWORK1),
                              tnOthOdukXcProtectionState=working(3)
                           2) src=path (virtual ODUkP),
                              dest=protector (NETWORK2),
                              tnOthOdukXcProtectionState=protection(2)
                         - tnOthOdukNimTable: contains two entries:
                           1) worker    (NETWORK1)
                           2) protector (NETWORK2)
                           The settable attributes of both the worker and
                           protector entries in this table are configured via
                           the virtual ODUkP (tnOthOdukTtpTable). The read-only
                           values must be read from the tnOthOdukNimTable.
                         - tnOthOdukStatsRxConfigTable: contains three entries:
                           1) worker    (NETWORK1)
                           2) protector (NETWORK2)
                           3) path      (virtual ODUkP)
                         In case protection is disabled, the following applies:
                         - tnOthOdukXcTable: contains the following
                           bi-directional cross-connect entry:
                           1) src=path (virtual ODUkP), dest=worker (NETWORK1)
                              tnOthOdukXcProtectionState=none(1)
                         - tnOthOdukNimTable: contains one entry:
                           1) protector (NETWORK2)
                         - tnOthOdukStatsRxConfigTable: contains one entry
                           1) path      (virtual ODUkP)

                         For OTN Client OTN Network system modes:
                           - otnNidOtu1ClientOtu1NetworkMode(6)
                           - otnNidOtu2ClientOtu2NetworkMode(7)
                           - otnNidOtu2eClientOtu2eNetworkMode(8)
                         in case protection is enabled, the following applies:
                         - tnOthOdukXcTable: contains the following
                           bi-directional cross-connect entries:
                           1) src=virtual ODUkPm
                              dest=worker (NETWORK1),
                              tnOthOdukXcProtectionState=working(3)
                           2) src=virtual ODUkPm
                              dest=worker (NETWORK2),
                              tnOthOdukXcProtectionState=protection(2)
                         - tnOthOdukNimTable: contains four entries:
                           1) worker      (NETWORK1)
                           2) protector   (NETWORK2)
                           3) virtual NIM (VIRTUAL ODUkPm)
                           4) CLIENT1 NIM (CLIENT1)
                           The settable attributes of both the worker and
                           protector entries in this table are configured via
                           the virtual ODUkPm (NIM).
                           The read-only values of the worker and protector NIM
                           must be read from the tnOthOdukNimTable.
                         - tnOthOdukStatsRxConfigTable: contains four entries:
                           1) worker      (NETWORK1)
                           2) protector   (NETWORK2)
                           3) virtual NIM (VIRTUAL ODUkPm)
                           4) CLIENT1 NIM (CLIENT1)
                         In case protection is disabled, the following applies:
                         - tnOthOdukXcTable: contains the following
                           bi-directional cross-connect entry:
                           1) src=virtual NIM (Virtual ODUkPm)
                              dest=worker (NETWORK1)
                              tnOthOdukXcProtectionState=none(1)
                         - tnOthOdukNimTable: contains three entries:
                           1) protector   (NETWORK2)
                           2) virtual NIM (VIRTUAL ODUkPm)
                           3) CLIENT1 NIM (CLIENT1)
                         - tnOthOdukStatsRxConfigTable: contains two entries:
                           1) virtual NIM (VIRTUAL ODUkPm)
                           2) CLIENT1 NIM (CLIENT1)

                         When changing from unprotected to protected or vice
                         versa the system automatically creates or deletes
                         table entries as indicated above. Note that in an
                         unprotected configuration NETWORK2 supports: in-band
                         management and interface associated OTN objects."

        VARIATION       tnOthOdukApsFromedIfIndex
            ACCESS      read-only
            DESCRIPTION "Setting of this object is not allowed. The same
                         bit encoding is used as for tnOthOdukApsToIfIndex.
                         This index value contains the value that corresponds
                         with the worker port (NETWORK1)."

        VARIATION       tnOthOdukApsFromedIfIndexLo
            ACCESS      read-only
            DESCRIPTION "Setting of this object is not allowed. The same
                         bit encoding is used as for tnOthIfIndexLo.
                         This index value contains the value that corresponds
                         with the worker port (NETWORK1)."

        VARIATION       tnOthOdukApsFromingIfIndex
            ACCESS      read-only
            DESCRIPTION "Setting of this object is not allowed. The same
                         bit encoding is used as for tnOthOdukApsToIfIndex.
                         In case protection is enabled this index value
                         contains the value that corresponds with the
                         protection port (NETWORK2).
                         In case protection is disabled this index value
                         contains the value zero."

        VARIATION       tnOthOdukApsFromingIfIndexLo
            ACCESS      read-only
            DESCRIPTION "Setting of this object is not allowed. The same
                         bit encoding is used as for tnOthIfIndexLo.
                         In case protection is enabled this index value
                         contains the value that corresponds with the
                         protection port (NETWORK2).
                         In case protection is disabled this index value
                         contains the value zero."

        VARIATION       tnOthOdukApsDescr
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnOthOdukApsMode
            SYNTAX      INTEGER { sncn(1) }
            DESCRIPTION "Limited set of values."

        VARIATION       tnOthOdukApsDirection
            SYNTAX      INTEGER { unidirectional(1) }
            DESCRIPTION "Limited support of values."

        VARIATION       tnOthOdukApsXcBidirectional
            ACCESS      not-implemented
            DESCRIPTION "This object is not supported."

        VARIATION       tnOthOdukApsHoldOffTimer
            DESCRIPTION "Limited set of values, value must a multiple of 10 ms
                         (milliseconds). E.g. 0=default, 10, 20, ... 10000."

        VARIATION       tnOthOdukApsGroupK1K2Trans
            ACCESS      read-only
            DESCRIPTION "Setting of this object is not allowed."

        VARIATION       tnOthOdukApsGroupMethod
            SYNTAX      INTEGER { pnim(1) }
            DESCRIPTION "Limited set of values."

        VARIATION       tnOthOdukApsPingMethod
            ACCESS      not-implemented
            DESCRIPTION "This object is not supported."

        VARIATION       tnOthOdukApsCurrentStatus
            DESCRIPTION "The value zero is always returned."

        VARIATION       tnOthOdukApsGroupID
            ACCESS      not-implemented
            DESCRIPTION "This object is not supported."

        VARIATION       tnOthOdukApsOduXcRate
            SYNTAX      INTEGER { odu1(3), odu2(6), odu2e(7), oduFlex(13) }
            DESCRIPTION "Limited set of values, supported values
                         The system assigns dependent of the tnPsdSystemMode
                         one of the values:
                         - otnNid1GbeClientOtu1NetworkMode(2)   -> odu1(3)
                         - otnNid1GbeClientOtu2NetworkMode(3)   -> odu2(6)
                         - otnNid10GbeClientOtu2NetworkMode(4)  -> odu2(6)
                         - otnNid10GbeClientOtu2eNetworkMode(5) -> odu2e(7)
                         - otnNidOtu1ClientOtu1NetworkMode(6)   -> odu1(3)
                         - otnNidOtu2ClientOtu2NetworkMode(7)   -> odu2(6)
                         - otnNidOtu2eClientOtu2eNetworkMode(8) -> odu2e(7)
                         - otnNid1GbEor10GbEClientOtu2OduFlexNetworkMode(10) -> oduFlex(13)
                         Which indicates the highest supported ODUk rate."

        VARIATION       tnOthOdukApsGroupCurrentStatus
            SYNTAX      INTEGER { lockoutNe(1), frcdNe(2), sfNe(3), sdNe(4),
                                  manNe(5), wtrNe(6), nr(8) }
            DESCRIPTION "Limited set of values."

        VARIATION       tnOthOdukApsSwitchCmd
            SYNTAX      INTEGER { noCmd(1),
                                  clear(2),
                                  lockoutOfProtection(3),
                                  forcedSwitchWorkToProtect(4),
                                  forcedSwitchProtectToWork(5),
                                  manualSwitchWorkToProtect(6),
                                  manualSwitchProtectToWork(7) }
            DESCRIPTION "Limited set of values."

        VARIATION       tnOthOdukApsCascadedUse
            ACCESS      not-implemented
            DESCRIPTION "This object is not supported."

        VARIATION       tnOthOdukApsReSize
            ACCESS      not-implemented
            DESCRIPTION "This object is not supported."

        VARIATION       tnOthOdukApsNewFromedTsList
            ACCESS      not-implemented
            DESCRIPTION "This object is not supported."

        VARIATION       tnOthOdukApsNewFromingTsList
            ACCESS      not-implemented
            DESCRIPTION "This object is not supported."

        VARIATION       tnOthOdukXcSrcIfIndex
            DESCRIPTION "See description tnOthIfIndex for the encoding rules.
                         For Ethernet Client OTN Network system modes:
                           - otnNid1GbeClientOtu1NetworkMode(2)
                           - otnNid1GbeClientOtu2NetworkMode(3)
                           - otnNid10GbeClientOtu2NetworkMode(4)
                           - otnNid10GbeClientOtu2eNetworkMode(5)
                           - otnNid1GbEor10GbEClientOtu2OduFlexNetworkMode(10)
                         the value of this object contains the value that
                         corresponds with the virtual ODUkP (path)
                         For OTN Client OTN Network system modes:
                           - otnNidOtu1ClientOtu1NetworkMode(6)
                           - otnNidOtu2ClientOtu2NetworkMode(7)
                           - otnNidOtu2eClientOtu2eNetworkMode(8)
                         the value of this object contains the value that
                         corresponds with the virtual ODUkPm (NIM).
"

        VARIATION        tnOthOdukXcSrcIfIndexLo
            DESCRIPTION "See description tnOthIfIndexLo for the encoding rules.
                         The value of this object contains the value that
                         corresponds with the virtual ODUkP (path) index or
                         virtual ODUkPm (NIM) depending on the system mode.
                         For more information, see description of
                         tnOthOdukXcSrcIfIndex."

        VARIATION       tnOthOdukXcDestIfIndex
            DESCRIPTION "Uses the same bit encoding as tnOthIfIndex.
                         The value of this object contains the value
                         that corresponds with the worker port (NETWORK1)
                         or the protector port (NETWORK2)."

        VARIATION       tnOthOdukXcDestIfIndexLo
            DESCRIPTION "Uses the same bit encoding as tnOthIfIndexLo.
                         For more information, see description of
                         tnOthOdukXcDestIfIndex."

        VARIATION       tnOthOdukXcRowStatus
            SYNTAX      INTEGER { active(1) }
            DESCRIPTION "Limited set of values.
                         The value of this object has implicitly the fixed
                         value active(1).
                         In case protection is enabled this table contains two
                         entries. In case protection is disabled this table
                         contains one entry, see description of
                         tnOthOdukApsAction for more details."

        VARIATION       tnOthOdukXcId
            DESCRIPTION "The encoded value of this object consists of two
                         parts: a shelfID and a XCID or groupID.
                         The shelfID (bits 31-24) has a fixed value 1.
                         The XCID or groupID (bits 23 - 0) is assigned by the
                         system where the first entry gets the
                         number 1 the next entry 2 and so forth."

        VARIATION       tnOthOdukXcRate
            SYNTAX      INTEGER { odu1(3), odu2(6), odu2e(7), oduFlex(13) }
            DESCRIPTION "The value of this object is a fixed value that is
                         determined by the system mode (tnPsdSystemMode)
                         as follows:
                         - otnNid1GbeClientOtu1NetworkMode(2)   -> odu1(3)
                         - otnNid1GbeClientOtu2NetworkMode(3)   -> odu2(6)
                         - otnNid10GbeClientOtu2NetworkMode(4)  -> odu2(6)
                         - otnNid10GbeClientOtu2eNetworkMode(5) -> odu2e(7)
                         - otnNidOtu1ClientOtu1NetworkMode(6)   -> odu1(3)
                         - otnNidOtu2ClientOtu2NetworkMode(7)   -> odu2(6)
                         - otnNidOtu2eClientOtu2eNetworkMode(8) -> odu2e(7).
                         - otnNid1GbEor10GbEClientOtu2OduFlexNetworkMode(10) -> oduFlex(13)."

        VARIATION       tnOthOdukXcName
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnOthOdukXcBidirectional
            SYNTAX      INTEGER { true(1) }
            DESCRIPTION "Fixed value to true, indicating that the connection is
                         always bidirectional."

        VARIATION       tnOthOdukXcProtectionState
            DESCRIPTION "The value is fixed, the below values and meaning
                         applies:
                         - none(1),      the connection is not protected
                         - working(3)    the working leg of a protected
                                         connection
                         - protection(2) the protection leg of a protected
                                         connection."

        VARIATION       tnOthOdukXcTopology
            ACCESS      not-implemented
            DESCRIPTION "This object is not supported."

        VARIATION       tnOthOdukXcResize
            ACCESS      not-implemented
            DESCRIPTION "This object is not supported."

        VARIATION       tnOthOdukXcNewFromTsList
            ACCESS      not-implemented
            DESCRIPTION "This object is not supported."

        VARIATION       tnOthOdukXcNewToTsList
            ACCESS      not-implemented
            DESCRIPTION "This object is not supported."

        VARIATION       tnOthOdukXcYangConnectionName
            ACCESS      not-implemented
            DESCRIPTION "This object is not supported."

--
-- Capabilities for TROPIC-L1SERVICE-MIB
-- Based on MIB version:  R15.0-LatestMIBs-221105
--

    SUPPORTS            TROPIC-L1SERVICE-MIB
        INCLUDES        { tnControlNetworkLinkGroup,
                          tnNetIfGroup,
                          tnNetIfFacilityGroup }

        VARIATION       tnCNLinkAutoStateSourceIP
            DESCRIPTION "This object must always be included in an SNMP
                         SET PDU together with object
                         tnCNLinkAutoStateSourceInetAddressType, otherwise
                         error 'inconsistent value' is returned."

        VARIATION       tnCNLinkAutoStateSourceInetAddressType
            DESCRIPTION "This object must always be included in an SNMP SET
                         PDU together with object tnCNLinkAutoStateSourceIP
                         when it is set to value ipv4(1), otherwise error
                         'inconsistent value' is returned.
                         This object must always be included in an SNMP SET PDU
                         together with object tnCNLinkAutoStateSourceInetAddress
                         when it is set to value ipv6(2), otherwise error
                         'inconsistent value' is returned."

        VARIATION       tnCNLinkAutoStateSourceInetAddress
            DESCRIPTION "This object must always be included in an SNMP
                         SET PDU together with object
                         tnCNLinkAutoStateSourceInetAddressType, otherwise
                         error 'inconsistent value' is returned."

        VARIATION       tnCNLinkDescr
            ACCESS      not-implemented
            DESCRIPTION "This object is not supported."

        VARIATION       tnCNLinkAdminStatus
            ACCESS      not-implemented
            DESCRIPTION "This object is not supported."

        VARIATION       tnCNLinkOperStatus
            ACCESS      not-implemented
            DESCRIPTION "This object is not supported."

        VARIATION       tnCNLinkPhysicalIfIndex
            ACCESS      not-implemented
            DESCRIPTION "This object is not supported."

        VARIATION       tnCNLinkIpAddress
            ACCESS      not-implemented
            DESCRIPTION "This object is not supported."

        VARIATION       tnCNLinkSubnetMask
            ACCESS      not-implemented
            DESCRIPTION "This object is not supported."

        VARIATION       tnCNLinkHelloInterval
            ACCESS      not-implemented
            DESCRIPTION "This object is not supported."

        VARIATION       tnCNLinkRtrDeadInterval
            ACCESS      not-implemented
            DESCRIPTION "This object is not supported."

        VARIATION       tnCNLinkTeMetric
            ACCESS      not-implemented
            DESCRIPTION "This object is not supported."

        VARIATION       tnCNLinkOspfRoutingState
            ACCESS      not-implemented
            DESCRIPTION "This object is not supported."

        VARIATION       tnCNLinkConfigIfType
            ACCESS      not-implemented
            DESCRIPTION "This object is not supported."

        VARIATION       tnCNLinkConfigRtrPriority
            ACCESS      not-implemented
            DESCRIPTION "This object is not supported."

        VARIATION       tnCNLinkEquipOperStatus
            ACCESS      not-implemented
            DESCRIPTION "This object is not supported."

        VARIATION       tnCNLinkDhcpEnabled
            ACCESS      not-implemented
            DESCRIPTION "This object is not supported."

        VARIATION       tnCNLinkSpeed
            ACCESS      not-implemented
            DESCRIPTION "This object is not supported."

        VARIATION       tnCNLinkDuplex
            ACCESS      not-implemented
            DESCRIPTION "This object is not supported."

        VARIATION       tnCNLinkProxyArp
            ACCESS      not-implemented
            DESCRIPTION "This object is not supported."

        VARIATION       tnCNLinkDHCPRange
            SYNTAX      Unsigned32 ( 1..10 )
            DESCRIPTION "Limited value range."

        VARIATION       tnCNLinkAdjState
            ACCESS      not-implemented
            DESCRIPTION "This object is not supported."

        VARIATION       tnCNLinkOscMode
            ACCESS      not-implemented
            DESCRIPTION "This object is not supported."

        VARIATION       tnCNLinkOspfAuthentType
            ACCESS      not-implemented
            DESCRIPTION "This object is not supported."

        VARIATION       tnCNLinkOspfAuthKey
            ACCESS      not-implemented
            DESCRIPTION "This object is not supported."

        VARIATION       tnCNLinkOspfAuthKeyId
            ACCESS      not-implemented
            DESCRIPTION "This object is not supported."

        VARIATION       tnCNLinkTdmxDcnConf
            ACCESS      not-implemented
            DESCRIPTION "This object is not supported."

        VARIATION       tnCNLinkInetAddressType
            ACCESS      not-implemented
            DESCRIPTION "This object is not supported."

        VARIATION       tnCNLinkInetAddress
            ACCESS      not-implemented
            DESCRIPTION "This object is not supported."

        VARIATION       tnCNLinkPrefixLength
            ACCESS      not-implemented
            DESCRIPTION "This object is not supported."

        VARIATION       tnCNLinkDhcpv6Enabled
            ACCESS      not-implemented
            DESCRIPTION "This object is not supported."

        VARIATION       tnCNLinkDHCPv6Range
            ACCESS      not-implemented
            DESCRIPTION "This object is not supported."

        VARIATION       tnCNLinkDHCPClient
            ACCESS      not-implemented
            DESCRIPTION "This object is not supported."

        VARIATION       tnCNLinkDHCPv6Client
            ACCESS      not-implemented
            DESCRIPTION "This object is not supported."

        VARIATION       tnCNLinkDHCPClientDfltGtwy
            ACCESS      not-implemented
            DESCRIPTION "This object is not supported."

        VARIATION       tnCNLinkEtherPortIpV6SLAAC
            ACCESS      not-implemented
            DESCRIPTION "This object is not supported."

        VARIATION       tnCNLinkOspfRetransint
            ACCESS      not-implemented
            DESCRIPTION "This object is not supported."

        VARIATION       tnCNLinkOspfv3AdjStateId
            ACCESS      not-implemented
            DESCRIPTION "This object is not supported."

        VARIATION       tnCNLinkOspfNeighborRouterIp
            ACCESS      not-implemented
            DESCRIPTION "This object is not supported."

        VARIATION       tnCNLinkOspfv3NeighborRouterIp
            ACCESS      not-implemented
            DESCRIPTION "This object is not supported."

        VARIATION       tnCNLinkOspfNeighborIp
            ACCESS      not-implemented
            DESCRIPTION "This object is not supported."

        VARIATION       tnCNLinkOspfv3NeighborInetAddress
            ACCESS      not-implemented
            DESCRIPTION "This object is not supported."

        VARIATION       tnCNLinkRole
            ACCESS      not-implemented
            DESCRIPTION "This object is not supported."

        VARIATION       tnCNLinkDHCPServerIPv6SLAAC
            ACCESS      not-implemented
            DESCRIPTION "This object is not supported."

        VARIATION       tnCNLinkRouterAdvAutonomousFlag
            ACCESS      not-implemented
            DESCRIPTION "This object is not supported."

        VARIATION       tnCNLinkRouterAdvDefaultLifeTime
            ACCESS      not-implemented
            DESCRIPTION "This object is not supported."

        VARIATION       tnCNLinkRouterAdvDefaultPreference
            ACCESS      not-implemented
            DESCRIPTION "This object is not supported."

        VARIATION       tnCNLinkRouterAdvMaxRtrAdvInterval
            ACCESS      not-implemented
            DESCRIPTION "This object is not supported."

        VARIATION       tnCNLinkRouterAdvManagedFlag
            ACCESS      not-implemented
            DESCRIPTION "This object is not supported."

        VARIATION       tnCNLinkRouterAdvOtherConfigFlag
            ACCESS      not-implemented
            DESCRIPTION "This object is not supported."

        VARIATION       tnCNLinkRouterAdvPreferredLifeTime
            ACCESS      not-implemented
            DESCRIPTION "This object is not supported."

        VARIATION       tnCNLinkRouterAdvSendAdvertState
            ACCESS      not-implemented
            DESCRIPTION "This object is not supported."

        VARIATION       tnCNLinkRouterAdvValidLifeTime
            ACCESS      not-implemented
            DESCRIPTION "This object is not supported."

        VARIATION       tnCNLinkOspfv3HelloInterval
            ACCESS      not-implemented
            DESCRIPTION "This object is not supported."

        VARIATION       tnCNLinkOspfv3TeMetric
            ACCESS      not-implemented
            DESCRIPTION "This object is not supported."

        VARIATION       tnCNLinkOspfv3Retransint
            ACCESS      not-implemented
            DESCRIPTION "This object is not supported."

        VARIATION       tnCNLinkOspfv3RtrDeadInterval
            ACCESS      not-implemented
            DESCRIPTION "This object is not supported."

        VARIATION       tnCNLinkOspfv3ConfigRtrPriority
            ACCESS      not-implemented
            DESCRIPTION "This object is not supported."

        VARIATION       tnCNLinkOspfv3RoutingState
            ACCESS      not-implemented
            DESCRIPTION "This object is not supported."

        VARIATION       tnCNLinkOspfOscRoutingState
            ACCESS      not-implemented
            DESCRIPTION "This object is not supported."

        VARIATION       tnCNLinkOspfv6OscRoutingState
            ACCESS      not-implemented
            DESCRIPTION "This object is not supported."

        VARIATION       tnCNLinkDHCPBootFileName
            ACCESS      not-implemented
            DESCRIPTION "This object is not supported."

        VARIATION       tnCNLinkDHCPClassName
            ACCESS      not-implemented
            DESCRIPTION "This object is not supported."

        VARIATION       tnNetIfIndex
            DESCRIPTION "The value of this object is mapped on the port
                         number, see description ifIndex (IF-MIB).
                         For OTN system modes:
                         - The system creates a maximum of 3 entries in the
                           tnNetIfTable:
                           1) NETWORK1(1)
                           2) NETWORK2(2)
                           3) CLIENT1(3), this is only applicable for OTN
                              Client system modes:
                              - otnNidOtu1ClientOtu1NetworkMode(6)
                              - otnNidOtu2ClientOtu2NetworkMode(7)
                              - otnNidOtu2eClientOtu2eNetworkMode(8)
                         - Only one HDLC channel can be locally terminated per
                           physical interface.
                         For the ethNid1GbEor10GbEClient10GbENetworkMode(9)
                         system mode the system creates one entry in the
                         tnNetIfTable:
                           1) NETWORK(129)"

        VARIATION       tnNetIfTypeOfOperation
            ACCESS      not-implemented
            DESCRIPTION "This object is not supported."

        VARIATION       tnNetIfStatus
            DESCRIPTION "The value cannot be set to enabled in the
                         following cases:
                         1) For OTN system modes:
                            otnNid1GbeClientOtu1NetworkMode(2)
                            otnNid1GbeClientOtu2NetworkMode(3)
                            otnNid10GbeClientOtu2NetworkMode(4)
                            otnNid10GbeClientOtu2eNetworkMode(5)
                            otnNidOtu1ClientOtu1NetworkMode(6)
                            otnNidOtu2ClientOtu2NetworkMode(7)
                            otnNidOtu2eClientOtu2eNetworkMode(8)
                            otnNid1GbEor10GbEClientOtu2OduFlexNetworkMode(10)
                           - when no tnNetIfFacility is added for this object.
                           - when the value of tnPsdManualIpv4AddressAddr for
                           the loopback interface equals all zero.
                         2) For the ethNid1GbEor10GbEClient10GbENetworkMode
                            system mode:
                           - when no tnPsdNetIfEthFacility is added for this
                             object.
                           - when the value of tnPsdNetIfIpAddr equals an all
                             zero IPv4 address."

        VARIATION       tnNetIfPacketType
            SYNTAX      INTEGER { std(1) }
            DESCRIPTION "Limited set of values."

        VARIATION       tnNetIfMtu
            SYNTAX      Integer32 (1500)
            DESCRIPTION "The value is fixed set to 1500."

        VARIATION       tnNetIfHelloInterval
            ACCESS      not-implemented
            DESCRIPTION "This object is not supported."

        VARIATION       tnNetIfRtrDeadInterval
            ACCESS      not-implemented
            DESCRIPTION "This object is not supported."

        VARIATION       tnNetIfMetric
            ACCESS      not-implemented
            DESCRIPTION "This object is not supported."

        VARIATION       tnNetIfOspfAuthentType
            ACCESS      not-implemented
            DESCRIPTION "This object is not supported."

        VARIATION       tnNetIfOspfAuthKey
            ACCESS      not-implemented
            DESCRIPTION "This object is not supported."

        VARIATION       tnNetIfOspfAuthKeyId
            ACCESS      not-implemented
            DESCRIPTION "This object is not supported."

        VARIATION       tnNetIfCnLinkAdjState
            ACCESS      not-implemented
            DESCRIPTION "This object is not supported."

        VARIATION       tnNetIfOSPFAreaNumberId
            ACCESS      not-implemented
            DESCRIPTION "This object is not supported."

        VARIATION       tnNetIfOspfRetransint
            ACCESS      not-implemented
            DESCRIPTION "This object is not supported."

        VARIATION       tnNetIfOspfv3AdjStateId
            ACCESS      not-implemented
            DESCRIPTION "This object is not supported."

        VARIATION       tnNetIfOspfNeighborRouterIp
            ACCESS      not-implemented
            DESCRIPTION "This object is not supported."

        VARIATION       tnNetIfOspfv3NeighborRouterIp
            ACCESS      not-implemented
            DESCRIPTION "This object is not supported."

        VARIATION       tnNetIfOspfNeighborIp
            ACCESS      not-implemented
            DESCRIPTION "This object is not supported."

        VARIATION       tnNetIfOspfv3NeighborInetAddress
            ACCESS      not-implemented
            DESCRIPTION "This object is not supported."

        VARIATION       tnNetIfIPv6LinkLocalInetAddress
            ACCESS      not-implemented
            DESCRIPTION "This object is not supported."

        VARIATION       tnNetIfLcpEchoInterval
            ACCESS      not-implemented
            DESCRIPTION "This object is not supported."

        VARIATION       tnNetIfLcpEchoFailure
            ACCESS      not-implemented
            DESCRIPTION "This object is not supported."

        VARIATION       tnNetIfOspfStatus
            ACCESS      not-implemented
            DESCRIPTION "This object is not supported."

        VARIATION       tnNetIfOspfv3AreaNumberId
            ACCESS      not-implemented
            DESCRIPTION "This object is not supported."

        VARIATION       tnNetIfOspfv3HelloInterval
            ACCESS      not-implemented
            DESCRIPTION "This object is not supported."

        VARIATION       tnNetIfOspfv3Metric
            ACCESS      not-implemented
            DESCRIPTION "This object is not supported."

        VARIATION       tnNetIfOspfv3Retransint
            ACCESS      not-implemented
            DESCRIPTION "This object is not supported."

        VARIATION       tnNetIfOspfv3RtrDeadInterval
            ACCESS      not-implemented
            DESCRIPTION "This object is not supported."

        VARIATION       tnNetIfOspfv3ConfigRtrPriority
            ACCESS      not-implemented
            DESCRIPTION "This object is not supported."

        VARIATION       tnNetIfOspfv3Status
            ACCESS      not-implemented
            DESCRIPTION "This object is not supported."

        VARIATION       tnNetIfFacilityIfIndex
            DESCRIPTION "The index value uses the same encoding rules as
                         applied to tnOthIfIndex (see description
                         tnOthIfIndex).
                         In OTN system modes
                         - otnNid1GbeClientOtu1NetworkMode(2)
                         - otnNid1GbeClientOtu2NetworkMode(3)
                         - otnNid10GbeClientOtu2NetworkMode(4)
                         - otnNid10GbeClientOtu2eNetworkMode(5)
                         - otnNidOtu1ClientOtu1NetworkMode(6)
                         - otnNidOtu2ClientOtu2NetworkMode(7)
                         - otnNidOtu2eClientOtu2eNetworkMode(8)
                         - otnNid1GbEor10GbEClientOtu2OduFlexNetworkMode(10)
                         entries can be added to the tnNetIfFacilityTable."

        VARIATION       tnNetIfFacilityIfIndexLo
            DESCRIPTION "The index value uses the same encoding rules as
                         applied to tnOthIfIndexLo (see description
                         tnOthIfIndexLo), with the difference that the LO-ODU
                         fields are not used, i.e. have zero values. This is
                         due to NetIfFacility functionality only being
                         supported at Ho-ODU level.
                         For gcc0 (i.e. OTU index) identification HO-ODU type
                         is set to NULL and the Container type is set to
                         OTU_GCC(8).
                         For gcc1/gcc2 the Container type is 'Higher-Order
                         ODU NIM' for all OTN system modes except mode
                         otnNid1GbEor10GbEClientOtu2OduFlexNetworkMode(10),
                         for which the Container type is 'ODU TP', due to the
                         NetIfFacility being related to the Odu2P instance of
                         the Network port. In the other OTN system modes the
                         NetIfFacility is related to the ODUkPm instance of
                         the Network port.
                         See description tnNetIfFacilityIfIndex for
                         system mode details."

        VARIATION       tnNetIfFacilityTypeOfOperation
            DESCRIPTION "In OTN system modes (see description
                         tnNetIfFacilityIfIndex for details) it is allowed
                         to create or remove entries in the
                         tnNetIfFacilityTable.
                         Operation empty(1) fails in case the corresponding
                         tnNetIfIndex is in use by a static IP route and
                         when tnNetIfStatus is equal to enabled(1).
                         In case padding is enabled on the tnNetIfEntry
                         (CLI-only feature) the deletion of the facility
                         by setting the value of this object to empty(1)
                         is rejected. Padding must first be disabled using
                         the CLI, then it is permitted to delete this
                         facility."

--
-- Capabilities for TROPIC-STATISTICS-MIB
-- Based on MIB version:  R15.0-LatestMIBs-221105
--
    SUPPORTS            TROPIC-STATISTICS-MIB
        INCLUDES        { tnOtuStatsPortGroup,
                          tnOthOtukStatsGroup,
                          tnOthOdukStatsTcmEnableGroup,
                          tnOthOdukStatsTcmConfigGroup,
                          tnOthOdukStatsTcmGroup,
                          tnOthOdukStatsControlGroup,
                          tnOthOdukStatsRxConfigGroup,
                          tnOthOdukStatsRxGroup,
                          tnStatsTCAProfileGroup,
                          tnStatsTCAGroup,
                          tnOthOtukStatsThresholdScalarsGroup,
                          tnTcmStatsThresholdScalarsGroup,
                          tnOthOdukStatsRxThresholdScalarsGroup }

        VARIATION       tnOtuStatsPortIntervalLength
            SYNTAX      Unsigned32 ( 900 | 86400 )
            DESCRIPTION "The value is fixed and depends on the tnStatsInterval
                         value.
                         For 15 minute interval (tnStatsInterval = 0) : 900
                         For 1 day interval     (tnStatsInterval = 1) : 86400."

        VARIATION       tnOtuStatsPortNumberOfBins
            SYNTAX      Unsigned32 ( 1 | 96 )
            DESCRIPTION "The value is fixed and depends on the tnStatsInterval
                         value.
                         For 15 minute interval (tnStatsInterval = 0) : 96
                         For 1 day interval     (tnStatsInterval = 1) : 1."

        VARIATION       tnOtuStatsPortProfileId
            SYNTAX      Unsigned32 ( 1 | 2 | 8 )
            DESCRIPTION "Limited set of values. Three profiles can be selected:
                         1=Disabled: all TCA values are zero, read only.
                         2=User: user can provision TCA values, read write.
                         8=Default: all TCA values are set to default values,
                           read-only."

        VARIATION       tnOtuStatsPortIntervalLength1day
            ACCESS      not-implemented
            DESCRIPTION "This object is not supported."

        VARIATION       tnOtuStatsPortNumberOfBins1day
            ACCESS      not-implemented
            DESCRIPTION "This object is not supported."

        VARIATION       tnOtuStatsPortProfileId1day
            ACCESS      not-implemented
            DESCRIPTION "This object is not supported."

        VARIATION       tnOtuStatsPortEnable
            SYNTAX      INTEGER { enable(1) }
            DESCRIPTION "The value of this object is fixed to enable(1)."

        VARIATION       tnOthOtukStatsBin
            DESCRIPTION "Only the current bin (value 0) can be retrieved
                         with SNMP GET command query. History bins
                         (bin number 1 and greater) can only be retrieved using
                         PM file transfer."

        VARIATION       tnOthOtukStatsBinStatus
            SYNTAX      INTEGER { partial(6), adjusted(7), dataLong(8), dataComplete(9) }
            DESCRIPTION "Limit set of values.
                         The values have the following meaning:
                          partial:  the bin misses more than 10 seconds for the interval
                          adjusted: the bin counters were reset during the interval
                          dataLong: the bin contains more than 10 seconds too many for
                                    the interval
                          dataComplete: none of the above, normal interval"

        VARIATION       tnOthOtukStatRxRsUncorrCnt
            ACCESS      not-implemented
            DESCRIPTION "This object is not supported."

        VARIATION       tnOthOtukStatRxBERPreFEC
            ACCESS      not-implemented
            DESCRIPTION "This object is not supported."

        VARIATION       tnOthOtukStatRxBERPostFEC
            ACCESS      not-implemented
            DESCRIPTION "This object is not supported."

        VARIATION       tnOthOtukStatNeRxBIAESErrCnt
            ACCESS      not-implemented
            DESCRIPTION "This object is not supported."

        VARIATION       tnOthOtukStatNeRxIAES
            ACCESS      not-implemented
            DESCRIPTION "This object is not supported."

        VARIATION       tnOthOtukStatFeRxIAES
            ACCESS      not-implemented
            DESCRIPTION "This object is not supported."

        VARIATION       tnOthOdukStatsTcmClearAll
            ACCESS      not-implemented
            DESCRIPTION "This object is not supported."

        VARIATION       tnOthOdukStatsTcmEnable
            SYNTAX      INTEGER { enable(1) }
            DESCRIPTION "The value of this object is fixed to enable(1)."

        VARIATION       tnOthOdukStatsTcmBin
            DESCRIPTION "Only the current bin (value 0) can be retrieved
                         with SNMP GET command query. History bins
                         (bin number 1 and greater) can only be retrieved using
                         PM file transfer."

        VARIATION       tnOthOdukStatsTcmConfigNumberOfBins
            SYNTAX      Unsigned32 ( 1 | 96 )
            DESCRIPTION "The value is fixed and depends on the tnStatsInterval
                         value.
                         For 15 minute interval (tnStatsInterval = 0) : 96
                         For 1 day interval     (tnStatsInterval = 1) : 1."

        VARIATION       tnOthOdukStatsTcmConfigProfileId
            SYNTAX      Unsigned32 ( 1 | 2 | 8 )
            DESCRIPTION "Limited set of values. Three profiles can be selected:
                         1=Disabled: all TCA values are zero, read only.
                         2=User: user can provision TCA values, read write.
                         8=Default: all TCA values are set to default values,
                           read-only."

        VARIATION       tnOthOdukStatsTcmConfigIntervalLength
            ACCESS      not-implemented
            DESCRIPTION "This object is not supported."

        VARIATION       tnOthOdukStatsTcmBinStatus
            SYNTAX      INTEGER { partial(6), adjusted(7), dataLong(8), dataComplete(9) }
            DESCRIPTION "Limit set of values.
                         The values have the following meaning:
                          partial:  the bin misses more than 10 seconds for the interval
                          adjusted: the bin counters were reset during the interval
                          dataLong: the bin contains more than 10 seconds too many for
                                    the interval
                          dataComplete: none of the above, normal interval"

        VARIATION       tnOthOdukStatsTcmNeRxIAESErrCnt
            ACCESS      not-implemented
            DESCRIPTION "This object is not supported."

        VARIATION       tnOthOdukStatsTcmFeRxBIAESErrCnt
            ACCESS      not-implemented
            DESCRIPTION "This object is not supported."

        VARIATION       tnOthOdukStatsClearAll
            ACCESS      not-implemented
            DESCRIPTION "This object is not supported."

        VARIATION       tnOthOdukStatsRxEnable
            SYNTAX      INTEGER { enable(1) }
            DESCRIPTION "The value of this object is fixed to enable(1)."

        VARIATION       tnOthOdukStatsTxEnable
            SYNTAX      INTEGER { disable(2) }
            DESCRIPTION "The value of this object is fixed to disable(2)."

        VARIATION       tnOthOdukStatsBin
            DESCRIPTION "Only the current bin (value 0) can be retrieved
                         with SNMP GET command query. History bins
                         (bin number 1 and greater) can only be retrieved using
                         PM file transfer."

        VARIATION       tnOthOdukStatsRxNumberofBins
            SYNTAX      Unsigned32 ( 1 | 96 )
            DESCRIPTION "The value is fixed and depends on the tnStatsInterval
                         value.
                         For 15 minute interval (tnStatsInterval = 0) : 96
                         For 1 day interval     (tnStatsInterval = 1) : 1."

        VARIATION       tnOthOdukStatsRxProfileid
            SYNTAX      Unsigned32 ( 1 | 2 | 8 )
            DESCRIPTION "Limited set of values. Three profiles can be selected:
                         1=Disabled: all TCA values are zero, read only.
                         2=User: user can provision TCA values, read write.
                         8=Default: all TCA values are set to default values,
                           read-only."

        VARIATION       tnOthOdukStatsRxIntervalLength
            SYNTAX      Unsigned32 ( 900 | 86400 )
            DESCRIPTION "The value is fixed and depends on the tnStatsInterval
                         value.
                         For 15 minute interval (tnStatsInterval = 0) : 900
                         For 1 day interval     (tnStatsInterval = 1) : 86400."

        VARIATION       tnOthOdukStatsRxBinStatus
            SYNTAX      INTEGER { partial(6), adjusted(7), dataLong(8), dataComplete(9) }
            DESCRIPTION "Limit set of values.
                         The values have the following meaning:
                          partial:  the bin misses more than 10 seconds for the interval
                          adjusted: the bin counters were reset during the interval
                          dataLong: the bin contains more than 10 seconds too many for
                                    the interval
                          dataComplete: none of the above, normal interval"

        VARIATION       tnStatsTCAProfileId
            SYNTAX      Unsigned32 ( 1 | 2 | 8 )
            DESCRIPTION "Three profiles are created by the system:
                         1=Disabled: all TCA values are zero, read only.
                         2=User: user can provision TCA values, read write.
                         8=Default: all TCA values are set to default values,
                           read-only."

        VARIATION       tnStatsTCAProfileDescr
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnStatsTCAValue
            DESCRIPTION "Only the TCA value for profileId 2 can be modified.
                         The TCA values for profileId 1 and 8 are read-only."

        VARIATION       tnOthOtu1StatRxRsCorrCnt15MinTr
            ACCESS      not-implemented
            DESCRIPTION "This object is not supported."

        VARIATION       tnOthOtu1StatRxRsCorrCnt15MinRtr
            ACCESS      not-implemented
            DESCRIPTION "This object is not supported."

        VARIATION       tnOthOtu1StatRxRsCorrCnt1DayTr
            ACCESS      not-implemented
            DESCRIPTION "This object is not supported."

        VARIATION       tnOthOtu1StatRxRsUncorrCnt15MinTr
            ACCESS      not-implemented
            DESCRIPTION "This object is not supported."

        VARIATION       tnOthOtu1StatRxRsUncorrCnt15MinRtr
            ACCESS      not-implemented
            DESCRIPTION "This object is not supported."

        VARIATION       tnOthOtu1StatRxRsUncorrCnt1DayTr
            ACCESS      not-implemented
            DESCRIPTION "This object is not supported."

        VARIATION       tnOthOtu1StatRxNeSMBIP8ErrCnt15MinRtr
            ACCESS      not-implemented
            DESCRIPTION "This object is not supported."

        VARIATION       tnOthOtu1StatRxFeSMBIP8ErrCnt15MinRtr
            ACCESS      not-implemented
            DESCRIPTION "This object is not supported."

        VARIATION       tnOthOtu2StatRxRsCorrCnt15MinTr
            ACCESS      not-implemented
            DESCRIPTION "This object is not supported."

        VARIATION       tnOthOtu2StatRxRsCorrCnt15MinRtr
            ACCESS      not-implemented
            DESCRIPTION "This object is not supported."

        VARIATION       tnOthOtu2StatRxRsCorrCnt1DayTr
            ACCESS      not-implemented
            DESCRIPTION "This object is not supported."

        VARIATION       tnOthOtu2StatRxRsUncorrCnt15MinTr
            ACCESS      not-implemented
            DESCRIPTION "This object is not supported."

        VARIATION       tnOthOtu2StatRxRsUncorrCnt15MinRtr
            ACCESS      not-implemented
            DESCRIPTION "This object is not supported."

        VARIATION       tnOthOtu2StatRxRsUncorrCnt1DayTr
            ACCESS      not-implemented
            DESCRIPTION "This object is not supported."

        VARIATION       tnOthOtu2StatRxNeSMBIP8ErrCnt15MinRtr
            ACCESS      not-implemented
            DESCRIPTION "This object is not supported."

        VARIATION       tnOthOtu2StatRxFeSMBIP8ErrCnt15MinRtr
            ACCESS      not-implemented
            DESCRIPTION "This object is not supported."

        VARIATION       tnOthOtu3StatRxRsCorrCnt15MinTr
            ACCESS      not-implemented
            DESCRIPTION "This object is not supported."

        VARIATION       tnOthOtu3StatRxRsCorrCnt15MinRtr
            ACCESS      not-implemented
            DESCRIPTION "This object is not supported."

        VARIATION       tnOthOtu3StatRxRsCorrCnt1DayTr
            ACCESS      not-implemented
            DESCRIPTION "This object is not supported."

        VARIATION       tnOthOtu3StatRxRsUncorrCnt15MinTr
            ACCESS      not-implemented
            DESCRIPTION "This object is not supported."

        VARIATION       tnOthOtu3StatRxRsUncorrCnt15MinRtr
            ACCESS      not-implemented
            DESCRIPTION "This object is not supported."

        VARIATION       tnOthOtu3StatRxRsUncorrCnt1DayTr
            ACCESS      not-implemented
            DESCRIPTION "This object is not supported."

        VARIATION       tnOthOtu3StatRxNeSMBIP8ErrCnt15MinTr
            ACCESS      not-implemented
            DESCRIPTION "This object is not supported."

        VARIATION       tnOthOtu3StatRxNeSMBIP8ErrCnt15MinRtr
            ACCESS      not-implemented
            DESCRIPTION "This object is not supported."

        VARIATION       tnOthOtu3StatRxNeSMBIP8ErrCnt1DayTr
            ACCESS      not-implemented
            DESCRIPTION "This object is not supported."

        VARIATION       tnOthOtu3StatRxFeSMBIP8ErrCnt15MinTr
            ACCESS      not-implemented
            DESCRIPTION "This object is not supported."

        VARIATION       tnOthOtu3StatRxFeSMBIP8ErrCnt15MinRtr
            ACCESS      not-implemented
            DESCRIPTION "This object is not supported."

        VARIATION       tnOthOtu3StatRxFeSMBIP8ErrCnt1DayTr
            ACCESS      not-implemented
            DESCRIPTION "This object is not supported."

        VARIATION       tnOthOtu4StatRxRsCorrCnt15MinTr
            ACCESS      not-implemented
            DESCRIPTION "This object is not supported."

        VARIATION       tnOthOtu4StatRxRsCorrCnt15MinRtr
            ACCESS      not-implemented
            DESCRIPTION "This object is not supported."

        VARIATION       tnOthOtu4StatRxRsCorrCnt1DayTr
            ACCESS      not-implemented
            DESCRIPTION "This object is not supported."

        VARIATION       tnOthOtu4StatRxRsUncorrCnt15MinTr
            ACCESS      not-implemented
            DESCRIPTION "This object is not supported."

        VARIATION       tnOthOtu4StatRxRsUncorrCnt15MinRtr
            ACCESS      not-implemented
            DESCRIPTION "This object is not supported."

        VARIATION       tnOthOtu4StatRxRsUncorrCnt1DayTr
            ACCESS      not-implemented
            DESCRIPTION "This object is not supported."

        VARIATION       tnOthOtu4StatRxNeSMBIP8ErrCnt15MinTr
            ACCESS      not-implemented
            DESCRIPTION "This object is not supported."

        VARIATION       tnOthOtu4StatRxNeSMBIP8ErrCnt15MinRtr
            ACCESS      not-implemented
            DESCRIPTION "This object is not supported."

        VARIATION       tnOthOtu4StatRxNeSMBIP8ErrCnt1DayTr
            ACCESS      not-implemented
            DESCRIPTION "This object is not supported."

        VARIATION       tnOthOtu4StatRxFeSMBIP8ErrCnt15MinTr
            ACCESS      not-implemented
            DESCRIPTION "This object is not supported."

        VARIATION       tnOthOtu4StatRxFeSMBIP8ErrCnt15MinRtr
            ACCESS      not-implemented
            DESCRIPTION "This object is not supported."

        VARIATION       tnOthOtu4StatRxFeSMBIP8ErrCnt1DayTr
            ACCESS      not-implemented
            DESCRIPTION "This object is not supported."

        VARIATION       tnOthOtukStatRxBERPreFEC15MinTr
            ACCESS      not-implemented
            DESCRIPTION "This object is not supported."

        VARIATION       tnOthOtukStatRxBERPreFEC15MinRtr
            ACCESS      not-implemented
            DESCRIPTION "This object is not supported."

        VARIATION       tnOthOtukStatRxBERPreFEC1DayTr
            ACCESS      not-implemented
            DESCRIPTION "This object is not supported."

        VARIATION       tnOthOtukStatRxBERPostFEC15MinTr
            ACCESS      not-implemented
            DESCRIPTION "This object is not supported."

        VARIATION       tnOthOtukStatRxBERPostFEC15MinRtr
            ACCESS      not-implemented
            DESCRIPTION "This object is not supported."

        VARIATION       tnOthOtukStatRxBERPostFEC1DayTr
            ACCESS      not-implemented
            DESCRIPTION "This object is not supported."

        VARIATION       tnOthOtukStatRxNeSMES15MinRtr
            ACCESS      not-implemented
            DESCRIPTION "This object is not supported."

        VARIATION       tnOthOtukStatRxFeSMES15MinRtr
            ACCESS      not-implemented
            DESCRIPTION "This object is not supported."

        VARIATION       tnOthOtukStatRxNeSMSES15MinRtr
            ACCESS      not-implemented
            DESCRIPTION "This object is not supported."

        VARIATION       tnOthOtukStatRxFeSMSES15MinRtr
            ACCESS      not-implemented
            DESCRIPTION "This object is not supported."

        VARIATION       tnOthOtukStatRxNeSMUAS15MinRtr
            ACCESS      not-implemented
            DESCRIPTION "This object is not supported."

        VARIATION       tnOthOtukStatRxFeSMUAS15MinRtr
            ACCESS      not-implemented
            DESCRIPTION "This object is not supported."

        VARIATION       tnOthOtukStatRxNeIAES15MinTr
            ACCESS      not-implemented
            DESCRIPTION "This object is not supported."

        VARIATION       tnOthOtukStatRxNeIAES15MinRtr
            ACCESS      not-implemented
            DESCRIPTION "This object is not supported."

        VARIATION       tnOthOtukStatRxNeIAES1DayTr
            ACCESS      not-implemented
            DESCRIPTION "This object is not supported."

        VARIATION       tnOthOtukStatRxFeIAES15MinTr
            ACCESS      not-implemented
            DESCRIPTION "This object is not supported."

        VARIATION       tnOthOtukStatRxFeIAES15MinRtr
            ACCESS      not-implemented
            DESCRIPTION "This object is not supported."

        VARIATION       tnOthOtukStatRxFeIAES1DayTr
            ACCESS      not-implemented
            DESCRIPTION "This object is not supported."

        VARIATION       tnOthOtucStatRxNeSMBIP8ErrCnt15MinTr
            ACCESS      not-implemented
            DESCRIPTION "This object is not supported."

        VARIATION       tnOthOtucStatRxNeSMBIP8ErrCnt15MinRtr
            ACCESS      not-implemented
            DESCRIPTION "This object is not supported."

        VARIATION       tnOthOtucStatRxNeSMBIP8ErrCnt1DayTr
            ACCESS      not-implemented
            DESCRIPTION "This object is not supported."

        VARIATION       tnOthOtucStatRxFeSMBIP8ErrCnt15MinTr
            ACCESS      not-implemented
            DESCRIPTION "This object is not supported."

        VARIATION       tnOthOtucStatRxFeSMBIP8ErrCnt15MinRtr
            ACCESS      not-implemented
            DESCRIPTION "This object is not supported."

        VARIATION       tnOthOtucStatRxFeSMBIP8ErrCnt1DayTr
            ACCESS      not-implemented
            DESCRIPTION "This object is not supported."

        VARIATION       tnOthOtutc1StatRxNeSMBIP8ErrCnt15MinTr
            ACCESS      not-implemented
            DESCRIPTION "This object is not supported."

        VARIATION       tnOthOtutc1StatRxNeSMBIP8ErrCnt15MinRtr
            ACCESS      not-implemented
            DESCRIPTION "This object is not supported."

        VARIATION       tnOthOtutc1StatRxNeSMBIP8ErrCnt1DayTr
            ACCESS      not-implemented
            DESCRIPTION "This object is not supported."

        VARIATION       tnOthOtutc1StatRxFeSMBIP8ErrCnt15MinTr
            ACCESS      not-implemented
            DESCRIPTION "This object is not supported."

        VARIATION       tnOthOtutc1StatRxFeSMBIP8ErrCnt15MinRtr
            ACCESS      not-implemented
            DESCRIPTION "This object is not supported."

        VARIATION       tnOthOtutc1StatRxFeSMBIP8ErrCnt1DayTr
            ACCESS      not-implemented
            DESCRIPTION "This object is not supported."

        VARIATION       tnOthOtutc4StatRxNeSMBIP8ErrCnt15MinTr
            ACCESS      not-implemented
            DESCRIPTION "This object is not supported."

        VARIATION       tnOthOtutc4StatRxNeSMBIP8ErrCnt15MinRtr
            ACCESS      not-implemented
            DESCRIPTION "This object is not supported."

        VARIATION       tnOthOtutc4StatRxNeSMBIP8ErrCnt1DayTr
            ACCESS      not-implemented
            DESCRIPTION "This object is not supported."

        VARIATION       tnOthOtutc4StatRxFeSMBIP8ErrCnt15MinTr
            ACCESS      not-implemented
            DESCRIPTION "This object is not supported."

        VARIATION       tnOthOtutc4StatRxFeSMBIP8ErrCnt15MinRtr
            ACCESS      not-implemented
            DESCRIPTION "This object is not supported."

        VARIATION       tnOthOtutc4StatRxFeSMBIP8ErrCnt1DayTr
            ACCESS      not-implemented
            DESCRIPTION "This object is not supported."

        VARIATION       tnOthOdu0StatsTcmNeRxBIP8ErrCnt15MinTr
            ACCESS      not-implemented
            DESCRIPTION "This object is not supported."

        VARIATION       tnOthOdu0StatsTcmNeRxBIP8ErrCnt15MinRtr
            ACCESS      not-implemented
            DESCRIPTION "This object is not supported."

        VARIATION       tnOthOdu0StatsTcmNeRxBIP8ErrCnt1DayTr
            ACCESS      not-implemented
            DESCRIPTION "This object is not supported."

        VARIATION       tnOthOdu0StatsTcmFeRxBIP8ErrCnt15MinTr
            ACCESS      not-implemented
            DESCRIPTION "This object is not supported."

        VARIATION       tnOthOdu0StatsTcmFeRxBIP8ErrCnt15MinRtr
            ACCESS      not-implemented
            DESCRIPTION "This object is not supported."

        VARIATION       tnOthOdu0StatsTcmFeRxBIP8ErrCnt1DayTr
            ACCESS      not-implemented
            DESCRIPTION "This object is not supported."

        VARIATION       tnOthOdu1StatsTcmNeRxBIP8ErrCnt15MinRtr
            ACCESS      not-implemented
            DESCRIPTION "This object is not supported."

        VARIATION       tnOthOdu1StatsTcmFeRxBIP8ErrCnt15MinRtr
            ACCESS      not-implemented
            DESCRIPTION "This object is not supported."

        VARIATION       tnOthOdu2StatsTcmNeRxBIP8ErrCnt15MinRtr
            ACCESS      not-implemented
            DESCRIPTION "This object is not supported."

        VARIATION       tnOthOdu2StatsTcmFeRxBIP8ErrCnt15MinRtr
            ACCESS      not-implemented
            DESCRIPTION "This object is not supported."

        VARIATION       tnOthOdu3StatsTcmNeRxBIP8ErrCnt15MinTr
            ACCESS      not-implemented
            DESCRIPTION "This object is not supported."

        VARIATION       tnOthOdu3StatsTcmNeRxBIP8ErrCnt15MinRtr
            ACCESS      not-implemented
            DESCRIPTION "This object is not supported."

        VARIATION       tnOthOdu3StatsTcmNeRxBIP8ErrCnt1DayTr
            ACCESS      not-implemented
            DESCRIPTION "This object is not supported."

        VARIATION       tnOthOdu3StatsTcmFeRxBIP8ErrCnt15MinTr
            ACCESS      not-implemented
            DESCRIPTION "This object is not supported."

        VARIATION       tnOthOdu3StatsTcmFeRxBIP8ErrCnt15MinRtr
            ACCESS      not-implemented
            DESCRIPTION "This object is not supported."

        VARIATION       tnOthOdu3StatsTcmFeRxBIP8ErrCnt1DayTr
            ACCESS      not-implemented
            DESCRIPTION "This object is not supported."

        VARIATION       tnOthOdu4StatsTcmNeRxBIP8ErrCnt15MinTr
            ACCESS      not-implemented
            DESCRIPTION "This object is not supported."

        VARIATION       tnOthOdu4StatsTcmNeRxBIP8ErrCnt15MinRtr
            ACCESS      not-implemented
            DESCRIPTION "This object is not supported."

        VARIATION       tnOthOdu4StatsTcmNeRxBIP8ErrCnt1DayTr
            ACCESS      not-implemented
            DESCRIPTION "This object is not supported."

        VARIATION       tnOthOdu4StatsTcmFeRxBIP8ErrCnt15MinTr
            ACCESS      not-implemented
            DESCRIPTION "This object is not supported."

        VARIATION       tnOthOdu4StatsTcmFeRxBIP8ErrCnt15MinRtr
            ACCESS      not-implemented
            DESCRIPTION "This object is not supported."

        VARIATION       tnOthOdu4StatsTcmFeRxBIP8ErrCnt1DayTr
            ACCESS      not-implemented
            DESCRIPTION "This object is not supported."

        VARIATION       tnOthOdukStatsTcmNeRxES15MinRtr
            ACCESS      not-implemented
            DESCRIPTION "This object is not supported."

        VARIATION       tnOthOdukStatsTcmFeRxES15MinRtr
            ACCESS      not-implemented
            DESCRIPTION "This object is not supported."

        VARIATION       tnOthOdukStatsTcmNeRxSES15MinRtr
            ACCESS      not-implemented
            DESCRIPTION "This object is not supported."

        VARIATION       tnOthOdukStatsTcmFeRxSES15MinRtr
            ACCESS      not-implemented
            DESCRIPTION "This object is not supported."

        VARIATION       tnOthOdukStatsTcmNeRxUAS15MinRtr
            ACCESS      not-implemented
            DESCRIPTION "This object is not supported."

        VARIATION       tnOthOdukStatsTcmFeRxUAS15MinRtr
            ACCESS      not-implemented
            DESCRIPTION "This object is not supported."

        VARIATION       tnOthOduflexGFPStatsTcmNeRxBIP8ErrCnt15MinTr
            ACCESS      not-implemented
            DESCRIPTION "This object is not supported."

        VARIATION       tnOthOduflexGFPStatsTcmNeRxBIP8ErrCnt1DayTr
            ACCESS      not-implemented
            DESCRIPTION "This object is not supported."

        VARIATION       tnOthOduflexGFPStatsTcmFeRxBIP8ErrCnt15MinTr
            ACCESS      not-implemented
            DESCRIPTION "This object is not supported."

        VARIATION       tnOthOduflexGFPStatsTcmFeRxBIP8ErrCnt1DayTr
            ACCESS      not-implemented
            DESCRIPTION "This object is not supported."

        VARIATION       tnOthOduflexFC400StatsTcmNeRxBIP8ErrCnt15MinTr
            ACCESS      not-implemented
            DESCRIPTION "This object is not supported."

        VARIATION       tnOthOduflexFC400StatsTcmNeRxBIP8ErrCnt1DayTr
            ACCESS      not-implemented
            DESCRIPTION "This object is not supported."

        VARIATION       tnOthOduflexFC400StatsTcmFeRxBIP8ErrCnt15MinTr
            ACCESS      not-implemented
            DESCRIPTION "This object is not supported."

        VARIATION       tnOthOduflexFC400StatsTcmFeRxBIP8ErrCnt1DayTr
            ACCESS      not-implemented
            DESCRIPTION "This object is not supported."

        VARIATION       tnOthOduflexFC800StatsTcmNeRxBIP8ErrCnt15MinTr
            ACCESS      not-implemented
            DESCRIPTION "This object is not supported."

        VARIATION       tnOthOduflexFC800StatsTcmNeRxBIP8ErrCnt1DayTr
            ACCESS      not-implemented
            DESCRIPTION "This object is not supported."

        VARIATION       tnOthOduflexFC800StatsTcmFeRxBIP8ErrCnt15MinTr
            ACCESS      not-implemented
            DESCRIPTION "This object is not supported."

        VARIATION       tnOthOduflexFC800StatsTcmFeRxBIP8ErrCnt1DayTr
            ACCESS      not-implemented
            DESCRIPTION "This object is not supported."

        VARIATION       tnOthOduflexFC1600StatsTcmNeRxBIP8ErrCnt15MinTr
            ACCESS      not-implemented
            DESCRIPTION "This object is not supported."

        VARIATION       tnOthOduflexFC1600StatsTcmNeRxBIP8ErrCnt1DayTr
            ACCESS      not-implemented
            DESCRIPTION "This object is not supported."

        VARIATION       tnOthOduflexFC1600StatsTcmFeRxBIP8ErrCnt15MinTr
            ACCESS      not-implemented
            DESCRIPTION "This object is not supported."

        VARIATION       tnOthOduflexFC1600StatsTcmFeRxBIP8ErrCnt1DayTr
            ACCESS      not-implemented
            DESCRIPTION "This object is not supported."

        VARIATION       tnOthOduflexIBSDRStatsTcmNeRxBIP8ErrCnt15MinTr
            ACCESS      not-implemented
            DESCRIPTION "This object is not supported."

        VARIATION       tnOthOduflexIBSDRStatsTcmNeRxBIP8ErrCnt1DayTr
            ACCESS      not-implemented
            DESCRIPTION "This object is not supported."

        VARIATION       tnOthOduflexIBSDRStatsTcmFeRxBIP8ErrCnt15MinTr
            ACCESS      not-implemented
            DESCRIPTION "This object is not supported."

        VARIATION       tnOthOduflexIBSDRStatsTcmFeRxBIP8ErrCnt1DayTr
            ACCESS      not-implemented
            DESCRIPTION "This object is not supported."

        VARIATION       tnOthOduflexIBDDRStatsTcmNeRxBIP8ErrCnt15MinTr
            ACCESS      not-implemented
            DESCRIPTION "This object is not supported."

        VARIATION       tnOthOduflexIBDDRStatsTcmNeRxBIP8ErrCnt1DayTr
            ACCESS      not-implemented
            DESCRIPTION "This object is not supported."

        VARIATION       tnOthOduflexIBDDRStatsTcmFeRxBIP8ErrCnt15MinTr
            ACCESS      not-implemented
            DESCRIPTION "This object is not supported."

        VARIATION       tnOthOduflexIBDDRStatsTcmFeRxBIP8ErrCnt1DayTr
            ACCESS      not-implemented
            DESCRIPTION "This object is not supported."

        VARIATION       tnOthOduflexIBQDRStatsTcmNeRxBIP8ErrCnt15MinTr
            ACCESS      not-implemented
            DESCRIPTION "This object is not supported."

        VARIATION       tnOthOduflexIBQDRStatsTcmNeRxBIP8ErrCnt1DayTr
            ACCESS      not-implemented
            DESCRIPTION "This object is not supported."

        VARIATION       tnOthOduflexIBQDRStatsTcmFeRxBIP8ErrCnt15MinTr
            ACCESS      not-implemented
            DESCRIPTION "This object is not supported."

        VARIATION       tnOthOduflexIBQDRStatsTcmFeRxBIP8ErrCnt1DayTr
            ACCESS      not-implemented
            DESCRIPTION "This object is not supported."

        VARIATION       tnOthOduflex3GSDI18StatsTcmNeRxBIP8ErrCnt15MinTr
            ACCESS      not-implemented
            DESCRIPTION "This object is not supported."

        VARIATION       tnOthOduflex3GSDI18StatsTcmNeRxBIP8ErrCnt1DayTr
            ACCESS      not-implemented
            DESCRIPTION "This object is not supported."

        VARIATION       tnOthOduflex3GSDI18StatsTcmFeRxBIP8ErrCnt15MinTr
            ACCESS      not-implemented
            DESCRIPTION "This object is not supported."

        VARIATION       tnOthOduflex3GSDI18StatsTcmFeRxBIP8ErrCnt1DayTr
            ACCESS      not-implemented
            DESCRIPTION "This object is not supported."

        VARIATION       tnOthOduflex3GSDI19StatsTcmNeRxBIP8ErrCnt15MinTr
            ACCESS      not-implemented
            DESCRIPTION "This object is not supported."

        VARIATION       tnOthOduflex3GSDI19StatsTcmNeRxBIP8ErrCnt1DayTr
            ACCESS      not-implemented
            DESCRIPTION "This object is not supported."

        VARIATION       tnOthOduflex3GSDI19StatsTcmFeRxBIP8ErrCnt15MinTr
            ACCESS      not-implemented
            DESCRIPTION "This object is not supported."

        VARIATION       tnOthOduflex3GSDI19StatsTcmFeRxBIP8ErrCnt1DayTr
            ACCESS      not-implemented
            DESCRIPTION "This object is not supported."

        VARIATION       tnOthOduflexGFPStatsTcmFeRxBIP8ErrCnt15MinRtr
            ACCESS      not-implemented
            DESCRIPTION "This object is not supported."

        VARIATION       tnOthOduflexGFPStatsTcmNeRxBIP8ErrCnt15MinRtr
            ACCESS      not-implemented
            DESCRIPTION "This object is not supported."

        VARIATION       tnOthOduflexFC400StatsTcmFeRxBIP8ErrCnt15MinRtr
            ACCESS      not-implemented
            DESCRIPTION "This object is not supported."

        VARIATION       tnOthOduflexFC400StatsTcmNeRxBIP8ErrCnt15MinRtr
            ACCESS      not-implemented
            DESCRIPTION "This object is not supported."

        VARIATION       tnOthOduflexFC800StatsTcmFeRxBIP8ErrCnt15MinRtr
            ACCESS      not-implemented
            DESCRIPTION "This object is not supported."

        VARIATION       tnOthOduflexFC800StatsTcmNeRxBIP8ErrCnt15MinRtr
            ACCESS      not-implemented
            DESCRIPTION "This object is not supported."

        VARIATION       tnOthOduflexFC1600StatsTcmFeRxBIP8ErrCnt15MinRtr
            ACCESS      not-implemented
            DESCRIPTION "This object is not supported."

        VARIATION       tnOthOduflexFC1600StatsTcmNeRxBIP8ErrCnt15MinRtr
            ACCESS      not-implemented
            DESCRIPTION "This object is not supported."

        VARIATION       tnOthOduflexIBSDRStatsTcmFeRxBIP8ErrCnt15MinRtr
            ACCESS      not-implemented
            DESCRIPTION "This object is not supported."

        VARIATION       tnOthOduflexIBSDRStatsTcmNeRxBIP8ErrCnt15MinRtr
            ACCESS      not-implemented
            DESCRIPTION "This object is not supported."

        VARIATION       tnOthOduflexIBDDRStatsTcmFeRxBIP8ErrCnt15MinRtr
            ACCESS      not-implemented
            DESCRIPTION "This object is not supported."

        VARIATION       tnOthOduflexIBDDRStatsTcmNeRxBIP8ErrCnt15MinRtr
            ACCESS      not-implemented
            DESCRIPTION "This object is not supported."

        VARIATION       tnOthOduflexIBQDRStatsTcmFeRxBIP8ErrCnt15MinRtr
            ACCESS      not-implemented
            DESCRIPTION "This object is not supported."

        VARIATION       tnOthOduflexIBQDRStatsTcmNeRxBIP8ErrCnt15MinRtr
            ACCESS      not-implemented
            DESCRIPTION "This object is not supported."

        VARIATION       tnOthOduflex3GSDI18StatsTcmFeRxBIP8ErrCnt15MinRtr
            ACCESS      not-implemented
            DESCRIPTION "This object is not supported."

        VARIATION       tnOthOduflex3GSDI18StatsTcmNeRxBIP8ErrCnt15MinRtr
            ACCESS      not-implemented
            DESCRIPTION "This object is not supported."

        VARIATION       tnOthOduflex3GSDI19StatsTcmFeRxBIP8ErrCnt15MinRtr
            ACCESS      not-implemented
            DESCRIPTION "This object is not supported."

        VARIATION       tnOthOduflex3GSDI19StatsTcmNeRxBIP8ErrCnt15MinRtr
            ACCESS      not-implemented
            DESCRIPTION "This object is not supported."

        VARIATION       tnOthOducStatsTcmNeRxBIP8ErrCnt15MinTr
            ACCESS      not-implemented
            DESCRIPTION "This object is not supported."

        VARIATION       tnOthOducStatsTcmNeRxBIP8ErrCnt15MinRtr
            ACCESS      not-implemented
            DESCRIPTION "This object is not supported."

        VARIATION       tnOthOducStatsTcmNeRxBIP8ErrCnt1DayTr
            ACCESS      not-implemented
            DESCRIPTION "This object is not supported."

        VARIATION       tnOthOducStatsTcmFeRxBIP8ErrCnt15MinTr
            ACCESS      not-implemented
            DESCRIPTION "This object is not supported."

        VARIATION       tnOthOducStatsTcmFeRxBIP8ErrCnt15MinRtr
            ACCESS      not-implemented
            DESCRIPTION "This object is not supported."

        VARIATION       tnOthOducStatsTcmFeRxBIP8ErrCnt1DayTr
            ACCESS      not-implemented
            DESCRIPTION "This object is not supported."

        VARIATION       tnOthOduflex400GBEStatsTcmNeRxBIP8ErrCnt15MinTr
            ACCESS      not-implemented
            DESCRIPTION "This object is not supported."

        VARIATION       tnOthOduflex400GBEStatsTcmNeRxBIP8ErrCnt15MinRtr
            ACCESS      not-implemented
            DESCRIPTION "This object is not supported."

        VARIATION       tnOthOduflex400GBEStatsTcmNeRxBIP8ErrCnt1DayTr
            ACCESS      not-implemented
            DESCRIPTION "This object is not supported."

        VARIATION       tnOthOduflex400GBEStatsTcmFeRxBIP8ErrCnt15MinTr
            ACCESS      not-implemented
            DESCRIPTION "This object is not supported."

        VARIATION       tnOthOduflex400GBEStatsTcmFeRxBIP8ErrCnt15MinRtr
            ACCESS      not-implemented
            DESCRIPTION "This object is not supported."

        VARIATION       tnOthOduflex400GBEStatsTcmFeRxBIP8ErrCnt1DayTr
            ACCESS      not-implemented
            DESCRIPTION "This object is not supported."

        VARIATION       tnOthOdu0StatRxNeBIP8ErrCnt15MinTr
            ACCESS      not-implemented
            DESCRIPTION "This object is not supported."

        VARIATION       tnOthOdu0StatRxNeBIP8ErrCnt15MinRtr
            ACCESS      not-implemented
            DESCRIPTION "This object is not supported."

        VARIATION       tnOthOdu0StatRxNeBIP8ErrCnt1DayTr
            ACCESS      not-implemented
            DESCRIPTION "This object is not supported."

        VARIATION       tnOthOdu0StatRxFeBIP8ErrCnt15MinTr
            ACCESS      not-implemented
            DESCRIPTION "This object is not supported."

        VARIATION       tnOthOdu0StatRxFeBIP8ErrCnt15MinRtr
            ACCESS      not-implemented
            DESCRIPTION "This object is not supported."

        VARIATION       tnOthOdu0StatRxFeBIP8ErrCnt1DayTr
            ACCESS      not-implemented
            DESCRIPTION "This object is not supported."

        VARIATION       tnOthOdu1StatRxNeBIP8ErrCnt15MinRtr
            ACCESS      not-implemented
            DESCRIPTION "This object is not supported."

        VARIATION       tnOthOdu1StatRxFeBIP8ErrCnt15MinRtr
            ACCESS      not-implemented
            DESCRIPTION "This object is not supported."

        VARIATION       tnOthOdu2StatRxNeBIP8ErrCnt15MinRtr
            ACCESS      not-implemented
            DESCRIPTION "This object is not supported."

        VARIATION       tnOthOdu2StatRxFeBIP8ErrCnt15MinRtr
            ACCESS      not-implemented
            DESCRIPTION "This object is not supported."

        VARIATION       tnOthOdu3StatRxNeBIP8ErrCnt15MinTr
            ACCESS      not-implemented
            DESCRIPTION "This object is not supported."

        VARIATION       tnOthOdu3StatRxNeBIP8ErrCnt15MinRtr
            ACCESS      not-implemented
            DESCRIPTION "This object is not supported."

        VARIATION       tnOthOdu3StatRxNeBIP8ErrCnt1DayTr
            ACCESS      not-implemented
            DESCRIPTION "This object is not supported."

        VARIATION       tnOthOdu3StatRxFeBIP8ErrCnt15MinTr
            ACCESS      not-implemented
            DESCRIPTION "This object is not supported."

        VARIATION       tnOthOdu3StatRxFeBIP8ErrCnt15MinRtr
            ACCESS      not-implemented
            DESCRIPTION "This object is not supported."

        VARIATION       tnOthOdu3StatRxFeBIP8ErrCnt1DayTr
            ACCESS      not-implemented
            DESCRIPTION "This object is not supported."

        VARIATION       tnOthOdu4StatRxNeBIP8ErrCnt15MinTr
            ACCESS      not-implemented
            DESCRIPTION "This object is not supported."

        VARIATION       tnOthOdu4StatRxNeBIP8ErrCnt15MinRtr
            ACCESS      not-implemented
            DESCRIPTION "This object is not supported."

        VARIATION       tnOthOdu4StatRxNeBIP8ErrCnt1DayTr
            ACCESS      not-implemented
            DESCRIPTION "This object is not supported."

        VARIATION       tnOthOdu4StatRxFeBIP8ErrCnt15MinTr
            ACCESS      not-implemented
            DESCRIPTION "This object is not supported."

        VARIATION       tnOthOdu4StatRxFeBIP8ErrCnt15MinRtr
            ACCESS      not-implemented
            DESCRIPTION "This object is not supported."

        VARIATION       tnOthOdu4StatRxFeBIP8ErrCnt1DayTr
            ACCESS      not-implemented
            DESCRIPTION "This object is not supported."

        VARIATION       tnOthOdukStatRxNeES15MinRtr
            ACCESS      not-implemented
            DESCRIPTION "This object is not supported."

        VARIATION       tnOthOdukStatRxFeES15MinRtr
            ACCESS      not-implemented
            DESCRIPTION "This object is not supported."

        VARIATION       tnOthOdukStatRxNeSES15MinRtr
            ACCESS      not-implemented
            DESCRIPTION "This object is not supported."

        VARIATION       tnOthOdukStatRxFeSES15MinRtr
            ACCESS      not-implemented
            DESCRIPTION "This object is not supported."

        VARIATION       tnOthOdukStatRxNeUAS15MinRtr
            ACCESS      not-implemented
            DESCRIPTION "This object is not supported."

        VARIATION       tnOthOdukStatRxFeUAS15MinRtr
            ACCESS      not-implemented
            DESCRIPTION "This object is not supported."

        VARIATION       tnOthOduflexGFPRxNeBIP8ErrCnt15MinTr
            ACCESS      not-implemented
            DESCRIPTION "This object is not supported."

        VARIATION       tnOthOduflexGFPRxNeBIP8ErrCnt15MinRtr
            ACCESS      not-implemented
            DESCRIPTION "This object is not supported."

        VARIATION       tnOthOduflexGFPRxNeBIP8ErrCnt1DayTr
            ACCESS      not-implemented
            DESCRIPTION "This object is not supported."

        VARIATION       tnOthOduflexGFPRxFeBIP8ErrCnt15MinTr
            ACCESS      not-implemented
            DESCRIPTION "This object is not supported."

        VARIATION       tnOthOduflexGFPRxFeBIP8ErrCnt15MinRtr
            ACCESS      not-implemented
            DESCRIPTION "This object is not supported."

        VARIATION       tnOthOduflexGFPRxFeBIP8ErrCnt1DayTr
            ACCESS      not-implemented
            DESCRIPTION "This object is not supported."

        VARIATION       tnOthOduflexFC400RxNeBIP8ErrCnt15MinTr
            ACCESS      not-implemented
            DESCRIPTION "This object is not supported."

        VARIATION       tnOthOduflexFC400RxNeBIP8ErrCnt15MinRtr
            ACCESS      not-implemented
            DESCRIPTION "This object is not supported."

        VARIATION       tnOthOduflexFC400RxNeBIP8ErrCnt1DayTr
            ACCESS      not-implemented
            DESCRIPTION "This object is not supported."

        VARIATION       tnOthOduflexFC400RxFeBIP8ErrCnt15MinTr
            ACCESS      not-implemented
            DESCRIPTION "This object is not supported."

        VARIATION       tnOthOduflexFC400RxFeBIP8ErrCnt15MinRtr
            ACCESS      not-implemented
            DESCRIPTION "This object is not supported."

        VARIATION       tnOthOduflexFC400RxFeBIP8ErrCnt1DayTr
            ACCESS      not-implemented
            DESCRIPTION "This object is not supported."

        VARIATION       tnOthOduflexFC800RxNeBIP8ErrCnt15MinTr
            ACCESS      not-implemented
            DESCRIPTION "This object is not supported."

        VARIATION       tnOthOduflexFC800RxNeBIP8ErrCnt15MinRtr
            ACCESS      not-implemented
            DESCRIPTION "This object is not supported."

        VARIATION       tnOthOduflexFC800RxNeBIP8ErrCnt1DayTr
            ACCESS      not-implemented
            DESCRIPTION "This object is not supported."

        VARIATION       tnOthOduflexFC800RxFeBIP8ErrCnt15MinTr
            ACCESS      not-implemented
            DESCRIPTION "This object is not supported."

        VARIATION       tnOthOduflexFC800RxFeBIP8ErrCnt15MinRtr
            ACCESS      not-implemented
            DESCRIPTION "This object is not supported."

        VARIATION       tnOthOduflexFC800RxFeBIP8ErrCnt1DayTr
            ACCESS      not-implemented
            DESCRIPTION "This object is not supported."

        VARIATION       tnOthOduflexFC1600RxNeBIP8ErrCnt15MinTr
            ACCESS      not-implemented
            DESCRIPTION "This object is not supported."

        VARIATION       tnOthOduflexFC1600RxNeBIP8ErrCnt15MinRtr
            ACCESS      not-implemented
            DESCRIPTION "This object is not supported."

        VARIATION       tnOthOduflexFC1600RxNeBIP8ErrCnt1DayTr
            ACCESS      not-implemented
            DESCRIPTION "This object is not supported."

        VARIATION       tnOthOduflexFC1600RxFeBIP8ErrCnt15MinTr
            ACCESS      not-implemented
            DESCRIPTION "This object is not supported."

        VARIATION       tnOthOduflexFC1600RxFeBIP8ErrCnt15MinRtr
            ACCESS      not-implemented
            DESCRIPTION "This object is not supported."

        VARIATION       tnOthOduflexFC1600RxFeBIP8ErrCnt1DayTr
            ACCESS      not-implemented
            DESCRIPTION "This object is not supported."

        VARIATION       tnOthOduflexIBSDRRxNeBIP8ErrCnt15MinTr
            ACCESS      not-implemented
            DESCRIPTION "This object is not supported."

        VARIATION       tnOthOduflexIBSDRRxNeBIP8ErrCnt15MinRtr
            ACCESS      not-implemented
            DESCRIPTION "This object is not supported."

        VARIATION       tnOthOduflexIBSDRRxNeBIP8ErrCnt1DayTr
            ACCESS      not-implemented
            DESCRIPTION "This object is not supported."

        VARIATION       tnOthOduflexIBSDRRxFeBIP8ErrCnt15MinTr
            ACCESS      not-implemented
            DESCRIPTION "This object is not supported."

        VARIATION       tnOthOduflexIBSDRRxFeBIP8ErrCnt15MinRtr
            ACCESS      not-implemented
            DESCRIPTION "This object is not supported."

        VARIATION       tnOthOduflexIBSDRRxFeBIP8ErrCnt1DayTr
            ACCESS      not-implemented
            DESCRIPTION "This object is not supported."

        VARIATION       tnOthOduflexIBDDRRxNeBIP8ErrCnt15MinTr
            ACCESS      not-implemented
            DESCRIPTION "This object is not supported."

        VARIATION       tnOthOduflexIBDDRRxNeBIP8ErrCnt15MinRtr
            ACCESS      not-implemented
            DESCRIPTION "This object is not supported."

        VARIATION       tnOthOduflexIBDDRRxNeBIP8ErrCnt1DayTr
            ACCESS      not-implemented
            DESCRIPTION "This object is not supported."

        VARIATION       tnOthOduflexIBDDRRxFeBIP8ErrCnt15MinTr
            ACCESS      not-implemented
            DESCRIPTION "This object is not supported."

        VARIATION       tnOthOduflexIBDDRRxFeBIP8ErrCnt15MinRtr
            ACCESS      not-implemented
            DESCRIPTION "This object is not supported."

        VARIATION       tnOthOduflexIBDDRRxFeBIP8ErrCnt1DayTr
            ACCESS      not-implemented
            DESCRIPTION "This object is not supported."

        VARIATION       tnOthOduflexIBQDRRxNeBIP8ErrCnt15MinTr
            ACCESS      not-implemented
            DESCRIPTION "This object is not supported."

        VARIATION       tnOthOduflexIBQDRRxNeBIP8ErrCnt15MinRtr
            ACCESS      not-implemented
            DESCRIPTION "This object is not supported."

        VARIATION       tnOthOduflexIBQDRRxNeBIP8ErrCnt1DayTr
            ACCESS      not-implemented
            DESCRIPTION "This object is not supported."

        VARIATION       tnOthOduflexIBQDRRxFeBIP8ErrCnt15MinTr
            ACCESS      not-implemented
            DESCRIPTION "This object is not supported."

        VARIATION       tnOthOduflexIBQDRRxFeBIP8ErrCnt15MinRtr
            ACCESS      not-implemented
            DESCRIPTION "This object is not supported."

        VARIATION       tnOthOduflexIBQDRRxFeBIP8ErrCnt1DayTr
            ACCESS      not-implemented
            DESCRIPTION "This object is not supported."

        VARIATION       tnOthOduflex3GSDI18RxNeBIP8ErrCnt15MinTr
            ACCESS      not-implemented
            DESCRIPTION "This object is not supported."

        VARIATION       tnOthOduflex3GSDI18RxNeBIP8ErrCnt15MinRtr
            ACCESS      not-implemented
            DESCRIPTION "This object is not supported."

        VARIATION       tnOthOduflex3GSDI18RxNeBIP8ErrCnt1DayTr
            ACCESS      not-implemented
            DESCRIPTION "This object is not supported."

        VARIATION       tnOthOduflex3GSDI18RxFeBIP8ErrCnt15MinTr
            ACCESS      not-implemented
            DESCRIPTION "This object is not supported."

        VARIATION       tnOthOduflex3GSDI18RxFeBIP8ErrCnt15MinRtr
            ACCESS      not-implemented
            DESCRIPTION "This object is not supported."

        VARIATION       tnOthOduflex3GSDI18RxFeBIP8ErrCnt1DayTr
            ACCESS      not-implemented
            DESCRIPTION "This object is not supported."

        VARIATION       tnOthOduflex3GSDI19RxNeBIP8ErrCnt15MinTr
            ACCESS      not-implemented
            DESCRIPTION "This object is not supported."

        VARIATION       tnOthOduflex3GSDI19RxNeBIP8ErrCnt15MinRtr
            ACCESS      not-implemented
            DESCRIPTION "This object is not supported."

        VARIATION       tnOthOduflex3GSDI19RxNeBIP8ErrCnt1DayTr
            ACCESS      not-implemented
            DESCRIPTION "This object is not supported."

        VARIATION       tnOthOduflex3GSDI19RxFeBIP8ErrCnt15MinTr
            ACCESS      not-implemented
            DESCRIPTION "This object is not supported."

        VARIATION       tnOthOduflex3GSDI19RxFeBIP8ErrCnt15MinRtr
            ACCESS      not-implemented
            DESCRIPTION "This object is not supported."

        VARIATION       tnOthOduflex3GSDI19RxFeBIP8ErrCnt1DayTr
            ACCESS      not-implemented
            DESCRIPTION "This object is not supported."

        VARIATION       tnOthOducStatRxNeBIP8ErrCnt15MinTr
            ACCESS      not-implemented
            DESCRIPTION "This object is not supported."

        VARIATION       tnOthOducStatRxNeBIP8ErrCnt15MinRtr
            ACCESS      not-implemented
            DESCRIPTION "This object is not supported."

        VARIATION       tnOthOducStatRxNeBIP8ErrCnt1DayTr
            ACCESS      not-implemented
            DESCRIPTION "This object is not supported."

        VARIATION       tnOthOducStatRxFeBIP8ErrCnt15MinTr
            ACCESS      not-implemented
            DESCRIPTION "This object is not supported."

        VARIATION       tnOthOducStatRxFeBIP8ErrCnt15MinRtr
            ACCESS      not-implemented
            DESCRIPTION "This object is not supported."

        VARIATION       tnOthOducStatRxFeBIP8ErrCnt1DayTr
            ACCESS      not-implemented
            DESCRIPTION "This object is not supported."

        VARIATION       tnOthOduflex400GBERxNeBIP8ErrCnt15MinTr
            ACCESS      not-implemented
            DESCRIPTION "This object is not supported."

        VARIATION       tnOthOduflex400GBERxNeBIP8ErrCnt15MinRtr
            ACCESS      not-implemented
            DESCRIPTION "This object is not supported."

        VARIATION       tnOthOduflex400GBERxNeBIP8ErrCnt1DayTr
            ACCESS      not-implemented
            DESCRIPTION "This object is not supported."

        VARIATION       tnOthOduflex400GBERxFeBIP8ErrCnt15MinTr
            ACCESS      not-implemented
            DESCRIPTION "This object is not supported."

        VARIATION       tnOthOduflex400GBERxFeBIP8ErrCnt15MinRtr
            ACCESS      not-implemented
            DESCRIPTION "This object is not supported."

        VARIATION       tnOthOduflex400GBERxFeBIP8ErrCnt1DayTr
            ACCESS      not-implemented
            DESCRIPTION "This object is not supported."

        VARIATION       tnOthOduflexFC3200RxNeBIP8ErrCnt15MinTr
            ACCESS      not-implemented
            DESCRIPTION "This object is not supported."

        VARIATION       tnOthOduflexFC3200RxNeBIP8ErrCnt15MinRtr
            ACCESS      not-implemented
            DESCRIPTION "This object is not supported."

        VARIATION       tnOthOduflexFC3200RxNeBIP8ErrCnt1DayTr
            ACCESS      not-implemented
            DESCRIPTION "This object is not supported."

        VARIATION       tnOthOduflexFC3200RxFeBIP8ErrCnt15MinTr
            ACCESS      not-implemented
            DESCRIPTION "This object is not supported."

        VARIATION       tnOthOduflexFC3200RxFeBIP8ErrCnt15MinRtr
            ACCESS      not-implemented
            DESCRIPTION "This object is not supported."

        VARIATION       tnOthOduflexFC3200RxFeBIP8ErrCnt1DayTr
            ACCESS      not-implemented
            DESCRIPTION "This object is not supported."

        VARIATION       tnOthOdutc1StatRxNeBIP8ErrCnt15MinTr
            ACCESS      not-implemented
            DESCRIPTION "This object is not supported."

        VARIATION       tnOthOdutc1StatRxNeBIP8ErrCnt15MinRtr
            ACCESS      not-implemented
            DESCRIPTION "This object is not supported."

        VARIATION       tnOthOdutc1StatRxNeBIP8ErrCnt1DayTr
            ACCESS      not-implemented
            DESCRIPTION "This object is not supported."

        VARIATION       tnOthOdutc1StatRxFeBIP8ErrCnt15MinTr
            ACCESS      not-implemented
            DESCRIPTION "This object is not supported."

        VARIATION       tnOthOdutc1StatRxFeBIP8ErrCnt15MinRtr
            ACCESS      not-implemented
            DESCRIPTION "This object is not supported."

        VARIATION       tnOthOdutc1StatRxFeBIP8ErrCnt1DayTr
            ACCESS      not-implemented
            DESCRIPTION "This object is not supported."

        VARIATION       tnOthOdutc4StatRxNeBIP8ErrCnt15MinTr
            ACCESS      not-implemented
            DESCRIPTION "This object is not supported."

        VARIATION       tnOthOdutc4StatRxNeBIP8ErrCnt15MinRtr
            ACCESS      not-implemented
            DESCRIPTION "This object is not supported."

        VARIATION       tnOthOdutc4StatRxNeBIP8ErrCnt1DayTr
            ACCESS      not-implemented
            DESCRIPTION "This object is not supported."

        VARIATION       tnOthOdutc4StatRxFeBIP8ErrCnt15MinTr
            ACCESS      not-implemented
            DESCRIPTION "This object is not supported."

        VARIATION       tnOthOdutc4StatRxFeBIP8ErrCnt15MinRtr
            ACCESS      not-implemented
            DESCRIPTION "This object is not supported."

        VARIATION       tnOthOdutc4StatRxFeBIP8ErrCnt1DayTr
            ACCESS      not-implemented
            DESCRIPTION "This object is not supported."

--
-- Capabilities for TN-PMON-MIB
-- Based on MIB version:  R15.0-LatestMIBs-221105
--
-- There are no conformance groups defined in TN-PMON-MIB.
-- Due to this omission this section is listed in comment style and
-- the supported tables are included instead of the groups.
--
--  SUPPORTS            TN-PMON-MIB
--      INCLUDES        { tnPmonPolicyTable,
--                        tnPmonTcaTable,
--                        tnEthPortStatsTable,
--                        tnEthCfmTWSlmStatsTable,
--                        tnEthCfmTWDmStatsTable }
--
--      VARIATION       tnPmonPolicyType
--          SYNTAX      INTEGER { port(1),
--                                eth-cfm-two-way-slm(3),
--                                eth-cfm-two-way-dm(4) }
--          DESCRIPTION "Limit set of values."
--
--      VARIATION       tnPmonPolicyId
--          SYNTAX      Integer32 ( 1 | 2 | 8 )
--          DESCRIPTION "Limit set of values, the following meaning applies:
--                       1=Disabled: all TCA values are zero, read only.
--                       2=User: user can provision TCA values, read write.
--                       8=Default: all TCA values are set to default values,
--                         read-only."
--
--      VARIATION       tnPmonPolicyRowStatus
--          SYNTAX      INTEGER { active(1) }
--          DESCRIPTION "Limited set of values.
--                       Three policies are created by the system with the
--                       following policy IDs and properties:
--                       1=Disabled: all TCA values are zero, read only.
--                       2=User: user can provision TCA values, read write.
--                       8=Default: all TCA values are set to default values,
--                         read-only."
--
--      VARIATION       tnPmonPolicyDescription
--          DESCRIPTION "The following ASCII characters from ITU Recommendation
--                       T.50 are supported:
--                       The G0 character set - values 0x20 - 0x7E, with the
--                       following exceptions:
--                       - value 0x22: double quotes
--                       - value 0x27: single quote
--                       - value 0x3f: question mark
--                       - value 0x5c: backslash
--                       The reason of these exceptions is that those
--                       characters conflict with the Command Line Interface
--                       (CLI)."
--
--      VARIATION       tnPmonPolicyNumOfBins15Min
--          SYNTAX      Integer32 ( 33 )
--          DESCRIPTION "Limited set of values.
--                       For port policies:
--                       - tnPmonPolicyType equals port(1)
--                       - value is fixed to 33 history bins.
--                       For SLM policies:
--                       - tnPmonPolicyType equals eth-cfm-two-way-slm(3).
--                       - value is fixed to 33 history bins.
--                       For DM policies:
--                       - tnPmonPolicyType equals eth-cfm-two-way-dm(4).
--                       - value is fixed to 33 history bins."
--
--      VARIATION       tnPmonPolicyNumOfBins1Day
--          SYNTAX      Integer32 ( 8 )
--          DESCRIPTION "Limited set of values.
--                       For port policies:
--                       - tnPmonPolicyType equals port(1)
--                       - value is fixed to 8 history bins.
--                       For SLM policies:
--                       - tnPmonPolicyType equals eth-cfm-two-way-slm(3).
--                       - value is fixed to 8 history bins.
--                       For DM policies:
--                       - tnPmonPolicyType equals eth-cfm-two-way-dm(4).
--                       - value is fixed to 8 history bins."
--
--      VARIATION       tnPmonPolicyFlrInterval15Min
--          ACCESS      not-implemented
--          DESCRIPTION "This object is not supported."
--
--      VARIATION       tnPmonPolicyFlrInterval1Day
--          ACCESS      not-implemented
--          DESCRIPTION "This object is not supported."
--
--      VARIATION       tnPmonPolicyFlrAvailabilityInterval15Min
--          ACCESS      not-implemented
--          DESCRIPTION "This object is not supported."
--
--      VARIATION       tnPmonPolicyFlrAvailabilityInterval1Day
--          ACCESS      not-implemented
--          DESCRIPTION "This object is not supported."
--
--      VARIATION       tnPmonPolicyNumOfBinsContinuous
--          DESCRIPTION "For port policies:
--                       - tnPmonPolicyType equals port(1)
--                       - value is fixed to 0, no continuous bin supported.
--                       For SLM policies:
--                       - tnPmonPolicyType equals eth-cfm-two-way-slm(3).
--                       - value is fixed to 1, continuous bin is supported.
--                       For DM policies:
--                       - tnPmonPolicyType equals eth-cfm-two-way-dm(4).
--                       - value is fixed to 0, no continuous bin supported."
--
--      VARIATION       tnPmonPolicyAvailFlrThreshold
--          ACCESS      not-implemented
--          DESCRIPTION "This object is not supported. It is superseded by
--                      tnPsdOamEthCfmPingCtlAvailFlrThreshold
--                      (TROPIC-PSD-MIB)."
--
--      VARIATION       tnPmonPolicyAvailFlrNumOfIntervals
--          ACCESS      not-implemented
--          DESCRIPTION "This object is not supported. It is superseded by
--                      tnPsdOamEthCfmPingCtlAvailFlrNumOfIntervals
--                      (TROPIC-PSD-MIB)."
--
--      VARIATION       tnPmonPolicyFramesPerDeltaT
--          ACCESS      not-implemented
--          DESCRIPTION "This object is not supported."
--
--      VARIATION       tnPmonTcaId
--          DESCRIPTION "Following TCA IDs are assigned:
--                       For Port:
--                       - IFINOCTETS  :  1 (15min, 1Day)
--                       - IFINDISCARDS:  3 (15min, 1Day)
--                       - IFINERRORS  :  4 (15min, 1Day)
--                       - IFOUTOCTETS :  8 (15min, 1Day)
--                       - IFINPACKETS : 14 (15min, 1Day)
--                       - IFOUTPACKETS: 15 (15min, 1Day)
--                       For SLM:
--                       - aN_FLR      :  2 (15min, 1Day, Cont)
--                       - xN_FLR      :  3 (             Cont)
--                       - aF_FLR      :  5 (15min, 1Day, Cont)
--                       - xF_FLR      :  6 (             Cont)
--                       - N_HLI       :  7 (15min, 1Day)
--                       - F_HLI       :  8 (15min, 1Day)
--                       For DM:
--                       - aB_FD       :  2 (15min, 1Day)
--                       - xB_FD       :  3 (15min, 1Day)
--                       - aN_FDV      :  5 (15min, 1Day)
--                       - xN_FDV      :  6 (15min, 1Day)
--                       - AF_FDV      :  8 (15min, 1Day)
--                       - XF_FDV      :  9 (15min, 1Day)"
--
--      VARIATION       tnPmonTcaSubgroup
--          SYNTAX      Integer32 ( 1 )
--          DESCRIPTION "Value is fixed to 1.
--                       Value 1 is used for Port, SLM and DM TCAs."
--
--      VARIATION       tnPmonTcaVariable
--          DESCRIPTION "Following OIDs are supported.
--                       For Port (tnEthPortStatsTable):
--                       - tnEthPortStatsIfInPkts
--                       - tnEthPortStatsIfInOctets
--                       - tnEthPortStatsIfInDiscards
--                       - tnEthPortStatsIfInErrors
--                       - tnEthPortStatsIfOutPkts
--                       - tnEthPortStatsIfOutOctets
--                       For SLM (tnEthCfmTWSlmStatsTable):
--                       - tnEthCfmTWSlmStatsNearEndFrameLossRatioAverage
--                       - tnEthCfmTWSlmStatsNearEndFrameLossRatioMax
--                       - tnEthCfmTWSlmStatsFarEndFrameLossRatioAverage
--                       - tnEthCfmTWSlmStatsFarEndFrameLossRatioMax
--                       - tnEthCfmTWSlmStatsNearEndHighLoss
--                       - tnEthCfmTWSlmStatsFarEndHighLoss
--                       For DM (tnEthCfmTWDmStatsTable):
--                       - tnEthCfmTWDmStatsRoundTripFrameDelayAverage
--                       - tnEthCfmTWDmStatsRoundTripFrameDelayMax
--                       - tnEthCfmTWDmStatsNearEndFrameDelayVariationAverage
--                       - tnEthCfmTWDmStatsNearEndFrameDelayVariationMax
--                       - tnEthCfmTWDmStatsFarEndFrameDelayVariationAverage
--                       - tnEthCfmTWDmStatsFarEndFrameDelayVariationMax"
--
--      VARIATION       tnPmonTcaValue
--          DESCRIPTION "Only the entries in this table with policyId equals to
--                       value 2 (User policy) are allowed to be modified.
--                       Table entries with policy IDs other then value 2 are
--                       not allowed to be modified, in case a user attempts to
--                       modify such entries an error will be returned.
--                       The following TCA ranges are defined:
--                       In case a value is not in the range an error is
--                       returned.
--                       For Port:
--                       - IFINOCTETS   15min range: 0 - 1099511627775
--                       - IFINOCTETS   1Day  range: 0 - 1099511627775
--                       - IFINDISCARDS 15min range: 0 - 1099511627775
--                       - IFINDISCARDS 1Day  range: 0 - 1099511627775
--                       - IFINERRORS   15min range: 0 - 1099511627775
--                       - IFINERRORS   1Day  range: 0 - 1099511627775
--                       - IFOUTOCTETS  15min range: 0 - 1099511627775
--                       - IFOUTOCTETS  1Day  range: 0 - 1099511627775
--                       - IFINPACKETS  15min range: 0 - 1099511627775
--                       - IFINPACKETS  1Day  range: 0 - 1099511627775
--                       - IFOUTPACKETS 15min range: 0 - 1099511627775
--                       - IFOUTPACKETS 1Day  range: 0 - 1099511627775
--                       For SLM:
--                       The FLR stats values 100%=1000000000
--                       The HLI stats are based on a fixed
--                       interval of 60 seconds.
--                       - aN_FLR       15min range: 0 - 1000000000
--                       - aN_FLR       1Day  range: 0 - 1000000000
--                       - aN_FLR       Cont  range: 0 - 1000000000
--                       - xN_FLR       Cont  range: 0 - 1000000000
--                       - aF_FLR       15min range: 0 - 1000000000
--                       - aF_FLR       1Day  range: 0 - 1000000000
--                       - aF_FLR       Cont  range: 0 - 1000000000
--                       - xF_FLR       Cont  range: 0 - 1000000000
--                       - N_HLI        15min range: 0 - 15
--                       - N_HLI        1Day  range: 0 - 1440
--                       - F_HLI        15min range: 0 - 15
--                       - F_HLI        1Day  range: 0 - 1440
--                       For DM:
--                       The value represents micro seconds.
--                       - aB_FD        15min range: 0 - 2147583
--                       - aB_FD        1Day  range: 0 - 2147583
--                       - xB_FD        15min range: 0 - 2147583
--                       - xB_FD        1Day  range: 0 - 2147583
--                       - aN_FDV       15min range: 0 - 2147583
--                       - aN_FDV       1Day  range: 0 - 2147583
--                       - xN_FDV       15min range: 0 - 2147583
--                       - xN_FDV       1Day  range: 0 - 2147583
--                       - AF_FDV       15min range: 0 - 2147583
--                       - AF_FDV       1Day  range: 0 - 2147583
--                       - XF_FDV       15min range: 0 - 2147583
--                       - XF_FDV       1Day  range: 0 - 2147583"
--
--      VARIATION       tnEthPortStatsBin
--          DESCRIPTION "Only the current bin (value 0) can be retrieved
--                       with SNMP GET command query. History bins
--                       (bin number 1 and greater) can only be retrieved using
--                       PM file transfer."
--
--      VARIATION       tnEthPortStatsBinStatus
--          SYNTAX      INTEGER { partial(6), adjusted(7), dataLong(8), dataComplete(9) }
--          DESCRIPTION "Limit set of values.
--                       The values have the following meaning:
--                        partial:  the bin misses more than 10 seconds for the interval
--                        adjusted: the bin counters were reset during the interval
--                        dataLong: the bin contains more than 10 seconds too many for
--                                  the interval
--                        dataComplete: none of the above, normal interval"
--
--      VARIATION       tnEthPortStatsStartTime
--          DESCRIPTION "Supported."
--
--      VARIATION       tnEthPortStatsTotalMembers
--          ACCESS      not-implemented
--          DESCRIPTION "This object is not supported."
--
--      VARIATION       tnEthPortStatsIfInOctets
--          DESCRIPTION "Supported."
--
--      VARIATION       tnEthPortStatsIfInUcastPkts
--          DESCRIPTION "Supported."
--
--      VARIATION       tnEthPortStatsIfInDiscards
--          DESCRIPTION "Supported."
--
--      VARIATION       tnEthPortStatsIfInErrors
--          DESCRIPTION "Supported."
--
--      VARIATION       tnEthPortStatsIfInUnknownProtos
--          DESCRIPTION "Supported."
--
--      VARIATION       tnEthPortStatsIfInMulticastPkts
--          DESCRIPTION "Supported."
--
--      VARIATION       tnEthPortStatsIfInBroadcastPkts
--          DESCRIPTION "Supported."
--
--      VARIATION       tnEthPortStatsIfOutOctets
--          DESCRIPTION "Supported."
--
--      VARIATION       tnEthPortStatsIfOutUcastPkts
--          DESCRIPTION "Supported."
--
--      VARIATION       tnEthPortStatsIfOutDiscards
--          ACCESS      not-implemented
--          DESCRIPTION "This object is not supported."
--
--      VARIATION       tnEthPortStatsIfOutErrors
--          ACCESS      not-implemented
--          DESCRIPTION "This object is not supported."
--
--      VARIATION       tnEthPortStatsIfOutMulticastPkts
--          DESCRIPTION "Supported."
--
--      VARIATION       tnEthPortStatsIfOutBroadcastPkts
--          DESCRIPTION "Supported."
--
--      VARIATION       tnEthPortStatsIfInPkts
--          DESCRIPTION "Supported."
--
--      VARIATION       tnEthPortStatsIfOutPkts
--          DESCRIPTION "Supported."
--
--      VARIATION       tnEthPortEtherStatsDropEvents
--          ACCESS      not-implemented
--          DESCRIPTION "This object is not supported."
--
--      VARIATION       tnEthPortEtherStatsBroadcastPkts
--          ACCESS      not-implemented
--          DESCRIPTION "This object is not supported."
--
--      VARIATION       tnEthPortEtherStatsMulticastPkts
--          ACCESS      not-implemented
--          DESCRIPTION "This object is not supported."
--
--      VARIATION       tnEthPortEtherStatsCRCAlignErrors
--          ACCESS      not-implemented
--          DESCRIPTION "This object is not supported."
--
--      VARIATION       tnEthPortEtherStatsUndersizePkts
--          ACCESS      not-implemented
--          DESCRIPTION "This object is not supported."
--
--      VARIATION       tnEthPortEtherStatsOversizePkts
--          ACCESS      not-implemented
--          DESCRIPTION "This object is not supported."
--
--      VARIATION       tnEthPortEtherStatsFragments
--          ACCESS      not-implemented
--          DESCRIPTION "This object is not supported."
--
--      VARIATION       tnEthPortEtherStatsJabbers
--          ACCESS      not-implemented
--          DESCRIPTION "This object is not supported."
--
--      VARIATION       tnEthPortEtherStatsCollisions
--          ACCESS      not-implemented
--          DESCRIPTION "This object is not supported."
--
--      VARIATION       tnEthPortEtherStatsHighCapacityPkts
--          ACCESS      not-implemented
--          DESCRIPTION "This object is not supported."
--
--      VARIATION       tnEthPortEtherStatsHighCapacityOctets
--          ACCESS      not-implemented
--          DESCRIPTION "This object is not supported."
--
--      VARIATION       tnEthPortEtherStatsHighCapacityPkts64Octets
--          ACCESS      not-implemented
--          DESCRIPTION "This object is not supported."
--
--      VARIATION       tnEthPortEtherStatsHighCapacityPkts65to127Octets
--          ACCESS      not-implemented
--          DESCRIPTION "This object is not supported."
--
--      VARIATION       tnEthPortEtherStatsHighCapacityPkts128to255Octets
--          ACCESS      not-implemented
--          DESCRIPTION "This object is not supported."
--
--      VARIATION       tnEthPortEtherStatsHighCapacityPkts256to511Octets
--          ACCESS      not-implemented
--          DESCRIPTION "This object is not supported."
--
--      VARIATION       tnEthPortEtherStatsHighCapacityPkts512to1023Octets
--          ACCESS      not-implemented
--          DESCRIPTION "This object is not supported."
--
--      VARIATION       tnEthPortEtherStatsHighCapacityPkts1024to1518Octets
--          ACCESS      not-implemented
--          DESCRIPTION "This object is not supported."
--
--      VARIATION       tnEthPortEtherStatsHighCapacityPkts1519toMaxOctets
--          ACCESS      not-implemented
--          DESCRIPTION "This object is not supported."
--
--      VARIATION       tnEthCfmTWSlmStatsTestName
--          DESCRIPTION "The value of this object originates from the
--                       tnOamPingCtlTestIndex (TN-OAM-TEST-MIB)."
--
--      VARIATION       tnEthCfmTWSlmStatsInterval
--          SYNTAX      Integer32 ( 0 | 1 | 2 )
--          DESCRIPTION "Limited value range.
--                       Value 0: 15 minute interval.
--                       Value 1: 1 day interval.
--                       Value 2: continuous bin interval."
--
--      VARIATION       tnEthCfmTWSlmStatsBin
--          SYNTAX      Integer32 ( 0..33 )
--          DESCRIPTION "Limited value range.
--                       - 15 minute bins : [0..33]
--                       - 1 day bins     : [0.. 8]
--                       - continuous bins: [0]
--                       Value 0 corresponds with the current bin. Values
--                       greater then 0 are history bins.
--                       Only the current bin (value 0) can be retrieved
--                       with SNMP GET command query. History bins
--                       (bin number 1 and greater) can only be retrieved using
--                       PM file transfer.
--                       The continuous bin does not contain history bins and
--                       is therefore not included in the PM file.
--                       In case tnPsdSoamEnable (TROPIC-PSD-MIB) changes
--                       from the value true(1) to false(2) the system removes
--                       all current bin (bin number 0) entries in this table.
--                       History PM data (bin number > 0) is not removed and
--                       can be requested via the PM file transfer."
--
--      VARIATION       tnEthCfmTWSlmStatsBinStatus
--          SYNTAX      INTEGER { partial(6), adjusted(7), dataLong(8), dataComplete(9) }
--          DESCRIPTION "Limit set of values.
--                       The values have the following meaning:
--                        partial:  the bin misses more than 10 seconds for the interval
--                        adjusted: the bin counters were reset during the interval
--                        dataLong: the bin contains more than 10 seconds too many for
--                                  the interval
--                        dataComplete: none of the above, normal interval"
--
--      VARIATION       tnEthCfmTWSlmStatsStartTime
--          DESCRIPTION "Supported."
--
--      VARIATION       tnEthCfmTWSlmStatsTotalMembers
--          ACCESS      not-implemented
--          DESCRIPTION "This object is not supported."
--
--      VARIATION       tnEthCfmTWSlmStatsNearEndFrameLossRatioMin
--          DESCRIPTION "This counter is supported in:
--                       - continuous bin (tnEthCfmTWSlmStatsInterval = 2).
--                       The value of this counter must be interpreted as
--                       a fractional number. The NMS must divide the
--                       value of this object by 10.000.000."
--
--      VARIATION       tnEthCfmTWSlmStatsNearEndFrameLossRatioAverage
--          DESCRIPTION "This counter is supported in:
--                       - 15 minute bin  (tnEthCfmTWSlmStatsInterval = 0).
--                       - 1 day bin      (tnEthCfmTWSlmStatsInterval = 1).
--                       - continuous bin (tnEthCfmTWSlmStatsInterval = 2).
--                       The value of this counter must be interpreted as
--                       a fractional number. The NMS must divide the
--                       value of this object by 10.000.000."
--
--      VARIATION       tnEthCfmTWSlmStatsNearEndFrameLossRatioMax
--          DESCRIPTION "This counter is supported in:
--                       - continuous bin (tnEthCfmTWSlmStatsInterval = 2).
--                       The value of this counter must be interpreted as
--                       a fractional number. The NMS must divide the
--                       value of this object by 10.000.000."
--
--      VARIATION       tnEthCfmTWSlmStatsFarEndFrameLossRatioMin
--          DESCRIPTION "This counter is supported in:
--                       - continuous bin (tnEthCfmTWSlmStatsInterval = 2).
--                       The value of this counter must be interpreted as
--                       a fractional number. The NMS must divide the
--                       value of this object by 10.000.000."
--
--      VARIATION       tnEthCfmTWSlmStatsFarEndFrameLossRatioAverage
--          DESCRIPTION "This counter is supported in:
--                       - 15 minute bin  (tnEthCfmTWSlmStatsInterval = 0).
--                       - 1 day bin      (tnEthCfmTWSlmStatsInterval = 1).
--                       - continuous bin (tnEthCfmTWSlmStatsInterval = 2).
--                       The value of this counter must be interpreted as
--                       a fractional number. The NMS must divide the
--                       value of this object by 10.000.000."
--
--      VARIATION       tnEthCfmTWSlmStatsFarEndFrameLossRatioMax
--          DESCRIPTION "This counter is supported in:
--                       - continuous bin (tnEthCfmTWSlmStatsInterval = 2).
--                       The value of this counter must be interpreted as
--                       a fractional number. The NMS must divide the
--                       value of this object by 10.000.000."
--
--      VARIATION       tnEthCfmTWSlmStatsNearEndHighLoss
--          DESCRIPTION "This counter is supported in:
--                       - 15 minute bin (tnEthCfmTWSlmStatsInterval = 0).
--                       - 1 day bin     (tnEthCfmTWSlmStatsInterval = 1)."
--
--      VARIATION       tnEthCfmTWSlmStatsFarEndHighLoss
--          DESCRIPTION "This counter is supported in:
--                       - 15 minute bin (tnEthCfmTWSlmStatsInterval = 0).
--                       - 1 day bin     (tnEthCfmTWSlmStatsInterval = 1)."
--
--      VARIATION       tnEthCfmTWSlmStatsNearEndUnavailable
--          DESCRIPTION "This counter is supported in:
--                       - 15 minute bin (tnEthCfmTWSlmStatsInterval = 0).
--                       - 1 day bin     (tnEthCfmTWSlmStatsInterval = 1)."
--
--      VARIATION       tnEthCfmTWSlmStatsFarEndUnavailable
--          DESCRIPTION "This counter is supported in:
--                       - 15 minute bin (tnEthCfmTWSlmStatsInterval = 0).
--                       - 1 day bin     (tnEthCfmTWSlmStatsInterval = 1)."
--
--      VARIATION       tnEthCfmTWDmStatsTestName
--          DESCRIPTION "The value of this object originates from the
--                      tnOamPingCtlTestIndex (TN-OAM-TEST-MIB)."
--
--      VARIATION       tnEthCfmTWDmStatsInterval
--          SYNTAX      Integer32 ( 0 | 1 )
--          DESCRIPTION "Limited value range.
--                       Value 0: 15 minute interval.
--                       Value 1: 1 day interval."
--
--      VARIATION       tnEthCfmTWDmStatsBin
--          SYNTAX      Integer32 ( 0..33 )
--          DESCRIPTION "Limited value range.
--                       - 15 minute bins: [0..33]
--                       - 1 day bins    : [0.. 8]
--                       Value 0 corresponds with the current bin. Values
--                       greater then 0 are history bins.
--                       Only the current bin (value 0) can be retrieved
--                       with SNMP GET command query. History bins
--                       (bin number 1 and greater) can only be retrieved using
--                       PM file transfer.
--                       In case tnPsdSoamEnable (TROPIC-PSD-MIB) changes
--                       from the value true(1) to false(2) the system removes
--                       all current bin (bin number 0) entries in this table.
--                       History PM data (bin number > 0) is not removed and
--                       can be requested via the PM file transfer."
--
--      VARIATION       tnEthCfmTWDmStatsBinStatus
--          SYNTAX      INTEGER { partial(6), adjusted(7), dataLong(8), dataComplete(9) }
--          DESCRIPTION "Limit set of values.
--                       The values have the following meaning:
--                        partial:  the bin misses more than 10 seconds for the interval
--                        adjusted: the bin counters were reset during the interval
--                        dataLong: the bin contains more than 10 seconds too many for
--                                  the interval
--                        dataComplete: none of the above, normal interval"
--
--      VARIATION       tnEthCfmTWDmStatsStartTime
--          DESCRIPTION "Supported."
--
--      VARIATION       tnEthCfmTWDmStatsTotalMembers
--          ACCESS      not-implemented
--          DESCRIPTION "This object is not supported."
--
--      VARIATION       tnEthCfmTWDmStatsRoundTripFrameDelayMin
--          DESCRIPTION "The counter value is expressed in micro seconds
--                       and is supported in:
--                       - 15 minute bin (tnEthCfmTWDmStatsInterval = 0).
--                       - 1 day bin     (tnEthCfmTWDmStatsInterval = 1)."
--
--      VARIATION       tnEthCfmTWDmStatsRoundTripFrameDelayAverage
--          DESCRIPTION "The counter value is expressed in micro seconds
--                       and is supported in:
--                       - 15 minute bin (tnEthCfmTWDmStatsInterval = 0).
--                       - 1 day bin     (tnEthCfmTWDmStatsInterval = 1)."
--
--      VARIATION       tnEthCfmTWDmStatsRoundTripFrameDelayMax
--          DESCRIPTION "The counter value is expressed in micro seconds
--                       and is supported in:
--                       - 15 minute bin (tnEthCfmTWDmStatsInterval = 0).
--                       - 1 day bin     (tnEthCfmTWDmStatsInterval = 1)."
--
--      VARIATION       tnEthCfmTWDmStatsNearEndFrameDelayVariationMin
--          DESCRIPTION "The counter value is expressed in micro seconds
--                       and is supported in::
--                       - 15 minute bin (tnEthCfmTWDmStatsInterval = 0).
--                       - 1 day bin     (tnEthCfmTWDmStatsInterval = 1)."
--
--      VARIATION       tnEthCfmTWDmStatsNearEndFrameDelayVariationAverage
--          DESCRIPTION "The counter value is expressed in micro seconds
--                       and is supported in:
--                       - 15 minute bin (tnEthCfmTWDmStatsInterval = 0).
--                       - 1 day bin     (tnEthCfmTWDmStatsInterval = 1)."
--
--      VARIATION       tnEthCfmTWDmStatsNearEndFrameDelayVariationMax
--          DESCRIPTION "The counter value is expressed in micro seconds
--                       and is supported in:
--                       - 15 minute bin (tnEthCfmTWDmStatsInterval = 0).
--                       - 1 day bin     (tnEthCfmTWDmStatsInterval = 1)."
--
--      VARIATION       tnEthCfmTWDmStatsFarEndFrameDelayVariationMin
--          DESCRIPTION "The counter value is expressed in micro seconds
--                       and is supported in:
--                       - 15 minute bin (tnEthCfmTWDmStatsInterval = 0).
--                       - 1 day bin     (tnEthCfmTWDmStatsInterval = 1)."
--
--      VARIATION       tnEthCfmTWDmStatsFarEndFrameDelayVariationAverage
--          DESCRIPTION "The counter value is expressed in micro seconds
--                       and is supported in:
--                       - 15 minute bin (tnEthCfmTWDmStatsInterval = 0).
--                       - 1 day bin     (tnEthCfmTWDmStatsInterval = 1)."
--
--      VARIATION       tnEthCfmTWDmStatsFarEndFrameDelayVariationMax
--          DESCRIPTION "The counter value is expressed in micro seconds
--                       and is supported in:
--                       - 15 minute bin (tnEthCfmTWDmStatsInterval = 0).
--                       - 1 day bin     (tnEthCfmTWDmStatsInterval = 1)."
--
--      VARIATION       tnEthCfmTWDmStatsNearEndFrameDelayMin
--          ACCESS      not-implemented
--          DESCRIPTION "This object is not supported."
--
--      VARIATION       tnEthCfmTWDmStatsNearEndFrameDelayAverage
--          ACCESS      not-implemented
--          DESCRIPTION "This object is not supported."
--
--      VARIATION       tnEthCfmTWDmStatsNearEndFrameDelayMax
--          ACCESS      not-implemented
--          DESCRIPTION "This object is not supported."
--
--      VARIATION       tnEthCfmTWDmStatsFarEndFrameDelayMin
--          ACCESS      not-implemented
--          DESCRIPTION "This object is not supported."
--
--      VARIATION       tnEthCfmTWDmStatsFarEndFrameDelayAverage
--          ACCESS      not-implemented
--          DESCRIPTION "This object is not supported."
--
--      VARIATION       tnEthCfmTWDmStatsFarEndFrameDelayMax
--          ACCESS      not-implemented
--          DESCRIPTION "This object is not supported."
--

--
-- Capabilities for TN-PORT-MIB
-- Based on MIB version:  R15.0-LatestMIBs-221105
--
-- There are no conformance groups defined in TN-PORT-MIB.
-- Due to this omission this section is listed in comment style and
-- the supported tables are included instead of the groups.
--
--  SUPPORTS            TN-PORT-MIB
--      INCLUDES        { tnPortEtherTable }
--
--      VARIATION       tnPortEtherMTU
--          ACCESS      not-implemented
--          DESCRIPTION "This object is not supported."
--
--      VARIATION       tnPortEtherDuplex
--          ACCESS      not-implemented
--          DESCRIPTION "This object is not supported."
--
--      VARIATION       tnPortEtherSpeed
--          SYNTAX      INTEGER { notApplicable(0),
--                                speed100(2),
--                                speed1000(3) }
--          DESCRIPTION "Limited set of values.
--                       When the value is notApplicable(0), it can
--                       not be changed to any of the other values.
--                       When the value is not notApplicable(0), it
--                       can not be changed to notApplicable(0)."
--
--      VARIATION       tnPortEtherAutoNegotiate
--          ACCESS      not-implemented
--          DESCRIPTION "This object is not supported."
--
--      VARIATION       tnPortEtherOperDuplex
--          ACCESS      not-implemented
--          DESCRIPTION "This object is not supported."
--
--      VARIATION       tnPortEtherOperSpeed
--          ACCESS      not-implemented
--          DESCRIPTION "This object is not supported."
--
--      VARIATION       tnPortEtherAcctPolicyId
--          SYNTAX      Integer32 ( 1 | 2 | 8 )
--          DESCRIPTION "Limit set of values: 1,2,8.
--                       1=Disabled: all TCA values are zero, read only.
--                       2=User: user can provision TCA values, read write.
--                       8=Default: all TCA values are set to default values,
--                       read-only.
--                       The system creates entries which depends on the
--                       system mode (tnPsdSystemMode):
--                       For the ethNid1GbEor10GbEClient10GbENetworkMode(9):
--                       {NETWORK1,NETWORK2,NETWORK,CLIENT1,CLIENT2,CLIENT}
--                       For system modes
--                       - otnNid1GbeClientOtu1NetworkMode(2)
--                       - otnNid1GbeClientOtu2NetworkMode(3)
--                       - otnNid10GbeClientOtu2NetworkMode(4)
--                       - otnNid10GbeClientOtu2eNetworkMode(5)
--                       - otnNid1GbEor10GbEClientOtu2OduFlexNetworkMode(10)
--                       : {CLIENT1,CLIENT}."
--
--      VARIATION       tnPortEtherCollectStats
--          DESCRIPTION "The supported value is system mode dependent.
--                       - ethNid1GbEor10GbEClient10GbENetworkMode(9): {true}
--                       For system modes
--                       - otnNid1GbeClientOtu1NetworkMode(2)
--                       - otnNid1GbeClientOtu2NetworkMode(3)
--                       - otnNid10GbeClientOtu2NetworkMode(4)
--                       - otnNid10GbeClientOtu2eNetworkMode(5)
--                       - otnNid1GbEor10GbEClientOtu2OduFlexNetworkMode(10)
--                       : {false=default, true}.
--                         CLIENT1 is read-only and the value can only be
--                         modified using the CLIENT instance from which it is
--                         derived."
--
--      VARIATION       tnPortEtherMDIMDIX
--          ACCESS      not-implemented
--          DESCRIPTION "This object is not supported."
--
--      VARIATION       tnPortEtherXGigMode
--          ACCESS      not-implemented
--          DESCRIPTION "This object is not supported."
--
--      VARIATION       tnPortEtherEgressRate
--          ACCESS      not-implemented
--          DESCRIPTION "This object is not supported."
--
--      VARIATION       tnPortEtherDot1qEtype
--          ACCESS      not-implemented
--          DESCRIPTION "This object is not supported."
--
--      VARIATION       tnPortEtherQinqEtype
--          ACCESS      not-implemented
--          DESCRIPTION "This object is not supported."
--
--      VARIATION       tnPortEtherIngressRate
--          ACCESS      not-implemented
--          DESCRIPTION "This object is not supported."
--
--      VARIATION       tnPortEtherReportAlarm
--          ACCESS      not-implemented
--          DESCRIPTION "This object is not supported."
--
--      VARIATION       tnPortEtherReportAlarmStatus
--          ACCESS      not-implemented
--          DESCRIPTION "This object is not supported."
--
--      VARIATION       tnPortEtherPkts1519toMax
--          ACCESS      not-implemented
--          DESCRIPTION "This object is not supported."
--
--      VARIATION       tnPortEtherHCOverPkts1519toMax
--          ACCESS      not-implemented
--          DESCRIPTION "This object is not supported."
--
--      VARIATION       tnPortEtherHCPkts1519toMax
--          ACCESS      not-implemented
--          DESCRIPTION "This object is not supported."
--
--      VARIATION       tnPortEtherLacpTunnel
--          ACCESS      not-implemented
--          DESCRIPTION "This object is not supported."
--
--      VARIATION       tnPortEtherDownWhenLoopedEnabled
--          ACCESS      not-implemented
--          DESCRIPTION "This object is not supported."
--
--      VARIATION       tnPortEtherDownWhenLoopedKeepAlive
--          ACCESS      not-implemented
--          DESCRIPTION "This object is not supported."
--
--      VARIATION       tnPortEtherDownWhenLoopedRetry
--          ACCESS      not-implemented
--          DESCRIPTION "This object is not supported."
--
--      VARIATION       tnPortEtherDownWhenLoopedState
--          ACCESS      not-implemented
--          DESCRIPTION "This object is not supported."
--
--      VARIATION       tnPortEtherPBBEtype
--          ACCESS      not-implemented
--          DESCRIPTION "This object is not supported."
--
--      VARIATION       tnPortEtherSingleFiber
--          ACCESS      not-implemented
--          DESCRIPTION "This object is not supported."
--
--      VARIATION       tnPortEtherSSM
--          ACCESS      not-implemented
--          DESCRIPTION "This object is not supported."
--
--      VARIATION       tnPortEtherDWLUseBroadcastAddr
--          ACCESS      not-implemented
--          DESCRIPTION "This object is not supported."
--
--      VARIATION       tnPortEtherSSMCodeType
--          ACCESS      not-implemented
--          DESCRIPTION "This object is not supported."
--
--      VARIATION       tnPortEtherSSMTxDus
--          ACCESS      not-implemented
--          DESCRIPTION "This object is not supported."
--
--      VARIATION       tnPortEtherSSMRxEsmc
--          ACCESS      not-implemented
--          DESCRIPTION "This object is not supported."
--
--      VARIATION       tnPortEtherSSMTxQualityLevel
--          ACCESS      not-implemented
--          DESCRIPTION "This object is not supported."
--
--      VARIATION       tnPortEtherQinqEtypelink
--          ACCESS      not-implemented
--          DESCRIPTION "This object is not supported."
--
--      VARIATION       tnPortEtherOperEgressRate
--          ACCESS      not-implemented
--          DESCRIPTION "This object is not supported."
--

-- Capabilities for TN-LAG-MIB
-- Based on MIB version:  R15.0-LatestMIBs-221105
--
-- There are no conformance groups defined in TN-LAG-MIB.
-- Due to this omission this section is listed in comment style and
-- the supported tables are included instead of the groups.
--
--  SUPPORTS            TN-LAG-MIB
--      INCLUDES        { tnLagCommandTable,
--                        tnLagPortTable }
--
--
--      VARIATION       tnLagCommand
--          SYNTAX      INTEGER { noCmd(0), force(2) }
--          DESCRIPTION "Limited set of values.
--                       The value of this object is only accepted in case
--                       tnLagCommandActiveStdby is present in the varbinds
--                       of the SNMP-set request PDU and is only allowed
--                       for a 1+1 LAG.
--                       This object can be used to request this subgroup to
--                       be active or standby.
--                       Initially there are no entries in the
--                       tnLagCommandTable. The system creates and deletes
--                       entries in this table dependent on the value of
--                       tnLagPortSubgroup. See description tnLagPortSubgroup
--                       for details.
--                       The following combinations are possible:
--                       - force(2) and active(1) : request to make this
--                                                  subgroup active.
--                       - force(2) and standby(2): request to make this
--                                                  subgroup standby.
--                       - noCmd(2)               : no request is made.
--                       Objects tnPsdLagCommandSubgroupSelected or
--                       tnLagPortActiveStdby can be used to verify whether
--                       the subgroup is active.
--                       Upon read always noCmd(2) is returned."
--
--      VARIATION       tnLagCommandActiveStdby
--          DESCRIPTION "The value of this object is only accepted in case
--                       tnLagCommand is present in the varbinds of the
--                       SNMP-set request PDU. See description tnLagCommand."
--
--      VARIATION       tnLagCommandAllMc
--          ACCESS      not-implemented
--          DESCRIPTION "This object is not supported."
--
--      VARIATION       tnLagCommandMcPeerIpType
--          ACCESS      not-implemented
--          DESCRIPTION "This object is not supported."
--
--      VARIATION       tnLagCommandMcPeerIpAddr
--          ACCESS      not-implemented
--          DESCRIPTION "This object is not supported."
--
--      VARIATION       tnLagPortSubgroup
--          SYNTAX       INTEGER (-1|1|2)
--          DESCRIPTION "Limited set of values.
--                       This object is used to enable the LAG functionality on
--                       the logical CLIENT or logical NETWORK interface and
--                       can be used to construct a std-LAG or a 1+1 LAG
--                       implementation.
--                       Permitted LAG members on logical CLIENT:
--                       - CLIENT1
--                       - CLIENT2
--                       Permitted LAG members of logical NETWORK:
--                       - NETWORK1
--                       - NETWORK2
--                       The values of this object have following meaning:
--                       - value -1: port is not assigned to LAG
--                                   (initial value).
--                       - value  1: port is assigned to LAG.
--                                   Used to construct std-LAG.
--                       - value  2: port is assigned to LAG.
--                                   Used to implement 1+1 LAG.
--                       The order of subgroup assignment is enforced.
--                       Constructing LAG:
--                       For constructing a LAG first subgroup 1 must
--                       be assigned to port 1 (CLIENT1, NETWORK1), a
--                       std-LAG is created.
--                       Then port 2 (CLIENT2, NETWORK2) may be assigned
--                       subgroup value 1 (std-LAG) or 2 (1+1 LAG).
--                       Removing LAG:
--                       Similarly for removing LAG functionality on the
--                       logical CLIENT or NETWORK port the order is enforced
--                       only in the opposite way: first port 2
--                       (CLIENT2, NETWORK2) must be set to value -1,
--                       then port 1 (CLIENT1, NETWORK1) is set to value -1.
--                       Modifying LAG:
--                       - 1+1 LAG -> std-LAG: change subgroup number
--                         of port 2 (CLIENT2, NETWORK2) from 2 to 1.
--                       - std-LAG -> 1+1 LAG: change subgroup number
--                         of port 2 (CLIENT2, NETWORK2) from 1 to 2.
--                       In case value 1 or 2 is assigned the system creates
--                       a corresponding entry in the tnLagCommandTable and
--                       the entries in the dot3adAggTable and
--                       dot3adAggPortTable are updated.
--                       In case value -1 is assigned the system removes
--                       the corresponding entry from the tnLagCommandTable
--                       and the dot3adAggTable and dot3adAggPortTable are
--                       updated. Please refer to capability descriptions of
--                       dot3adAggTable and dot3adAggPortTable for details."
--
--      VARIATION       tnLagPortActiveStdby
--          DESCRIPTION "Supported."
--
--      VARIATION       tnLagPortLinkId
--          ACCESS      not-implemented
--          DESCRIPTION "This object is not supported."

--
-- Capabilities for IEEE8023-LAG-MIB
-- Based on MIB version:  R15.0-LatestMIBs-221105
--

    SUPPORTS            IEEE8023-LAG-MIB
        INCLUDES        { dot3adAggGroup,
                          dot3adAggPortListGroup,
                          dot3adAggPortGroup }

        VARIATION       dot3adAggIndex
            DESCRIPTION "The system creates only in tnPsdSystemMode
                         ethNid1GbEor10GbEClient10GbENetworkMode(9) the
                         following entries in this table:
                         NETWORK(1) = ifIndex.NETWORK (0x01018100) & 0x00007F00
                         CLIENT(3)  = ifIndex.CLIENT  (0x01018300) & 0x00007F00
                         The entries in this table are always present and
                         cannot be removed."

        VARIATION       dot3adAggActorSystemID
            ACCESS      read-only
            DESCRIPTION "Setting of this object is not allowed.
                         The value of this object equals to the system MAC
                         address."

        VARIATION       dot3adAggActorSystemPriority
            ACCESS      read-only
            DESCRIPTION "Setting of this object is not allowed.
                         The value of this object equals 0x8000."

        VARIATION       dot3adAggAggregateOrIndividual
            ACCESS      not-implemented
            DESCRIPTION "This object is not supported."

        VARIATION       dot3adAggActorAdminKey
            ACCESS      read-only
            DESCRIPTION "Setting of this object is not allowed.
                         The value of this object equals:
                         CLIENTMAC & 0xFFFF or NETWORKMAC & 0xFFFF.
                         Where CLIENTMAC is the MAC address of the logical
                         CLIENT interface and NETWORKMAC  is the MAC address
                         of the logical NETWORK interface."

        VARIATION       dot3adAggMACAddress
            DESCRIPTION "The value corresponds either to the MAC address of
                         the logical CLIENT interface or to the MAC address of
                         the logical NETWORK interface."

        VARIATION       dot3adAggActorOperKey
            DESCRIPTION "The value equals dot3adAggActorAdminKey."

        VARIATION       dot3adAggCollectorMaxDelay
            ACCESS      not-implemented
            DESCRIPTION "This object is not supported."

        VARIATION       dot3adAggPortIndex
            DESCRIPTION "The system creates only in tnPsdSystemMode
                         ethNid1GbEor10GbEClient10GbENetworkMode(9) entries
                         in this table for the following interfaces:
                         - NETWORK1(1)
                         - NETWORK2(2)
                         - CLIENT1(3)
                         - CLIENT2(4)
                         The entries in this table are always present and
                         cannot be removed.
                         The value of the indexes correspond with the
                         encoding of ifIndex (IF-MIB):
                         shelf = (value & 0x7F000000) >> 24
                         slot  = (value & 0x00FF0000) >> 16
                         port  = (value & 0x0000FF00) >>  8
                         The value of shelf and slot are always fixed to 1.
                         The value of port ranges from 1 till 4."

        VARIATION       dot3adAggPortActorSystemPriority
            ACCESS      read-only
            DESCRIPTION "The value equals dot3adAggActorSystemPriority."

        VARIATION       dot3adAggPortActorSystemID
            DESCRIPTION "The value equals dot3adAggActorSystemID."

        VARIATION       dot3adAggPortActorAdminKey
            ACCESS      read-only
            DESCRIPTION "The actorAdminKey value is controlled by
                         tnLagPortSubgroup (TN-LAG-MIB).
                         In case the port is assigned to the LAG group
                         the value equals
                         dot3adAggActorAdminKey{CLIENT, NETWORK} else the value
                         equals 0."

        VARIATION       dot3adAggPortActorOperKey
            DESCRIPTION "The value equals dot3adAggPortActorAdminKey."

        VARIATION       dot3adAggPortPartnerAdminSystemPriority
            ACCESS      not-implemented
            DESCRIPTION "This object is not supported."

        VARIATION       dot3adAggPortPartnerAdminSystemID
            ACCESS      not-implemented
            DESCRIPTION "This object is not supported."

        VARIATION       dot3adAggPortPartnerAdminKey
            ACCESS      read-only
            DESCRIPTION "The value is read-only."

        VARIATION       dot3adAggPortSelectedAggID
            DESCRIPTION "The value is dependent on tnLagPortSubgroup
                        (TN-LAG-MIB)."

        VARIATION       dot3adAggPortActorPortPriority
            ACCESS      read-only
            DESCRIPTION "The value is read-only. The following constrains
                         are enforced:
                         CLIENT1 < CLIENT2, NETWORK1 < NETWORK2."

        VARIATION       dot3adAggPortPartnerAdminPort
            ACCESS      not-implemented
            DESCRIPTION "This object is not supported."

        VARIATION       dot3adAggPortPartnerAdminPortPriority
            ACCESS      not-implemented
            DESCRIPTION "This object is not supported."

        VARIATION       dot3adAggPortActorAdminState
            ACCESS      read-only
            DESCRIPTION "The value is depends on tnLagPortActiveStdby
                         (TN-LAG-MIB)."

        VARIATION       dot3adAggPortPartnerAdminState
            ACCESS      not-implemented
            DESCRIPTION "This object is not supported."

        VARIATION       dot3adAggPortAggregateOrIndividual
            DESCRIPTION "The value is dependent on tnLagPortActiveStdby
                        (TN-LAG-MIB)."

--
-- Capabilities for IEEE8021-CFM-MIB
-- Based on MIB version:  R15.0-LatestMIBs-221105
--

    SUPPORTS            IEEE8021-CFM-MIB
        INCLUDES        { dot1agCfmMdGroup,
                          dot1agCfmMaGroup,
                          dot1agCfmMepGroup,
                          dot1agCfmMepDbGroup }

        VARIATION       dot1agCfmMdTableNextIndex
            ACCESS      not-implemented
            DESCRIPTION "This object is not supported."

        VARIATION       dot1agCfmMdName
            DESCRIPTION "A value of none(1) in the associated
                         Dot1agCfmMaintDomainNameType object
                         (dot1agCfmMdFormat) means that no Maintenance
                         Domain name is present, and the contents of the
                         Dot1agCfmMaintDomainName object is meaningless.
                         The object value is ignored and not used in the CFM
                         PDUs."

        VARIATION       dot1agCfmMdFormat
            SYNTAX      INTEGER { none(1) }
            DESCRIPTION "Limited set of values."

        VARIATION       dot1agCfmMdMhfCreation
            ACCESS      not-implemented
            DESCRIPTION "This object is not supported."

        VARIATION       dot1agCfmMdMhfIdPermission
            ACCESS      not-implemented
            DESCRIPTION "This object is not supported."

        VARIATION       dot1agCfmMdMaNextIndex
            ACCESS      not-implemented
            DESCRIPTION "This object is not supported."

        VARIATION       dot1agCfmMdRowStatus
            SYNTAX      INTEGER { active(1),
                                  createAndGo(4),
                                  destroy(6) }
            DESCRIPTION "Limited set of values.
                         Maximum of 8 entries are supported regardless of the
                         value of this object.
                         In case createAndGo(4) is given all mandatory RC
                         objects must be provided in the varbinds of the SNMP
                         set PDU.
                         In case a mandatory object is not provided the
                         default value is applied to the entry.
                         In case an object leads to an error no entry is
                         created. As long as the dot1agCfmMdIndex is used
                         in other tables assigning the value destroy(6) is
                         rejected.
                         In case for none of the ports has Service OAM enabled
                         i.e. tnPsdSoamEnable is true(1), all entries are
                         removed from this table and no new entries can be
                         created."

        VARIATION       dot1agCfmMaNetFormat
            DESCRIPTION "Limited set of values. Only format
                         ituReserved(32) ITU-ICC is supported, see ITU-T Rec.
                         G.8031/Y.1731."

        VARIATION       dot1agCfmMaNetName
            DESCRIPTION "ITU-ICC requires max length 13 characters.
                         The following ASCII characters from ITU Recommendation
                         T.50 are supported:
                         The G0 character set - values 0x21 - 0x7E, excluding
                         the following values:
                         - value 0x22: double quotes
                         - value 0x27: single quote
                         - value 0x3f: question mark
                         - value 0x5c: backslash
                         The value of this object must be unique within the
                         scope of the MD.
                         The system performs no checks on MEG ID values.
                         The system applies NULL characters in case needed."

        VARIATION       dot1agCfmMaNetCcmInterval
            SYNTAX      INTEGER { interval100ms(3),
                                  interval1s(4),
                                  interval10s(5),
                                  interval1min(6),
                                  interval10min(7) }
            DESCRIPTION "Limited set of values."

        VARIATION       dot1agCfmMaNetRowStatus
            SYNTAX      INTEGER { active(1),
                                  createAndGo(4),
                                  destroy(6) }
            DESCRIPTION "Limited set of values.
                         Maximum of 8 entries are supported regardless of the
                         value of this object.
                         In case createAndGo(4) is given all mandatory RC
                         objects must be provided in the varbinds of the SNMP
                         set PDU.
                         In case a mandatory object is not provided the
                         default value is applied to the entry.
                         In case an object of this table leads to an error,
                         no entry is created.
                         As long as the dot1agCfmMaIndex is used in other
                         tables assigning the value destroy(6) is rejected.
                         Value createAndGo(4) is rejected in case the
                         associated dot1agCfmMdRowStatus is not equal to
                         active(1).
                         In case for none of the ports has Service OAM enabled
                         i.e. tnPsdSoamEnable is true(1), all entries are
                         removed from this table and no new entries can be
                         created."

        VARIATION       dot1agCfmMaComponentId
            SYNTAX      Unsigned32 (1)
            DESCRIPTION "Fixed value 1."

        VARIATION       dot1agCfmMaCompPrimaryVlanId
            SYNTAX      Integer32 (1 .. 4094)
            DESCRIPTION "Limited set of values. Value 0 is not supported.
                         A maximum of two MEPs can be associated per VLAN."

        VARIATION       dot1agCfmMaCompMhfCreation
            ACCESS      not-implemented
            DESCRIPTION "This object is not supported."

        VARIATION       dot1agCfmMaCompIdPermission
            ACCESS      not-implemented
            DESCRIPTION "This object is not supported."

        VARIATION       dot1agCfmMaCompRowStatus
            SYNTAX      INTEGER { active(1),
                                  createAndGo(4),
                                  destroy(6) }
            DESCRIPTION "Limited set of values.
                         Maximum of 8 entries are supported regardless of the
                         value of this object.
                         In case createAndGo(4) is given all mandatory RC
                         objects must be provided in the varbinds of the SNMP
                         set PDU.
                         In case a mandatory object is not provided the
                         default value is applied to the entry.
                         In case an object of this table leads to an error,
                         no entry is created.
                         Value createAndGo(4) is rejected in case there is no
                         associated dot1agCfmMaNetEntry.
                         Value destroy(6) is rejected in case there exists an
                         associated dot1agCfmMepEntry.
                         In case for none of the ports has Service OAM enabled
                         i.e. tnPsdSoamEnable is true(1), all entries are
                         removed from this table and no new entries can be
                         created."

        VARIATION       dot1agCfmMaCompNumberOfVids
            ACCESS      not-implemented
            DESCRIPTION "This object is not supported."

        VARIATION       dot1agCfmMaMepListRowStatus
            SYNTAX      INTEGER { createAndGo(4),
                                  destroy(6) }
            DESCRIPTION "Limited set of values.
                         Per dot1agCfmMdIndex and dot1agCfmMaIndex combination
                         no more than two MEPIDs can be supported, i.e.
                         point-to-point associations only."

        VARIATION       dot1agCfmMepIfIndex
            ACCESS      read-only
            DESCRIPTION "The value is fixed to the ifIndex value
                         of logical CLIENT interface."

        VARIATION       dot1agCfmMepDirection
            ACCESS      read-only
            DESCRIPTION "Fixed value up(2)."

        VARIATION       dot1agCfmMepPrimaryVid
            ACCESS      read-only
            DESCRIPTION "The value is derived from
                         dot1agCfmMaCompPrimaryVlanId."

        VARIATION       dot1agCfmMepActive
            DESCRIPTION "The value false(2) is rejected in case the value of
                         dot1agCfmMepCciEnabled equals true(1) or in case
                         an on-demand LM, SLM or DM session is running or
                         in case a pro-active DM or SLM session is running."

        VARIATION       dot1agCfmMepFngState
            ACCESS      not-implemented
            DESCRIPTION "This object is not supported."

        VARIATION       dot1agCfmMepCciEnabled
            DESCRIPTION "The value of this object must be set to false(2)
                         in case the value of dot1agCfmMepActive is false(2)
                         otherwise an error is returned.
                         In case tnDot1agCfmMepFaultPropagation has the value
                         useIfStatusTLV(1) and setting the value of this object
                         to false(2) is rejected."

        VARIATION       dot1agCfmMepMacAddress
            DESCRIPTION "The value of this object is derived from logical
                         CLIENT MAC address."

        VARIATION       dot1agCfmMepLowPrDef
            ACCESS      not-implemented
            DESCRIPTION "This object is not supported."

        VARIATION       dot1agCfmMepFngAlarmTime
            ACCESS      not-implemented
            DESCRIPTION "This object is not supported."

        VARIATION       dot1agCfmMepFngResetTime
            ACCESS      not-implemented
            DESCRIPTION "This object is not supported."

        VARIATION       dot1agCfmMepHighestPrDefect
            ACCESS      not-implemented
            DESCRIPTION "This object is not supported."

        VARIATION       dot1agCfmMepDefects
            ACCESS      not-implemented
            DESCRIPTION "This object is not supported."

        VARIATION       dot1agCfmMepErrorCcmLastFailure
            ACCESS      not-implemented
            DESCRIPTION "This object is not supported."

        VARIATION       dot1agCfmMepXconCcmLastFailure
            ACCESS      not-implemented
            DESCRIPTION "This object is not supported."

        VARIATION       dot1agCfmMepCcmSequenceErrors
            ACCESS      not-implemented
            DESCRIPTION "This object is not supported."

        VARIATION       dot1agCfmMepCciSentCcms
            ACCESS      not-implemented
            DESCRIPTION "This object is not supported."

        VARIATION       dot1agCfmMepNextLbmTransId
            ACCESS      not-implemented
            DESCRIPTION "This object is not supported."

        VARIATION       dot1agCfmMepLbrIn
            ACCESS      not-implemented
            DESCRIPTION "This object is not supported."

        VARIATION       dot1agCfmMepLbrInOutOfOrder
            ACCESS      not-implemented
            DESCRIPTION "This object is not supported."

        VARIATION       dot1agCfmMepLbrBadMsdu
            ACCESS      not-implemented
            DESCRIPTION "This object is not supported."

        VARIATION       dot1agCfmMepLtmNextSeqNumber
            ACCESS      not-implemented
            DESCRIPTION "This object is not supported."

        VARIATION       dot1agCfmMepUnexpLtrIn
            ACCESS      not-implemented
            DESCRIPTION "This object is not supported."

        VARIATION       dot1agCfmMepLbrOut
            ACCESS      not-implemented
            DESCRIPTION "This object is not supported."

        VARIATION       dot1agCfmMepTransmitLbmStatus
            ACCESS      not-implemented
            DESCRIPTION "This object is not supported."

        VARIATION       dot1agCfmMepTransmitLbmDestMacAddress
            ACCESS      not-implemented
            DESCRIPTION "This object is not supported."

        VARIATION       dot1agCfmMepTransmitLbmDestMepId
            ACCESS      not-implemented
            DESCRIPTION "This object is not supported."

        VARIATION       dot1agCfmMepTransmitLbmDestIsMepId
            ACCESS      not-implemented
            DESCRIPTION "This object is not supported."

        VARIATION       dot1agCfmMepTransmitLbmMessages
            ACCESS      not-implemented
            DESCRIPTION "This object is not supported."

        VARIATION       dot1agCfmMepTransmitLbmDataTlv
            ACCESS      not-implemented
            DESCRIPTION "This object is not supported."

        VARIATION       dot1agCfmMepTransmitLbmVlanPriority
            ACCESS      not-implemented
            DESCRIPTION "This object is not supported."

        VARIATION       dot1agCfmMepTransmitLbmVlanDropEnable
            ACCESS      not-implemented
            DESCRIPTION "This object is not supported."

        VARIATION       dot1agCfmMepTransmitLbmResultOK
            ACCESS      not-implemented
            DESCRIPTION "This object is not supported."

        VARIATION       dot1agCfmMepTransmitLbmSeqNumber
            ACCESS      not-implemented
            DESCRIPTION "This object is not supported."

        VARIATION       dot1agCfmMepTransmitLtmStatus
            ACCESS      not-implemented
            DESCRIPTION "This object is not supported."

        VARIATION       dot1agCfmMepTransmitLtmFlags
            ACCESS      not-implemented
            DESCRIPTION "This object is not supported."

        VARIATION       dot1agCfmMepTransmitLtmTargetMacAddress
            ACCESS      not-implemented
            DESCRIPTION "This object is not supported."

        VARIATION       dot1agCfmMepTransmitLtmTargetMepId
            ACCESS      not-implemented
            DESCRIPTION "This object is not supported."

        VARIATION       dot1agCfmMepTransmitLtmTargetIsMepId
            ACCESS      not-implemented
            DESCRIPTION "This object is not supported."

        VARIATION       dot1agCfmMepTransmitLtmTtl
            ACCESS      not-implemented
            DESCRIPTION "This object is not supported."

        VARIATION       dot1agCfmMepTransmitLtmResult
            ACCESS      not-implemented
            DESCRIPTION "This object is not supported."

        VARIATION       dot1agCfmMepTransmitLtmSeqNumber
            ACCESS      not-implemented
            DESCRIPTION "This object is not supported."

        VARIATION       dot1agCfmMepTransmitLtmEgressIdentifier
            ACCESS      not-implemented
            DESCRIPTION "This object is not supported."

        VARIATION       dot1agCfmMepRowStatus
            SYNTAX      INTEGER { active(1),
                                  createAndGo(4),
                                  destroy(6) }
            DESCRIPTION "Limited set of values.
                         Maximum of 8 entries are supported regardless of the
                         value of this object.
                         In case createAndGo(4) is given all mandatory RC
                         objects must be provided in the varbinds of the SNMP
                         set PDU.
                         In case a mandatory object is not provided the
                         default value is applied to the entry.
                         In case an object of this table leads to an error,
                         no entry is created.
                         In case the value of dot1agCfmMaNetRowStatus and
                         dot1agCfmMaCompRowStatus are not equal to active(1)
                         createAndGo(4) is rejected and no entry is created.
                         The value destroy(6) is rejected in case:
                         - on-demand DM, LM or SLM session is running.
                         - pro-active DM or SLM session is running.
                         - one of the MEPs has tnDot1agCfmMepFaultPropagation
                           (TN-IEEE8021-CFM-MIB) set to useIfStatusTLV(1).
                           Prior to a destroy(6) all MEPs must have
                           tnDot1agCfmMepFaultPropagation set disabled(0).
                         In case for none of the ports has Service OAM enabled
                         i.e. tnPsdSoamEnable is true(1), all entries are
                         removed from this table and no new entries can be
                         created."

        VARIATION       dot1agCfmLtrForwarded
            ACCESS      not-implemented
            DESCRIPTION "This object is not supported."

        VARIATION       dot1agCfmLtrRelay
            ACCESS      not-implemented
            DESCRIPTION "This object is not supported."

        VARIATION       dot1agCfmLtrChassisIdSubtype
            ACCESS      not-implemented
            DESCRIPTION "This object is not supported."

        VARIATION       dot1agCfmLtrChassisId
            ACCESS      not-implemented
            DESCRIPTION "This object is not supported."

        VARIATION       dot1agCfmLtrManAddress
            ACCESS      not-implemented
            DESCRIPTION "This object is not supported."

        VARIATION       dot1agCfmLtrManAddressDomain
            ACCESS      not-implemented
            DESCRIPTION "This object is not supported."

        VARIATION       dot1agCfmLtrIngress
            ACCESS      not-implemented
            DESCRIPTION "This object is not supported."

        VARIATION       dot1agCfmLtrIngressMac
            ACCESS      not-implemented
            DESCRIPTION "This object is not supported."

        VARIATION       dot1agCfmLtrIngressPortIdSubtype
            ACCESS      not-implemented
            DESCRIPTION "This object is not supported."

        VARIATION       dot1agCfmLtrIngressPortId
            ACCESS      not-implemented
            DESCRIPTION "This object is not supported."

        VARIATION       dot1agCfmLtrEgress
            ACCESS      not-implemented
            DESCRIPTION "This object is not supported."

        VARIATION       dot1agCfmLtrEgressMac
            ACCESS      not-implemented
            DESCRIPTION "This object is not supported."

        VARIATION       dot1agCfmLtrEgressPortIdSubtype
            ACCESS      not-implemented
            DESCRIPTION "This object is not supported."

        VARIATION       dot1agCfmLtrEgressPortId
            ACCESS      not-implemented
            DESCRIPTION "This object is not supported."

        VARIATION       dot1agCfmLtrTerminalMep
            ACCESS      not-implemented
            DESCRIPTION "This object is not supported."

        VARIATION       dot1agCfmLtrLastEgressIdentifier
            ACCESS      not-implemented
            DESCRIPTION "This object is not supported."

        VARIATION       dot1agCfmLtrNextEgressIdentifier
            ACCESS      not-implemented
            DESCRIPTION "This object is not supported."

        VARIATION       dot1agCfmLtrTtl
            ACCESS      not-implemented
            DESCRIPTION "This object is not supported."

        VARIATION       dot1agCfmLtrOrganizationSpecificTlv
            ACCESS      not-implemented
            DESCRIPTION "This object is not supported."

        VARIATION       dot1agCfmMepDbRMepFailedOkTime
            ACCESS      not-implemented
            DESCRIPTION "This object is not supported."

        VARIATION       dot1agCfmMepDbPortStatusTlv
            ACCESS      not-implemented
            DESCRIPTION "This object is not supported."

        VARIATION       dot1agCfmMepDbChassisIdSubtype
            ACCESS      not-implemented
            DESCRIPTION "This object is not supported."

        VARIATION       dot1agCfmMepDbChassisId
            ACCESS      not-implemented
            DESCRIPTION "This object is not supported."

        VARIATION       dot1agCfmMepDbManAddressDomain
            ACCESS      not-implemented
            DESCRIPTION "This object is not supported."

        VARIATION       dot1agCfmMepDbManAddress
            ACCESS      not-implemented
            DESCRIPTION "This object is not supported."

--
-- Capabilities for TN-IEEE8021-CFM-MIB
-- Based on MIB version:  R15.0-LatestMIBs-221105
--
-- There are no conformance groups defined in TN-IEEE8021-CFM-MIB.
-- Due to this omission this section is listed in comment style and
-- the supported tables are included instead of the groups.
--
--  SUPPORTS            TN-IEEE8021-CFM-MIB
--      INCLUDES        { tnDot1agCfmMepTable,
--                        tnDot1agCfmMepDelayRsltTable,
--                        tnDot1agCfmMepSlmTWTestTable,
--                        tnDot1agCfmMepSlmTestRsltTable,
--                        tnDot1agCfmMepOndemandLmTestTable,
--                        tnDot1agCfmMepOndemandLmTestRsltTable }
--
--      VARIATION       tnDot1agCfmMepSdpId
--          ACCESS      not-implemented
--          DESCRIPTION "This object is not supported."
--
--      VARIATION       tnDot1agCfmMepVcId
--          ACCESS      not-implemented
--          DESCRIPTION "This object is not supported."
--
--      VARIATION       tnDot1agCfmMepMacAddress
--          ACCESS      not-implemented
--          DESCRIPTION "This object is not supported."
--
--      VARIATION       tnDot1agCfmMepAisEnable
--          ACCESS      not-implemented
--          DESCRIPTION "This object is not supported."
--
--      VARIATION       tnDot1agCfmMepAisMegLevel
--          ACCESS      not-implemented
--          DESCRIPTION "This object is not supported."
--
--      VARIATION       tnDot1agCfmMepAisPriority
--          ACCESS      not-implemented
--          DESCRIPTION "This object is not supported."
--
--      VARIATION       tnDot1agCfmMepAisInterval
--          ACCESS      not-implemented
--          DESCRIPTION "This object is not supported."
--
--      VARIATION       tnDot1agCfmMepEthRxAisInterval
--          ACCESS      not-implemented
--          DESCRIPTION "This object is not supported."
--
--      VARIATION       tnDot1agCfmMepEthRxAis
--          ACCESS      not-implemented
--          DESCRIPTION "This object is not supported."
--
--      VARIATION       tnDot1agCfmMepEthAisTxCount
--          ACCESS      not-implemented
--          DESCRIPTION "This object is not supported."
--
--      VARIATION       tnDot1agCfmMepEthTestEnable
--          ACCESS      not-implemented
--          DESCRIPTION "This object is not supported."
--
--      VARIATION       tnDot1agCfmMepEthTestPattern
--          ACCESS      not-implemented
--          DESCRIPTION "This object is not supported."
--
--      VARIATION       tnDot1agCfmMepEthTestMacAddr
--          ACCESS      not-implemented
--          DESCRIPTION "This object is not supported."
--
--      VARIATION       tnDot1agCfmMepEthTestDataLen
--          ACCESS      not-implemented
--          DESCRIPTION "This object is not supported."
--
--      VARIATION       tnDot1agCfmMepEthTestPriority
--          ACCESS      not-implemented
--          DESCRIPTION "This object is not supported."
--
--      VARIATION       tnDot1agCfmMepOWDTMacAddress
--          ACCESS      not-implemented
--          DESCRIPTION "This object is not supported."
--
--      VARIATION       tnDot1agCfmMepOWDTPriority
--          ACCESS      not-implemented
--          DESCRIPTION "This object is not supported."
--
--      VARIATION       tnDot1agCfmMepTWDTMacAddress
--          DESCRIPTION "The value of this object must be a unicast MAC
--                       address and may not be set to an all zero value.
--                       In order to initiate the start of a two-way on-demand
--                       delay measurement (DM) the value of this object must
--                       contain a valid MAC address value and this object must
--                       must be present in the varbinds of the SNMP-SET
--                       request together with tnPsdDot1agCfmMepDmTWTestStatus
--                       (TROPIC-PSD-MIB) with the value set to enabled(1).
--                       The set command will be rejected in case:
--                       - a pro-active DM measurement is running on this MEP.
--                       - the previous on-demand DM is still running
--                         (tnPsdDot1agCfmMepDmTWTestStatus is enabled(1)).
--                       - dot1agCfmMepActive is false(2) for this instance."
--
--      VARIATION       tnDot1agCfmMepTWDTPriority
--          DESCRIPTION "In order to set the value this object must be present
--                       in the varbinds of the SNMP SET request that
--                       initiates the start of the on-demand measurement, see
--                       tnDot1agCfmMepTWDTMacAddress for details."
--
--      VARIATION       tnDot1agCfmMepSvcId
--          ACCESS      not-implemented
--          DESCRIPTION "This object is not supported."
--
--      VARIATION       tnDot1agCfmMepControlMep
--          ACCESS      not-implemented
--          DESCRIPTION "This object is not supported."
--
--      VARIATION       tnDot1agCfmMepEthTestThreshold
--          ACCESS      not-implemented
--          DESCRIPTION "This object is not supported."
--
--      VARIATION       tnDot1agCfmMepOWDTThreshold
--          ACCESS      not-implemented
--          DESCRIPTION "This object is not supported."
--
--      VARIATION       tnDot1agCfmMepMcLagInactive
--          ACCESS      not-implemented
--          DESCRIPTION "This object is not supported."
--
--      VARIATION       tnDot1agCfmMepTWDTDataSize
--          DESCRIPTION "In order to set the value this object must be present
--                       in the varbinds of the SNMP SET request that
--                       initiates the start of the on-demand measurement, see
--                       tnDot1agCfmMepTWDTMacAddress for details."
--
--      VARIATION       tnDot1agCfmMepTransmitLbmDataTlvSize
--          ACCESS      not-implemented
--          DESCRIPTION "This object is not supported."
--
--      VARIATION       tnDot1agCfmMepType
--          ACCESS      not-implemented
--          DESCRIPTION "This object is not supported."
--
--      VARIATION       tnDot1agCfmMepFaultPropagation
--          SYNTAX       INTEGER { disabled(0), useIfStatusTLV(1) }
--          DESCRIPTION "Limited set of values.
--                       This object is used for Link Loss Forwarding via
--                       CCM - TLV. The value useIfStatusTLV(1) is restricted
--                       for 1 up MEP instance. The system autonomously raises
--                       USALS alarm (Up Stream Automatic Laser Shutdown).
--                       The USALS alarm contains additional information
--                       about the MEP that triggered the shutdown.
--                       In case dot1agCfmMepCciEnabled equals false(2) and the
--                       value of this object is set to useIfStatusTLV(1) the
--                       SNMP SET request is rejected."
--
--      VARIATION       tnDot1agCfmMepOWDTDataSize
--          ACCESS      not-implemented
--          DESCRIPTION "This object is not supported."
--
--      VARIATION       tnDot1agCfmMepAlmProfName
--          ACCESS      not-implemented
--          DESCRIPTION "This object is not supported."
--
--      VARIATION       tnDot1agCfmMepDelaySrcMacAddr
--          DESCRIPTION "The MAC address value of this object is equal to the
--                       remote MAC address value that is used in the
--                       on-demand DM test, i.e. tnDot1agCfmMepTWDTMacAddress."
--
--      VARIATION       tnDot1agCfmMepDelayTestDelay
--          DESCRIPTION "Supported. The value is expressed in micro seconds."
--
--      VARIATION       tnDot1agCfmMepDelayVariation
--          DESCRIPTION "Supported. The value is expressed in micro seconds."
--
--      VARIATION       tnDot1agCfmMepDelayNearEndTestDelay
--          ACCESS      not-implemented
--          DESCRIPTION "This object is not supported."
--
--      VARIATION       tnDot1agCfmMepDelayNearEndVariation
--          ACCESS      not-implemented
--          DESCRIPTION "This object is not supported."
--
--      VARIATION       tnDot1agCfmMepDelayFarEndTestDelay
--          ACCESS      not-implemented
--          DESCRIPTION "This object is not supported."
--
--      VARIATION       tnDot1agCfmMepDelayFarEndVariation
--          ACCESS      not-implemented
--          DESCRIPTION "This object is not supported."
--
--      VARIATION       tnDot1agCfmMepSlmTWTestStatus
--          DESCRIPTION "In order to start an on-demand SLM test it is
--                       mandatory that the value this object is set to
--                       enabled(1) and that this object is be present in the
--                       varbinds of the SNMP SET request that initiates the
--                       start of the on-demand measurement, see
--                       tnDot1agCfmMepSlmTWMacAddress for details.
--                       An on-demand SLM session can be stopped by setting the
--                       the value of this object to disabled(2).
--                       In case the test has ended regardless of the result,
--                       the system sets the value of this object to
--                       disabled(2). A trap notification is only sent in case
--                       the test successfully completed."
--
--      VARIATION       tnDot1agCfmMepSlmTWTestId
--          DESCRIPTION "Supported."
--
--      VARIATION       tnDot1agCfmMepSlmTWMacAddress
--          DESCRIPTION "The value of this object must be a unicast MAC
--                       address and may not be set to an all zero value.
--                       In order to initiate the start of a two-way on-demand
--                       synthetic loss measurement (SLM) the value of this
--                       object must contain a valid MAC address value and
--                       this object must be present together with
--                       tnDot1agCfmMepSlmTWTestStatus with
--                       the value set to enabled(1).
--                       The set command will be rejected in case:
--                       - the previous on-demand SLM is still running.
--                         (tnDot1agCfmMepSlmTWTestStatus is enabled(1)).
--                       - dot1agCfmMepActive is false(2) for this instance.
--                       - when 8 pro-active SLM sessions are running on this
--                         MEP.
--                       - when a total of 32 SLM (the sum of pro-active and
--                         on-demand) sessions are running on the system."
--
--      VARIATION       tnDot1agCfmMepSlmTWPriority
--          DESCRIPTION "Supported."
--
--      VARIATION       tnDot1agCfmMepSlmTWInterval
--          ACCESS      not-implemented
--          DESCRIPTION "This object is not supported. It is obsoleted by
--                       object tnPsdDot1agCfmMepSlmTWInterval
--                       (TROPIC-PSD-MIB)."
--
--      VARIATION       tnDot1agCfmMepSlmTWTimeout
--          ACCESS      not-implemented
--          DESCRIPTION "This object is not supported."
--
--      VARIATION       tnDot1agCfmMepSlmTWDataSize
--          DESCRIPTION "Supported."
--
--      VARIATION       tnDot1agCfmMepSlmTWSendCount
--          DESCRIPTION "The dependencies per tnPsdDot1agCfmMepSlmTWInterval
--                       (TROPIC-PSD-MIB) are:
--                       The product of tnPsdDot1agCfmMepSlmTWInterval and
--                       the value of this object must be a multiple of 1
--                       second, otherwise an error is returned.
--                       - interval10ms(2) : 100 <= sendCount <= 1000
--                       - interval100ms(3): 10  <= sendCount <= 1000
--                       - interval1s(4)   : 1   <= sendCount <= 1000
--                       - interval10s(5)  : 1   <= sendCount <= 1000
--                       In order to set the value this object must be present
--                       in the varbinds of the SNMP SET request that
--                       initiates the start of the on-demand measurement, see
--                       tnDot1agCfmMepSlmTWMacAddress for details."
--
--      VARIATION       tnDot1agCfmMepSlmTWIntervalRedef
--          ACCESS      not-implemented
--          DESCRIPTION "This object is not supported."
--
--      VARIATION       tnDot1agCfmMepSlmTWIntrvlUnits
--          ACCESS      not-implemented
--          DESCRIPTION "This object is not supported."
--
--      VARIATION       tnDot1agCfmMepSlmTestId
--          DESCRIPTION "Supported."
--
--      VARIATION       tnDot1agCfmMepSlmRemoteMepId
--          DESCRIPTION "Supported."
--
--      VARIATION       tnDot1agCfmMepSlmLastTxSeqF
--          ACCESS      not-implemented
--          DESCRIPTION "This object is not supported."
--
--      VARIATION       tnDot1agCfmMepSlmPacketIn
--          DESCRIPTION "Supported."
--
--      VARIATION       tnDot1agCfmMepSlmPacketLossIn
--          DESCRIPTION "Supported."
--
--      VARIATION       tnDot1agCfmMepSlmPacketLossOut
--          DESCRIPTION "Supported."
--
--      VARIATION       tnDot1agCfmMepSlmPacketUnack
--          DESCRIPTION "Supported."
--
--      VARIATION       tnDot1agCfmMepOndemandLmTestStatus
--          DESCRIPTION "In order to start an on-demand LM test it is mandatory
--                       that the value this object is set to enabled(1) and
--                       that this object is be present in the varbinds of the
--                       SNMP SET request that initiates the start of the
--                       on-demand measurement, see
--                       tnDot1agCfmMepOndemandLmDestMacAddress for details.
--                       An on-demand LM session can be stopped by setting the
--                       the value of this object to disabled(2).
--                       In case the test has ended regardless of the result,
--                       the system sets the value of this object to
--                       disabled(2). A trap notification is only sent in case
--                       the test successfully completed."
--
--      VARIATION       tnDot1agCfmMepOndemandLmDestMacAddress
--          DESCRIPTION "The value of this object must be a unicast MAC
--                       address and may not be set to an all zero value.
--                       In order to initiate the start of a two-way on-demand
--                       loss measurement (LM) the value of this object must
--                       contain a valid MAC address value and this object must
--                       be present together with
--                       tnDot1agCfmMepOndemandLmTestStatus with the value set
--                       to enabled(1).
--                       The set command will be rejected in case:
--                       - the previous on-demand LM is still running.
--                         (tnDot1agCfmMepOndemandLmTestStatus is enabled(1)).
--                       - dot1agCfmMepActive is false(2) for this instance."
--
--      VARIATION       tnDot1agCfmMepOndemandLmPriority
--          DESCRIPTION "In order to set the value this object must be present
--                       in the varbinds of the SNMP SET request that
--                       initiates the start of the on-demand measurement, see
--                       tnDot1agCfmMepOndemandLmDestMacAddress for details."
--
--      VARIATION       tnDot1agCfmMepOndemandLmInterval
--          SYNTAX      INTEGER { interval100ms(3),
--                                interval1s(4),
--                                interval10s(5) }
--          DESCRIPTION "Limited set of values.
--                       In order to set the value this object must be present
--                       in the varbinds of the SNMP SET request that
--                       initiates the start of the on-demand measurement, see
--                       tnDot1agCfmMepOndemandLmDestMacAddress for details."
--
--      VARIATION       tnDot1agCfmMepOndemandLmSendCount
--          DESCRIPTION "The dependencies per tnDot1agCfmMepOndemandLmInterval
--                       are:
--                       - The product of tnDot1agCfmMepOndemandLmInterval and
--                         the value of this object must be a multiple of 1
--                         second, otherwise an error is returned.
--                       - interval100ms(3): 10 <= sendCount <= 100
--                       - interval1s(4)   : 2  <= sendCount <= 101
--                       - interval10s(5)  : 2  <= sendCount <  29
--                       In order for the counters to not overflow (10Gbit/s
--                       and 84 byte frames) the send count must be smaller
--                       than 29 for interval10s(5).
--                       In order to set the value this object must be present
--                       in the varbinds of the SNMP SET request that
--                       initiates the start of the on-demand measurement, see
--                       tnDot1agCfmMepOndemandLmDestMacAddress for details."
--
--      VARIATION       tnDot1agCfmMepOndemandLmTimeout
--          ACCESS      not-implemented
--          DESCRIPTION "This object is not supported."
--
--      VARIATION       tnDot1agCfmMepOndemandLmSessionStatus
--          ACCESS      not-implemented
--          DESCRIPTION "This object is not supported."
--
--      VARIATION       tnDot1agCfmMepOndemandLmTnTF
--          DESCRIPTION "Supported."
--
--      VARIATION       tnDot1agCfmMepOndemandLmTnLF
--          DESCRIPTION "Supported."
--
--      VARIATION       tnDot1agCfmMepOndemandLmTfTF
--          DESCRIPTION "Supported."
--
--      VARIATION       tnDot1agCfmMepOndemandLmTfLF
--          DESCRIPTION "Supported."
--
--      VARIATION       tnDot1agCfmMepOndemandLmUnack
--          DESCRIPTION "Supported."
--
--      VARIATION       tnDot1agCfmMepOndemandLmRemoteMacAddr
--          ACCESS      not-implemented
--          DESCRIPTION "This object is not supported."
--

-- Capabilities for TN-OAM-TEST-MIB
-- Based on MIB version:  R15.0-LatestMIBs-221105
--
-- There are no conformance groups defined in TN-OAM-TEST-MIB.
-- Due to this omission this section is listed in comment style and
-- the supported tables are included instead of the groups.
--
--  SUPPORTS            TN-OAM-TEST-MIB
--      INCLUDES        { tnOamPingCtlTable,
--                        tnOamEthCfmPingCtlTable,
--                        tnOamSaaCtlTable }
--
--      VARIATION       tnOamPingCtlTestIndex
--          DESCRIPTION "The following ASCII characters from ITU Recommendation
--                       T.50 are supported:
--                       The G0 character set - values 0x21 - 0x7E, with the
--                       following exceptions:
--                       - value 0x22: double quotes
--                       - value 0x27: single quote
--                       - value 0x3f: question mark
--                       - value 0x5c: backslash
--                       - value 0x2d: dash"
--
--      VARIATION       tnOamPingCtlRowStatus
--          SYNTAX      INTEGER { active(1),
--                                createAndGo(4),
--                                destroy(6) }
--          DESCRIPTION "Limited set of values.
--                       In case createAndGo(4) is given all settable
--                       objects must be provided (unless the default value
--                       suffices) in the varbinds of the SNMP
--                       set PDU. For creating a pro-active SOAM test entry,
--                       the following objects must be included in the
--                       varbinds SNMP SET request:
--                       1) tnOamEthCfmPingCtlTable:
--                          - tnOamEthCfmPingCtlTgtMacAddr
--                          - tnOamEthCfmPingCtlSrcMdIndex
--                          - tnOamEthCfmPingCtlSrcMaIndex
--                          - tnOamEthCfmPingCtlSrcMepId
--                       2) tnPsdOamEthCfmPingCtlTable (TROPIC-PSD-MIB):
--                          - tnPsdOamEthCfmPingCtlPriority (default value 7)
--                       In case the referenced source MEP from the
--                       tnOamEthCfmPingCtlTable does not exist or in case the
--                       referenced MEP is not active (dot1agCfmMepActive) the
--                       createAndGo request is rejected.
--                       The combination of below objects must be unique:
--                       - tnSysSwitchId
--                       - tnOamEthCfmPingCtlSrcMdIndex
--                       - tnOamEthCfmPingCtlSrcMaIndex
--                       - tnOamEthCfmPingCtlSrcMepId
--                       - tnOamPingCtlTestMode
--                       - tnPsdOamEthCfmPingCtlPriority
--                       - tnOamPingCtlInterval
--                       - tnOamPingCtlSize
--                       - tnOamEthCfmPingCtlTgtMacAddr
--                       For SLM (tnOamPingCtlTestMode = ethCfmTwoWaySlm(22)):
--                       - Per MEP a maximum 8 SLM session may be created
--                         (sum of pro-active and on-demand SLM sessions).
--                       - The system supports a maximum of 32 SLM (sum of
--                         pro-active and on-demand SLM sessions)
--                         sessions.
--                       For DM (tnOamPingCtlTestMode = ethCfmTwoWayDelay(20)):
--                       - Per MEP a maximum of 1 DM session may be
--                         created (sum of pro-active and on-demand DM
--                         sessions).
--                       In case an object leads to an error no entry is
--                       created.
--                       Performance monitoring (PM) starts immediately when
--                       the entry is created.
--                       A bin only contains evaluated data.
--                       A current bin can never contain more then 40 active
--                       and 40 inactive PM measurement data.
--                       In case needed the system removes the oldest inactive
--                       PM measurement data.
--                       The data for an inactive current PM measurement is
--                       available till the next interval boundary.
--                       The user must be aware that in case of reusing the
--                       tnOamPingCtlTestIndex that the current inactive PM
--                       measurement data is removed.
--                       The following PM measurement data is stored in a
--                       15min or 1Day history PM bin:
--                       - All active PM measurement data at the end of the
--                         bin.
--                       - All in-active PM measurement data with a measurement
--                         time longer than the bin period.
--                       History PM measurement remains available even after a
--                       PM session is deleted and is removed over time
--                       depending on the maximum supported number of history
--                       bins.
--                       In case for none of the ports has Service OAM enabled
--                       i.e. tnPsdSoamEnable is true(1), all entries are
--                       removed from this table and no new entries can be
--                       created."
--
--
--      VARIATION       tnOamPingCtlStorageType
--          SYNTAX      INTEGER { nonVolatile(3) }
--          DESCRIPTION "Limited set of values."
--
--      VARIATION       tnOamPingCtlDescr
--          ACCESS      not-implemented
--          DESCRIPTION "This object is not supported."
--
--      VARIATION       tnOamPingCtlTestMode
--          SYNTAX      INTEGER { ethCfmTwoWayDelay(20),
--                                ethCfmTwoWaySlm(22) }
--          DESCRIPTION "Limited set of values.
--                       The value of this object may not be changed after the
--                       creation of this entry."
--
--      VARIATION       tnOamPingCtlAdminStatus
--          ACCESS      not-implemented
--          DESCRIPTION "This object is not supported."
--
--      VARIATION       tnOamPingCtlOrigSdpId
--          ACCESS      not-implemented
--          DESCRIPTION "This object is not supported."
--
--      VARIATION       tnOamPingCtlRespSdpId
--          ACCESS      not-implemented
--          DESCRIPTION "This object is not supported."
--
--      VARIATION       tnOamPingCtlFcName
--          ACCESS      not-implemented
--          DESCRIPTION "This object is not supported."
--
--      VARIATION       tnOamPingCtlProfile
--          ACCESS      not-implemented
--          DESCRIPTION "This object is not supported."
--
--      VARIATION       tnOamPingCtlMtuStartSize
--          ACCESS      not-implemented
--          DESCRIPTION "This object is not supported."
--
--      VARIATION       tnOamPingCtlMtuEndSize
--          ACCESS      not-implemented
--          DESCRIPTION "This object is not supported."
--
--      VARIATION       tnOamPingCtlMtuStepSize
--          ACCESS      not-implemented
--          DESCRIPTION "This object is not supported."
--
--      VARIATION       tnOamPingCtlTargetIpAddress
--          ACCESS      not-implemented
--          DESCRIPTION "This object is not supported."
--
--      VARIATION       tnOamPingCtlServiceId
--          ACCESS      not-implemented
--          DESCRIPTION "This object is not supported."
--
--      VARIATION       tnOamPingCtlLocalSdp
--          ACCESS      not-implemented
--          DESCRIPTION "This object is not supported."
--
--      VARIATION       tnOamPingCtlRemoteSdp
--          ACCESS      not-implemented
--          DESCRIPTION "This object is not supported."
--
--      VARIATION       tnOamPingCtlSize
--          SYNTAX      Unsigned32 (0 .. 9558)
--          DESCRIPTION "Limited set of values.
--                       For SLM sessions the range is: 0 - 9558
--                       For DM sessions the range is : 0 - 9542
--                       The value of this object may not be changed after the
--                       creation of this entry."
--
--      VARIATION       tnOamPingCtlTimeOut
--          ACCESS      not-implemented
--          DESCRIPTION "This object is not supported."
--
--      VARIATION       tnOamPingCtlProbeCount
--          ACCESS      not-implemented
--          DESCRIPTION "This object is not supported."
--
--      VARIATION       tnOamPingCtlInterval
--          SYNTAX      Unsigned32 (10 | 100 | 1000| 10000)
--          DESCRIPTION "Limited set of values.
--                       Supported interval values for SLM:
--                       10,100,1000 and 10000 ms (default: 100ms)
--                       Supported interval values for DM:
--                       100,1000 and 10000 ms (default: 1000ms)
--                       The value of this object may not be changed after the
--                       creation of this entry."
--
--      VARIATION       tnOamPingCtlMaxRows
--          ACCESS      not-implemented
--          DESCRIPTION "This object is not supported."
--
--      VARIATION       tnOamPingCtlTrapGeneration
--          ACCESS      not-implemented
--          DESCRIPTION "This object is not supported."
--
--      VARIATION       tnOamPingCtlTrapProbeFailureFilter
--          ACCESS      not-implemented
--          DESCRIPTION "This object is not supported."
--
--      VARIATION       tnOamPingCtlTrapTestFailureFilter
--          ACCESS      not-implemented
--          DESCRIPTION "This object is not supported."
--
--      VARIATION       tnOamPingCtlSAA
--          ACCESS      not-implemented
--          DESCRIPTION "This object is not supported."
--
--      VARIATION       tnOamPingCtlRuns
--          ACCESS      not-implemented
--          DESCRIPTION "This object is not supported."
--
--      VARIATION       tnOamPingCtlFailures
--          ACCESS      not-implemented
--          DESCRIPTION "This object is not supported."
--
--      VARIATION       tnOamPingCtlLastRunResult
--          ACCESS      not-implemented
--          DESCRIPTION "This object is not supported."
--
--      VARIATION       tnOamPingCtlLastChanged
--          ACCESS      not-implemented
--          DESCRIPTION "This object is not supported."
--
--      VARIATION       tnOamPingCtlVRtrID
--          ACCESS      not-implemented
--          DESCRIPTION "This object is not supported."
--
--      VARIATION       tnOamPingCtlTgtAddrType
--          ACCESS      not-implemented
--          DESCRIPTION "This object is not supported."
--
--      VARIATION       tnOamPingCtlTgtAddress
--          ACCESS      not-implemented
--          DESCRIPTION "This object is not supported."
--
--      VARIATION       tnOamPingCtlSrcAddrType
--          ACCESS      not-implemented
--          DESCRIPTION "This object is not supported."
--
--      VARIATION       tnOamPingCtlSrcAddress
--          ACCESS      not-implemented
--          DESCRIPTION "This object is not supported."
--
--      VARIATION       tnOamPingCtlDnsName
--          ACCESS      not-implemented
--          DESCRIPTION "This object is not supported."
--
--      VARIATION       tnOamPingCtlDNSRecord
--          ACCESS      not-implemented
--          DESCRIPTION "This object is not supported."
--
--      VARIATION       tnOamPingCtlIntervalUnits
--          ACCESS      not-implemented
--          DESCRIPTION "This object is not supported."
--
--      VARIATION       tnOamEthCfmPingCtlTgtMacAddr
--          DESCRIPTION "The value of this object must be an unicast MAC
--                       address. The all zero value is rejected.
--                       The value of this object may not be changed after the
--                       creation of this entry."
--
--      VARIATION       tnOamEthCfmPingCtlSrcMdIndex
--          DESCRIPTION "The value of this object must reference to an existing
--                       MD entry in the dot1agCfmMdTable.
--                       The value of this object may not be changed after the
--                       creation of this entry."
--
--      VARIATION       tnOamEthCfmPingCtlSrcMaIndex
--          DESCRIPTION "The value of this object must reference to an existing
--                       MA entry in the dot1agCfmMaNetTable.
--                       The value of this object may not be changed after the
--                       creation of this entry."
--
--      VARIATION       tnOamEthCfmPingCtlSrcMepId
--          DESCRIPTION "The value of this object must reference to an existing
--                       MEP entry in the dot1agCfmMepTable.
--                       The value of this object may not be changed after the
--                       creation of this entry."
--
--      VARIATION       tnOamSaaCtlTestIndex
--          DESCRIPTION "Entries in this table are automatically created when
--                       an entry is created in the tnOamPingCtlTable.
--                       Similarly an entry is removed from this table when
--                       an entry is removed from the tnOamPingCtlTable."
--
--      VARIATION       tnOamSaaCtlRowStatus
--          SYNTAX      INTEGER { active(1) }
--          DESCRIPTION "Limited set of values."
--
--      VARIATION       tnOamSaaCtlStorageType
--          ACCESS      not-implemented
--          DESCRIPTION "This object is not supported."
--
--      VARIATION       tnOamSaaCtlLastChanged
--          ACCESS      not-implemented
--          DESCRIPTION "This object is not supported."
--
--      VARIATION       tnOamSaaCtlAdminStatus
--          ACCESS      not-implemented
--          DESCRIPTION "This object is not supported."
--
--      VARIATION       tnOamSaaCtlDescr
--          ACCESS      not-implemented
--          DESCRIPTION "This object is not supported."
--
--      VARIATION       tnOamSaaCtlTestMode
--          ACCESS      not-implemented
--          DESCRIPTION "This object is not supported."
--
--      VARIATION       tnOamSaaCtlRuns
--          ACCESS      not-implemented
--          DESCRIPTION "This object is not supported."
--
--      VARIATION       tnOamSaaCtlFailures
--          ACCESS      not-implemented
--          DESCRIPTION "This object is not supported."
--
--      VARIATION       tnOamSaaCtlLastRunResult
--          ACCESS      not-implemented
--          DESCRIPTION "This object is not supported."
--
--      VARIATION       tnOamSaaCtlAcctPolicyId
--          SYNTAX      Integer32 (1 | 2 | 8)
--          DESCRIPTION "Three policies are created by the system
--                       (tnPmonPolicyTable, TN-PMON-MIB) and only
--                       one of these three policies may be assigned:
--                       1 = Disabled: all TCA values are zero, read only.
--                       2 = User: user can provision TCA values, read write.
--                       8 = Default: all TCA values are set to default values,
--                           read-only.
--                       When a pro-active SOAM session is created the default
--                       policyId is 8. The value of this object may be
--                       modified after the pro-active SOAM session is
--                       created."
--
--      VARIATION       tnOamSaaCtlSuppressAccounting
--          ACCESS      not-implemented
--          DESCRIPTION "This object is not supported."
--
--      VARIATION       tnOamSaaCtlContinuous
--          ACCESS      not-implemented
--          DESCRIPTION "This object is not supported."
--
--      VARIATION       tnOamSaaCtlKeepProbeHistoryAdm
--          ACCESS      not-implemented
--          DESCRIPTION "This object is not supported."
--
--      VARIATION       tnOamSaaCtlKeepProbeHistoryOpr
--          ACCESS      not-implemented
--          DESCRIPTION "This object is not supported."
--
--      VARIATION       tnOamSaaCtlAlmProfName
--          ACCESS      not-implemented
--          DESCRIPTION "This object is not supported."
--

--
-- Capabilities for TROPIC-GENERIC-NOTIFICATION-MIB
-- Based on MIB version:  R15.0-LatestMIBs-221105
--

    SUPPORTS            TROPIC-GENERIC-NOTIFICATION-MIB
        INCLUDES        { tnGenericTrapBufferGroup,
                          tnGenericAlarmNotifsGroup,
                          tnGenericEventNotifsGroup,
                          tnGenericScalarConfigChangeNotifGroup,
                          tnGenericInterfaceConfigChangeNotifGroup,
                          tnGenericInterfaceStateChangeNotifGroup,
                          tnGenericOptIfConfigChangeNotifGroup,
                          tnGenericTnAccessPortConfigChangeNotifGroup,
                          tnGenericTnOpticalPortConfigChangeNotifGroup,
                          tnGenericTnOtuOduConfigChangeNotifGroup,
                          tnGenericTnOthConfigChangeNotifGroup,
                          tnGenericTnOthCreDelNotifGroup,
                          tnGenericTnL1ServiceConfigChangeNotifGroup,
                          tnGenericTnL1ServiceCreDelNotifGroup,
                          tnGenericTnStatisticsConfigChangeNotifGroup,
                          tnGenericTnLagConfigChangeNotifGroup,
                          tnGenericTnPmonConfigChangeNotifGroup,
                          tnGenericTnPortConfigChangeNotifGroup,
                          tnGenericDot1agCfmConfigChangeNotifGroup,
                          tnGenericDot1agCfmCreDelNotifGroup,
                          tnGenericTnDot1agCfmConfigChangeNotifGroup,
                          tnGenericTnOamTestConfigChangeNotifGroup,
                          tnGenericTnOamTestCreDelNotifGroup }

        VARIATION       tnGenericTrapCategory
            SYNTAX      INTEGER { criticalAlarms(1),
                                  majorAlarms(2),
                                  minorAlarms(3),
                                  stateChanges(4),
                                  uiActions(5),
                                  generalEvents(6),
                                  notAlarmed(7),
                                  security(11),
                                  warningAlarms(12) }
            DESCRIPTION "Limited set of values."

        VARIATION       tnGenericTrapNumber
            DESCRIPTION "The value of this object corresponds with the value
                         of the request-id field of the corresponding SNMP trap
                         PDU.
                         The retrieval of the tnGenericTrapBufferTable may
                         result in a large data transfer.
                         The maximum size of the tnGenericTrapBufferTable is
                         9000 entries.
                         When issuing a get request for this table the SNMP
                         manager must use a timeout value of 7 seconds or more.
                         At a moment a get request is issued for this table
                         the data is internally cached for a period of 5
                         minutes.
                         Any following get request that is issued before the
                         expiration of 5 minutes will result in a reply from
                         the cache. This means that new traps that are sent
                         before the cache times out are not present in the
                         results.
                         It is strongly advised to use the following properties
                         for the SNMP get request PDU:
                         - Request type: getBulkRequest (5)
                         - Row wise retrieval. Repeaters are trunked by:
                           100 / #nr columns.
                         Only SNMPv3 users with access group admin are allowed
                         to retrieve the tnGenericTrapBufferTable."

        VARIATION       tnGenericTrapCondition
            SYNTAX      INTEGER { none(0),
                                  frcdWkSwBk(31),
                                  frcdWkSwPr(32),
                                  lof(41),
                                  los(43),
                                  manWkSwBk(49),
                                  manWkSwPr(50),
                                  tim(81),
                                  wkSwPr(84),
                                  wkSwBk(109),
                                  man(112),
                                  lockoutOfPr(120),
                                  intrusion(121),
                                  usAls(134),
                                  gfpLof(140),
                                  plm(151),
                                  dwLom(197),
                                  lck(221),
                                  oci(222),
                                  ssf(223),
                                  bdi(224),
                                  deg(228),
                                  lanLfi(230),
                                  lanRfi(231),
                                  boardEqpt(237),
                                  timOdu(242),
                                  bdiOdu(243),
                                  ssfOdu(244),
                                  ntpOoSync(265),
                                  unknownSfpXfp(270),
                                  mismatchSfpXfp(271),
                                  degOtu(363),
                                  tBbeOtu15Min(365),
                                  tEsOtu15Min(373),
                                  tFecc15Min(380),
                                  tSesOtu15Min(392),
                                  tUasOtu15Min(398),
                                  tBbeOdu15Min(401),
                                  tEsOdu15Min(402),
                                  tSesOdu15Min(403),
                                  tUasOdu15Min(404),
                                  tBbeOtu1Day(409),
                                  tEsOtu1Day(417),
                                  tFecc1Day(424),
                                  tSesOtu1Day(436),
                                  tUasOtu1Day(442),
                                  tBbeOdu1Day(445),
                                  tEsOdu1Day(446),
                                  tSesOdu1Day(447),
                                  tUasOdu1Day(448),
                                  intTempHigh(458),
                                  replUnitMissMOD(467),
                                  eqptPort(470),
                                  uruS(574),
                                  tFebbeOtu15Min(585),
                                  tFeesOtu15Min(586),
                                  tFesesOtu15Min(587),
                                  tFeuasOtu15Min(588),
                                  tFebbeOtu1Day(589),
                                  tFeesOtu1Day(590),
                                  tFesesOtu1Day(591),
                                  tFeuasOtu1Day(592),
                                  tFebbeOdu15Min(593),
                                  tFeesOdu15Min(594),
                                  tFesesOdu15Min(595),
                                  tFeuasOdu15Min(596),
                                  tFebbeOdu1Day(597),
                                  tFeesOdu1Day(598),
                                  tFesesOdu1Day(599),
                                  tFeuasOdu1Day(600),
                                  msim(602),
                                  wtr(617),
                                  ssfTcm(619),
                                  lckTcm(620),
                                  ociTcm(621),
                                  degTcm(622),
                                  bdiTcm(623),
                                  timTcm(624),
                                  ltcTcm(625),
                                  tBbeTcm15Min(628),
                                  tEsTcm15Min(629),
                                  tSesTcm15Min(630),
                                  tUasTcm15Min(631),
                                  tFebbeTcm15Min(633),
                                  tFeesTcm15Min(634),
                                  tFesesTcm15Min(635),
                                  tFeuasTcm15Min(636),
                                  tBbeTcm1Day(638),
                                  tEsTcm1Day(639),
                                  tSesTcm1Day(640),
                                  tUasTcm1Day(641),
                                  tFebbeTcm1Day(643),
                                  tFeesTcm1Day(644),
                                  tFesesTcm1Day(645),
                                  tFeuasTcm1Day(646),
                                  lofLom(691),
                                  mepLoc(708),
                                  mepMmg(709),
                                  rdi(712),
                                  egressSSF(736),
                                  csf(739),
                                  lagLos(742),
                                  unL(744),
                                  unM(745),
                                  unP(746),
                                  unPr(747),
                                  csfGfp(889),
                                  gfpUpm(890),
                                  tPmonPortIfInPackets15Min(917),
                                  tPmonPortIfOutPackets15Min(918),
                                  tPmonPortIfInOctets15Min(919),
                                  tPmonPortIfOutOctets15Min(920),
                                  tPmonPortIfInDiscards15Min(921),
                                  tPmonPortIfInErrors15Min(923),
                                  tPmonDmaBfd15Min(943),
                                  tPmonDmxBfd15Min(944),
                                  tPmonDmanFdv15Min(945),
                                  tPmonDmxnFdv15Min(946),
                                  tPmonDmafFdv15Min(947),
                                  tPmonDmxfFdv15Min(948),
                                  tPmonPortIfInPackets1Day(951),
                                  tPmonPortIfOutPackets1Day(952),
                                  tPmonPortIfInOctets1Day(953),
                                  tPmonPortIfOutOctets1Day(954),
                                  tPmonPortIfInDiscards1Day(955),
                                  tPmonPortIfInErrors1Day(957),
                                  tPmonSlmanFlr1Day(977),
                                  tPmonSlmafFlr1Day(979),
                                  tPmonDmaBfd1Day(981),
                                  tPmonDmxBfd1Day(982),
                                  tPmonDmanFdv1Day(983),
                                  tPmonDmxnFdv1Day(984),
                                  tPmonDmafFdv1Day(985),
                                  tPmonDmxfFdv1Day(986),
                                  commDown(1019),
                                  ssfOtu(1024),
                                  tPmonSlmanflr15Min(1030),
                                  tPmonSlmafflr15Min(1031),
                                  tPmonSlmnhli15Min(1032),
                                  tPmonSlmfhli15Min(1033),
                                  tPmonSlmnhli1Day(1044),
                                  tPmonSlmfhli1Day(1045),
                                  tPmonSlmxfflrContinuous(1054),
                                  tPmonSlmxnflrContinuous(1055),
                                  tPmonSlmanflrContinuous(1056),
                                  tPmonSlmafflrContinuous(1057),
                                  gfpExm(1182),
                                  eCondUruO(1189),
                                  eCondUruP(1190),
                                  nuat(1377),
                                  fuat(1378),
                                  lagProtLos(1476),
                                  unitInit(1479),
                                  prbsLSS(1623),
                                  neCertValidityWarn(1807),
                                  neCertValidityExp(1808) }
            DESCRIPTION "Limited set of values."

        VARIATION       tnGenericTrapConfigurationChangeCounter
            ACCESS      not-implemented
            DESCRIPTION "This object is not supported."

        VARIATION       tnGenericTrapEntityType
            SYNTAX      INTEGER { all(1),
                                  tenGige(2),
                                  eqpt(3),
                                  gige(4),
                                  otu1(10),
                                  otu2(11),
                                  session(19),
                                  odu1(25),
                                  odu2(26),
                                  oduf(52),
                                  mep(59),
                                  odu2Tcm(60),
                                  odu2e(64),
                                  otuOdu1(67),
                                  otuOdu2(68),
                                  otuOdu2e(69),
                                  odu2Oduf(76),
                                  odu1Tcm(98),
                                  odu2eTcm(99),
                                  lag(102),
                                  otu2e(138),
                                  netif(190) }
            DESCRIPTION "Limited set of values. Only applicable for alarm
                         notifications. Value 0 is not part of TnEntityType
                         syntax and now used to indicate that entityType
                         is not applicable."

--      VARIATION       tnGenericSecurityEnableInterfaceNotif
--          DESCRIPTION "This trap is used to notify the enabling of the DEBUG
--                       port."

--      VARIATION       tnGenericSecurityDisableInterfaceNotif
--          DESCRIPTION "This trap is used to notify the disabling of the
--                       DEBUG port."

--      VARIATION       tnGenericPmBinsRolledOverNotif
--          DESCRIPTION "This trap is used to notify that all performance
--                       monitoring history data is available."

--
-- Capabilities for TROPIC-GENERIC-LOG-MIB
-- Based on MIB version:  R15.0-LatestMIBs-221105
--

    SUPPORTS            TROPIC-GENERIC-LOG-MIB
        INCLUDES        { tnGenericActiveAlarmGroup,
                          tnGenericCriticalAlarmGroup,
                          tnGenericMajorAlarmGroup,
                          tnGenericMinorAlarmGroup,
                          tnGenericStateChangeGroup,
                          tnGenericUserActionGroup,
                          tnGenericUserActionGroup2,
                          tnGenericGeneralEventGroup,
                          tnGenericNotAlarmedGroup,
                          tnGenericSecurityGroup,
                          tnGenericWarningAlarmGroup }

        VARIATION       tnGenericActiveAlarmSerialNumber
            DESCRIPTION "The value of this object corresponds with the value
                         of the request-id field of the corresponding
                         SNMP trap PDU and matches with the index value of
                         the tnGenericTrapBufferTable."

        VARIATION       tnGenericActiveAlarmCategory
            SYNTAX      INTEGER { criticalAlarms(1),
                                  majorAlarms(2),
                                  minorAlarms(3),
                                  notAlarmed(7),
                                  warningAlarms(12) }
            DESCRIPTION "Limited set of values."

        VARIATION       tnGenericActiveAlarmCondition
            SYNTAX      INTEGER { frcdWkSwBk(31),
                                  frcdWkSwPr(32),
                                  lof(41),
                                  los(43),
                                  manWkSwBk(49),
                                  manWkSwPr(50),
                                  tim(81),
                                  wkSwPr(84),
                                  wkSwBk(109),
                                  man(112),
                                  lockoutOfPr(120),
                                  intrusion(121),
                                  usAls(134),
                                  gfpLof(140),
                                  plm(151),
                                  dwLom(197),
                                  lck(221),
                                  oci(222),
                                  ssf(223),
                                  bdi(224),
                                  deg(228),
                                  lanLfi(230),
                                  lanRfi(231),
                                  boardEqpt(237),
                                  timOdu(242),
                                  bdiOdu(243),
                                  ssfOdu(244),
                                  ntpOoSync(265),
                                  unknownSfpXfp(270),
                                  mismatchSfpXfp(271),
                                  degOtu(363),
                                  tBbeOtu15Min(365),
                                  tEsOtu15Min(373),
                                  tFecc15Min(380),
                                  tSesOtu15Min(392),
                                  tUasOtu15Min(398),
                                  tBbeOdu15Min(401),
                                  tEsOdu15Min(402),
                                  tSesOdu15Min(403),
                                  tUasOdu15Min(404),
                                  tBbeOtu1Day(409),
                                  tEsOtu1Day(417),
                                  tFecc1Day(424),
                                  tSesOtu1Day(436),
                                  tUasOtu1Day(442),
                                  tBbeOdu1Day(445),
                                  tEsOdu1Day(446),
                                  tSesOdu1Day(447),
                                  tUasOdu1Day(448),
                                  intTempHigh(458),
                                  replUnitMissMOD(467),
                                  eqptPort(470),
                                  uruS(574),
                                  tFebbeOtu15Min(585),
                                  tFeesOtu15Min(586),
                                  tFesesOtu15Min(587),
                                  tFeuasOtu15Min(588),
                                  tFebbeOtu1Day(589),
                                  tFeesOtu1Day(590),
                                  tFesesOtu1Day(591),
                                  tFeuasOtu1Day(592),
                                  tFebbeOdu15Min(593),
                                  tFeesOdu15Min(594),
                                  tFesesOdu15Min(595),
                                  tFeuasOdu15Min(596),
                                  tFebbeOdu1Day(597),
                                  tFeesOdu1Day(598),
                                  tFesesOdu1Day(599),
                                  tFeuasOdu1Day(600),
                                  msim(602),
                                  wtr(617),
                                  ssfTcm(619),
                                  lckTcm(620),
                                  ociTcm(621),
                                  degTcm(622),
                                  bdiTcm(623),
                                  timTcm(624),
                                  ltcTcm(625),
                                  tBbeTcm15Min(628),
                                  tEsTcm15Min(629),
                                  tSesTcm15Min(630),
                                  tUasTcm15Min(631),
                                  tFebbeTcm15Min(633),
                                  tFeesTcm15Min(634),
                                  tFesesTcm15Min(635),
                                  tFeuasTcm15Min(636),
                                  tBbeTcm1Day(638),
                                  tEsTcm1Day(639),
                                  tSesTcm1Day(640),
                                  tUasTcm1Day(641),
                                  tFebbeTcm1Day(643),
                                  tFeesTcm1Day(644),
                                  tFesesTcm1Day(645),
                                  tFeuasTcm1Day(646),
                                  lofLom(691),
                                  mepLoc(708),
                                  mepMmg(709),
                                  rdi(712),
                                  egressSSF(736),
                                  csf(739),
                                  lagLos(742),
                                  unL(744),
                                  unM(745),
                                  unP(746),
                                  unPr(747),
                                  csfGfp(889),
                                  gfpUpm(890),
                                  tPmonPortIfInPackets15Min(917),
                                  tPmonPortIfOutPackets15Min(918),
                                  tPmonPortIfInOctets15Min(919),
                                  tPmonPortIfOutOctets15Min(920),
                                  tPmonPortIfInDiscards15Min(921),
                                  tPmonPortIfInErrors15Min(923),
                                  tPmonDmaBfd15Min(943),
                                  tPmonDmxBfd15Min(944),
                                  tPmonDmanFdv15Min(945),
                                  tPmonDmxnFdv15Min(946),
                                  tPmonDmafFdv15Min(947),
                                  tPmonDmxfFdv15Min(948),
                                  tPmonPortIfInPackets1Day(951),
                                  tPmonPortIfOutPackets1Day(952),
                                  tPmonPortIfInOctets1Day(953),
                                  tPmonPortIfOutOctets1Day(954),
                                  tPmonPortIfInDiscards1Day(955),
                                  tPmonPortIfInErrors1Day(957),
                                  tPmonSlmanFlr1Day(977),
                                  tPmonSlmafFlr1Day(979),
                                  tPmonDmaBfd1Day(981),
                                  tPmonDmxBfd1Day(982),
                                  tPmonDmanFdv1Day(983),
                                  tPmonDmxnFdv1Day(984),
                                  tPmonDmafFdv1Day(985),
                                  tPmonDmxfFdv1Day(986),
                                  commDown(1019),
                                  ssfOtu(1024),
                                  tPmonSlmanflr15Min(1030),
                                  tPmonSlmafflr15Min(1031),
                                  tPmonSlmnhli15Min(1032),
                                  tPmonSlmfhli15Min(1033),
                                  tPmonSlmnhli1Day(1044),
                                  tPmonSlmfhli1Day(1045),
                                  tPmonSlmxfflrContinuous(1054),
                                  tPmonSlmxnflrContinuous(1055),
                                  tPmonSlmanflrContinuous(1056),
                                  tPmonSlmafflrContinuous(1057),
                                  gfpExm(1182),
                                  eCondUruO(1189),
                                  eCondUruP(1190),
                                  nuat(1377),
                                  fuat(1378),
                                  lagProtLos(1476),
                                  unitInit(1479),
                                  prbsLSS(1623),
                                  neCertValidityWarn(1807),
                                  neCertValidityExp(1808) }
            DESCRIPTION "Limited set of values."

        VARIATION       tnGenericActiveAlarmEntityType
            SYNTAX      INTEGER { all(1),
                                  tenGige(2),
                                  eqpt(3),
                                  gige(4),
                                  otu1(10),
                                  otu2(11),
                                  session(19),
                                  odu1(25),
                                  odu2(26),
                                  oduf(52),
                                  mep(59),
                                  odu2Tcm(60),
                                  odu2e(64),
                                  otuOdu1(67),
                                  otuOdu2(68),
                                  otuOdu2e(69),
                                  odu2Oduf(76),
                                  odu1Tcm(98),
                                  odu2eTcm(99),
                                  lag(102),
                                  otu2e(138),
                                  netif(190) }
            DESCRIPTION "Limited set of values."

        VARIATION       tnGenericCriticalAlarmLogSerialNumber
            DESCRIPTION "The value of this object corresponds with the value
                         of the request-id field of the corresponding
                         SNMP trap PDU and matches with the index value of
                         the tnGenericTrapBufferTable.
                         The maximum size of this log is 1000 entries."

        VARIATION       tnGenericCriticalAlarmLogCondition
            SYNTAX      INTEGER { frcdWkSwBk(31),
                                  frcdWkSwPr(32),
                                  lof(41),
                                  los(43),
                                  manWkSwBk(49),
                                  manWkSwPr(50),
                                  tim(81),
                                  wkSwPr(84),
                                  wkSwBk(109),
                                  man(112),
                                  lockoutOfPr(120),
                                  intrusion(121),
                                  usAls(134),
                                  gfpLof(140),
                                  plm(151),
                                  dwLom(197),
                                  lck(221),
                                  oci(222),
                                  ssf(223),
                                  bdi(224),
                                  deg(228),
                                  lanLfi(230),
                                  lanRfi(231),
                                  boardEqpt(237),
                                  timOdu(242),
                                  bdiOdu(243),
                                  ssfOdu(244),
                                  ntpOoSync(265),
                                  unknownSfpXfp(270),
                                  mismatchSfpXfp(271),
                                  degOtu(363),
                                  tBbeOtu15Min(365),
                                  tEsOtu15Min(373),
                                  tFecc15Min(380),
                                  tSesOtu15Min(392),
                                  tUasOtu15Min(398),
                                  tBbeOdu15Min(401),
                                  tEsOdu15Min(402),
                                  tSesOdu15Min(403),
                                  tUasOdu15Min(404),
                                  tBbeOtu1Day(409),
                                  tEsOtu1Day(417),
                                  tFecc1Day(424),
                                  tSesOtu1Day(436),
                                  tUasOtu1Day(442),
                                  tBbeOdu1Day(445),
                                  tEsOdu1Day(446),
                                  tSesOdu1Day(447),
                                  tUasOdu1Day(448),
                                  intTempHigh(458),
                                  replUnitMissMOD(467),
                                  eqptPort(470),
                                  uruS(574),
                                  tFebbeOtu15Min(585),
                                  tFeesOtu15Min(586),
                                  tFesesOtu15Min(587),
                                  tFeuasOtu15Min(588),
                                  tFebbeOtu1Day(589),
                                  tFeesOtu1Day(590),
                                  tFesesOtu1Day(591),
                                  tFeuasOtu1Day(592),
                                  tFebbeOdu15Min(593),
                                  tFeesOdu15Min(594),
                                  tFesesOdu15Min(595),
                                  tFeuasOdu15Min(596),
                                  tFebbeOdu1Day(597),
                                  tFeesOdu1Day(598),
                                  tFesesOdu1Day(599),
                                  tFeuasOdu1Day(600),
                                  msim(602),
                                  wtr(617),
                                  ssfTcm(619),
                                  lckTcm(620),
                                  ociTcm(621),
                                  degTcm(622),
                                  bdiTcm(623),
                                  timTcm(624),
                                  ltcTcm(625),
                                  tBbeTcm15Min(628),
                                  tEsTcm15Min(629),
                                  tSesTcm15Min(630),
                                  tUasTcm15Min(631),
                                  tFebbeTcm15Min(633),
                                  tFeesTcm15Min(634),
                                  tFesesTcm15Min(635),
                                  tFeuasTcm15Min(636),
                                  tBbeTcm1Day(638),
                                  tEsTcm1Day(639),
                                  tSesTcm1Day(640),
                                  tUasTcm1Day(641),
                                  tFebbeTcm1Day(643),
                                  tFeesTcm1Day(644),
                                  tFesesTcm1Day(645),
                                  tFeuasTcm1Day(646),
                                  lofLom(691),
                                  mepLoc(708),
                                  mepMmg(709),
                                  rdi(712),
                                  egressSSF(736),
                                  csf(739),
                                  lagLos(742),
                                  unL(744),
                                  unM(745),
                                  unP(746),
                                  unPr(747),
                                  csfGfp(889),
                                  gfpUpm(890),
                                  tPmonPortIfInPackets15Min(917),
                                  tPmonPortIfOutPackets15Min(918),
                                  tPmonPortIfInOctets15Min(919),
                                  tPmonPortIfOutOctets15Min(920),
                                  tPmonPortIfInDiscards15Min(921),
                                  tPmonPortIfInErrors15Min(923),
                                  tPmonDmaBfd15Min(943),
                                  tPmonDmxBfd15Min(944),
                                  tPmonDmanFdv15Min(945),
                                  tPmonDmxnFdv15Min(946),
                                  tPmonDmafFdv15Min(947),
                                  tPmonDmxfFdv15Min(948),
                                  tPmonPortIfInPackets1Day(951),
                                  tPmonPortIfOutPackets1Day(952),
                                  tPmonPortIfInOctets1Day(953),
                                  tPmonPortIfOutOctets1Day(954),
                                  tPmonPortIfInDiscards1Day(955),
                                  tPmonPortIfInErrors1Day(957),
                                  tPmonSlmanFlr1Day(977),
                                  tPmonSlmafFlr1Day(979),
                                  tPmonDmaBfd1Day(981),
                                  tPmonDmxBfd1Day(982),
                                  tPmonDmanFdv1Day(983),
                                  tPmonDmxnFdv1Day(984),
                                  tPmonDmafFdv1Day(985),
                                  tPmonDmxfFdv1Day(986),
                                  commDown(1019),
                                  ssfOtu(1024),
                                  tPmonSlmanflr15Min(1030),
                                  tPmonSlmafflr15Min(1031),
                                  tPmonSlmnhli15Min(1032),
                                  tPmonSlmfhli15Min(1033),
                                  tPmonSlmnhli1Day(1044),
                                  tPmonSlmfhli1Day(1045),
                                  tPmonSlmxfflrContinuous(1054),
                                  tPmonSlmxnflrContinuous(1055),
                                  tPmonSlmanflrContinuous(1056),
                                  tPmonSlmafflrContinuous(1057),
                                  gfpExm(1182),
                                  eCondUruO(1189),
                                  eCondUruP(1190),
                                  nuat(1377),
                                  fuat(1378),
                                  lagProtLos(1476),
                                  unitInit(1479),
                                  prbsLSS(1623),
                                  neCertValidityWarn(1807),
                                  neCertValidityExp(1808) }
            DESCRIPTION "Limited set of values."

        VARIATION       tnGenericCriticalAlarmLogEntityType
            SYNTAX      INTEGER { all(1),
                                  tenGige(2),
                                  eqpt(3),
                                  gige(4),
                                  otu1(10),
                                  otu2(11),
                                  session(19),
                                  odu1(25),
                                  odu2(26),
                                  oduf(52),
                                  mep(59),
                                  odu2Tcm(60),
                                  odu2e(64),
                                  otuOdu1(67),
                                  otuOdu2(68),
                                  otuOdu2e(69),
                                  odu2Oduf(76),
                                  odu1Tcm(98),
                                  odu2eTcm(99),
                                  lag(102),
                                  otu2e(138),
                                  netif(190) }
            DESCRIPTION "Limited set of values."

        VARIATION       tnGenericMajorAlarmLogSerialNumber
            DESCRIPTION "The value of this object corresponds with the value
                         of the request-id field of the corresponding
                         SNMP trap PDU and matches with the index value of
                         the tnGenericTrapBufferTable.
                         The maximum size of this log is 1000 entries."

        VARIATION       tnGenericMajorAlarmLogCondition
            SYNTAX      INTEGER { frcdWkSwBk(31),
                                  frcdWkSwPr(32),
                                  lof(41),
                                  los(43),
                                  manWkSwBk(49),
                                  manWkSwPr(50),
                                  tim(81),
                                  wkSwPr(84),
                                  wkSwBk(109),
                                  man(112),
                                  lockoutOfPr(120),
                                  intrusion(121),
                                  usAls(134),
                                  gfpLof(140),
                                  plm(151),
                                  dwLom(197),
                                  lck(221),
                                  oci(222),
                                  ssf(223),
                                  bdi(224),
                                  deg(228),
                                  lanLfi(230),
                                  lanRfi(231),
                                  boardEqpt(237),
                                  timOdu(242),
                                  bdiOdu(243),
                                  ssfOdu(244),
                                  ntpOoSync(265),
                                  unknownSfpXfp(270),
                                  mismatchSfpXfp(271),
                                  degOtu(363),
                                  tBbeOtu15Min(365),
                                  tEsOtu15Min(373),
                                  tFecc15Min(380),
                                  tSesOtu15Min(392),
                                  tUasOtu15Min(398),
                                  tBbeOdu15Min(401),
                                  tEsOdu15Min(402),
                                  tSesOdu15Min(403),
                                  tUasOdu15Min(404),
                                  tBbeOtu1Day(409),
                                  tEsOtu1Day(417),
                                  tFecc1Day(424),
                                  tSesOtu1Day(436),
                                  tUasOtu1Day(442),
                                  tBbeOdu1Day(445),
                                  tEsOdu1Day(446),
                                  tSesOdu1Day(447),
                                  tUasOdu1Day(448),
                                  intTempHigh(458),
                                  replUnitMissMOD(467),
                                  eqptPort(470),
                                  uruS(574),
                                  tFebbeOtu15Min(585),
                                  tFeesOtu15Min(586),
                                  tFesesOtu15Min(587),
                                  tFeuasOtu15Min(588),
                                  tFebbeOtu1Day(589),
                                  tFeesOtu1Day(590),
                                  tFesesOtu1Day(591),
                                  tFeuasOtu1Day(592),
                                  tFebbeOdu15Min(593),
                                  tFeesOdu15Min(594),
                                  tFesesOdu15Min(595),
                                  tFeuasOdu15Min(596),
                                  tFebbeOdu1Day(597),
                                  tFeesOdu1Day(598),
                                  tFesesOdu1Day(599),
                                  tFeuasOdu1Day(600),
                                  msim(602),
                                  wtr(617),
                                  ssfTcm(619),
                                  lckTcm(620),
                                  ociTcm(621),
                                  degTcm(622),
                                  bdiTcm(623),
                                  timTcm(624),
                                  ltcTcm(625),
                                  tBbeTcm15Min(628),
                                  tEsTcm15Min(629),
                                  tSesTcm15Min(630),
                                  tUasTcm15Min(631),
                                  tFebbeTcm15Min(633),
                                  tFeesTcm15Min(634),
                                  tFesesTcm15Min(635),
                                  tFeuasTcm15Min(636),
                                  tBbeTcm1Day(638),
                                  tEsTcm1Day(639),
                                  tSesTcm1Day(640),
                                  tUasTcm1Day(641),
                                  tFebbeTcm1Day(643),
                                  tFeesTcm1Day(644),
                                  tFesesTcm1Day(645),
                                  tFeuasTcm1Day(646),
                                  lofLom(691),
                                  mepLoc(708),
                                  mepMmg(709),
                                  rdi(712),
                                  egressSSF(736),
                                  csf(739),
                                  lagLos(742),
                                  unL(744),
                                  unM(745),
                                  unP(746),
                                  unPr(747),
                                  csfGfp(889),
                                  gfpUpm(890),
                                  tPmonPortIfInPackets15Min(917),
                                  tPmonPortIfOutPackets15Min(918),
                                  tPmonPortIfInOctets15Min(919),
                                  tPmonPortIfOutOctets15Min(920),
                                  tPmonPortIfInDiscards15Min(921),
                                  tPmonPortIfInErrors15Min(923),
                                  tPmonDmaBfd15Min(943),
                                  tPmonDmxBfd15Min(944),
                                  tPmonDmanFdv15Min(945),
                                  tPmonDmxnFdv15Min(946),
                                  tPmonDmafFdv15Min(947),
                                  tPmonDmxfFdv15Min(948),
                                  tPmonPortIfInPackets1Day(951),
                                  tPmonPortIfOutPackets1Day(952),
                                  tPmonPortIfInOctets1Day(953),
                                  tPmonPortIfOutOctets1Day(954),
                                  tPmonPortIfInDiscards1Day(955),
                                  tPmonPortIfInErrors1Day(957),
                                  tPmonSlmanFlr1Day(977),
                                  tPmonSlmafFlr1Day(979),
                                  tPmonDmaBfd1Day(981),
                                  tPmonDmxBfd1Day(982),
                                  tPmonDmanFdv1Day(983),
                                  tPmonDmxnFdv1Day(984),
                                  tPmonDmafFdv1Day(985),
                                  tPmonDmxfFdv1Day(986),
                                  commDown(1019),
                                  ssfOtu(1024),
                                  tPmonSlmanflr15Min(1030),
                                  tPmonSlmafflr15Min(1031),
                                  tPmonSlmnhli15Min(1032),
                                  tPmonSlmfhli15Min(1033),
                                  tPmonSlmnhli1Day(1044),
                                  tPmonSlmfhli1Day(1045),
                                  tPmonSlmxfflrContinuous(1054),
                                  tPmonSlmxnflrContinuous(1055),
                                  tPmonSlmanflrContinuous(1056),
                                  tPmonSlmafflrContinuous(1057),
                                  gfpExm(1182),
                                  eCondUruO(1189),
                                  eCondUruP(1190),
                                  nuat(1377),
                                  fuat(1378),
                                  lagProtLos(1476),
                                  unitInit(1479),
                                  prbsLSS(1623),
                                  neCertValidityWarn(1807),
                                  neCertValidityExp(1808) }
            DESCRIPTION "Limited set of values."

        VARIATION       tnGenericMajorAlarmLogEntityType
            SYNTAX      INTEGER { all(1),
                                  tenGige(2),
                                  eqpt(3),
                                  gige(4),
                                  otu1(10),
                                  otu2(11),
                                  session(19),
                                  odu1(25),
                                  odu2(26),
                                  oduf(52),
                                  mep(59),
                                  odu2Tcm(60),
                                  odu2e(64),
                                  otuOdu1(67),
                                  otuOdu2(68),
                                  otuOdu2e(69),
                                  odu2Oduf(76),
                                  odu1Tcm(98),
                                  odu2eTcm(99),
                                  lag(102),
                                  otu2e(138),
                                  netif(190) }
            DESCRIPTION "Limited set of values."

        VARIATION       tnGenericMinorAlarmLogSerialNumber
            DESCRIPTION "The value of this object corresponds with the value
                         of the request-id field of the corresponding
                         SNMP trap PDU and matches with the index value of
                         the tnGenericTrapBufferTable.
                         The maximum size of this log is 1000 entries."

        VARIATION       tnGenericMinorAlarmLogCondition
            SYNTAX      INTEGER { frcdWkSwBk(31),
                                  frcdWkSwPr(32),
                                  lof(41),
                                  los(43),
                                  manWkSwBk(49),
                                  manWkSwPr(50),
                                  tim(81),
                                  wkSwPr(84),
                                  wkSwBk(109),
                                  man(112),
                                  lockoutOfPr(120),
                                  intrusion(121),
                                  usAls(134),
                                  gfpLof(140),
                                  plm(151),
                                  dwLom(197),
                                  lck(221),
                                  oci(222),
                                  ssf(223),
                                  bdi(224),
                                  deg(228),
                                  lanLfi(230),
                                  lanRfi(231),
                                  boardEqpt(237),
                                  timOdu(242),
                                  bdiOdu(243),
                                  ssfOdu(244),
                                  ntpOoSync(265),
                                  unknownSfpXfp(270),
                                  mismatchSfpXfp(271),
                                  degOtu(363),
                                  tBbeOtu15Min(365),
                                  tEsOtu15Min(373),
                                  tFecc15Min(380),
                                  tSesOtu15Min(392),
                                  tUasOtu15Min(398),
                                  tBbeOdu15Min(401),
                                  tEsOdu15Min(402),
                                  tSesOdu15Min(403),
                                  tUasOdu15Min(404),
                                  tBbeOtu1Day(409),
                                  tEsOtu1Day(417),
                                  tFecc1Day(424),
                                  tSesOtu1Day(436),
                                  tUasOtu1Day(442),
                                  tBbeOdu1Day(445),
                                  tEsOdu1Day(446),
                                  tSesOdu1Day(447),
                                  tUasOdu1Day(448),
                                  intTempHigh(458),
                                  replUnitMissMOD(467),
                                  eqptPort(470),
                                  uruS(574),
                                  tFebbeOtu15Min(585),
                                  tFeesOtu15Min(586),
                                  tFesesOtu15Min(587),
                                  tFeuasOtu15Min(588),
                                  tFebbeOtu1Day(589),
                                  tFeesOtu1Day(590),
                                  tFesesOtu1Day(591),
                                  tFeuasOtu1Day(592),
                                  tFebbeOdu15Min(593),
                                  tFeesOdu15Min(594),
                                  tFesesOdu15Min(595),
                                  tFeuasOdu15Min(596),
                                  tFebbeOdu1Day(597),
                                  tFeesOdu1Day(598),
                                  tFesesOdu1Day(599),
                                  tFeuasOdu1Day(600),
                                  msim(602),
                                  wtr(617),
                                  ssfTcm(619),
                                  lckTcm(620),
                                  ociTcm(621),
                                  degTcm(622),
                                  bdiTcm(623),
                                  timTcm(624),
                                  ltcTcm(625),
                                  tBbeTcm15Min(628),
                                  tEsTcm15Min(629),
                                  tSesTcm15Min(630),
                                  tUasTcm15Min(631),
                                  tFebbeTcm15Min(633),
                                  tFeesTcm15Min(634),
                                  tFesesTcm15Min(635),
                                  tFeuasTcm15Min(636),
                                  tBbeTcm1Day(638),
                                  tEsTcm1Day(639),
                                  tSesTcm1Day(640),
                                  tUasTcm1Day(641),
                                  tFebbeTcm1Day(643),
                                  tFeesTcm1Day(644),
                                  tFesesTcm1Day(645),
                                  tFeuasTcm1Day(646),
                                  lofLom(691),
                                  mepLoc(708),
                                  mepMmg(709),
                                  rdi(712),
                                  egressSSF(736),
                                  csf(739),
                                  lagLos(742),
                                  unL(744),
                                  unM(745),
                                  unP(746),
                                  unPr(747),
                                  csfGfp(889),
                                  gfpUpm(890),
                                  tPmonPortIfInPackets15Min(917),
                                  tPmonPortIfOutPackets15Min(918),
                                  tPmonPortIfInOctets15Min(919),
                                  tPmonPortIfOutOctets15Min(920),
                                  tPmonPortIfInDiscards15Min(921),
                                  tPmonPortIfInErrors15Min(923),
                                  tPmonDmaBfd15Min(943),
                                  tPmonDmxBfd15Min(944),
                                  tPmonDmanFdv15Min(945),
                                  tPmonDmxnFdv15Min(946),
                                  tPmonDmafFdv15Min(947),
                                  tPmonDmxfFdv15Min(948),
                                  tPmonPortIfInPackets1Day(951),
                                  tPmonPortIfOutPackets1Day(952),
                                  tPmonPortIfInOctets1Day(953),
                                  tPmonPortIfOutOctets1Day(954),
                                  tPmonPortIfInDiscards1Day(955),
                                  tPmonPortIfInErrors1Day(957),
                                  tPmonSlmanFlr1Day(977),
                                  tPmonSlmafFlr1Day(979),
                                  tPmonDmaBfd1Day(981),
                                  tPmonDmxBfd1Day(982),
                                  tPmonDmanFdv1Day(983),
                                  tPmonDmxnFdv1Day(984),
                                  tPmonDmafFdv1Day(985),
                                  tPmonDmxfFdv1Day(986),
                                  commDown(1019),
                                  ssfOtu(1024),
                                  tPmonSlmanflr15Min(1030),
                                  tPmonSlmafflr15Min(1031),
                                  tPmonSlmnhli15Min(1032),
                                  tPmonSlmfhli15Min(1033),
                                  tPmonSlmnhli1Day(1044),
                                  tPmonSlmfhli1Day(1045),
                                  tPmonSlmxfflrContinuous(1054),
                                  tPmonSlmxnflrContinuous(1055),
                                  tPmonSlmanflrContinuous(1056),
                                  tPmonSlmafflrContinuous(1057),
                                  gfpExm(1182),
                                  eCondUruO(1189),
                                  eCondUruP(1190),
                                  nuat(1377),
                                  fuat(1378),
                                  lagProtLos(1476),
                                  unitInit(1479),
                                  prbsLSS(1623),
                                  neCertValidityWarn(1807),
                                  neCertValidityExp(1808) }
            DESCRIPTION "Limited set of values."

        VARIATION       tnGenericMinorAlarmLogEntityType
            SYNTAX      INTEGER { all(1),
                                  tenGige(2),
                                  eqpt(3),
                                  gige(4),
                                  otu1(10),
                                  otu2(11),
                                  session(19),
                                  odu1(25),
                                  odu2(26),
                                  oduf(52),
                                  mep(59),
                                  odu2Tcm(60),
                                  odu2e(64),
                                  otuOdu1(67),
                                  otuOdu2(68),
                                  otuOdu2e(69),
                                  odu2Oduf(76),
                                  odu1Tcm(98),
                                  odu2eTcm(99),
                                  lag(102),
                                  otu2e(138),
                                  netif(190) }
            DESCRIPTION "Limited set of values."

        VARIATION       tnGenericStateChangeLogSerialNumber
            DESCRIPTION "The value of this object corresponds with the value
                         of the request-id field of the corresponding
                         SNMP trap PDU and matches with the index value of
                         the tnGenericTrapBufferTable.
                         The maximum size of this log is 1000 entries."

        VARIATION       tnGenericUserActionLogSerialNumber
            DESCRIPTION "The value of this object corresponds with the value
                         of the request-id field of the corresponding
                         SNMP trap PDU and matches with the index value of
                         the tnGenericTrapBufferTable.
                         The maximum size of this log is 1000 entries."

        VARIATION       tnGenericUserActionLogConfigurationChangeCounter
            ACCESS      not-implemented
            DESCRIPTION "This object is not supported."

        VARIATION       tnGenericUserActionLogUserID
            DESCRIPTION "For CLI users that perform a configuration change the
                         value of this object contains the user name of the
                         CLI user that applied the configuration change.
                         For SNMPv3 users that perform a configuration change
                         the value of this object is always 'snmp', the SNMPv3
                         USM user name is not logged."

        VARIATION       tnGenericGeneralEventLogSerialNumber
            DESCRIPTION "The value of this object corresponds with the value
                         of the request-id field of the corresponding
                         SNMP trap PDU and matches with the index value of
                         the tnGenericTrapBufferTable.
                         The maximum size of this log is 1000 entries."

        VARIATION       tnGenericNotAlarmedLogSerialNumber
            DESCRIPTION "The value of this object corresponds with the value
                         of the request-id field of the corresponding
                         SNMP trap PDU and matches with the index value of
                         the tnGenericTrapBufferTable.
                         The maximum size of this log is 1000 entries."

        VARIATION       tnGenericNotAlarmedLogCondition
            SYNTAX      INTEGER { frcdWkSwBk(31),
                                  frcdWkSwPr(32),
                                  lof(41),
                                  los(43),
                                  manWkSwBk(49),
                                  manWkSwPr(50),
                                  tim(81),
                                  wkSwPr(84),
                                  wkSwBk(109),
                                  man(112),
                                  lockoutOfPr(120),
                                  intrusion(121),
                                  usAls(134),
                                  gfpLof(140),
                                  plm(151),
                                  dwLom(197),
                                  lck(221),
                                  oci(222),
                                  ssf(223),
                                  bdi(224),
                                  deg(228),
                                  lanLfi(230),
                                  lanRfi(231),
                                  boardEqpt(237),
                                  timOdu(242),
                                  bdiOdu(243),
                                  ssfOdu(244),
                                  ntpOoSync(265),
                                  unknownSfpXfp(270),
                                  mismatchSfpXfp(271),
                                  degOtu(363),
                                  tBbeOtu15Min(365),
                                  tEsOtu15Min(373),
                                  tFecc15Min(380),
                                  tSesOtu15Min(392),
                                  tUasOtu15Min(398),
                                  tBbeOdu15Min(401),
                                  tEsOdu15Min(402),
                                  tSesOdu15Min(403),
                                  tUasOdu15Min(404),
                                  tBbeOtu1Day(409),
                                  tEsOtu1Day(417),
                                  tFecc1Day(424),
                                  tSesOtu1Day(436),
                                  tUasOtu1Day(442),
                                  tBbeOdu1Day(445),
                                  tEsOdu1Day(446),
                                  tSesOdu1Day(447),
                                  tUasOdu1Day(448),
                                  intTempHigh(458),
                                  replUnitMissMOD(467),
                                  eqptPort(470),
                                  uruS(574),
                                  tFebbeOtu15Min(585),
                                  tFeesOtu15Min(586),
                                  tFesesOtu15Min(587),
                                  tFeuasOtu15Min(588),
                                  tFebbeOtu1Day(589),
                                  tFeesOtu1Day(590),
                                  tFesesOtu1Day(591),
                                  tFeuasOtu1Day(592),
                                  tFebbeOdu15Min(593),
                                  tFeesOdu15Min(594),
                                  tFesesOdu15Min(595),
                                  tFeuasOdu15Min(596),
                                  tFebbeOdu1Day(597),
                                  tFeesOdu1Day(598),
                                  tFesesOdu1Day(599),
                                  tFeuasOdu1Day(600),
                                  msim(602),
                                  wtr(617),
                                  ssfTcm(619),
                                  lckTcm(620),
                                  ociTcm(621),
                                  degTcm(622),
                                  bdiTcm(623),
                                  timTcm(624),
                                  ltcTcm(625),
                                  tBbeTcm15Min(628),
                                  tEsTcm15Min(629),
                                  tSesTcm15Min(630),
                                  tUasTcm15Min(631),
                                  tFebbeTcm15Min(633),
                                  tFeesTcm15Min(634),
                                  tFesesTcm15Min(635),
                                  tFeuasTcm15Min(636),
                                  tBbeTcm1Day(638),
                                  tEsTcm1Day(639),
                                  tSesTcm1Day(640),
                                  tUasTcm1Day(641),
                                  tFebbeTcm1Day(643),
                                  tFeesTcm1Day(644),
                                  tFesesTcm1Day(645),
                                  tFeuasTcm1Day(646),
                                  lofLom(691),
                                  mepLoc(708),
                                  mepMmg(709),
                                  rdi(712),
                                  egressSSF(736),
                                  csf(739),
                                  lagLos(742),
                                  unL(744),
                                  unM(745),
                                  unP(746),
                                  unPr(747),
                                  csfGfp(889),
                                  gfpUpm(890),
                                  tPmonPortIfInPackets15Min(917),
                                  tPmonPortIfOutPackets15Min(918),
                                  tPmonPortIfInOctets15Min(919),
                                  tPmonPortIfOutOctets15Min(920),
                                  tPmonPortIfInDiscards15Min(921),
                                  tPmonPortIfInErrors15Min(923),
                                  tPmonDmaBfd15Min(943),
                                  tPmonDmxBfd15Min(944),
                                  tPmonDmanFdv15Min(945),
                                  tPmonDmxnFdv15Min(946),
                                  tPmonDmafFdv15Min(947),
                                  tPmonDmxfFdv15Min(948),
                                  tPmonPortIfInPackets1Day(951),
                                  tPmonPortIfOutPackets1Day(952),
                                  tPmonPortIfInOctets1Day(953),
                                  tPmonPortIfOutOctets1Day(954),
                                  tPmonPortIfInDiscards1Day(955),
                                  tPmonPortIfInErrors1Day(957),
                                  tPmonSlmanFlr1Day(977),
                                  tPmonSlmafFlr1Day(979),
                                  tPmonDmaBfd1Day(981),
                                  tPmonDmxBfd1Day(982),
                                  tPmonDmanFdv1Day(983),
                                  tPmonDmxnFdv1Day(984),
                                  tPmonDmafFdv1Day(985),
                                  tPmonDmxfFdv1Day(986),
                                  commDown(1019),
                                  ssfOtu(1024),
                                  tPmonSlmanflr15Min(1030),
                                  tPmonSlmafflr15Min(1031),
                                  tPmonSlmnhli15Min(1032),
                                  tPmonSlmfhli15Min(1033),
                                  tPmonSlmnhli1Day(1044),
                                  tPmonSlmfhli1Day(1045),
                                  tPmonSlmxfflrContinuous(1054),
                                  tPmonSlmxnflrContinuous(1055),
                                  tPmonSlmanflrContinuous(1056),
                                  tPmonSlmafflrContinuous(1057),
                                  gfpExm(1182),
                                  eCondUruO(1189),
                                  eCondUruP(1190),
                                  nuat(1377),
                                  fuat(1378),
                                  lagProtLos(1476),
                                  unitInit(1479),
                                  prbsLSS(1623),
                                  neCertValidityWarn(1807),
                                  neCertValidityExp(1808) }
            DESCRIPTION "Limited set of values."

        VARIATION       tnGenericNotAlarmedLogEntityType
            SYNTAX      INTEGER { all(1),
                                  tenGige(2),
                                  eqpt(3),
                                  gige(4),
                                  otu1(10),
                                  otu2(11),
                                  session(19),
                                  odu1(25),
                                  odu2(26),
                                  oduf(52),
                                  mep(59),
                                  odu2Tcm(60),
                                  odu2e(64),
                                  otuOdu1(67),
                                  otuOdu2(68),
                                  otuOdu2e(69),
                                  odu2Oduf(76),
                                  odu1Tcm(98),
                                  odu2eTcm(99),
                                  lag(102),
                                  otu2e(138),
                                  netif(190) }
            DESCRIPTION "Limited set of values."

        VARIATION       tnGenericSecurityLogSerialNumber
            DESCRIPTION "The value of this object corresponds with the value
                         of the request-id field of the corresponding
                         SNMP trap PDU and matches with the index value of
                         the tnGenericTrapBufferTable.
                         The maximum size of this log is 1000 entries.
                         Only SNMPv3 users with access group admin are allowed
                         to retrieve the tnGenericSecurityLogBufferTable."


        VARIATION       tnGenericWarningAlarmLogSerialNumber
            DESCRIPTION "The value of this object corresponds with the value
                         of the request-id field of the corresponding
                         SNMP trap PDU and matches with the index value of
                         the tnGenericTrapBufferTable.
                         The maximum size of this log is 1000 entries."

        VARIATION       tnGenericWarningAlarmLogCondition
            SYNTAX      INTEGER { frcdWkSwBk(31),
                                  frcdWkSwPr(32),
                                  lof(41),
                                  los(43),
                                  manWkSwBk(49),
                                  manWkSwPr(50),
                                  tim(81),
                                  wkSwPr(84),
                                  wkSwBk(109),
                                  man(112),
                                  lockoutOfPr(120),
                                  intrusion(121),
                                  usAls(134),
                                  gfpLof(140),
                                  plm(151),
                                  dwLom(197),
                                  lck(221),
                                  oci(222),
                                  ssf(223),
                                  bdi(224),
                                  deg(228),
                                  lanLfi(230),
                                  lanRfi(231),
                                  boardEqpt(237),
                                  timOdu(242),
                                  bdiOdu(243),
                                  ssfOdu(244),
                                  ntpOoSync(265),
                                  unknownSfpXfp(270),
                                  mismatchSfpXfp(271),
                                  degOtu(363),
                                  tBbeOtu15Min(365),
                                  tEsOtu15Min(373),
                                  tFecc15Min(380),
                                  tSesOtu15Min(392),
                                  tUasOtu15Min(398),
                                  tBbeOdu15Min(401),
                                  tEsOdu15Min(402),
                                  tSesOdu15Min(403),
                                  tUasOdu15Min(404),
                                  tBbeOtu1Day(409),
                                  tEsOtu1Day(417),
                                  tFecc1Day(424),
                                  tSesOtu1Day(436),
                                  tUasOtu1Day(442),
                                  tBbeOdu1Day(445),
                                  tEsOdu1Day(446),
                                  tSesOdu1Day(447),
                                  tUasOdu1Day(448),
                                  intTempHigh(458),
                                  replUnitMissMOD(467),
                                  eqptPort(470),
                                  uruS(574),
                                  tFebbeOtu15Min(585),
                                  tFeesOtu15Min(586),
                                  tFesesOtu15Min(587),
                                  tFeuasOtu15Min(588),
                                  tFebbeOtu1Day(589),
                                  tFeesOtu1Day(590),
                                  tFesesOtu1Day(591),
                                  tFeuasOtu1Day(592),
                                  tFebbeOdu15Min(593),
                                  tFeesOdu15Min(594),
                                  tFesesOdu15Min(595),
                                  tFeuasOdu15Min(596),
                                  tFebbeOdu1Day(597),
                                  tFeesOdu1Day(598),
                                  tFesesOdu1Day(599),
                                  tFeuasOdu1Day(600),
                                  msim(602),
                                  wtr(617),
                                  ssfTcm(619),
                                  lckTcm(620),
                                  ociTcm(621),
                                  degTcm(622),
                                  bdiTcm(623),
                                  timTcm(624),
                                  ltcTcm(625),
                                  tBbeTcm15Min(628),
                                  tEsTcm15Min(629),
                                  tSesTcm15Min(630),
                                  tUasTcm15Min(631),
                                  tFebbeTcm15Min(633),
                                  tFeesTcm15Min(634),
                                  tFesesTcm15Min(635),
                                  tFeuasTcm15Min(636),
                                  tBbeTcm1Day(638),
                                  tEsTcm1Day(639),
                                  tSesTcm1Day(640),
                                  tUasTcm1Day(641),
                                  tFebbeTcm1Day(643),
                                  tFeesTcm1Day(644),
                                  tFesesTcm1Day(645),
                                  tFeuasTcm1Day(646),
                                  lofLom(691),
                                  mepLoc(708),
                                  mepMmg(709),
                                  rdi(712),
                                  egressSSF(736),
                                  csf(739),
                                  lagLos(742),
                                  unL(744),
                                  unM(745),
                                  unP(746),
                                  unPr(747),
                                  csfGfp(889),
                                  gfpUpm(890),
                                  tPmonPortIfInPackets15Min(917),
                                  tPmonPortIfOutPackets15Min(918),
                                  tPmonPortIfInOctets15Min(919),
                                  tPmonPortIfOutOctets15Min(920),
                                  tPmonPortIfInDiscards15Min(921),
                                  tPmonPortIfInErrors15Min(923),
                                  tPmonDmaBfd15Min(943),
                                  tPmonDmxBfd15Min(944),
                                  tPmonDmanFdv15Min(945),
                                  tPmonDmxnFdv15Min(946),
                                  tPmonDmafFdv15Min(947),
                                  tPmonDmxfFdv15Min(948),
                                  tPmonPortIfInPackets1Day(951),
                                  tPmonPortIfOutPackets1Day(952),
                                  tPmonPortIfInOctets1Day(953),
                                  tPmonPortIfOutOctets1Day(954),
                                  tPmonPortIfInDiscards1Day(955),
                                  tPmonPortIfInErrors1Day(957),
                                  tPmonSlmanFlr1Day(977),
                                  tPmonSlmafFlr1Day(979),
                                  tPmonDmaBfd1Day(981),
                                  tPmonDmxBfd1Day(982),
                                  tPmonDmanFdv1Day(983),
                                  tPmonDmxnFdv1Day(984),
                                  tPmonDmafFdv1Day(985),
                                  tPmonDmxfFdv1Day(986),
                                  commDown(1019),
                                  ssfOtu(1024),
                                  tPmonSlmanflr15Min(1030),
                                  tPmonSlmafflr15Min(1031),
                                  tPmonSlmnhli15Min(1032),
                                  tPmonSlmfhli15Min(1033),
                                  tPmonSlmnhli1Day(1044),
                                  tPmonSlmfhli1Day(1045),
                                  tPmonSlmxfflrContinuous(1054),
                                  tPmonSlmxnflrContinuous(1055),
                                  tPmonSlmanflrContinuous(1056),
                                  tPmonSlmafflrContinuous(1057),
                                  gfpExm(1182),
                                  eCondUruO(1189),
                                  eCondUruP(1190),
                                  nuat(1377),
                                  fuat(1378),
                                  lagProtLos(1476),
                                  unitInit(1479),
                                  prbsLSS(1623),
                                  neCertValidityWarn(1807),
                                  neCertValidityExp(1808) }
            DESCRIPTION "Limited set of values."

        VARIATION       tnGenericWarningAlarmLogEntityType
            SYNTAX      INTEGER { all(1),
                                  tenGige(2),
                                  eqpt(3),
                                  gige(4),
                                  otu1(10),
                                  otu2(11),
                                  session(19),
                                  odu1(25),
                                  odu2(26),
                                  oduf(52),
                                  mep(59),
                                  odu2Tcm(60),
                                  odu2e(64),
                                  otuOdu1(67),
                                  otuOdu2(68),
                                  otuOdu2e(69),
                                  odu2Oduf(76),
                                  odu1Tcm(98),
                                  odu2eTcm(99),
                                  lag(102),
                                  otu2e(138),
                                  netif(190) }
            DESCRIPTION "Limited set of values."

--
-- Capabilities for TROPIC-EXPRSCALARS
-- Based on MIB version:  R15.0-LatestMIBs-221105
--

    SUPPORTS            TROPIC-EXPRSCALARS
        INCLUDES        { tnExprSysRadiusServersGroup,
                          tnExprSysRadiusGroup }

        VARIATION       tnSysRadiusServerIpAddress
            ACCESS      not-implemented
            DESCRIPTION "This object is not supported."

        VARIATION       tnSysRadiusServerIpPort
            DESCRIPTION "This object must always be included in an SNMP SET
                         PDU together with object tnSysRadiusServerRowStatus,
                         otherwise error 'inconsistent value' is returned."

        VARIATION       tnSysRadiusServerSharedSecret
            DESCRIPTION "This object must always be included in an SNMP SET
                         PDU together with object tnSysRadiusServerRowStatus,
                         otherwise error 'inconsistent value' is returned."

        VARIATION       tnSysRadiusServerInetAddressType
            DESCRIPTION "This object must always be included in an SNMP SET
                         PDU together with objects tnSysRadiusServerRowStatus,
                         and tnSysRadiusServerInetAddress, otherwise error
                         'inconsistent value' is returned."

        VARIATION       tnSysRadiusServerInetAddress
            DESCRIPTION "This object must always be included in an SNMP SET
                         PDU together with object tnSysRadiusServerRowStatus,
                         and tnSysRadiusServerInetAddressType, otherwise
                         error 'inconsistent value' is returned."

        VARIATION       tnSysRadiusServerRowStatus
            SYNTAX      INTEGER { active(1),
                                  createAndGo(4),
                                  destroy(6) }
            DESCRIPTION "Limited set of values.
                         The row status can only be set to createAnGo(4) for
                         row creation, or to destroy(6) for row deletion.
                         When reading, always value active(1) is read.

                         This object must always be included in an SNMP SET
                         PDU together with the following objects :
                          - tnSysRadiusServerIpPort
                          - tnSysRadiusServerSharedSecret
                          - tnSysRadiusServerInetAddress
                          - tnSysRadiusServerInetAddressType
                         otherwise error 'inconsistent value' is returned."

        VARIATION       tnSysRadiusServerType
            ACCESS      not-implemented
            DESCRIPTION "This object is not supported."

        VARIATION       tnSysRadiusServerDomain
            ACCESS      not-implemented
            DESCRIPTION "This object is not supported."

        VARIATION       tnSysRadiusTimeout
            SYNTAX      Unsigned32 (1..1000)
            DEFVAL      { 5 }
            DESCRIPTION "Limited value range."

        VARIATION       tnSysRadiusRetries
            SYNTAX      Unsigned32 (1..100)
            DEFVAL      { 3 }
            DESCRIPTION "Limited value range."

        VARIATION       tnSysAuthenOrder
            SYNTAX      INTEGER { local(1),
                                  radius(2),
                                  radiusThenLocal(3) }
            DEFVAL      { local }
            DESCRIPTION "Limited set of values."

        VARIATION       tnSysRadiusSecState
            ACCESS      not-implemented
            DESCRIPTION "This object is not supported."

--
-- Capabilities for TROPIC-PSD-MIB
-- Based on MIB version:  R15.0-LatestMIBs-221105
--

    SUPPORTS            TROPIC-PSD-MIB
        INCLUDES        { tnPsdSystemGroup,
                          tnPsdShelfGroup,
                          tnPsdSlotGroup,
                          tnPsdCardGroup,
                          tnPsdEquipmentEventGroup,
                          tnPsdEquipmentChangeGroup,
                          tnPsdSfpGroup,
                          tnPsdSfp2Group,
                          tnPsdDdmDataGroup,
                          tnPsdInterfaceConfigChangeNotifGroup,
                          tnPsdInterfaceStateChangeNotifGroup,
                          tnPsdInterfaceEventNotifGroup,
                          tnPsdLagGroup,
                          tnPsdAlsGroup,
                          tnPsdSnmpTrapDest2Group,
                          tnPsdSnmpConfigChangeNotifGroup,
                          tnPsdSnmpCreDelNotifGroup,
                          tnPsdDatabaseGroup,
                          tnPsdSoftwareGroup,
                          tnPsdSoftwareEventGroup,
                          tnPsdTimeGroup,
                          tnPsdTimeConfigChangeNotifGroup,
                          tnPsdIpGroup,
                          tnPsdIp2Group,
                          tnPsdIp3Group,
                          tnPsdIpConfigChangeNotifGroup,
                          tnPsdIpConfigChangeNotif2Group,
                          tnPsdIpConfigChangeNotif3Group,
                          tnPsdIpCreDelNotifGroup,
                          tnPsdIpCreDelNotif2Group,
                          tnPsdIpStateChangeNotifGroup,
                          tnPsdFaultGroup,
                          tnPsdFaultChangeNotifGroup,
                          tnPsdSysDiscoveryGroup,
                          tnPsdOtnGroup,
                          tnPsdOtn2Group,
                          tnPsdOtn3Group,
                          tnPsdOtnConfigChangeNotifGroup,
                          tnPsdOtnConfigChangeNotif2Group,
                          tnPsdOtnConfigChangeNotif3Group,
                          tnPsdCfmGroup,
                          tnPsdCfmConfigChangeNotifGroup,
                          tnPsdPmGroup,
                          tnPsdPmEthStatsGroup,
                          tnPsdPmEthStatsConfigChangeNotifGroup }

        VARIATION       tnPsdSystemMode
            SYNTAX      INTEGER {
                             factoryDefault(1),
                             otnNid1GbeClientOtu1NetworkMode(2),
                             otnNid1GbeClientOtu2NetworkMode(3),
                             otnNid10GbeClientOtu2NetworkMode(4),
                             otnNid10GbeClientOtu2eNetworkMode(5),
                             otnNidOtu1ClientOtu1NetworkMode(6),
                             otnNidOtu2ClientOtu2NetworkMode(7),
                             otnNidOtu2eClientOtu2eNetworkMode(8),
                             ethNid1GbEor10GbEClient10GbENetworkMode(9),
                             otnNid1GbEor10GbEClientOtu2OduFlexNetworkMode(10)
                        }
            DESCRIPTION "Limited set of values.

                         The system mode can be divided in 3 categories:
                         1) Default:
                         - factoryDefault(1)
                         2) OTN NID related system modes:
                         - otnNid1GbeClientOtu1NetworkMode(2)
                         - otnNid1GbeClientOtu2NetworkMode(3)
                         - otnNid10GbeClientOtu2NetworkMode(4)
                         - otnNid10GbeClientOtu2eNetworkMode(5)
                         - otnNidOtu1ClientOtu1NetworkMode(6)
                         - otnNidOtu2ClientOtu2NetworkMode(7)
                         - otnNidOtu2eClientOtu2eNetworkMode(8)
                         - otnNid1GbEor10GbEClientOtu2OduFlexNetworkMode(10)
                         3) Ethernet (ETH) NID related system modes:
                         - ethNid1GbEor10GbEClient10GbENetworkMode(9)

                         In case the value of this object equals
                         factoryDefault(1) the following applies:
                         - Only the following system mode value independent
                           interfaces are present: OAM&P, CRAFT and loopback.
                         - There are no specific ETH or OTN NID related objects
                           present.
                           For example this means that in factoryDefault(1)
                           mode there is no management
                           possible for objects related to ODUkT, ODUkNim,
                           ODUkT, ODUk APS or XC.
                         For an OTN NID system mode OTN related objects are
                         present.
                         Similarly for an ETH NID system mode Ethernet related
                         objects are present.
                         If the value of tnPsdPmTcaReportingMethod is standing
                         only the ethNid1GbEor10GbEClient10GbENetworkMode(9)
                         is accepted. Otherwise the SNMP SET request is
                         rejected."

        VARIATION       tnPsdShelfName
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnPsdShelfDescr
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnPsdShelfLocation
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnPsdShelfLatitude
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."


        VARIATION       tnPsdShelfLongitude
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnPsdShelfAltitude
            DESCRIPTION "The following ASCII characters from ITU Recommendation
                         T.50 are supported:
                         The G0 character set - values 0x20 - 0x7E, with the
                         following exceptions:
                         - value 0x22: double quotes
                         - value 0x27: single quote
                         - value 0x3f: question mark
                         - value 0x5c: backslash
                         The reason of these exceptions is that those
                         characters conflict with the Command Line Interface
                         (CLI)."

        VARIATION       tnPsdSfpProgrammedChannel
            SYNTAX      Unsigned32(0 | 12..60 | 10011..10060)
            DESCRIPTION "Limited set of values.
                         The value 0 means that no channel is assigned. No
                         checks are performed with respect to the capabilities
                         of the inserted SFP. The tnPsdSfpInfoTuningStatus
                         (TROPIC-PSD-MIB) can be used to retrieve the tuning
                         status."

        VARIATION       tnPsdSfpInfoTuningStatus
            DESCRIPTION "The value of this object is not subject to internal
                         caching of the SNMP agent. This means that the value
                         is always directly retrieved from the system.
                         The following meaning is assigned to the values:
                         - notApplicable(0): in case tuning is not supported,
                           tnPsdSfpInfoTunable has value false(2).
                         - tuningOK(1): the SFP is correctly tuned.
                         - tuningFreqProvisionedToZero(2): the provisioned
                           frequency is zero, this corresponds with value 0 of
                           tnPsdSfpProgrammedChannel (TROPIC-PSD-MIB). For
                           tunable SFPs the laser is turned off.
                         - tuningInProgress(3): the SFP is busy tuning.
                         - tuningFreqProvisionedOutOfRange(4): the provisioned
                           frequency is not supported by the inserted tunable
                           SFP. In this case the
                           tnGenericOpticsModuleMismatchRaisedNotif is sent
                           with mismatchSfpXfp(271) condition.
                         - tuningFailure(5): the tunable inserted SFP was
                           not able to tune within the required time. In this
                           case the tnGenericEqptPortRaisedNotif is sent with
                           eqptPort(470) condition."

        VARIATION       tnPsdAlsWaitToRestart
            SYNTAX      Unsigned32 (60..300)
            DESCRIPTION "Limited value range."

        VARIATION       tnPsdAlsTxTime
            SYNTAX      Unsigned32 (20..100)
            DESCRIPTION "Limited value range. Step size is 5."

        VARIATION       tnPsdSnmpTrapDestServerId
            DESCRIPTION "The following ASCII characters from ITU Recommendation
                         T.50 are supported: [A-Z][a-z][0-9]_."

        VARIATION       tnPsdSnmpTrapDestAddrType
            SYNTAX      INTEGER { unknown(0), ipv4(1), ipv6(2) }
            DESCRIPTION "Limited set of values.
                         Value unknown(0) is merely the read-only initial
                         value of this object, and can not be configured.
                         A change to the value of this object while the table
                         entry is active(1) leads to a partial restart of the
                         SNMP agent."

        VARIATION       tnPsdSnmpTrapDestAddr
            DESCRIPTION "A change to the value of this object while the table
                         entry is active(1) leads to a partial restart of the
                         SNMP agent.
                         An error is returned in the following cases:
                         - In case an all zero IPv4 or IPv6 address is given
                           for an active entry.
                         - In case tnPsdSnmpTrapDestDyingGasp is set the true
                           and a IPv6 address is given (only IPv4 destinations
                           are supported for the sending of a dying gasp SNMP
                           trap).
                         - The combination of the value of this object and
                           tnPsdSnmpTrapDestPort already occurs in an other
                           entry in this table. Similar destinations
                           (same IP and same UDP port are not allowed)."

        VARIATION       tnPsdSnmpTrapDestPort
            SYNTAX      Unsigned32(1..65535)
            DESCRIPTION "Limited set of values.
                         A change to the value of this object while the table
                         entry is active(1) leads to a partial restart of the
                         SNMP agent.
                         An error is returned when the combination of the value
                         of this object and tnPsdSnmpTrapDestAddr already
                         occurs in an other entry in this table. Similar
                         destinations (same IP and same UDP port are not
                         allowed)."

        VARIATION       tnPsdSnmpTrapDestCommunity
            DESCRIPTION "The following ASCII characters from ITU Recommendation
                         T.50 are supported: [A-Z][a-z][0-9]_.-
                         A change to the value of this object while the table
                         entry is active(1) leads to a partial restart of the
                         SNMP agent."

        VARIATION       tnPsdSnmpTrapDestDyingGasp
            DESCRIPTION "Only one active(1) entry in the table may have this
                         object value set to the value true.
                         For OTN NID system modes:
                         - The dying gasp trap PDUs can only be sent over the
                           ECC (Embedded Communication Channel) network
                           interfaces.
                         - The status (tnNetIfStatus) must be set to
                           enabled(1) in order for the dying gasp trap PDU to
                           be able to be sent.
                         For ETH NID system modes:
                         - The dying gasp trap PDUs are sent over the in-band
                           network interface NETWORK. In case LAG is
                           functionally disabled (see description
                           tnLagPortSubgroup) the dying gasp PDUs are sent
                           over NETWORK1. In case LAG is enabled the LACP
                           protocol determines over which port the dying gasp
                           is sent, either the NETWORK1 or NETWORK2 interface.
                         There is no check performed on the reachability or
                         correctness of the configured IP address of the trap
                         destination server.
                         In case the value of this object is set to true
                         and tnPsdSnmpTrapDestAddr contains an IPv6 address
                         an error is returned. Only IPv4 destinations are
                         supported for the sending of a dying gasp SNMP trap."

        VARIATION       tnPsdSnmpTrapDestRowStatus
            SYNTAX      INTEGER { active(1),
                                  notInService(2),
                                  createAndWait(5),
                                  destroy(6) }
            DESCRIPTION "Limited set of values.
                         A change of the value of this object to active(1) or
                         notInService(2) leads to a partial restart of the
                         SNMP agent."

        VARIATION       tnPsdSnmpTrapDestRowStatus
            DESCRIPTION "A maximum of ten trap destination server instances
                         can be created."

        VARIATION       tnPsdDatabaseBackupAndRestoreRemoteHostAddrType
            SYNTAX      INTEGER { unknown(0), ipv4(1), ipv6(2) }
            DESCRIPTION "Limited set of values.
                         Value unknown(0) is merely the read-only initial
                         value of this object and can not be configured."

        VARIATION       tnPsdSoftwareRemoteHostAddrType
            SYNTAX      INTEGER { unknown(0), ipv4(1), ipv6(2) }
            DESCRIPTION "Limited set of values.
                         Value unknown(0) is merely the read-only initial
                         value of this object and can not be configured."

        VARIATION       tnPsdShelfTime
            DESCRIPTION "Timezone offsets may not be set. The timezone hours
                         and minutes of the DateAndTime string must contain
                         the value zero, otherwise an error is returned."

        VARIATION       tnPsdNtpStatus
            ACCESS      not-implemented
            DESCRIPTION "This object is not supported."

        VARIATION       tnPsdNtpStratum
            ACCESS      not-implemented
            DESCRIPTION "This object is not supported."

        VARIATION       tnPsdNtpAccuracy
            ACCESS      not-implemented
            DESCRIPTION "This object is not supported."

        VARIATION       tnPsdNtpServerAddrType
            SYNTAX      INTEGER { unknown(0), ipv4(1), ipv6(2) }
            DESCRIPTION "Limited set of values."

        VARIATION       tnPsdNtpServerAddr
            DESCRIPTION "The NTP server instance can be functionally disabled
                         by setting the IP address to an all zero value.
                         An all zero value is accepted of type ipv4(1) with a
                         length of four octets or of type ipv6(2) with a
                         length of sixteen octets."

        VARIATION       tnPsdNtpServerSystemServer
            ACCESS      not-implemented
            DESCRIPTION "This object is not supported."

        VARIATION       tnPsdNtpServerReachable
            ACCESS      not-implemented
            DESCRIPTION "This object is not supported."

        VARIATION       tnPsdNtpServerReachabilityData
            ACCESS      not-implemented
            DESCRIPTION "This object is not supported."

        VARIATION       tnPsdNtpServerPollTime
            ACCESS      not-implemented
            DESCRIPTION "This object is not supported."

        VARIATION       tnPsdEnforceSrcIpV4ToLoopbackIpV4
            DESCRIPTION "When the value of this object is changed from
                         the value false to true, the IPv4 address of the
                         loopback interface in object
                         tnPsdManualIpv4AddressAddr must contain a value that
                         is unequal to an all zero value, otherwise an error
                         is returned."

        VARIATION       tnPsdEnforceSrcIpV6ToLoopbackIpV6
            DESCRIPTION "When the value of this object is changed from
                         the value false to true, the IPv6 address of the
                         loopback interface in object
                         tnPsdManualIpv6AddressAddr must contain a value that
                         is unequal to an all zero value, otherwise an error
                         is returned."

        VARIATION       tnPsdManualIpv4AddressAddr
            DESCRIPTION "Only the OAM&P and loopback interface support the
                         configuration of a manual IPv4 address.
                         Changing a non-zero IPv4 address of the loopback
                         interface will result in a warm restart of the system.
                         Changing the IPv4 address of the loopback interface to
                         an all zero value is forbidden unless the value was
                         already all zero (no change).
                         Changing the IPv4 address of the loopback interface
                         to an all zero value is only possible by setting the
                         tnPsdSystemMode to factoryDefault(1).
                         In this case the complete configuration that is
                         stored in the database is lost.
                         Changing the OAM&P interface to an all zero address
                         is allowed and means that no IP address is assigned.
                         An all zero or all ones subnet value in the IPv4
                         address is not permitted and results in an error code.
                         An IPv4 address of which the host part is set to all
                         ones (directed broadcast) is not permitted and results
                         in an error code.
                         The following addresses are not allowed and result
                         in an error code:
                         0.0.0.0/8          This host on this network
                         127.0.0.0/8        Loopback
                         169.254.0.0/16     Link Local
                         192.0.0.0/24       IETF Protocol Assignments
                         192.0.0.0/29       IPv4 Service Continuity Prefix
                         192.0.0.8/32       IPv4 dummy address
                         192.0.0.9/32       Port Control Protocol Anycast
                         192.0.0.170/32     NAT64/DNS64 Discovery
                         192.0.0.171/32     NAT64/DNS64 Discovery
                         192.0.2.0/24       Documentation (TEST-NET-1)
                         192.31.196.0/24    AS112-v4
                         192.52.193.0/24    AMT
                         192.88.99.0/24     Deprecated (6to4 Relay Anycast)
                         192.175.48.0/24    Direct Delegation AS112 Service
                         198.18.0.0/15      Benchmarking
                         198.51.100.0/24    Documentation (TEST-NET-2)
                         203.0.113.0/24     Documentation (TEST-NET-3)
                         224.0.0.0/4        IPv4 Multicast
                         240.0.0.0/4        Reserved
                         255.255.255.255/32 Limited Broadcast"

        VARIATION       tnPsdManualIpv6AddressAddr
            DESCRIPTION "Only the OAM&P and loopback interface support the
                         configuration of a manual IPv6 address.
                         Changing a non-zero IPv6 address of the loopback
                         interface will result in a warm restart of the system.
                         Changing the IPv6 address of the loopback interface to
                         an all zero value is forbidden unless the value was
                         already all zero (no change).
                         Changing the IPv6 address of the loopback interface
                         to an all zero value is only possible by setting the
                         tnPsdSystemMode to factoryDefault(1).
                         In this case all configuration stored in the
                         database is lost.
                         Changing the IPv6 address of the OAM&P interface to
                         an all zero address is allowed and this enables
                         Stateless Address Auto-configuration (SLAAC).
                         In case SLAAC is enabled, user configured static IPv6
                         routes are ignored for this interface.
                         In case the IPv6 address of the OAM&P interface is
                         changed to a non-zero IPv6 address, SLAAC will be
                         disabled.
                         An all zero or all ones subnet value in the IPv6
                         address is not permitted and results in an error code.
                         An IPv6 address of which the host part is set to all
                         ones (directed broadcast) is not permitted and results
                         in an error code.
                         The following addresses are not allowed and result
                         in an error code:
                         ::1/128           Loopback Address
                         ::/128            Unspecified Address
                         ::ffff:0:0/96     IPv4-mapped Address
                         64:ff9b::/96      IPv4-IPv6 Translat.
                         100::/64          Discard-Only Address Block
                         2001::/23         IETF Protocol Assignments
                         2001::/32         TEREDO
                         2001:1::1/128     Port Control Protocol Anycast
                         2001:2::/48       Benchmarking
                         2001:3::/32       AMT
                         2001:4:112::/48   AS112-v6
                         2001:5::/32       EID Space for LISP
                         2001:10::/28      Deprecated (previously ORCHID)
                         2001:20::/28      ORCHIDv2
                         2001:db8::/32     Documentation
                         2002::/16[2]      6to4
                         2620:4f:8000::/48 Direct Delegation AS112 Service
                         fe80::/10         Linked-Scoped Unicast
                         fec0::/10         Depreciated/Site-local scoped
                         ff::/8            IPv6 multicast."

        VARIATION       tnPsdActualIpAddressAddr
            DESCRIPTION "Only IP addresses of objects that have an ifIndex
                         identification are listed in this table.
                         Specifically the IP addresses of following
                         interfaces are listed in this table:
                         - loopback
                         - CRAFT
                         - OAM&P
                         IP addresses of In-Band Management interfaces (NETIF)
                         are not listed in this table."

        VARIATION       tnPsdDhcpClientV4Enabled
            DESCRIPTION "In case the value of this object is set to true
                         the IPv4 address is acquired by DHCP. This means that
                         the manual provisioned IPv4 address of object
                         tnPsdManualIpv4AddressAddr with corresponding ifIndex
                         of the tnPsdManualIpv4AddressTable will not be present
                         in the tnPsdActualIpAddressTable."

        VARIATION       tnPsdStaticRouteDestType
            DESCRIPTION "In this release routes for network interfaces
                         (tnNetIfTable, TROPIC-L1SERVICE-MIB) only support
                         ipv4(1).
                         In case tnPsdStaticRouteNetIfIndex contains a non-zero
                         value, the value of this object must be set to
                         ipv4(1) another value will cause an error to be
                         returned."

        VARIATION       tnPsdStaticRouteGatewayType
            DESCRIPTION "For OTN NID system modes:
                         otnNid1GbeClientOtu1NetworkMode(2)
                         otnNid1GbeClientOtu2NetworkMode(3)
                         otnNid10GbeClientOtu2NetworkMode(4)
                         otnNid10GbeClientOtu2eNetworkMode(5)
                         otnNidOtu1ClientOtu1NetworkMode(6)
                         otnNidOtu2ClientOtu2NetworkMode(7)
                         otnNidOtu2eClientOtu2eNetworkMode(8)
                         otnNid1GbEor10GbEClientOtu2OduFlexNetworkMode(10)
                         - In case tnPsdStaticRouteNetIfIndex contains a
                           non-zero value, the value of this object must be set
                           to unknown(0), indicating that the gateway IP
                           address is not used in this route.
                         For ETH NID system mode
                         ethNid1GbEor10GbEClient10GbENetworkMode(9):
                         - In case tnPsdStaticRouteNetIfIndex contains a
                           non-zero value, the value of this object can only be
                           set to ipv4(1)."

        VARIATION       tnPsdStaticRouteGateway
            DESCRIPTION "For OTN NID system modes:
                         otnNid1GbeClientOtu1NetworkMode(2)
                         otnNid1GbeClientOtu2NetworkMode(3)
                         otnNid10GbeClientOtu2NetworkMode(4)
                         otnNid10GbeClientOtu2eNetworkMode(5)
                         otnNidOtu1ClientOtu1NetworkMode(6)
                         otnNidOtu2ClientOtu2NetworkMode(7)
                         otnNidOtu2eClientOtu2eNetworkMode(8)
                         otnNid1GbEor10GbEClientOtu2OduFlexNetworkMode(10)
                         - In case tnPsdStaticRouteNetIfIndex contains a
                           non-zero value, the value of this object must be set
                           to no value, with a length of zero octets,
                           indicating that the gateway IP address is not used
                           in this route.
                         For ETH NID system mode
                         ethNid1GbEor10GbEClient10GbENetworkMode(9):
                         - In case tnPsdStaticRouteNetIfIndex contains a
                           non-zero value, the value of this object must
                           contain a valid IPv4 address value, IPv6 addresses
                           are not allowed."

        VARIATION       tnPsdStaticRouteIfIndex
            DESCRIPTION "The value of this object must reference an interface
                         which tnIfType equals dcn(40) or use the value zero
                         to indicate that no interface ifIndex (ifTable,
                         IF-MIB) is referenced for this route.
                         In case tnPsdStaticRouteNetIfIndex contains a non zero
                         value the value of this object must contain the value
                         zero.
                         In this release only the ifIndex value of the OAM&P
                         port is supported. In case the CRAFT port or loopback
                         port is referenced an error is returned."

        VARIATION       tnPsdStaticRouteNetIfIndex
            DESCRIPTION "The value of this object must reference an ECC
                         (Embedded Communication Channel) network interface or
                         an in-band Ethernet management channel network
                         interface or use the value 0 in order to indicate
                         no network interface is referenced for this route.
                         In case the value of this object is unequal to zero,
                         an existing network interface tnNetIfIndex
                         (tnNetIfTable, TROPIC-L1SERVICE-MIB) must be
                         referenced otherwise an error is returned.
                         In case tnPsdStaticRouteIfIndex contains a non zero
                         value the value of this object must contain the value
                         zero.
                         The tnNetIfStatus of the referenced network interface
                         must be enabled(1). In case it is disabled(2) an error
                         is returned."

        VARIATION       tnPsdStaticRouteRowStatus
            SYNTAX      INTEGER { active(1),
                                  notInService(2),
                                  createAndWait(5),
                                  destroy(6) }
            DESCRIPTION "Limited set of values.
                         A maximum of two hundred static route instances can be
                         created."

        VARIATION       tnPsdNetIfIpAddrType
            SYNTAX      INTEGER { ipv4(1) }
            DESCRIPTION "Only in ethNid1GbEor10GbEClient10GbENetworkMode(9)
                         system mode this object is allowed to be configured.
                         The only supported value is ipv4(1).
                         For all other system modes this object is read-only
                         and a SNMP-SET command is rejected."

        VARIATION       tnPsdNetIfIpAddr
            DESCRIPTION "Only in ethNid1GbEor10GbEClient10GbENetworkMode(9)
                         system mode this object is allowed to be configured.
                         Only IPv4 address values are allowed.
                         In this system mode it is mandatory that a valid IP
                         address value (see rules of object
                         tnPsdManualIpv4AddressAddr) is configured for this
                         object, before setting tnNetIfStatus
                         (TROPIC-L1SERVICE-MIB) to the the value enable(1).
                         For all other system modes this object is read-only
                         and a SNMP-SET command is rejected."

        VARIATION       tnPsdNetIfIpPrefixLen
            SYNTAX      Unsigned32 (1..32)
            DESCRIPTION "Only in ethNid1GbEor10GbEClient10GbENetworkMode(9)
                         system mode this object is allowed to be configured.
                         Because this object applies to IPv4 addresses only,
                         its value is limited to IPv4 range 1 - 32.
                         For all other system modes this object is read-only
                         and a SNMP-SET command is rejected."

        VARIATION       tnPsdNetIfMonitoring
            DESCRIPTION "In case the value of this object is set to enabled(1)
                         ICMP ping messages are sent to the remote peer.
                         In case the remote peer becomes unreachable the value
                         of tnPsdNetIfOperStatus will be set to down(2).
                         In case the value of this object is set to disabled(2)
                         no ICMP ping messages are sent to the remote peer and
                         the value of tnPsdNetIfOperStatus will be fixed set
                         to up(1).
                         Only in ethNid1GbEor10GbEClient10GbENetworkMode(9)
                         system mode this object is allowed to be configured
                         and set to enabled(1).
                         For all other system modes this object has the fixed
                         value disabled(2)."

        VARIATION       tnPsdNetIfRemoteIpAddrType
            SYNTAX      INTEGER { ipv4(1) }
            DESCRIPTION "Fixed value."

        VARIATION       tnPsdNetIfIp6AddrType
            SYNTAX      INTEGER { ipv6(2) }
            DESCRIPTION "Only in ethNid1GbEor10GbEClient10GbENetworkMode(9)
                         system mode this object is allowed to be configured.
                         The only supported value is ipv6(2).
                         For all other system modes this object is read-only
                         and a SNMP-SET command is rejected."

        VARIATION       tnPsdNetIfIp6Addr
            DESCRIPTION "Only in ethNid1GbEor10GbEClient10GbENetworkMode(9)
                         system mode this object is allowed to be configured.
                         Only IPv6 address values are allowed.
                         In this system mode it is mandatory that a valid IP
                         address value (see rules of object
                         tnPsdManualIpv6AddressAddr) is configured for this
                         object, before setting tnNetIfStatus
                         (TROPIC-L1SERVICE-MIB) to the the value enable(1).
                         For all other system modes this object is read-only
                         and a SNMP-SET command is rejected."

        VARIATION       tnPsdNetIfIp6PrefixLen
            DESCRIPTION "Only in ethNid1GbEor10GbEClient10GbENetworkMode(9)
                         system mode this object is allowed to be configured.
                         For all other system modes this object is read-only
                         and a SNMP-SET command is rejected."

        VARIATION       tnPsdNetIfRemoteIp6AddrType
            SYNTAX      INTEGER { ipv6(2) }
            DESCRIPTION "Fixed value."

        VARIATION       tnPsdNetIfMonitoring6
            DESCRIPTION "In case the value of this object is set to enabled(1)
                         ICMP6 ping messages are sent to the remote peer.
                         In case the remote peer becomes unreachable the value
                         of tnPsdNetIfOperStatus will be set to down(2).
                         In case the value of this object is set to disabled(2)
                         no ICMP6 ping messages are sent to the remote peer and
                         the value of tnPsdNetIfOperStatus will be fixed set
                         to up(1).
                         Only in ethNid1GbEor10GbEClient10GbENetworkMode(9)
                         system mode this object is allowed to be configured
                         and set to enabled(1).
                         For all other system modes this object has the fixed
                         value disabled(2)."

        VARIATION       tnPsdNetIfEthFacilityTypeOfOperation
            DESCRIPTION "Only in the ethNid1GbEor10GbEClient10GbENetworkMode(9)
                         system mode it is allowed to create
                         or remove entries in the tnPsdNetIfEthFacilityTable
                         Operation empty(1) fails in case the corresponding
                         tnNetIfIndex is in use by a static IP route and
                         when tnNetIfStatus is equal to enabled(1).
                         A maximum of 1 entry is allowed."

        VARIATION       tnPsdNetIfEthFacilityPriorityEgress
            SYNTAX      Unsigned32( 7 )
            DESCRIPTION "Fixed value 7."

        VARIATION       tnPsdNetIfEthFacilityDropEligibleEgress
            SYNTAX      INTEGER{ false(2) }
            DESCRIPTION "Fixed value false(2)."

        VARIATION       tnPsdAsapName
            DESCRIPTION "The value of this object is fixed to an empty string.
                         In case the value is set to another value an error is
                         returned."

        VARIATION       tnPsdAsapFaultProfileCondition
            SYNTAX      INTEGER { frcdWkSwBk(31),
                                  frcdWkSwPr(32),
                                  lof(41),
                                  los(43),
                                  manWkSwBk(49),
                                  manWkSwPr(50),
                                  tim(81),
                                  wkSwPr(84),
                                  wkSwBk(109),
                                  man(112),
                                  lockoutOfPr(120),
                                  intrusion(121),
                                  usAls(134),
                                  gfpLof(140),
                                  plm(151),
                                  dwLom(197),
                                  lck(221),
                                  oci(222),
                                  ssf(223),
                                  bdi(224),
                                  deg(228),
                                  lanLfi(230),
                                  lanRfi(231),
                                  boardEqpt(237),
                                  timOdu(242),
                                  bdiOdu(243),
                                  ssfOdu(244),
                                  ntpOoSync(265),
                                  unknownSfpXfp(270),
                                  mismatchSfpXfp(271),
                                  degOtu(363),
                                  tBbeOtu15Min(365),
                                  tEsOtu15Min(373),
                                  tFecc15Min(380),
                                  tSesOtu15Min(392),
                                  tUasOtu15Min(398),
                                  tBbeOdu15Min(401),
                                  tEsOdu15Min(402),
                                  tSesOdu15Min(403),
                                  tUasOdu15Min(404),
                                  tBbeOtu1Day(409),
                                  tEsOtu1Day(417),
                                  tFecc1Day(424),
                                  tSesOtu1Day(436),
                                  tUasOtu1Day(442),
                                  tBbeOdu1Day(445),
                                  tEsOdu1Day(446),
                                  tSesOdu1Day(447),
                                  tUasOdu1Day(448),
                                  intTempHigh(458),
                                  replUnitMissMOD(467),
                                  eqptPort(470),
                                  uruS(574),
                                  tFebbeOtu15Min(585),
                                  tFeesOtu15Min(586),
                                  tFesesOtu15Min(587),
                                  tFeuasOtu15Min(588),
                                  tFebbeOtu1Day(589),
                                  tFeesOtu1Day(590),
                                  tFesesOtu1Day(591),
                                  tFeuasOtu1Day(592),
                                  tFebbeOdu15Min(593),
                                  tFeesOdu15Min(594),
                                  tFesesOdu15Min(595),
                                  tFeuasOdu15Min(596),
                                  tFebbeOdu1Day(597),
                                  tFeesOdu1Day(598),
                                  tFesesOdu1Day(599),
                                  tFeuasOdu1Day(600),
                                  msim(602),
                                  wtr(617),
                                  ssfTcm(619),
                                  lckTcm(620),
                                  ociTcm(621),
                                  degTcm(622),
                                  bdiTcm(623),
                                  timTcm(624),
                                  ltcTcm(625),
                                  tBbeTcm15Min(628),
                                  tEsTcm15Min(629),
                                  tSesTcm15Min(630),
                                  tUasTcm15Min(631),
                                  tFebbeTcm15Min(633),
                                  tFeesTcm15Min(634),
                                  tFesesTcm15Min(635),
                                  tFeuasTcm15Min(636),
                                  tBbeTcm1Day(638),
                                  tEsTcm1Day(639),
                                  tSesTcm1Day(640),
                                  tUasTcm1Day(641),
                                  tFebbeTcm1Day(643),
                                  tFeesTcm1Day(644),
                                  tFesesTcm1Day(645),
                                  tFeuasTcm1Day(646),
                                  lofLom(691),
                                  mepLoc(708),
                                  mepMmg(709),
                                  rdi(712),
                                  egressSSF(736),
                                  csf(739),
                                  lagLos(742),
                                  unL(744),
                                  unM(745),
                                  unP(746),
                                  unPr(747),
                                  csfGfp(889),
                                  gfpUpm(890),
                                  tPmonPortIfInPackets15Min(917),
                                  tPmonPortIfOutPackets15Min(918),
                                  tPmonPortIfInOctets15Min(919),
                                  tPmonPortIfOutOctets15Min(920),
                                  tPmonPortIfInDiscards15Min(921),
                                  tPmonPortIfInErrors15Min(923),
                                  tPmonDmaBfd15Min(943),
                                  tPmonDmxBfd15Min(944),
                                  tPmonDmanFdv15Min(945),
                                  tPmonDmxnFdv15Min(946),
                                  tPmonDmafFdv15Min(947),
                                  tPmonDmxfFdv15Min(948),
                                  tPmonPortIfInPackets1Day(951),
                                  tPmonPortIfOutPackets1Day(952),
                                  tPmonPortIfInOctets1Day(953),
                                  tPmonPortIfOutOctets1Day(954),
                                  tPmonPortIfInDiscards1Day(955),
                                  tPmonPortIfInErrors1Day(957),
                                  tPmonSlmanFlr1Day(977),
                                  tPmonSlmafFlr1Day(979),
                                  tPmonDmaBfd1Day(981),
                                  tPmonDmxBfd1Day(982),
                                  tPmonDmanFdv1Day(983),
                                  tPmonDmxnFdv1Day(984),
                                  tPmonDmafFdv1Day(985),
                                  tPmonDmxfFdv1Day(986),
                                  commDown(1019),
                                  ssfOtu(1024),
                                  tPmonSlmanflr15Min(1030),
                                  tPmonSlmafflr15Min(1031),
                                  tPmonSlmnhli15Min(1032),
                                  tPmonSlmfhli15Min(1033),
                                  tPmonSlmnhli1Day(1044),
                                  tPmonSlmfhli1Day(1045),
                                  tPmonSlmxfflrContinuous(1054),
                                  tPmonSlmxnflrContinuous(1055),
                                  tPmonSlmanflrContinuous(1056),
                                  tPmonSlmafflrContinuous(1057),
                                  gfpExm(1182),
                                  eCondUruO(1189),
                                  eCondUruP(1190),
                                  nuat(1377),
                                  fuat(1378),
                                  lagProtLos(1476),
                                  unitInit(1479),
                                  prbsLSS(1623),
                                  neCertValidityWarn(1807),
                                  neCertValidityExp(1808) }
            DESCRIPTION "Limited set of values."

        VARIATION       tnPsdFaultAlarmRaiseTime
            SYNTAX      Unsigned32 (0..600)
            DESCRIPTION "Limited value range.
                         Only multiples of 5 deciseconds (500ms) are allowed.
                         When a value is given that is not a multiple of 5
                         deciseconds an error is returned."

        VARIATION       tnPsdFaultAlarmClearTime
            SYNTAX      Unsigned32 (0..600)
            DESCRIPTION "Limited value range.
                         Only multiples of 5 deciseconds (500ms) are allowed.
                         When a value is given that is not a multiple of 5
                         deciseconds an error is returned."

        VARIATION       tnPsdSysDiscoveryServerAddrType
            SYNTAX      INTEGER { unknown(0), ipv4(1), ipv6(2) }
            DESCRIPTION "Limited set of values.
                         Value unknown(0) is merely the read-only initial
                         value of this object and can not be configured."

        VARIATION       tnPsdOdukTtpDmReflection
            DESCRIPTION "Enabling delay measurement reflection on ODUkP (path)
                         termination points is only supported in the following
                         system modes:
                         - otnNid1GbeClientOtu1NetworkMode(2)
                         - otnNid1GbeClientOtu2NetworkMode(3)
                         - otnNid10GbeClientOtu2NetworkMode(4)
                         - otnNid10GbeClientOtu2eNetworkMode(5)
                         - otnNid1GbEor10GbEClientOtu2OduFlexNetworkMode(10)"

        VARIATION       tnPsdOdukTtpDmSessionType
            SYNTAX      INTEGER { onDemand(1) }
            DESCRIPTION "Limited set of values."

        VARIATION       tnPsdOdukTtpDmStart
            DESCRIPTION "Starting a delay measurement on ODUkP (path)
                         termination point is only supported for the
                         following system modes:
                         - otnNid1GbeClientOtu1NetworkMode(2)
                         - otnNid1GbeClientOtu2NetworkMode(3)
                         - otnNid10GbeClientOtu2NetworkMode(4)
                         - otnNid10GbeClientOtu2eNetworkMode(5)
                         - otnNid1GbEor10GbEClientOtu2OduFlexNetworkMode(10)"

        VARIATION       tnPsdOdukTtpPrbsGenerator
            DESCRIPTION "This object is only present in the following system
                         modes:
                         - otnNid1GbeClientOtu1NetworkMode(2)
                         - otnNid1GbeClientOtu2NetworkMode(3)
                         - otnNid10GbeClientOtu2NetworkMode(4)
                         - otnNid10GbeClientOtu2eNetworkMode(5)."

        VARIATION       tnPsdOdukTtpPrbsGeneratorInvert
            DESCRIPTION "This object is only present in the following system
                         modes:
                         - otnNid1GbeClientOtu1NetworkMode(2)
                         - otnNid1GbeClientOtu2NetworkMode(3)
                         - otnNid10GbeClientOtu2NetworkMode(4)
                         - otnNid10GbeClientOtu2eNetworkMode(5)."

        VARIATION       tnPsdOdukTtpPrbsMonitor
            DESCRIPTION "This object is only present in the following system
                         modes:
                         - otnNid1GbeClientOtu1NetworkMode(2)
                         - otnNid1GbeClientOtu2NetworkMode(3)
                         - otnNid10GbeClientOtu2NetworkMode(4)
                         - otnNid10GbeClientOtu2eNetworkMode(5)."

        VARIATION       tnPsdOdukTtpPrbsMonitorInvert
            DESCRIPTION "This object is only present in the following system
                         modes:
                         - otnNid1GbeClientOtu1NetworkMode(2)
                         - otnNid1GbeClientOtu2NetworkMode(3)
                         - otnNid10GbeClientOtu2NetworkMode(4)
                         - otnNid10GbeClientOtu2eNetworkMode(5)."

        VARIATION       tnPsdOdukTtpPrbsErrorPropagation
            DESCRIPTION "This object is only present in the following system
                         modes:
                         - otnNid1GbeClientOtu1NetworkMode(2)
                         - otnNid1GbeClientOtu2NetworkMode(3)
                         - otnNid10GbeClientOtu2NetworkMode(4)
                         - otnNid10GbeClientOtu2eNetworkMode(5)."

        VARIATION       tnPsdCfmTransportIdentifier
            SYNTAX      Unsigned32 (1536..65535)
            DESCRIPTION "Limited set of values, range 0x600 - 0xffff.
                         This object is only present in the following system
                         modes:
                         - otnNid1GbeClientOtu1NetworkMode(2)
                         - otnNid1GbeClientOtu2NetworkMode(3)
                         - otnNid10GbeClientOtu2NetworkMode(4)
                         - ethNid1GbEor10GbEClient10GbENetworkMode(9)
                         - otnNid1GbEor10GbEClientOtu2OduFlexNetworkMode(10)."

        VARIATION       tnPsdOamEthCfmPingCtlPriority
            DESCRIPTION "The value of this object can only be set upon creation
                         of an entry in the tnOamPingCtlTable using
                         tnOamPingCtlRowStatus (TN-OAM-TEST-MIB).
                         The priority values of this object can be mapped to
                         the following forwarding classes and correspond with
                         the values of TEXTUAL-CONVENTION TFCType (TN-TC-MIB):
                         - be (0)
                         - l2 (1)
                         - af (2)
                         - l1 (3)
                         - h2 (4)
                         - ef (5)
                         - h1 (6)
                         - nc (7)"

        VARIATION       tnPsdOamEthCfmPingCtlAvailFlrThreshold
            SYNTAX      Unsigned32 (1..100)
            DESCRIPTION "Limited range of values.
                         Only applicable to SLM sessions.
                         For other session types the value of this object
                         is ignored.
                         The value of this object can only be set upon creation
                         of an entry in the tnOamPingCtlTable using
                         tnOamPingCtlRowStatus (TN-OAM-TEST-MIB)."

        VARIATION       tnPsdOamEthCfmPingCtlAvailFlrNumOfIntervals
            DESCRIPTION "Only applicable to SLM sessions.
                         The delta-t for both 15 minute and 1 day intervals
                         is fixed to 60 seconds, see
                         (tnPsdOamEthCfmPingCtlAvailFlrInterval15Min,
                         tnPsdOamEthCfmPingCtlAvailFlrInterval1Day).
                         For other sessions types the value of this object
                         is ignored.
                         The value of this object can only be set upon creation
                         of an entry in the tnOamPingCtlTable using
                         tnOamPingCtlRowStatus (TN-OAM-TEST-MIB)."

        VARIATION       tnPsdOamEthCfmPingCtlAvailFlrInterval15Min
            SYNTAX      Unsigned32 (60)
            DESCRIPTION "Fixed value. Only applicable to SLM sessions."

        VARIATION       tnPsdOamEthCfmPingCtlAvailFlrInterval1Day
            SYNTAX      Unsigned32 (60)
            DESCRIPTION "Fixed value. Only applicable to SLM sessions."

        VARIATION       tnPsdDot1agCfmMepDmTWTestStatus
            DESCRIPTION "In order to start an on-demand DM test it is mandatory
                         that the value this object is set to enabled(1) and
                         that this object is be present in the varbinds of the
                         SNMP SET request that initiates the start of the
                         on-demand measurement, see
                         tnDot1agCfmMepTWDTMacAddress (TN-IEEE8021-CFM-MIB)
                         for details.
                         An on-demand DM session can be stopped by setting
                         the value of this object to disabled(2).
                         In case the test has ended regardless of the result,
                         the system sets the value of this object to
                         disabled(2). A trap notification is only sent in case
                         the test successfully completed."

        VARIATION       tnPsdDot1agCfmMepSlmTWInterval
            SYNTAX      INTEGER { interval10ms(2),
                                  interval100ms(3),
                                  interval1s(4),
                                  interval10s(5) }
            DESCRIPTION "Limited set of values.
                         In order to set the value this object must be present
                         in the varbinds of the SNMP SET request that
                         initiates the start of the on-demand measurement, see
                         tnDot1agCfmMepSlmTWMacAddress (TN-IEEE8021-CFM-MIB)
                         for details."

        VARIATION       tnPsdSoamEnable
            DESCRIPTION "For the following system modes the system creates
                         an entry in this table for the ifIndex value of
                         the logical CLIENT interface with supported values:
                         - ethNid1GbEor10GbEClient10GbENetworkMode: true(1)
                         - otnNid1GbeClientOtu1NetworkMode: true(1), false(2)
                         - otnNid1GbeClientOtu2NetworkMode: true(1), false(2)
                         - otnNid10GbeClientOtu2NetworkMode: true(1), false(2)
                         - otnNid1GbEor10GbEClientOtu2OduFlexNetworkMode: true(1), false(2)
                         The following tables may be affected, see capability
                         description for more details:
                         - dot1agCfmMaMepListTable (IEEE8021-CFM-MIB)
                         - dot1agCfmMepTable (IEEE8021-CFM-MIB)
                         - tnDot1agCfmMepTable (TN-IEEE8021-CFM-MIB)
                         - dot1agCfmMepDbTable (IEEE8021-CFM-MIB)
                         - tnOamPingCtlTable (TN-OAM-TEST-MIB)
                         - tnOamSaaCtlTable (TN-OAM-TEST-MIB)
                         - tnEthCfmTWSlmStatsTable (TN-PMON-MIB)
                         - tnEthCfmTWDmStatsTable (TN-PMON-MIB)."

        VARIATION       tnPsdPmTcaReportingMethod
            DESCRIPTION "transient(1) corresponds with stateless and
                         standing(2) corresponds with stateful TCA reporting.
                         The value standing(2) only applies to Ethernet port
                         TCAs and SOAM session TCAs (SLM, DM).
                         OTN TCAs are always handled via the transient(1)
                         method.
                         The value standing(2) is supported for the following
                         system modes:
                         - otnNid1GbeClientOtu1NetworkMode(2)
                         - otnNid1GbeClientOtu2NetworkMode(3)
                         - otnNid10GbeClientOtu2NetworkMode(4)
                         - otnNid10GbeClientOtu2eNetworkMode(5)
                         - ethNid1GbEor10GbEClient10GbENetworkMode(9)
                         - otnNid1GbEor10GbEClientOtu2OduFlexNetworkMode(10)
                         When changing the tnPsdSystemMode from
                         factoryDefault(1) to another system mode, the value
                         of tnPsdPmTcaReportingMethod will be evaluated.
                         In case the tnPsdPmTcaReportingMethod is not
                         supported for the newly chosen tnPsdSystemMode
                         the request to change the tnPsdSystemMode will be
                         rejected and an error will be returned.
                         In ethNid1GbEor10GbEClient10GbENetworkMode(9) the
                         value of this object cannot be modified. The user
                         is forced to first go to factoryDefault(1) mode
                         thereby loosing all settings, and then select the
                         desired value for this object.
                         For the following system modes the value of this
                         object can be modified, with the restriction that
                         all instances of tnPortEtherCollectStats
                         (TN-PORT-MIB) and tnPsdSoamEnable (TROPIC-PSD-MIB)
                         must have their value set to false,
                         i.e. Ethernet port performance monitoring and SOAM are
                         both disabled, otherwise the request is rejected:
                         - otnNid1GbeClientOtu1NetworkMode(2)
                         - otnNid1GbeClientOtu2NetworkMode(3)
                         - otnNid10GbeClientOtu2NetworkMode(4)
                         - otnNid10GbeClientOtu2eNetworkMode(5)
                         - otnNid1GbEor10GbEClientOtu2OduFlexNetworkMode(10)
                         System mode otnNid10GbeClientOtu2eNetworkMode(5) does
                         not have an entry in the tnPsdSoamTable therefore
                         for this mode only tnPortEtherCollectStats must be set
                         to disabled in order to change the value of this
                         object."

    ::= { tn1830PsdCapability 1 }

END
