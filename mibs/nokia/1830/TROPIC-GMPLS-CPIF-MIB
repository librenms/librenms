TROPIC-GMPLS-CPIF-MIB DEFINITIONS ::= BEGIN

-- (c) Copyright 2023 Nokia Networks.  All rights reserved.
-- This software is the confidential and proprietary property of
-- Nokia and may only be used in accordance with the terms of the
-- license agreement provided with this software.

IMPORTS
      MODULE-IDENTITY, OBJECT-TYPE,
      IpAddress,
      Unsigned32, Integer32                   FROM SNMPv2-SMI
      MODULE-COMPLIANCE, OBJECT-GROUP         FROM SNMPv2-CONF
      RowStatus, DisplayString,
      TruthValue                              FROM SNMPv2-TC
      InetAddressType, InetAddress,
      InetAddressIPv4                         FROM INET-ADDRESS-MIB
      tnGmplsMIBModules, tnGmplsObjs          FROM TROPIC-GLOBAL-REG;

  tnGmplsCpifMibModule MODULE-IDENTITY
      LAST-UPDATED    "201802231200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION     "GMPLS Control Plane Interface MIB types."

      REVISION        "201802231200Z"
      DESCRIPTION     "Updated the contact info."

      REVISION        "201611161200Z"
      DESCRIPTION     "Updated the contact info."

      REVISION        "201306271200Z"
      DESCRIPTION     "Initial version."

      ::= { tnGmplsMIBModules 1 }

---------------------------------------------------------------------------
-- Top level components of this MIB
---------------------------------------------------------------------------
  tnGmplsCpifMIB            OBJECT IDENTIFIER ::= { tnGmplsObjs 1 }

-- tables, scalars
  tnGmplsCpifObjs             OBJECT IDENTIFIER ::= { tnGmplsCpifMIB 1 }

-- traps
--  tnGmplsCpifNotifications  OBJECT IDENTIFIER ::= { tnGmplsCpifMIB 2 }
--  tnGmplsCpifNotifyPrefix   OBJECT IDENTIFIER ::= { tnGmplsCpifNotifications 0 }

  tnGmplsCpifConf           OBJECT IDENTIFIER ::= { tnGmplsCpifMIB 3 }
  tnGmplsCpifGroups         OBJECT IDENTIFIER ::= { tnGmplsCpifConf 1 }
  tnGmplsCpifCompliances    OBJECT IDENTIFIER ::= { tnGmplsCpifConf 2 }

--------------------------------------------------------------------------------
-- GMPLS CPIF Scalar
--------------------------------------------------------------------------------
    tnGmplsCpifAttributeTotal OBJECT-TYPE
        SYNTAX         Integer32
        MAX-ACCESS     read-only
        STATUS         current
        DESCRIPTION    "Total number of attributes in this MIB file."
        ::= { tnGmplsCpifObjs 1 }

---------------------------------------------------------------------------
-- Control Plane Neighbour Table
---------------------------------------------------------------------------
    tnGmplsCPNbrTable OBJECT-TYPE
        SYNTAX         SEQUENCE OF TnGmplsCPNbrEntry
        MAX-ACCESS     not-accessible
        STATUS         current
        DESCRIPTION    "The Control Plane Neighbour Table"
        ::= { tnGmplsCpifObjs 2 }

    tnGmplsCPNbrEntry OBJECT-TYPE
        SYNTAX         TnGmplsCPNbrEntry
        MAX-ACCESS     not-accessible
        STATUS         current
        DESCRIPTION    "An entry in this table represents an GMPLS LSP."
        REFERENCE      "?"
        INDEX          { tnGmplsCPNbrIfId }
        ::= { tnGmplsCPNbrTable 1 }

    TnGmplsCPNbrEntry ::= SEQUENCE {
        tnGmplsCPNbrIfId                  Unsigned32,
        tnGmplsCPNbrIfName                DisplayString,
        tnGmplsCPNbrAddrType              InetAddressType,
        tnGmplsCPNbrRemoteRouterAddr      InetAddress,
        tnGmplsCPNbrEncaps                INTEGER,
        tnGmplsCPNbrRemoteTEP             InetAddress,
        tnGmplsCPNbrOspfArea              IpAddress,
        tnGmplsCPNbrAdminStatus           INTEGER,
        tnGmplsCPNbrRemoteCPNodeId        InetAddressIPv4,
        tnGmplsCPNbrRowStatus             RowStatus
    }

    tnGmplsCPNbrIfId OBJECT-TYPE
        SYNTAX         Unsigned32
        MAX-ACCESS     not-accessible
        STATUS         current
        DESCRIPTION    "Interface index, uniquely identifies this row.
                        This Id maps to the GMPLS CLI interface index of
                        the CPNbr."
        ::= { tnGmplsCPNbrEntry 1 }

    tnGmplsCPNbrIfName OBJECT-TYPE
        SYNTAX         DisplayString
        MAX-ACCESS     read-create
        STATUS         current
        DESCRIPTION    "User label."
        ::= { tnGmplsCPNbrEntry 2 }

    tnGmplsCPNbrAddrType OBJECT-TYPE
        SYNTAX         InetAddressType
        MAX-ACCESS     read-create
        STATUS         current
        DESCRIPTION    "IPv4 only"
        ::= { tnGmplsCPNbrEntry 3 }

    tnGmplsCPNbrRemoteRouterAddr OBJECT-TYPE
        SYNTAX         InetAddress
        MAX-ACCESS     read-create
        STATUS         current
        DESCRIPTION    "Neighbor node id"
        ::= { tnGmplsCPNbrEntry 4 }

    tnGmplsCPNbrEncaps OBJECT-TYPE
        SYNTAX         INTEGER {
                         none(1),
                         ipinip(2),
                         gre(3)
                       }
        MAX-ACCESS     read-create
        STATUS         current
        DESCRIPTION    "Protocol encapsulation."
        DEFVAL         { none }
        ::= { tnGmplsCPNbrEntry 5 }

    tnGmplsCPNbrRemoteTEP OBJECT-TYPE
        SYNTAX         InetAddress
        MAX-ACCESS     read-create
        STATUS         current
        DESCRIPTION    "Remote tunnel end point for out of band (LAN i/f
                        address)."
        ::= { tnGmplsCPNbrEntry 6 }

    tnGmplsCPNbrOspfArea OBJECT-TYPE
        SYNTAX         IpAddress
        MAX-ACCESS     read-create
        STATUS         current
        DESCRIPTION    "Area Id of the DCN to this neighbour."
        ::= { tnGmplsCPNbrEntry 7 }

    tnGmplsCPNbrAdminStatus OBJECT-TYPE
        SYNTAX         INTEGER {
                         down(1),
                         up(2)
                       }
        MAX-ACCESS     read-create
        STATUS         current
        DESCRIPTION    "Administrative state."
        ::= { tnGmplsCPNbrEntry 8 }

    tnGmplsCPNbrRemoteCPNodeId OBJECT-TYPE
        SYNTAX         InetAddressIPv4
        MAX-ACCESS     read-create
        STATUS         current
        DESCRIPTION    "Remote Control Plane Node Id."
        ::= { tnGmplsCPNbrEntry 9 }

    tnGmplsCPNbrRowStatus OBJECT-TYPE
        SYNTAX         RowStatus
        MAX-ACCESS     read-create
        STATUS         current
        DESCRIPTION    "This variable is used to create, modify, and/or
                        delete a row in this table."
        ::= { tnGmplsCPNbrEntry 10 }

---------------------------------------------------------------------------
-- Resource Reservation Protocol Interface Table
---------------------------------------------------------------------------
    tnGmplsRsvpIfTable OBJECT-TYPE
        SYNTAX         SEQUENCE OF TnGmplsRsvpIfEntry
        MAX-ACCESS     not-accessible
        STATUS         current
        DESCRIPTION    "The Resource Reservation Protocol Interface Table."
        ::= { tnGmplsCpifObjs 3 }

    tnGmplsRsvpIfEntry OBJECT-TYPE
        SYNTAX         TnGmplsRsvpIfEntry
        MAX-ACCESS     not-accessible
        STATUS         current
        DESCRIPTION    "An entry in this table represents an GMPLS LSP."
        REFERENCE      "?"
        INDEX          { tnGmplsRsvpIfId }
        ::= { tnGmplsRsvpIfTable 1 }

    TnGmplsRsvpIfEntry ::= SEQUENCE {
        tnGmplsRsvpIfId              Unsigned32,
        tnGmplsRsvpIfName            DisplayString,
        tnGmplsRsvpIfType            INTEGER,
        tnGmplsRsvpIfEncaps          INTEGER,
        tnGmplsRsvpIfCPNbr           Unsigned32,
        tnGmplsRsvpIfAdminStatus     INTEGER,
        tnGmplsRsvpIfOpState         INTEGER,
        tnGmplsRsvpIfRowStatus       RowStatus
    }

    tnGmplsRsvpIfId OBJECT-TYPE
        SYNTAX         Unsigned32
        MAX-ACCESS     not-accessible
        STATUS         current
        DESCRIPTION    "Interface index, uniquely identifies this row.
                        This Id maps to the GMPLS CLI interface index of the CPNbr."
        ::= { tnGmplsRsvpIfEntry 1 }

    tnGmplsRsvpIfName OBJECT-TYPE
        SYNTAX         DisplayString
        MAX-ACCESS     read-create
        STATUS         current
        DESCRIPTION    "User label."
        ::= { tnGmplsRsvpIfEntry 2 }

    tnGmplsRsvpIfType OBJECT-TYPE
        SYNTAX         INTEGER {
                         uni(1),
                         nni(2)
--                         enni(3),
--                         ennig(4),
--                         unistar(5)
                       }
        MAX-ACCESS     read-create
        STATUS         current
        DESCRIPTION    "IPv4 only."
        DEFVAL         { nni }
        ::= { tnGmplsRsvpIfEntry 3 }

    tnGmplsRsvpIfEncaps OBJECT-TYPE
        SYNTAX         INTEGER {
                         none(1),
                         ipminimal(2)
                       }
        MAX-ACCESS     read-create
        STATUS         current
        DESCRIPTION    "Protocol encapsulation."
        DEFVAL         { none }
        ::= { tnGmplsRsvpIfEntry 4 }

    tnGmplsRsvpIfCPNbr OBJECT-TYPE
        SYNTAX         Unsigned32
        MAX-ACCESS     read-create
        STATUS         current
        DESCRIPTION    "Reference to CPNbr table, the CPNbrIfIndex."
        ::= { tnGmplsRsvpIfEntry 5 }

    tnGmplsRsvpIfAdminStatus OBJECT-TYPE
        SYNTAX         INTEGER {
                         down(1),
                         up(2)
                       }
        MAX-ACCESS     read-create
        STATUS         current
        DESCRIPTION    "Administrative state."
        ::= { tnGmplsRsvpIfEntry 6 }

    tnGmplsRsvpIfOpState OBJECT-TYPE
        SYNTAX         INTEGER {
                         down(1),
                         up(2),
                         degraded(3)
                       }
        MAX-ACCESS     read-only
        STATUS         current
        DESCRIPTION    "Operational state."
        ::= { tnGmplsRsvpIfEntry 7 }

    tnGmplsRsvpIfRowStatus OBJECT-TYPE
        SYNTAX         RowStatus
        MAX-ACCESS     read-create
        STATUS         current
        DESCRIPTION    "This variable is used to create, modify, and/or
                        delete a row in this table."
        ::= { tnGmplsRsvpIfEntry 8 }

---------------------------------------------------------------------------
-- Data Plane Routing (DPR) Interface Table
---------------------------------------------------------------------------
    tnGmplsDprIfTable OBJECT-TYPE
        SYNTAX         SEQUENCE OF TnGmplsDprIfEntry
        MAX-ACCESS     not-accessible
        STATUS         current
        DESCRIPTION    "The Data Plane Routing Interface Table."
        ::= { tnGmplsCpifObjs 4 }

    tnGmplsDprIfEntry OBJECT-TYPE
        SYNTAX         TnGmplsDprIfEntry
        MAX-ACCESS     not-accessible
        STATUS         current
        DESCRIPTION    "An entry in this table represents an GMPLS LSP."
        REFERENCE      "?"
        INDEX          { tnGmplsDprIfId }
        ::= { tnGmplsDprIfTable 1 }

    TnGmplsDprIfEntry ::= SEQUENCE {
        tnGmplsDprIfId              Unsigned32,
        tnGmplsDprIfName            DisplayString,
        tnGmplsDprIfType            INTEGER,
        tnGmplsDprIfEncaps          INTEGER,
        tnGmplsDprIfCPNbr           Unsigned32,
        tnGmplsDprIfAdminStatus     INTEGER,
        tnGmplsDprIfOpState         INTEGER,
        tnGmplsDprIfNVMismatch      TruthValue,
        tnGmplsDprIfRowStatus       RowStatus
    }

    tnGmplsDprIfId OBJECT-TYPE
        SYNTAX         Unsigned32
        MAX-ACCESS     not-accessible
        STATUS         current
        DESCRIPTION    "Interface index, uniquely identifies this row.
                        This Id maps to the GMPLS CLI interface index of
                        the CPNbr."
        ::= { tnGmplsDprIfEntry 1 }

    tnGmplsDprIfName OBJECT-TYPE
        SYNTAX         DisplayString
        MAX-ACCESS     read-create
        STATUS         current
        DESCRIPTION    "User label."
        ::= { tnGmplsDprIfEntry 2 }

    tnGmplsDprIfType OBJECT-TYPE
        SYNTAX         INTEGER {
                         nni(1)
--                         enni(2),
--                         ennig(3)
                       }
        MAX-ACCESS     read-create
        STATUS         current
        DESCRIPTION    "IPv4 only."
        DEFVAL         { nni }
        ::= { tnGmplsDprIfEntry 3 }

    tnGmplsDprIfEncaps OBJECT-TYPE
        SYNTAX         INTEGER {
                         ipminimal(1)
                       }
        MAX-ACCESS     read-create
        STATUS         current
        DESCRIPTION    "Protocol encapsulation."
        DEFVAL         { ipminimal }
        ::= { tnGmplsDprIfEntry 4 }

    tnGmplsDprIfCPNbr OBJECT-TYPE
        SYNTAX         Unsigned32
        MAX-ACCESS     read-create
        STATUS         current
        DESCRIPTION    "Reference to CPNbr table, the CPNbrIfIndex."
        ::= { tnGmplsDprIfEntry 5 }

    tnGmplsDprIfAdminStatus OBJECT-TYPE
        SYNTAX         INTEGER {
                         down(1),
                         up(2)
                       }
        MAX-ACCESS     read-create
        STATUS         current
        DESCRIPTION    "Administrative state."
        ::= { tnGmplsDprIfEntry 6 }

    tnGmplsDprIfOpState OBJECT-TYPE
        SYNTAX         INTEGER {
                         down(1),
                         up(2),
                         degraded(3)
                       }
        MAX-ACCESS     read-only
        STATUS         current
        DESCRIPTION    "Operational state."
        ::= { tnGmplsDprIfEntry 7 }

    tnGmplsDprIfNVMismatch OBJECT-TYPE
        SYNTAX         TruthValue
        MAX-ACCESS     read-only
        STATUS         current
        DESCRIPTION    "Network version mismatch state."
        ::= { tnGmplsDprIfEntry 8 }

    tnGmplsDprIfRowStatus OBJECT-TYPE
        SYNTAX         RowStatus
        MAX-ACCESS     read-create
        STATUS         current
        DESCRIPTION    "This variable is used to create, modify, and/or
                        delete a row in this table."
        ::= { tnGmplsDprIfEntry 9 }

---------------------------------------------------------------------------
-- Link Management Protocol (LMP) Interface Table
---------------------------------------------------------------------------
    tnGmplsLmpIfTable OBJECT-TYPE
        SYNTAX         SEQUENCE OF TnGmplsLmpIfEntry
        MAX-ACCESS     not-accessible
        STATUS         current
        DESCRIPTION    "The Link Management Protocol Interface Table."
        ::= { tnGmplsCpifObjs 5 }

    tnGmplsLmpIfEntry OBJECT-TYPE
        SYNTAX         TnGmplsLmpIfEntry
        MAX-ACCESS     not-accessible
        STATUS         current
        DESCRIPTION    "An entry in this table represents an GMPLS LSP."
        REFERENCE      "?"
        INDEX          { tnGmplsLmpIfId }
        ::= { tnGmplsLmpIfTable 1 }

    TnGmplsLmpIfEntry ::= SEQUENCE {
        tnGmplsLmpIfId                      Unsigned32,
        tnGmplsLmpIfName                    DisplayString,
        tnGmplsLmpIfCPNbr                   Unsigned32,
        tnGmplsLmpIfHelloEnabled            TruthValue,
        tnGmplsLmpIfLinkPropCorrEnabled     TruthValue,
        tnGmplsLmpIfTraceMonEnabled         TruthValue,
        tnGmplsLmpIfEndPointDiscEnabled     TruthValue,
        tnGmplsLmpIfAdminStatus             INTEGER,
        tnGmplsLmpIfOpState                 INTEGER,
        tnGmplsLmpIfRowStatus               RowStatus
    }

    tnGmplsLmpIfId OBJECT-TYPE
        SYNTAX         Unsigned32
        MAX-ACCESS     not-accessible
        STATUS         current
        DESCRIPTION    "Interface index, uniquely identifies this row.
                        This Id maps to the GMPLS CLI interface index of
                        the CPNbr."
        ::= { tnGmplsLmpIfEntry 1 }

    tnGmplsLmpIfName OBJECT-TYPE
        SYNTAX         DisplayString
        MAX-ACCESS     read-create
        STATUS         current
        DESCRIPTION    "User label."
        ::= { tnGmplsLmpIfEntry 2 }

    tnGmplsLmpIfCPNbr OBJECT-TYPE
        SYNTAX         Unsigned32
        MAX-ACCESS     read-create
        STATUS         current
        DESCRIPTION    "Reference to CPNbr table, the CPNbrIfIndex."
        ::= { tnGmplsLmpIfEntry 3 }

    tnGmplsLmpIfHelloEnabled OBJECT-TYPE
        SYNTAX         TruthValue
        MAX-ACCESS     read-create
        STATUS         current
        DESCRIPTION    "Hello protocol on/off."
        ::= { tnGmplsLmpIfEntry 4 }

    tnGmplsLmpIfLinkPropCorrEnabled OBJECT-TYPE
        SYNTAX         TruthValue
        MAX-ACCESS     read-create
        STATUS         current
        DESCRIPTION    "LMP Link property correlation on/off."
        ::= { tnGmplsLmpIfEntry 5 }

    tnGmplsLmpIfTraceMonEnabled OBJECT-TYPE
        SYNTAX         TruthValue
        MAX-ACCESS     read-create
        STATUS         current
        DESCRIPTION    "Hello protocol on/off."
        ::= { tnGmplsLmpIfEntry 6 }

    tnGmplsLmpIfEndPointDiscEnabled OBJECT-TYPE
        SYNTAX         TruthValue
        MAX-ACCESS     read-create
        STATUS         current
        DESCRIPTION    "Hello protocol on/off."
        ::= { tnGmplsLmpIfEntry 7 }

    tnGmplsLmpIfAdminStatus OBJECT-TYPE
        SYNTAX         INTEGER {
                         down(1),
                         up(2)
                       }
        MAX-ACCESS     read-create
        STATUS         current
        DESCRIPTION    "Administrative state."
        ::= { tnGmplsLmpIfEntry 8 }

    tnGmplsLmpIfOpState OBJECT-TYPE
        SYNTAX         INTEGER {
                         down(1),
                         up(2),
                         degraded(3)
                       }
        MAX-ACCESS     read-only
        STATUS         current
        DESCRIPTION    "Operational state."
        ::= { tnGmplsLmpIfEntry 9 }

    tnGmplsLmpIfRowStatus OBJECT-TYPE
        SYNTAX         RowStatus
        MAX-ACCESS     read-create
        STATUS         current
        DESCRIPTION    "This variable is used to create, modify, and/or
                        delete a row in this table."
        ::= { tnGmplsLmpIfEntry 10 }

---------------------------------------------------------------------------
-- Notifications.
---------------------------------------------------------------------------
--    tnGmplsCPNbrAdminStatusChange NOTIFICATION-TYPE
--        OBJECTS {
--            tnGmplsCPNbrIfId,
--            tnGmplsCPNbrAdminStatus
--        }
--        STATUS         current
--        DESCRIPTION    "This notification is generated when a status
--                        object is changed."
--    ::= { tnGmplsCpifNotifyPrefix 1 }
--
--    tnGmplsRsvpIfAdminStatusChange NOTIFICATION-TYPE
--        OBJECTS {
--            tnGmplsRsvpIfId,
--            tnGmplsRsvpIfAdminStatus
--        }
--        STATUS         current
--        DESCRIPTION    "This notification is generated when a
--                        administrative state object is changed."
--        ::= { tnGmplsCpifNotifyPrefix 2 }
--
--    tnGmplsRsvpIfOpStateChange NOTIFICATION-TYPE
--        OBJECTS {
--            tnGmplsRsvpIfId,
--            tnGmplsRsvpIfOpState
--        }
--        STATUS         current
--        DESCRIPTION    "This notification is generated when a
--                        operational state object is changed."
--        ::= { tnGmplsCpifNotifyPrefix 3 }
--
--    tnGmplsDprIfAdminStatusChange NOTIFICATION-TYPE
--        OBJECTS {
--            tnGmplsDprIfId,
--            tnGmplsDprIfAdminStatus
--        }
--        STATUS         current
--        DESCRIPTION    "This notification is generated when a
--                        administrative state object is changed."
--        ::= { tnGmplsCpifNotifyPrefix 4 }
--
--    tnGmplsDprIfOpStateChange NOTIFICATION-TYPE
--        OBJECTS {
--            tnGmplsDprIfId,
--            tnGmplsDprIfOpState
--        }
--        STATUS         current
--        DESCRIPTION    "This notification is generated when a
--                        operational state object is changed."
--        ::= { tnGmplsCpifNotifyPrefix 5 }
--
--    tnGmplsDprIfNVMismatchChange NOTIFICATION-TYPE
--        OBJECTS {
--            tnGmplsDprIfId,
--            tnGmplsDprIfNVMismatch
--        }
--        STATUS         current
--        DESCRIPTION    "This notification is generated when a
--                        mismatch of network version has changed."
--        ::= { tnGmplsCpifNotifyPrefix 6 }
--
--    tnGmplsLmpIfAdminStatusChange NOTIFICATION-TYPE
--        OBJECTS {
--            tnGmplsLmpIfId,
--            tnGmplsLmpIfAdminStatus
--        }
--        STATUS         current
--        DESCRIPTION    "This notification is generated when a
--                        administrative state object is changed."
--        ::= { tnGmplsCpifNotifyPrefix 7 }
--
--    tnGmplsLmpIfOpStateChange NOTIFICATION-TYPE
--        OBJECTS {
--            tnGmplsLmpIfId,
--            tnGmplsLmpIfOpState
--        }
--        STATUS         current
--        DESCRIPTION    "This notification is generated when a
--                        operational state object is changed."
--        ::= { tnGmplsCpifNotifyPrefix 8 }
--
-- End of notifications.

---------------------------------------------------------------------------
-- Conformance Group Definitions
---------------------------------------------------------------------------
    tnGmplsCpifObjsGroup OBJECT-GROUP
        OBJECTS {
            tnGmplsCpifAttributeTotal
        }
        STATUS         current
        DESCRIPTION    "."
        ::= { tnGmplsCpifGroups 1 }

    tnGmplsCPNbrGroup OBJECT-GROUP
        OBJECTS {
            tnGmplsCPNbrIfName,
            tnGmplsCPNbrAddrType,
            tnGmplsCPNbrRemoteRouterAddr,
            tnGmplsCPNbrEncaps,
            tnGmplsCPNbrRemoteTEP,
            tnGmplsCPNbrOspfArea,
            tnGmplsCPNbrAdminStatus,
            tnGmplsCPNbrRemoteCPNodeId,
            tnGmplsCPNbrRowStatus
        }
        STATUS         current
        DESCRIPTION    "The GMPLS control plane neighbour group of objects
                        providing for management of GMPLS NE entities."
        ::= { tnGmplsCpifGroups 2 }

    tnGmplsRsvpGroup OBJECT-GROUP
        OBJECTS {
            tnGmplsRsvpIfName,
            tnGmplsRsvpIfType,
            tnGmplsRsvpIfEncaps,
            tnGmplsRsvpIfCPNbr,
            tnGmplsRsvpIfAdminStatus,
            tnGmplsRsvpIfOpState,
            tnGmplsRsvpIfRowStatus
        }
        STATUS         current
        DESCRIPTION    "The GMPLS control plane rsvp group of objects
                        providing for management of GMPLS NE entities."
        ::= { tnGmplsCpifGroups 3 }

    tnGmplsDprGroup OBJECT-GROUP
        OBJECTS {
            tnGmplsDprIfName,
            tnGmplsDprIfType,
            tnGmplsDprIfEncaps,
            tnGmplsDprIfCPNbr,
            tnGmplsDprIfAdminStatus,
            tnGmplsDprIfOpState,
            tnGmplsDprIfNVMismatch,
            tnGmplsDprIfRowStatus
        }
        STATUS         current
        DESCRIPTION    "The GMPLS datplane plane routing group of objects
                        providing for management of GMPLS NE entities."
        ::= { tnGmplsCpifGroups 4 }

    tnGmplsLmpGroup OBJECT-GROUP
        OBJECTS {
            tnGmplsLmpIfName,
            tnGmplsLmpIfCPNbr,
            tnGmplsLmpIfHelloEnabled,
            tnGmplsLmpIfLinkPropCorrEnabled,
            tnGmplsLmpIfTraceMonEnabled,
            tnGmplsLmpIfEndPointDiscEnabled,
            tnGmplsLmpIfAdminStatus,
            tnGmplsLmpIfOpState,
            tnGmplsLmpIfRowStatus
        }
        STATUS         current
        DESCRIPTION    "The GMPLS control plane LMP group of objects
                        providing for management of GMPLS NE entities."
        ::= { tnGmplsCpifGroups 5 }
--
--    tnGmplsCPNbrNotificationGroup NOTIFICATION-GROUP
--        NOTIFICATIONS {
--            tnGmplsCPNbrAdminStatusChange
--        }
--        STATUS         current
--        DESCRIPTION    "Set of notifications implemented in this module.
--                        None is mandatory."
--        ::= { tnGmplsCpifGroups 6 }
--
--    tnGmplsRsvpNotificationGroup NOTIFICATION-GROUP
--        NOTIFICATIONS {
--            tnGmplsRsvpIfAdminStatusChange,
--            tnGmplsRsvpIfOpStateChange
--        }
--        STATUS         current
--        DESCRIPTION    "Set of notifications implemented in this module.
--                        None is mandatory."
--        ::= { tnGmplsCpifGroups 7 }
--
--    tnGmplsDprNotificationGroup NOTIFICATION-GROUP
--        NOTIFICATIONS {
--            tnGmplsDprIfAdminStatusChange,
--            tnGmplsDprIfOpStateChange,
--            tnGmplsDprIfNVMismatchChange
--        }
--        STATUS         current
--        DESCRIPTION    "Set of notifications implemented in this module.
--                        None is mandatory."
--        ::= { tnGmplsCpifGroups 8 }
--
--    tnGmplsLmpNotificationGroup NOTIFICATION-GROUP
--        NOTIFICATIONS {
--            tnGmplsLmpIfAdminStatusChange,
--            tnGmplsLmpIfOpStateChange
--        }
--        STATUS         current
--        DESCRIPTION    "Set of notifications implemented in this module.
--                        None is mandatory."
--        ::= { tnGmplsCpifGroups 9 }

---------------------------------------------------------------------------
-- Compliance Statements (mandatory)
---------------------------------------------------------------------------
    tnGmplsCpifCompliance MODULE-COMPLIANCE
        STATUS         current
        DESCRIPTION    "The compliance statement for SNMPv2 entities
                        which implement GMPLS NE."
        MODULE
        MANDATORY-GROUPS {
            tnGmplsCpifObjsGroup,
            tnGmplsCPNbrGroup,
            tnGmplsRsvpGroup,
            tnGmplsDprGroup,
            tnGmplsLmpGroup
--            tnGmplsCPNbrNotificationGroup,
--            tnGmplsRsvpNotificationGroup,
--            tnGmplsDprNotificationGroup,
--            tnGmplsLmpNotificationGroup
        }
        ::= { tnGmplsCpifCompliances 1 }

END -- DEFINITION OF TROPIC-GMPLS-CPIF-MIB
