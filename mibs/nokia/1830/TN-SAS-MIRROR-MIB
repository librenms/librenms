TN-SAS-MIRROR-MIB DEFINITIONS ::= BEGIN

-- (c) Copyright 2023 Nokia Networks.  All rights reserved.
-- This software is the confidential and proprietary property of
-- Nokia and may only be used in accordance with the terms of the
-- license agreement provided with this software.

IMPORTS
    MODULE-IDENTITY, OBJECT-TYPE
        FROM SNMPv2-SMI

--  OBJECT-GROUP
--      FROM SNMPv2-CONF


    tnSRMIBModules, tnSRObjs, tnSRNotifyPrefix,
    tnSASObjs, tnSASModules
        FROM TROPIC-GLOBAL-REG

    TProfileOrNone
        FROM TN-TC-MIB

    tnMirrorSourcePortEntry, tnMirrorDestinationEntry
        FROM TN-MIRROR-MIB

    ;

    tnSASMirrorMIBModule   MODULE-IDENTITY
        LAST-UPDATED    "201105010000Z"
        ORGANIZATION    "Alcatel"
        CONTACT-INFO
            "Alcatel 7x50 Support
             Web: http://www.alcatel.com/comps/pages/carrier_support.jhtml"
        DESCRIPTION
        "This document is the SNMP MIB module to manage and provision
         traffic mirroring on Alcatel 7x50 systems.

         This SNMP MIB module (Specification) embodies Alcatel's
         proprietary intellectual property.  Alcatel retains
         all title and ownership in the Specification, including any
         revisions.

         Alcatel grants all interested parties a non-exclusive
         license to use and distribute an unmodified copy of this
         Specification in connection with management of Alcatel
         products, and without fee, provided this copyright notice and
         license appear on all copies.

         This Specification is supplied 'as is', and Alcatel
         makes no warranty, either express or implied, as to the use,
         operation, condition, or performance of the Specification."

--
--  Revision History
--
        REVISION        "201105010000Z"
        DESCRIPTION     "Rev 1.0                01 Jan 2009 00:00
                         1.0 release of the TIMETRA-SAS-MIRROR-MIB."

        ::= { tnSASModules 13 }

tnSASMirrorObjects                  OBJECT IDENTIFIER ::= { tnSASObjs 13 }

tnMirrorSourcePortExtnTable OBJECT-TYPE
    SYNTAX       SEQUENCE OF TnMirrorSourcePortExtnEntry
    MAX-ACCESS   not-accessible
    STATUS       current
    DESCRIPTION
        "."
    ::= { tnSASMirrorObjects 1 }

tnMirrorSourcePortExtnEntry OBJECT-TYPE
    SYNTAX       TnMirrorSourcePortExtnEntry
    MAX-ACCESS   not-accessible
    STATUS       current
    DESCRIPTION
        "."
    AUGMENTS {tnMirrorSourcePortEntry}
    ::= { tnMirrorSourcePortExtnTable 1 }

TnMirrorSourcePortExtnEntry ::=
    SEQUENCE {
      tnMirrorSourcePortEgressMirroringType         INTEGER
    }

tnMirrorSourcePortEgressMirroringType OBJECT-TYPE
    SYNTAX          INTEGER {
                        true-egress-mirroring (1),
                        normal-egress-mirroring (2)
                    }
    MAX-ACCESS      read-create
    STATUS          current
    DESCRIPTION
      "With no-true-egress specified and when egress port mirroring is enabled,
        the mirrored copy of the packets will not be an exact replica of the forwarded
        copy. Some ofthe modifications applied to the forwarded packet in the egress
        processing path will no be available in the mirrored copy"
    DEFVAL { true-egress-mirroring }
    ::= { tnMirrorSourcePortExtnEntry 1 }

tnMirrorDestinationExtnTable OBJECT-TYPE
    SYNTAX       SEQUENCE OF TnMirrorDestinationExtnEntry
    MAX-ACCESS   not-accessible
    STATUS       current
    DESCRIPTION
        "."
    ::= { tnSASMirrorObjects 2 }

tnMirrorDestinationExtnEntry OBJECT-TYPE
    SYNTAX       TnMirrorDestinationExtnEntry
    MAX-ACCESS   not-accessible
    STATUS       current
    DESCRIPTION
        "."
    AUGMENTS {tnMirrorDestinationEntry}
    ::= { tnMirrorDestinationExtnTable 1 }

TnMirrorDestinationExtnEntry ::=
    SEQUENCE {
      tnMirrorDestinationFCProfile          TProfileOrNone,
      tnMirrorDestinationMirrorSourceType   INTEGER
    }

tnMirrorDestinationFCProfile OBJECT-TYPE
    SYNTAX          TProfileOrNone
    MAX-ACCESS      read-create
    STATUS          current
    DESCRIPTION
      "Specifies the profile of the packet associated with the forwarding class
       tnMirrorDestinationFC"
    DEFVAL { out }
    ::= { tnMirrorDestinationExtnEntry 1 }

tnMirrorDestinationMirrorSourceType OBJECT-TYPE
    SYNTAX          INTEGER {
                        local (1),
                        remote (2),
                        both (3)
                    }
    MAX-ACCESS      read-create
    STATUS          current
    DESCRIPTION
      "User can specify if the mirror services needs to support local mirror sources,
      remote mirror sources or both"
    DEFVAL { local }
    ::= { tnMirrorDestinationExtnEntry 2 }

-- tmnxSASMirrorGroups      OBJECT IDENTIFIER ::= { tnSASConfs 8 }

-- tmnxSASMirrorV1v0Group       OBJECT-GROUP
--    OBJECTS {
--                    tnMirrorSourcePortEgressMirroringType,
--                    tnMirrorDestinationFCProfile,
--                    tnMirrorDestinationMirrorSourceType
--                    }
--    STATUS        current
--    DESCRIPTION
--        "The group of objects supporting management of transport and
--         virtual routers on version 1.0 Alcatel 7210 SAS series systems."
--    ::= { tmnxSASMirrorGroups 1 }

END
