TROPIC-GENERIC-NOTIFICATION-MIB DEFINITIONS ::= BEGIN

-- (c) Copyright 2023 Nokia Networks.  All rights reserved.
-- This software is the confidential and proprietary property of
-- Nokia and may only be used in accordance with the terms of the
-- license agreement provided with this software.

IMPORTS
    OBJECT-TYPE, MODULE-IDENTITY,
    Counter32, Counter64, Integer32, Unsigned32,
    TimeTicks, IpAddress, NOTIFICATION-TYPE     FROM SNMPv2-SMI
    TEXTUAL-CONVENTION, DateAndTime, TruthValue FROM SNMPv2-TC
    MODULE-COMPLIANCE, NOTIFICATION-GROUP,
    OBJECT-GROUP                                FROM SNMPv2-CONF
    SnmpAdminString                             FROM SNMP-FRAMEWORK-MIB
    TnCondition, TnTrapCategory, TnEntityType   FROM TROPIC-TC
    tnSystemModules, tnGenericNotificationMIB   FROM TROPIC-GLOBAL-REG;

tnGenericNotificationMibModule MODULE-IDENTITY
    LAST-UPDATED    "202212230000Z"
    ORGANIZATION    "Nokia"
    CONTACT-INFO    "Nokia
                     Attn: Jeff Donnelly
                     600 Mountain Avenue
                     New Providence, NJ 07974

                     Phone: +1 732 221 6408
                     Email: jeff.donnelly@nokia.com"

    DESCRIPTION "The Generic Notification MIB."

    REVISION    "202301200000Z"
    DESCRIPTION "Added the following notifications:
                 tnGenericVoltageLowRaisedNotif
                 tnGenericVoltageLowClearedNotif."

    REVISION    "202212230000Z"
    DESCRIPTION "Added the following notifications:
                 - tnGenericNeCertValidityWarnRaisedNotif
                 - tnGenericNeCertValidityWarnClearedNotif
                 - tnGenericNeCertValidityExpRaisedNotif
                 - tnGenericNeCertValidityExpClearedNotif
                 - tnGenericTnOthOdukXcCreationNotif
                 - tnGenericTnOthOdukXcDeletionNotif."

    REVISION    "202211040000Z"
    DESCRIPTION "Added the following notifications:
                 - tnGenericTBerPreFec15minRaisedNotif
                 - tnGenericTBerPreFec15minClearedNotif
                 - tnGenericTBerPreFec1dayRaisedNotif
                 - tnGenericTBerPreFec1dayClearedNoti
                 - tnGenericTBerPostFec15minRaisedNotif
                 - tnGenericTBerPostFec15minClearedNotif
                 - tnGenericTBerPostFec1dayRaisedNotif
                 - tnGenericTBerPostFec1dayClearedNotif
                 - tnGenericUruSRaisedNotif
                 - tnGenericUruSClearedNotif."

    REVISION    "202210240000Z"
    DESCRIPTION "Added generic trap objects:
                 - tnGenericTrapOthOdukApsAction
                 - tnGenericTrapOthOdukApsFromedIfIndex
                 - tnGenericTrapOthOdukApsFromedIfIndexLo
                 - tnGenericTrapOthOdukApsFromingIfIndex
                 - tnGenericTrapOthOdukApsFromingIfIndexLo
                 and added tnGenericTnOthOdukApsGroupConvertNotif
                 which uses these objects.
                 Added these objects to tnGenericTrapGroup."

    REVISION    "202210120000Z"
    DESCRIPTION "1) Added the following OBJECT IDENTIFIERs:
                    tnGenericTransferPMDiscovery
                    tnGenericTransferPMDiscoveryNotifs
                    tnGenericTransferPMDiscoveryConformance
                    tnGenericTransferPMDiscoveryCompliances
                    tnGenericTransferPMDiscoveryGroups.
                 2) Added the following notifications:
                    - tnGenericTxAutoLaserShutdownRaisedNotif
                    - tnGenericTxAutoLaserShutdownClearedNotif
                    - tnGenericTransferPMDiscoveryCreationNotif
                    - tnGenericTransferPMDiscoveryDeletionNotif
                    - tnGenericTransferPMDiscoveryConfigChangeNotif."

    REVISION    "202108131200Z"
    DESCRIPTION "Added the following alarm trap:
                 - tnGenericTnControlNetworkLinkStateChangeNotif."

    REVISION    "202106251200Z"
    DESCRIPTION "Added the following alarm trap:
                 - tnGenericTnControlNetworkLinkConfigChangeNotif."

    REVISION    "202105071200Z"
    DESCRIPTION "Added the following alarm traps:
                 - tnGenericIntrusionRaisedNotif
                 - tnGenericIntrusionClearedNotif
                 - tnGenericNtpOutOfSyncRaisedNotif
                 - tnGenericNtpOutOfSyncClearedNotif."

    REVISION    "202011081200Z"
    DESCRIPTION "Added the following alarm traps:
                 - tnGenericSyslogServerCreationNotif
                 - tnGenericSyslogServerDeletionNotif
                 - tnGenericSyslogServerConfigChangeNotif."

    REVISION    "202010231200Z"
    DESCRIPTION "Added the following alarm traps:
                 - tnGenericCsfGfpRaisedNotif
                 - tnGenericCsfGfpClearedNotif
                 - tnGenericGfpExmRaisedNotif
                 - tnGenericGfpExmClearedNotif
                 - tnGenericGfpLofRaisedNotif
                 - tnGenericGfpLofClearedNotif
                 - tnGenericGfpUpmRaisedNotif
                 - tnGenericGfpUpmClearedNotif
                 - tnGenericLOFLOMRaisedNotif
                 - tnGenericLOFLOMClearedNotif
                 - tnGenericMsimRaisedNotif
                 - tnGenericMsimClearedNotif
                 - tnGenericPayloadTypeMismatchRaisedNotif
                 - tnGenericPayloadTypeMismatchClearedNotif."

    REVISION    "202003061200Z"
    DESCRIPTION "Added the following alarm trap:
                 - tnGenericRadiusServerConfigChangeNotif."

    REVISION    "202002281200Z"
    DESCRIPTION "Added the following alarm traps:
                 - tnGenericPRBSLSSRaisedNotif
                 - tnGenericPRBSLSSClearedNotif
                 - tnGenericDiscoverMeNotif
                 - tnGenericRadiusServerCreationNotif
                 - tnGenericRadiusServerDeletionNotif."

    REVISION    "201909041200Z"
    DESCRIPTION "Added the following alarm traps:
                 - tnGenericOduClientSignalFailureRaisedNotif
                 - tnGenericOduClientSignalFailureClearedNotif."

    REVISION    "201803191200Z"
    DESCRIPTION "Added the following alarm traps:
                 - tnGenericLocalFaultRaisedNotif
                 - tnGenericLocalFaultClearedNotif
                 - tnGenericRemoteFailureIndicationRaisedNotif
                 - tnGenericRemoteFailureIndicationClearedNotif."

    REVISION    "201802231200Z"
    DESCRIPTION "Updated the contact info."

    REVISION    "201711241200Z"
    DESCRIPTION "Added the following alarm traps:
                 - tnGenericOpticalOutputPowerUnachievableRaisedNotif
                 - tnGenericOpticalOutputPowerUnachievableClearedNotif
                 - tnGenericDiagnosticTerminalLoopbackActiveRaisedNotif
                 - tnGenericDiagnosticTerminalLoopbackActiveClearedNotif."

    REVISION    "201709251200Z"
    DESCRIPTION "Updated descriptions of SLM FLR alarm notifications.
                 Added following alarm traps:
                 - tnGenericTPmonSlmxnflrContRaisedNotif
                 - tnGenericTPmonSlmxnflrContClearedNotif
                 Added following security event traps:
                 - tnGenericSecurityExceededLoginAttemptsNotif
                 - tnGenericSecurityLockAccountNotif
                 - tnGenericSecurityUnlockAccountNotif
                 - tnGenericSecurityUnauthAccessAttemptNotif
                 - tnGenericSecurityEnableInterfaceNotif
                 - tnGenericSecurityDisableInterfaceNotif
                 Removed tnGenericTrapConfigurationChangeCounter from
                 event traps.
                 Added tnGenericTnIfConfigChangeNotif."

    REVISION    "201709221200Z"
    DESCRIPTION "Added following alarms:
                 - tnGenericCardMismatchRaisedNotif
                 - tnGenericCardMismatchClearedNotif"

    REVISION    "201709151200Z"
    DESCRIPTION "Added following alarms:
                 - tnGenericLagProtLosRaisedNotif
                 - tnGenericLagProtLosClearedNotif
                 - tnGenericMonitorExcRaisedNotif
                 - tnGenericMonitorExcClearedNotif
                 - tnGenericEquipmentLedOnRaisedNotif
                 - tnGenericEquipmentLedOnClearedNotif
                 - tnGenericUnitInitRaisedNotif
                 - tnGenericUnitInitClearedNotif"

    REVISION    "201708181200Z"
    DESCRIPTION "Added CFM pro-active attribute value change traps:
                 - tnGenericTnOamPingCtlCreationNotif
                 - tnGenericTnOamPingCtlDeletionNotif
                 - tnGenericTnOamSaaCtlConfigChangeNotif
                 Added CFM on-demand attribute value change and event traps:
                 - tnGenericTnDot1agCfmMepSlmTWTestConfigChangeNotif
                 - tnGenericTnDot1agCfmMepOndemandLmTestConfigChangeNotif
                 - tnGenericDot1agCfmDmTestCompleteNotif
                 - tnGenericDot1agCfmSlmTestCompleteNotif
                 - tnGenericDot1agCfmLmTestCompleteNotif"

    REVISION    "201707071200Z"
    DESCRIPTION "Added CFM attribute value change traps:
                 - tnGenericTnDot1agCfmMepConfigChangeNotif
                 - tnGenericDot1agCfmMdConfigChangeNotif
                 - tnGenericDot1agCfmMaNetConfigChangeNotif
                 - tnGenericDot1agCfmMaCompConfigChangeNotif
                 - tnGenericDot1agCfmMepConfigChangeNotif
                 - tnGenericDot1agCfmMdCreationNotif
                 - tnGenericDot1agCfmMdDeletionNotif
                 - tnGenericDot1agCfmMaNetCreationNotif
                 - tnGenericDot1agCfmMaNetDeletionNotif
                 - tnGenericDot1agCfmMaCompCreationNotif
                 - tnGenericDot1agCfmMaCompDeletionNotif
                 - tnGenericDot1agCfmMaMepListCreationNotif
                 - tnGenericDot1agCfmMaMepListDeletionNotif
                 - tnGenericDot1agCfmMepCreationNotif
                 - tnGenericDot1agCfmMepDeletionNotif
                 Added PMON and ethernet port attribute
                 value change traps:
                 - tnGenericTnPmonPolicyConfigChangeNotif
                 - tnGenericTnPmonTcaConfigChangeNotif
                 - tnGenericTnPortEtherConfigChangeNotif
                 Added tnGenericTrapEntityType to alarm notifications
                 and to tnGenericTrapBuffer.
                 Added LAG attribute value change traps:
                 - tnGenericTnLagPortConfigChangeNotif
                 - tnGenericTnLagCommandConfigChangeNotif
                 Added LAG event:
                 - tnGenericSubgroupSelectNotif
                 Added following alarms:
                 - tnGenericTFeBbeOdu15MinRaisedNotif
                 - tnGenericTFeBbeOdu15MinClearedNotif
                 - tnGenericTFeBbeOdu1DayRaisedNotif
                 - tnGenericTFeBbeOdu1DayClearedNotif
                 - tnGenericTFeEsOdu15MinRaisedNotif
                 - tnGenericTFeEsOdu15MinClearedNotif
                 - tnGenericTFeEsOdu1DayRaisedNotif
                 - tnGenericTFeEsOdu1DayClearedNotif
                 - tnGenericTFeSesOdu15MinRaisedNotif
                 - tnGenericTFeSesOdu15MinClearedNotif
                 - tnGenericTFeSesOdu1DayRaisedNotif
                 - tnGenericTFeSesOdu1DayClearedNotif
                 - tnGenericTFeUasOdu15MinRaisedNotif
                 - tnGenericTFeUasOdu15MinClearedNotif
                 - tnGenericTFeUasOdu1DayRaisedNotif
                 - tnGenericTFeUasOdu1DayClearedNotif
                 - tnGenericTFeBbeTcm15MinRaisedNotif
                 - tnGenericTFeBbeTcm15MinClearedNotif
                 - tnGenericTFeBbeTcm1DayRaisedNotif
                 - tnGenericTFeBbeTcm1DayClearedNotif
                 - tnGenericTFeEsTcm15MinRaisedNotif
                 - tnGenericTFeEsTcm15MinClearedNotif
                 - tnGenericTFeEsTcm1DayRaisedNotif
                 - tnGenericTFeEsTcm1DayClearedNotif
                 - tnGenericTFeSesTcm15MinRaisedNotif
                 - tnGenericTFeSesTcm15MinClearedNotif
                 - tnGenericTFeSesTcm1DayRaisedNotif
                 - tnGenericTFeSesTcm1DayClearedNotif
                 - tnGenericTFeUasTcm15MinRaisedNotif
                 - tnGenericTFeUasTcm15MinClearedNotif
                 - tnGenericTFeUasTcm1DayRaisedNotif
                 - tnGenericTFeUasTcm1DayClearedNotif
                 - tnGenericTFeBbeOtu15MinRaisedNotif
                 - tnGenericTFeBbeOtu15MinClearedNotif
                 - tnGenericTFeBbeOtu1DayRaisedNotif
                 - tnGenericTFeBbeOtu1DayClearedNotif
                 - tnGenericTFeEsOtu15MinRaisedNotif
                 - tnGenericTFeEsOtu15MinClearedNotif
                 - tnGenericTFeEsOtu1DayRaisedNotif
                 - tnGenericTFeEsOtu1DayClearedNotif
                 - tnGenericTFeSesOtu15MinRaisedNotif
                 - tnGenericTFeSesOtu15MinClearedNotif
                 - tnGenericTFeSesOtu1DayRaisedNotif
                 - tnGenericTFeSesOtu1DayClearedNotif
                 - tnGenericTFeUasOtu15MinRaisedNotif
                 - tnGenericTFeUasOtu15MinClearedNotif
                 - tnGenericTFeUasOtu1DayRaisedNotif
                 - tnGenericTFeUasOtu1DayClearedNotif
                 - tnGenericTPmonPortIfInPackets15MinRaisedNotif
                 - tnGenericTPmonPortIfInPackets15MinClearedNotif
                 - tnGenericTPmonPortIfInPackets1DayRaisedNotif
                 - tnGenericTPmonPortIfInPackets1DayClearedNotif
                 - tnGenericTPmonPortIfInOctets15MinRaisedNotif
                 - tnGenericTPmonPortIfInOctets15MinClearedNotif
                 - tnGenericTPmonPortIfInOctets1DayRaisedNotif
                 - tnGenericTPmonPortIfInOctets1DayClearedNotif
                 - tnGenericTPmonPortIfInDiscards15MinRaisedNotif
                 - tnGenericTPmonPortIfInDiscards15MinClearedNotif
                 - tnGenericTPmonPortIfInDiscards1DayRaisedNotif
                 - tnGenericTPmonPortIfInDiscards1DayClearedNotif
                 - tnGenericTPmonPortIfInErrors15MinRaisedNotif
                 - tnGenericTPmonPortIfInErrors15MinClearedNotif
                 - tnGenericTPmonPortIfInErrors1DayRaisedNotif
                 - tnGenericTPmonPortIfInErrors1DayClearedNotif
                 - tnGenericTPmonPortIfOutPackets15MinRaisedNotif
                 - tnGenericTPmonPortIfOutPackets15MinClearedNotif
                 - tnGenericTPmonPortIfOutPackets1DayRaisedNotif
                 - tnGenericTPmonPortIfOutPackets1DayClearedNotif
                 - tnGenericTPmonPortIfOutOctets15MinRaisedNotif
                 - tnGenericTPmonPortIfOutOctets15MinClearedNotif
                 - tnGenericTPmonPortIfOutOctets1DayRaisedNotif
                 - tnGenericTPmonPortIfOutOctets1DayClearedNotif
                 - tnGenericTPmonSlmanFlr1DayRaisedNotif
                 - tnGenericTPmonSlmanFlr1DayClearedNotif
                 - tnGenericTPmonSlmafFlr1DayRaisedNotif
                 - tnGenericTPmonSlmafFlr1DayClearedNotif
                 - tnGenericTPmonSlmanflr15MinRaisedNotif
                 - tnGenericTPmonSlmanflr15MinClearedNotif
                 - tnGenericTPmonSlmafflr15MinRaisedNotif
                 - tnGenericTPmonSlmafflr15MinClearedNotif
                 - tnGenericTPmonSlmnhli15MinRaisedNotif
                 - tnGenericTPmonSlmnhli15MinClearedNotif
                 - tnGenericTPmonSlmfhli15MinRaisedNotif
                 - tnGenericTPmonSlmfhli15MinClearedNotif
                 - tnGenericTPmonSlmnhli1DayRaisedNotif
                 - tnGenericTPmonSlmnhli1DayClearedNotif
                 - tnGenericTPmonSlmfhli1DayRaisedNotif
                 - tnGenericTPmonSlmfhli1DayClearedNotif
                 - tnGenericTPmonSlmxfflrContRaisedNotif
                 - tnGenericTPmonSlmxfflrContClearedNotif
                 - tnGenericTPmonSlmanflrContRaisedNotif
                 - tnGenericTPmonSlmanflrContClearedNotif
                 - tnGenericTPmonSlmafflrContRaisedNotif
                 - tnGenericTPmonSlmafflrContClearedNotif
                 - tnGenericTPmonDmaBfd15MinRaisedNotif
                 - tnGenericTPmonDmaBfd15MinClearedNotif
                 - tnGenericTPmonDmaBfd1DayRaisedNotif
                 - tnGenericTPmonDmaBfd1DayClearedNotif
                 - tnGenericTPmonDmafFdv15MinRaisedNotif
                 - tnGenericTPmonDmafFdv15MinClearedNotif
                 - tnGenericTPmonDmafFdv1DayRaisedNotif
                 - tnGenericTPmonDmafFdv1DayClearedNotif
                 - tnGenericTPmonDmanFdv15MinRaisedNotif
                 - tnGenericTPmonDmanFdv15MinClearedNotif
                 - tnGenericTPmonDmanFdv1DayRaisedNotif
                 - tnGenericTPmonDmanFdv1DayClearedNotif
                 - tnGenericTPmonDmxBfd15MinRaisedNotif
                 - tnGenericTPmonDmxBfd15MinClearedNotif
                 - tnGenericTPmonDmxBfd1DayRaisedNotif
                 - tnGenericTPmonDmxBfd1DayClearedNotif
                 - tnGenericTPmonDmxfFdv15MinRaisedNotif
                 - tnGenericTPmonDmxfFdv15MinClearedNotif
                 - tnGenericTPmonDmxfFdv1DayRaisedNotif
                 - tnGenericTPmonDmxfFdv1DayClearedNotif
                 - tnGenericTPmonDmxnFdv15MinRaisedNotif
                 - tnGenericTPmonDmxnFdv15MinClearedNotif
                 - tnGenericTPmonDmxnFdv1DayRaisedNotif
                 - tnGenericTPmonDmxnFdv1DayClearedNotif
                 - tnGenericLagLosRaisedNotif
                 - tnGenericLagLosClearedNotif
                 - tnGenericMepLocRaisedNotif
                 - tnGenericMepLocClearedNotif
                 - tnGenericUNLRaisedNotif
                 - tnGenericUNLClearedNotif
                 - tnGenericMepMmgRaisedNotif
                 - tnGenericMepMmgClearedNotif
                 - tnGenericUNMRaisedNotif
                 - tnGenericUNMClearedNotif
                 - tnGenericUNPrRaisedNotif
                 - tnGenericUNPrClearedNotif
                 - tnGenericRDIRaisedNotif
                 - tnGenericRDIClearedNotif
                 - tnGenericUNPRaisedNotif
                 - tnGenericUNPClearedNotif
                 - tnGenericNuatRaisedNotif
                 - tnGenericNuatClearedNotif
                 - tnGenericFuatRaisedNotif
                 - tnGenericFuatClearedNotif
                 - tnGenericAutoLaserOffDueToUpstreamFaultRaisedNotif
                 - tnGenericAutoLaserOffDueToUpstreamFaultClearedNotif
                 Added none(0) to TropicGenericTrapObjectValueType.
                 Added alarms with missing group to tnGenericAlarmNotifsGroup.
                 Added conformance groups for:
                 - tnGenericConfigurationChangeNotifsGroup
                 - tnGenericStateChangeNotifsGroup
                 - tnGenericTreeUpdateNotifsGroup"

    REVISION    "201703061200Z"
    DESCRIPTION "Renamed following traps:
                 tnGenericBackwardDefectIndicationEgressRaisedNotif to
                 tnGenericBackwardDefectIndicationRaisedNotif,
                 tnGenericBackwardDefectIndicationEgressClearedNotif to
                 tnGenericBackwardDefectIndicationClearedNotif,
                 tnGenericBdiOduOutRaisedNotif to
                 tnGenericOduBackwardDefectIndicationRaisedNotif,
                 tnGenericBdiOduOutClearedNotif to
                 tnGenericOduBackwardDefectIndicationClearedNotif,
                 tnGenericTBbeOdu1DayOutRaisedNotif to
                 tnGenericTBbeOdu1DayRaisedNotif,
                 tnGenericTBbeOdu1DayOutClearedNotif to
                 tnGenericTBbeOdu1DayClearedNotif
                 tnGenericTimOduOutRaisedNotif to
                 tnGenericOduTrailTraceIdentifierMismatchRaisedNotif
                 tnGenericTimOduOutClearedNotif to
                 tnGenericOduTrailTraceIdentifierMismatchClearedNotif,
                 Added following traps:
                 tnGenericOduSignalDegradeRaisedNotif,
                 tnGenericOduSignalDegradeClearedNotif,
                 tnGenericOduServerSignalFailureRaisedNotif,
                 tnGenericOduServerSignalFailureClearedNotif,
                 tnGenericOduUruPRaisedNotif, tnGenericOduUruPClearedNotif,
                 tnGenericTcmUruPRaisedNotif, tnGenericTcmUruPClearedNotif
                 tnGenericApsWorkingForceSwitchedToProtectRaisedNotif,
                 tnGenericApsWorkingForceSwitchedToProtectClearedNotif,
                 tnGenericTSesOdu15MinRaisedNotif,
                 tnGenericTSesOdu15MinClearedNotif,
                 tnGenericTSesOdu1DayRaisedNotif,
                 tnGenericTSesOdu1DayClearedNotif,
                 tnGenericTSesOtu15MinRaisedNotif,
                 tnGenericTSesOtu15MinClearedNotif,
                 tnGenericTSesOtu1DayRaisedNotif,
                 tnGenericTSesOtu1DayClearedNotif,
                 tnGenericTSesTcm15MinRaisedNotif,
                 tnGenericTSesTcm15MinClearedNotif,
                 tnGenericTSesTcm1DayRaisedNotif,
                 tnGenericTSesTcm1DayClearedNotif,
                 tnGenericTUasOdu15MinRaisedNotif,
                 tnGenericTUasOdu15MinClearedNotif,
                 tnGenericTUasOdu1DayRaisedNotif,
                 tnGenericTUasOdu1DayClearedNotif,
                 tnGenericTUasOtu15MinRaisedNotif,
                 tnGenericTUasOtu15MinClearedNotif,
                 tnGenericTUasOtu1DayRaisedNotif,
                 tnGenericTUasOtu1DayClearedNotif,
                 tnGenericTUasTcm15MinRaisedNotif,
                 tnGenericTUasTcm15MinClearedNotif,
                 tnGenericTUasTcm1DayRaisedNotif,
                 tnGenericTUasTcm1DayClearedNotif.
                 Changed the syntax of tnGenericTrapTime to Unsigned32."

    REVISION    "201702061200Z"
    DESCRIPTION "Added tnGenericSecurityAddAccountNotif,
                 tnGenericSecurityDeleteAccountNotif,
                 tnGenericSecurityChangeAccountNotif.
                 Added range to tnGenericLastIssuedTrapNumber.
                 Added tnGenericSecurityLoginNotif,
                 tnGenericSecurityLogoutNotif."

    REVISION    "201612211200Z"
    DESCRIPTION "Initial version."

    ::= { tnSystemModules 12 }

-------------------------------------------------------------------------------
-- Groups in the Generic Notification MIB Module
-------------------------------------------------------------------------------

tnGenericTrapBuffer                     OBJECT IDENTIFIER ::= { tnGenericNotificationMIB 1 }
tnGenericTrapBufferObjects              OBJECT IDENTIFIER ::= { tnGenericTrapBuffer 1 }
tnGenericTrapBufferConformance          OBJECT IDENTIFIER ::= { tnGenericTrapBuffer 2 }
tnGenericTrapBufferCompliances          OBJECT IDENTIFIER ::= { tnGenericTrapBufferConformance 1 }
tnGenericTrapBufferGroups               OBJECT IDENTIFIER ::= { tnGenericTrapBufferConformance 2 }

tnGenericTrap                           OBJECT IDENTIFIER ::= { tnGenericNotificationMIB 2 }
tnGenericTrapNotifs                     OBJECT IDENTIFIER ::= { tnGenericTrap 0 }
tnGenericTrapObjects                    OBJECT IDENTIFIER ::= { tnGenericTrap 1 }
tnGenericTrapConformance                OBJECT IDENTIFIER ::= { tnGenericTrap 2 }
tnGenericTrapCompliances                OBJECT IDENTIFIER ::= { tnGenericTrapConformance 1 }
tnGenericTrapGroups                     OBJECT IDENTIFIER ::= { tnGenericTrapConformance 2 }

tnGenericAlarm                          OBJECT IDENTIFIER ::= { tnGenericNotificationMIB 3 }
tnGenericAlarmNotifs                    OBJECT IDENTIFIER ::= { tnGenericAlarm 0 }
tnGenericAlarmConformance               OBJECT IDENTIFIER ::= { tnGenericAlarm 2 }
tnGenericAlarmCompliances               OBJECT IDENTIFIER ::= { tnGenericAlarmConformance 1 }
tnGenericAlarmGroups                    OBJECT IDENTIFIER ::= { tnGenericAlarmConformance 2 }

tnGenericEvent                          OBJECT IDENTIFIER ::= { tnGenericNotificationMIB 4 }
tnGenericEventNotifs                    OBJECT IDENTIFIER ::= { tnGenericEvent 0 }
tnGenericEventConformance               OBJECT IDENTIFIER ::= { tnGenericEvent 2 }
tnGenericEventCompliances               OBJECT IDENTIFIER ::= { tnGenericEventConformance 1 }
tnGenericEventGroups                    OBJECT IDENTIFIER ::= { tnGenericEventConformance 2 }

tnGenericScalar                         OBJECT IDENTIFIER ::= { tnGenericNotificationMIB 5 }
tnGenericScalarNotifs                   OBJECT IDENTIFIER ::= { tnGenericScalar 0 }
tnGenericScalarConformance              OBJECT IDENTIFIER ::= { tnGenericScalar 2 }
tnGenericScalarCompliances              OBJECT IDENTIFIER ::= { tnGenericScalarConformance 1 }
tnGenericScalarGroups                   OBJECT IDENTIFIER ::= { tnGenericScalarConformance 2 }

tnGenericInterface                      OBJECT IDENTIFIER ::= { tnGenericNotificationMIB 6 }
tnGenericInterfaceNotifs                OBJECT IDENTIFIER ::= { tnGenericInterface 0 }
tnGenericInterfaceConformance           OBJECT IDENTIFIER ::= { tnGenericInterface 2 }
tnGenericInterfaceCompliances           OBJECT IDENTIFIER ::= { tnGenericInterfaceConformance 1 }
tnGenericInterfaceGroups                OBJECT IDENTIFIER ::= { tnGenericInterfaceConformance 2 }

tnGenericOptIf                          OBJECT IDENTIFIER ::= { tnGenericNotificationMIB 7 }
tnGenericOptIfNotifs                    OBJECT IDENTIFIER ::= { tnGenericOptIf 0 }
tnGenericOptIfConformance               OBJECT IDENTIFIER ::= { tnGenericOptIf 2 }
tnGenericOptIfCompliances               OBJECT IDENTIFIER ::= { tnGenericOptIfConformance 1 }
tnGenericOptIfGroups                    OBJECT IDENTIFIER ::= { tnGenericOptIfConformance 2 }

tnGenericTnAccessPort                   OBJECT IDENTIFIER ::= { tnGenericNotificationMIB 8 }
tnGenericTnAccessPortNotifs             OBJECT IDENTIFIER ::= { tnGenericTnAccessPort 0 }
tnGenericTnAccessPortConformance        OBJECT IDENTIFIER ::= { tnGenericTnAccessPort 2 }
tnGenericTnAccessPortCompliances        OBJECT IDENTIFIER ::= { tnGenericTnAccessPortConformance 1 }
tnGenericTnAccessPortGroups             OBJECT IDENTIFIER ::= { tnGenericTnAccessPortConformance 2 }

tnGenericTnOpticalPort                  OBJECT IDENTIFIER ::= { tnGenericNotificationMIB 9 }
tnGenericTnOpticalPortNotifs            OBJECT IDENTIFIER ::= { tnGenericTnOpticalPort 0 }
tnGenericTnOpticalPortConformance       OBJECT IDENTIFIER ::= { tnGenericTnOpticalPort 2 }
tnGenericTnOpticalPortCompliances       OBJECT IDENTIFIER ::= { tnGenericTnOpticalPortConformance 1 }
tnGenericTnOpticalPortGroups            OBJECT IDENTIFIER ::= { tnGenericTnOpticalPortConformance 2 }

tnGenericTnOtuOdu                       OBJECT IDENTIFIER ::= { tnGenericNotificationMIB 10 }
tnGenericTnOtuOduNotifs                 OBJECT IDENTIFIER ::= { tnGenericTnOtuOdu 0 }
tnGenericTnOtuOduConformance            OBJECT IDENTIFIER ::= { tnGenericTnOtuOdu 2 }
tnGenericTnOtuOduCompliances            OBJECT IDENTIFIER ::= { tnGenericTnOtuOduConformance 1 }
tnGenericTnOtuOduGroups                 OBJECT IDENTIFIER ::= { tnGenericTnOtuOduConformance 2 }

tnGenericTnOth                          OBJECT IDENTIFIER ::= { tnGenericNotificationMIB 11 }
tnGenericTnOthNotifs                    OBJECT IDENTIFIER ::= { tnGenericTnOth 0 }
tnGenericTnOthConformance               OBJECT IDENTIFIER ::= { tnGenericTnOth 2 }
tnGenericTnOthCompliances               OBJECT IDENTIFIER ::= { tnGenericTnOthConformance 1 }
tnGenericTnOthGroups                    OBJECT IDENTIFIER ::= { tnGenericTnOthConformance 2 }

tnGenericTnL1Service                    OBJECT IDENTIFIER ::= { tnGenericNotificationMIB 12 }
tnGenericTnL1ServiceNotifs              OBJECT IDENTIFIER ::= { tnGenericTnL1Service 0 }
tnGenericTnL1ServiceConformance         OBJECT IDENTIFIER ::= { tnGenericTnL1Service 2 }
tnGenericTnL1ServiceCompliances         OBJECT IDENTIFIER ::= { tnGenericTnL1ServiceConformance 1 }
tnGenericTnL1ServiceGroups              OBJECT IDENTIFIER ::= { tnGenericTnL1ServiceConformance 2 }

tnGenericTnStatistics                   OBJECT IDENTIFIER ::= { tnGenericNotificationMIB 13 }
tnGenericTnStatisticsNotifs             OBJECT IDENTIFIER ::= { tnGenericTnStatistics 0 }
tnGenericTnStatisticsConformance        OBJECT IDENTIFIER ::= { tnGenericTnStatistics 2 }
tnGenericTnStatisticsCompliances        OBJECT IDENTIFIER ::= { tnGenericTnStatisticsConformance 1 }
tnGenericTnStatisticsGroups             OBJECT IDENTIFIER ::= { tnGenericTnStatisticsConformance 2 }

tnGenericTnLag                          OBJECT IDENTIFIER ::= { tnGenericNotificationMIB 14 }
tnGenericTnLagNotifs                    OBJECT IDENTIFIER ::= { tnGenericTnLag 0 }
tnGenericTnLagConformance               OBJECT IDENTIFIER ::= { tnGenericTnLag 2 }
tnGenericTnLagCompliances               OBJECT IDENTIFIER ::= { tnGenericTnLagConformance 1 }
tnGenericTnLagGroups                    OBJECT IDENTIFIER ::= { tnGenericTnLagConformance 2 }

tnGenericTnPmon                         OBJECT IDENTIFIER ::= { tnGenericNotificationMIB 15 }
tnGenericTnPmonNotifs                   OBJECT IDENTIFIER ::= { tnGenericTnPmon 0 }
tnGenericTnPmonConformance              OBJECT IDENTIFIER ::= { tnGenericTnPmon 2 }
tnGenericTnPmonCompliances              OBJECT IDENTIFIER ::= { tnGenericTnPmonConformance 1 }
tnGenericTnPmonGroups                   OBJECT IDENTIFIER ::= { tnGenericTnPmonConformance 2 }

tnGenericTnPort                         OBJECT IDENTIFIER ::= { tnGenericNotificationMIB 16 }
tnGenericTnPortNotifs                   OBJECT IDENTIFIER ::= { tnGenericTnPort 0 }
tnGenericTnPortConformance              OBJECT IDENTIFIER ::= { tnGenericTnPort 2 }
tnGenericTnPortCompliances              OBJECT IDENTIFIER ::= { tnGenericTnPortConformance 1 }
tnGenericTnPortGroups                   OBJECT IDENTIFIER ::= { tnGenericTnPortConformance 2 }

tnGenericDot1agCfm                      OBJECT IDENTIFIER ::= { tnGenericNotificationMIB 17 }
tnGenericDot1agCfmNotifs                OBJECT IDENTIFIER ::= { tnGenericDot1agCfm 0 }
tnGenericDot1agCfmConformance           OBJECT IDENTIFIER ::= { tnGenericDot1agCfm 2 }
tnGenericDot1agCfmCompliances           OBJECT IDENTIFIER ::= { tnGenericDot1agCfmConformance 1 }
tnGenericDot1agCfmGroups                OBJECT IDENTIFIER ::= { tnGenericDot1agCfmConformance 2 }

tnGenericTnDot1agCfm                    OBJECT IDENTIFIER ::= { tnGenericNotificationMIB 18 }
tnGenericTnDot1agCfmNotifs              OBJECT IDENTIFIER ::= { tnGenericTnDot1agCfm 0 }
tnGenericTnDot1agCfmConformance         OBJECT IDENTIFIER ::= { tnGenericTnDot1agCfm 2 }
tnGenericTnDot1agCfmCompliances         OBJECT IDENTIFIER ::= { tnGenericTnDot1agCfmConformance 1 }
tnGenericTnDot1agCfmGroups              OBJECT IDENTIFIER ::= { tnGenericTnDot1agCfmConformance 2 }

tnGenericTnOamTest                      OBJECT IDENTIFIER ::= { tnGenericNotificationMIB 19 }
tnGenericTnOamTestNotifs                OBJECT IDENTIFIER ::= { tnGenericTnOamTest 0 }
tnGenericTnOamTestConformance           OBJECT IDENTIFIER ::= { tnGenericTnOamTest 2 }
tnGenericTnOamTestCompliances           OBJECT IDENTIFIER ::= { tnGenericTnOamTestConformance 1 }
tnGenericTnOamTestGroups                OBJECT IDENTIFIER ::= { tnGenericTnOamTestConformance 2 }

tnGenericRadius                         OBJECT IDENTIFIER ::= { tnGenericNotificationMIB 20 }
tnGenericRadiusNotifs                   OBJECT IDENTIFIER ::= { tnGenericRadius 0 }
tnGenericRadiusConformance              OBJECT IDENTIFIER ::= { tnGenericRadius 2 }
tnGenericRadiusCompliances              OBJECT IDENTIFIER ::= { tnGenericRadiusConformance 1 }
tnGenericRadiusGroups                   OBJECT IDENTIFIER ::= { tnGenericRadiusConformance 2 }

tnGenericSyslog                         OBJECT IDENTIFIER ::= { tnGenericNotificationMIB 21 }
tnGenericSyslogNotifs                   OBJECT IDENTIFIER ::= { tnGenericSyslog 0 }
tnGenericSyslogConformance              OBJECT IDENTIFIER ::= { tnGenericSyslog 2 }
tnGenericSyslogCompliances              OBJECT IDENTIFIER ::= { tnGenericSyslogConformance 1 }
tnGenericSyslogGroups                   OBJECT IDENTIFIER ::= { tnGenericSyslogConformance 2 }

tnGenericTransferPMDiscovery            OBJECT IDENTIFIER ::= { tnGenericNotificationMIB 22 }
tnGenericTransferPMDiscoveryNotifs      OBJECT IDENTIFIER ::= { tnGenericTransferPMDiscovery 0 }
tnGenericTransferPMDiscoveryConformance OBJECT IDENTIFIER ::= { tnGenericTransferPMDiscovery 2 }
tnGenericTransferPMDiscoveryCompliances OBJECT IDENTIFIER ::= { tnGenericTransferPMDiscoveryConformance 1 }
tnGenericTransferPMDiscoveryGroups      OBJECT IDENTIFIER ::= { tnGenericTransferPMDiscoveryConformance 2 }

-------------------------------------------------------------------------------
-- Type Definitions
-------------------------------------------------------------------------------

TropicGenericTrapObjectValueType ::= TEXTUAL-CONVENTION
    STATUS         current
    DESCRIPTION    "The type of the changed object value.
                    Value none(0) indicates that no object
                    value is referenced."
    SYNTAX         INTEGER {
                       none(0),
                       counter32(1),
                       unsigned32(2),
                       timeTicks(3),
                       integer32(4),
                       ipAddress(5),
                       octetString(6),
                       objectId(7),
                       counter64(8)
                   }

-------------------------------------------------------------------------------
-- Generic Trap Buffer Table
-------------------------------------------------------------------------------

tnGenericTrapBufferTable OBJECT-TYPE
    SYNTAX         SEQUENCE OF TnGenericTrapBufferEntry
    MAX-ACCESS     not-accessible
    STATUS         current
    DESCRIPTION    "This table serves as a circular trap buffer for all
                    trap notifications destined for a Network Management
                    Station (NMS). When a trap event occurs, it is
                    copied into this table.  Subsequently, a trap
                    notification is sent to the NMS. If the NMS
                    temporarily loses its connection with the node
                    agent, any trap notifications missed during the
                    outage may be recovered from this table.  The
                    NMS can do this by referring to the sequence number
                    associated with the last received trap before the
                    outage and the sequence number associated with the
                    last missed trap sent by the node agent during the
                    outage. The sequence number of the last missed trap
                    can be determined by getting the value of object
                    tnGenericLastIssuedTrapNumber from the node agent."
    ::= { tnGenericTrapBufferObjects 1 }

tnGenericTrapBufferEntry OBJECT-TYPE
    SYNTAX         TnGenericTrapBufferEntry
    MAX-ACCESS     not-accessible
    STATUS         current
    DESCRIPTION    "Entry in tnGenericTrapBufferTable."
    INDEX          { tnGenericTrapNumber }
    ::= { tnGenericTrapBufferTable 1 }

TnGenericTrapBufferEntry ::=
    SEQUENCE {
        tnGenericTrapNumber                         Unsigned32,
        tnGenericTrapType                           OBJECT IDENTIFIER,
        tnGenericTrapObject                         OBJECT IDENTIFIER,
        tnGenericTrapObjectInstance                 SnmpAdminString,
        tnGenericTrapTime                           Unsigned32,
        tnGenericTrapCategory                       TnTrapCategory,
        tnGenericTrapDescr                          SnmpAdminString,
        tnGenericTrapData                           SnmpAdminString,
        tnGenericTrapServiceAffecting               TruthValue,
        tnGenericTrapCondition                      TnCondition,
        tnGenericTrapObjectValueType                TropicGenericTrapObjectValueType,
        tnGenericTrapObjectCounter32Val             Counter32,
        tnGenericTrapObjectUnsigned32Val            Unsigned32,
        tnGenericTrapObjectTimeTicksVal             TimeTicks,
        tnGenericTrapObjectInteger32Val             Integer32,
        tnGenericTrapObjectOctetStringVal           OCTET STRING,
        tnGenericTrapObjectIpAddressVal             IpAddress,
        tnGenericTrapObjectOidVal                   OBJECT IDENTIFIER,
        tnGenericTrapObjectCounter64Val             Counter64,
        tnGenericTrapDateAndTime                    DateAndTime,
        tnGenericTrapConfigurationChangeCounter     Unsigned32,
        tnGenericTrapEntityType                     TnEntityType
}

tnGenericTrapNumber OBJECT-TYPE
    SYNTAX         Unsigned32 (1..4294967295)
    MAX-ACCESS     not-accessible
    STATUS         current
    DESCRIPTION    "The independently incremented number associated
                    with the sequential ordering of traps."
    ::= { tnGenericTrapBufferEntry 1 }

tnGenericTrapType OBJECT-TYPE
    SYNTAX         OBJECT IDENTIFIER
    MAX-ACCESS     read-only
    STATUS         current
    DESCRIPTION    "The OID of the notification."
    ::= { tnGenericTrapBufferEntry 2 }

tnGenericTrapObject OBJECT-TYPE
    SYNTAX         OBJECT IDENTIFIER
    MAX-ACCESS     read-only
    STATUS         current
    DESCRIPTION    "OID of the object instance for which the trap
                    is issued."
    ::= { tnGenericTrapBufferEntry 3 }

tnGenericTrapObjectInstance OBJECT-TYPE
    SYNTAX         SnmpAdminString
    MAX-ACCESS     read-only
    STATUS         current
    DESCRIPTION    "Instance in ASCII string format of the object
                    for which the trap is issued."
    ::= { tnGenericTrapBufferEntry 4 }

tnGenericTrapTime OBJECT-TYPE
    SYNTAX         Unsigned32
    MAX-ACCESS     read-only
    STATUS         current
    DESCRIPTION    "The time at which the trap occurred, measured in
                    time ticks (seconds) from the year 1970."
    ::= { tnGenericTrapBufferEntry 5 }

tnGenericTrapCategory OBJECT-TYPE
    SYNTAX         TnTrapCategory
    MAX-ACCESS     read-only
    STATUS         current
    DESCRIPTION    "The trap category."
    ::= { tnGenericTrapBufferEntry 6 }

tnGenericTrapDescr OBJECT-TYPE
    SYNTAX         SnmpAdminString (SIZE(0..255))
    MAX-ACCESS     read-only
    STATUS         current
    DESCRIPTION    "A detailed description of the trap."
    ::= { tnGenericTrapBufferEntry 7 }

tnGenericTrapData OBJECT-TYPE
    SYNTAX         SnmpAdminString (SIZE(0..255))
    MAX-ACCESS     read-only
    STATUS         current
    DESCRIPTION    "Any application specific data relevant to the trap.
                    This could be the value of a changed attribute or
                    any other formatted information related to a
                    notification."
    ::= { tnGenericTrapBufferEntry 8 }

tnGenericTrapServiceAffecting OBJECT-TYPE
    SYNTAX         TruthValue
    MAX-ACCESS     read-only
    STATUS         current
    DESCRIPTION    "An indication as to whether or not this trap is
                    service affecting."
    ::= { tnGenericTrapBufferEntry 9 }

tnGenericTrapCondition OBJECT-TYPE
    SYNTAX         TnCondition
    MAX-ACCESS     read-only
    STATUS         current
    DESCRIPTION    "The condition."
    ::= { tnGenericTrapBufferEntry 10 }

tnGenericTrapObjectValueType OBJECT-TYPE
    SYNTAX         TropicGenericTrapObjectValueType
    MAX-ACCESS     read-only
    STATUS         current
    DESCRIPTION    "The type of the value. One and only one of the
                    value objects that follow must be instantiated,
                    based on this type."
    ::= { tnGenericTrapBufferEntry 11 }

tnGenericTrapObjectCounter32Val OBJECT-TYPE
    SYNTAX         Counter32
    MAX-ACCESS     read-only
    STATUS         current
    DESCRIPTION    "The value when tnGenericTrapObjectType is 'counter32'."
    ::= { tnGenericTrapBufferEntry 12 }

tnGenericTrapObjectUnsigned32Val OBJECT-TYPE
    SYNTAX         Unsigned32
    MAX-ACCESS     read-only
    STATUS         current
    DESCRIPTION    "The value when tnGenericTrapObjectType is 'unsigned32'."
    ::= { tnGenericTrapBufferEntry 13 }

tnGenericTrapObjectTimeTicksVal OBJECT-TYPE
    SYNTAX         TimeTicks
    MAX-ACCESS     read-only
    STATUS         current
    DESCRIPTION    "The value when tnGenericTrapObjectType is 'timeTicks'."
    ::= { tnGenericTrapBufferEntry 14 }

tnGenericTrapObjectInteger32Val OBJECT-TYPE
    SYNTAX         Integer32
    MAX-ACCESS     read-only
    STATUS         current
    DESCRIPTION    "The value when tnGenericTrapObjectType is 'integer32'."
    ::= { tnGenericTrapBufferEntry 15 }

tnGenericTrapObjectOctetStringVal OBJECT-TYPE
    SYNTAX         OCTET STRING
    MAX-ACCESS     read-only
    STATUS         current
    DESCRIPTION    "The value when tnGenericTrapObjectType is 'octetString'."
    ::= { tnGenericTrapBufferEntry 16 }

tnGenericTrapObjectIpAddressVal OBJECT-TYPE
    SYNTAX         IpAddress
    MAX-ACCESS     read-only
    STATUS         current
    DESCRIPTION    "The value when tnGenericTrapObjectType is 'ipAddress'.
                    Although this seems to be unfriendly for IPv6, we
                    have to recognize that there are a number of older
                    MIBs that do contain an IPv4 format address, known
                    as IpAddress.

                    IPv6 addresses are represented using TAddress or
                    InetAddress, and so the underlying datatype is
                    OCTET STRING, and their value would be stored in
                    the tnGenericTrapObjectOctetStringVal column."
    ::= { tnGenericTrapBufferEntry 17 }

tnGenericTrapObjectOidVal OBJECT-TYPE
    SYNTAX         OBJECT IDENTIFIER
    MAX-ACCESS     read-only
    STATUS         current
    DESCRIPTION    "The value when tnGenericTrapObjectType is 'objectId'."
    ::= { tnGenericTrapBufferEntry 18 }

tnGenericTrapObjectCounter64Val OBJECT-TYPE
    SYNTAX         Counter64
    MAX-ACCESS     read-only
    STATUS         current
    DESCRIPTION    "The value when tnGenericTrapObjectType is 'counter64'."
    ::= { tnGenericTrapBufferEntry 19 }

tnGenericTrapDateAndTime OBJECT-TYPE
    SYNTAX         DateAndTime
    MAX-ACCESS     read-only
    STATUS         current
    DESCRIPTION    "The date and time (UTC) at which the trap occurred."
    ::= { tnGenericTrapBufferEntry 20 }

tnGenericTrapConfigurationChangeCounter OBJECT-TYPE
    SYNTAX         Unsigned32
    MAX-ACCESS     read-only
    STATUS         current
    DESCRIPTION    "The trap configuration change counter.
                    Value 0 indicates that the counter is not applicable
                    for the this trap."
    ::= { tnGenericTrapBufferEntry 21 }

tnGenericTrapEntityType OBJECT-TYPE
    SYNTAX         TnEntityType
    MAX-ACCESS     read-only
    STATUS         current
    DESCRIPTION    "The entity type."
    ::= { tnGenericTrapBufferEntry 22 }

-------------------------------------------------------------------------------
-- Generic Trap Buffer Scalar Objects
-------------------------------------------------------------------------------

tnGenericLastIssuedTrapNumber OBJECT-TYPE
    SYNTAX         Unsigned32(1..4294967295)
    MAX-ACCESS     read-only
    STATUS         current
    DESCRIPTION    "The sequence number of last issued trap."
    ::= { tnGenericTrapBufferObjects 2 }

tnGenericTrapNumberResetToBeHandled OBJECT-TYPE
    SYNTAX         TruthValue
    MAX-ACCESS     read-write
    STATUS         current
    DESCRIPTION    "The value is true if the trap sequence number was
                    reset over the last network element restart.
                    It may be set to false if the NMS determines
                    that this condition no longer needs to be handled.
                    Sets with a value of true are ignored."
    ::= { tnGenericTrapBufferObjects 3 }

-------------------------------------------------------------------------------
-- Generic Trap Scalar Objects
-------------------------------------------------------------------------------

tnGenericTrapSeqNumber OBJECT-TYPE
    SYNTAX         Unsigned32
    MAX-ACCESS     accessible-for-notify
    STATUS         current
    DESCRIPTION    "The sequence number of the issued trap."
    ::= { tnGenericTrapObjects 1 }

tnGenericTrapOthOdukApsAction OBJECT-TYPE
    SYNTAX         INTEGER {
                     create(1),
                     delete(2),
                     update(3),
                     convertToProt(4),
                     convertToUnprot(5),
                     noCommand(6),
                     convertToUnprotFroming(7)
                   }
    MAX-ACCESS     accessible-for-notify
    STATUS         current
    DESCRIPTION    "The action command to control the APS group."
    ::= { tnGenericTrapObjects 2 }

tnGenericTrapOthOdukApsFromedIfIndex OBJECT-TYPE
    SYNTAX         Integer32
    MAX-ACCESS     accessible-for-notify
    STATUS         current
    DESCRIPTION    "The interface Index (high-order part) of the
                    ODUk entity in the working leg of the APS."
    ::= { tnGenericTrapObjects 3 }

tnGenericTrapOthOdukApsFromedIfIndexLo OBJECT-TYPE
    SYNTAX         Integer32
    MAX-ACCESS     accessible-for-notify
    STATUS         current
    DESCRIPTION    "The interface Index (low-order part)  of the
                    ODUk entity in the working leg of the APS."
    ::= { tnGenericTrapObjects 4 }

tnGenericTrapOthOdukApsFromingIfIndex OBJECT-TYPE
    SYNTAX         Integer32
    MAX-ACCESS     accessible-for-notify
    STATUS         current
    DESCRIPTION    "The interface Index (high-order part) of the
                    ODUk entity in the protection leg of the APS."
    ::= { tnGenericTrapObjects 5 }

tnGenericTrapOthOdukApsFromingIfIndexLo OBJECT-TYPE
    SYNTAX         Integer32
    MAX-ACCESS     accessible-for-notify
    STATUS         current
    DESCRIPTION    "The interface Index (low-order part)  of the
                    ODUk entity in the protection leg of the APS."
    ::= { tnGenericTrapObjects 6 }

-------------------------------------------------------------------------------
-- Generic Trap Notifications
-------------------------------------------------------------------------------

tnGenericConfigurationChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Generic configuration change notification."
::= { tnGenericTrapNotifs 1 }

tnGenericStateChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime
    }
    STATUS current
    DESCRIPTION "Generic state change notification."
::= { tnGenericTrapNotifs 2 }

tnGenericTreeUpdateNotif NOTIFICATION-TYPE
    OBJECTS {
        tnGenericTrapSeqNumber,
        tnGenericTrapObject,
        tnGenericTrapObjectInstance,
        tnGenericTrapTime,
        tnGenericTrapDateAndTime,
        tnGenericTrapCategory,
        tnGenericTrapConfigurationChangeCounter
    }
    STATUS      current
    DESCRIPTION "Generic tree update notification."
::= { tnGenericTrapNotifs 3 }

-------------------------------------------------------------------------------
-- Generic Alarm Notifications
-------------------------------------------------------------------------------

tnGenericBackwardDefectIndicationRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Backward Defect Indication raise notification."
    ::= { tnGenericAlarmNotifs 1 }

tnGenericBackwardDefectIndicationClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Backward Defect Indication Egress clear notification."
    ::= { tnGenericAlarmNotifs 2 }

tnGenericOduBackwardDefectIndicationRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Backward Defect Indication ODU raise notification."
    ::= { tnGenericAlarmNotifs 3 }

tnGenericOduBackwardDefectIndicationClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Backward Defect Indication ODU clear notification."
    ::= { tnGenericAlarmNotifs 4 }

tnGenericTcmBackwardDefectIndicationRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Backward Defect Indication TCM raise notification."
    ::= { tnGenericAlarmNotifs 5 }

tnGenericTcmBackwardDefectIndicationClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Backward Defect Indication TCM clear notification."
    ::= { tnGenericAlarmNotifs 6 }

tnGenericCommDownRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss of in band communication raise notification."
    ::= { tnGenericAlarmNotifs 7 }

tnGenericCommDownClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss of in band communication clear notification."
    ::= { tnGenericAlarmNotifs 8 }

tnGenericSignalDegradeRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Signal degrade raise notification."
    ::= { tnGenericAlarmNotifs 9 }

tnGenericSignalDegradeClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Signal degrade clear notification."
    ::= { tnGenericAlarmNotifs 10 }

tnGenericOduSignalDegradeRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Signal degrade ODU raise notification."
    ::= { tnGenericAlarmNotifs 11 }

tnGenericOduSignalDegradeClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Signal degrade ODU clear notification."
    ::= { tnGenericAlarmNotifs 12 }

tnGenericTcmSignalDegradeRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Signal degrade TCM raise notification."
    ::= { tnGenericAlarmNotifs 13 }

tnGenericTcmSignalDegradeClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Signal degrade TCM clear notification."
    ::= { tnGenericAlarmNotifs 14 }

tnGenericBoardEqptRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Board equipment failure raise notification."
    ::= { tnGenericAlarmNotifs 15 }

tnGenericBoardEqptClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Board equipment failure clear notification."
    ::= { tnGenericAlarmNotifs 16 }

tnGenericEqptPortRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Equipment port raise notification."
    ::= { tnGenericAlarmNotifs 17 }

tnGenericEqptPortClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Equipment port clear notification."
    ::= { tnGenericAlarmNotifs 18 }

tnGenericIntTempHighRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Internal temperature high raise notification."
    ::= { tnGenericAlarmNotifs 19 }

tnGenericIntTempHighClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Internal temperature high clear notification."
    ::= { tnGenericAlarmNotifs 20 }

tnGenericLockedIndicationRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Locked indication raise notification."
    ::= { tnGenericAlarmNotifs 21 }

tnGenericLockedIndicationClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Locked indication clear notification."
    ::= { tnGenericAlarmNotifs 22 }

tnGenericTcmLockedIndicationRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Locked indication TCM raise notification."
    ::= { tnGenericAlarmNotifs 23 }

tnGenericTcmLockedIndicationClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Locked indication TCM clear notification."
    ::= { tnGenericAlarmNotifs 24 }

tnGenericDwLossOfFrameRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Frame raise notification."
    ::= { tnGenericAlarmNotifs 25 }

tnGenericDwLossOfFrameClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Frame clear notification."
    ::= { tnGenericAlarmNotifs 26 }

tnGenericDwLossOfMultiFrameRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Multi Frame raise notification."
    ::= { tnGenericAlarmNotifs 27 }

tnGenericDwLossOfMultiFrameClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Multi Frame clear notification."
    ::= { tnGenericAlarmNotifs 28 }

tnGenericLossOfSignalRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Signal raise notification."
    ::= { tnGenericAlarmNotifs 29 }

tnGenericLossOfSignalClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Signal clear notification."
    ::= { tnGenericAlarmNotifs 30 }

tnGenericTcmLossofTandemConnectionRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss of Tandem Connection raise notification."
    ::= { tnGenericAlarmNotifs 31 }

tnGenericTcmLossofTandemConnectionClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss of Tandem Connection clear notification."
    ::= { tnGenericAlarmNotifs 32 }

tnGenericInMaintenanceRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "In Maintenance raise notification."
    ::= { tnGenericAlarmNotifs 33 }

tnGenericInMaintenanceClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "In Maintenance clear notification."
    ::= { tnGenericAlarmNotifs 34 }

tnGenericOpticsModuleMismatchRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optics Module Mismatch raise notification."
    ::= { tnGenericAlarmNotifs 35 }

tnGenericOpticsModuleMismatchClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optics Module Mismatch clear notification."
    ::= { tnGenericAlarmNotifs 36 }

tnGenericOpenConnectionIndicationRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Open Connection Indication raise notification."
    ::= { tnGenericAlarmNotifs 37 }

tnGenericOpenConnectionIndicationClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Open Connection Indication clear notification."
    ::= { tnGenericAlarmNotifs 38 }

tnGenericTcmOpenConnectionIndicationRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Open Connection Indication TCM raise notification."
    ::= { tnGenericAlarmNotifs 39 }

tnGenericTcmOpenConnectionIndicationClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Open Connection Indication TCM clear notification."
    ::= { tnGenericAlarmNotifs 40 }

tnGenericReplUnitMissMODRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Replaceable Unit Missing - module raise notification."
    ::= { tnGenericAlarmNotifs 41 }

tnGenericReplUnitMissMODClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Replaceable Unit Missing - module clear notification."
    ::= { tnGenericAlarmNotifs 42 }

tnGenericServerSignalFailureEgressRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Server Signal Failure Egress raise notification."
    ::= { tnGenericAlarmNotifs 43 }

tnGenericServerSignalFailureEgressClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Server Signal Failure Egress clear notification."
    ::= { tnGenericAlarmNotifs 44 }

tnGenericServerSignalFailureRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Server Signal Failure raise notification."
    ::= { tnGenericAlarmNotifs 45 }

tnGenericServerSignalFailureClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Server Signal Failure clear notification."
    ::= { tnGenericAlarmNotifs 46 }

tnGenericOduServerSignalFailureRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Server Signal Failure ODU raise notification."
    ::= { tnGenericAlarmNotifs 47 }

tnGenericOduServerSignalFailureClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Server Signal Failure ODU clear notification."
    ::= { tnGenericAlarmNotifs 48 }

tnGenericTcmServerSignalFailureRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Server Signal Failure TCM raise notification."
    ::= { tnGenericAlarmNotifs 49 }

tnGenericTcmServerSignalFailureClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Server Signal Failure TCM clear notification."
    ::= { tnGenericAlarmNotifs 50 }

tnGenericCardInitializingRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Card Initializing raise notification."
    ::= { tnGenericAlarmNotifs 51 }

tnGenericCardInitializingClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Card Initializing clear notification."
    ::= { tnGenericAlarmNotifs 52 }

tnGenericTBbeOdu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 15 minute bin - ODU raise notification."
    ::= { tnGenericAlarmNotifs 53 }

tnGenericTBbeOdu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 15 minute bin - ODU clear notification."
    ::= { tnGenericAlarmNotifs 54 }

tnGenericTBbeOdu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 1 day bin - ODU raise notification."
    ::= { tnGenericAlarmNotifs 55 }

tnGenericTBbeOdu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 1 day bin - ODU clear notification."
    ::= { tnGenericAlarmNotifs 56 }

tnGenericTBbeOtu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 15 minute bin - OTU raise notification."
    ::= { tnGenericAlarmNotifs 57 }

tnGenericTBbeOtu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 15 minute bin - OTU clear notification."
    ::= { tnGenericAlarmNotifs 58 }

tnGenericTBbeOtu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 1 day bin - OTU raise notification."
    ::= { tnGenericAlarmNotifs 59 }

tnGenericTBbeOtu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 1 day bin - OTU clear notification."
    ::= { tnGenericAlarmNotifs 60 }

tnGenericTBbeTcm15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 15 minute bin - TCM raise notification."
    ::= { tnGenericAlarmNotifs 61 }

tnGenericTBbeTcm15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 15 minute bin - TCM clear notification."
    ::= { tnGenericAlarmNotifs 62 }

tnGenericTBbeTcm1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 1 day bin - TCM raise notification."
    ::= { tnGenericAlarmNotifs 63 }

tnGenericTBbeTcm1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count Threshold Crossing Alert Near End
                 1 day bin - TCM clear notification."
    ::= { tnGenericAlarmNotifs 64 }

tnGenericTEsOdu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 15 minute bin - ODU raise notification."
    ::= { tnGenericAlarmNotifs 65 }

tnGenericTEsOdu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 15 minute bin - ODU clear notification."
    ::= { tnGenericAlarmNotifs 66 }

tnGenericTEsOdu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 1 day bin - ODU raise notification."
    ::= { tnGenericAlarmNotifs 67 }

tnGenericTEsOdu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 1 day bin - ODU clear notification."
    ::= { tnGenericAlarmNotifs 68 }

tnGenericTEsOtu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 15 minute bin - OTU raise notification."
    ::= { tnGenericAlarmNotifs 69 }

tnGenericTEsOtu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 15 minute bin - OTU clear notification."
    ::= { tnGenericAlarmNotifs 70 }

tnGenericTEsOtu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 1 day bin - OTU raise notification."
    ::= { tnGenericAlarmNotifs 71 }

tnGenericTEsOtu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 1 day bin - OTU clear notification."
    ::= { tnGenericAlarmNotifs 72 }

tnGenericTEsTcm15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 15 minute bin - TCM raise notification."
    ::= { tnGenericAlarmNotifs 73 }

tnGenericTEsTcm15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 15 minute bin - TCM clear notification."
    ::= { tnGenericAlarmNotifs 74 }

tnGenericTEsTcm1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 1 day bin - TCM  raise notification."
    ::= { tnGenericAlarmNotifs 75 }

tnGenericTEsTcm1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored seconds Threshold Crossing Alert Near End
                 1 day bin - TCM clear notification."
    ::= { tnGenericAlarmNotifs 76 }

tnGenericTFecc15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Forward error correction counter exceeds Threshold Crossing
                 Alert value 15 minute bin raised notification."
    ::= { tnGenericAlarmNotifs 77 }

tnGenericTFecc15MinClearedNotif  NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Forward error correction counter exceeds Threshold Crossing
                 Alert value 15 minute bin clear notification."
    ::= { tnGenericAlarmNotifs 78 }

tnGenericTFecc1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Forward error correction counter exceeds Threshold Crossing
                 Alert value 1 day bin raised notification."
    ::= { tnGenericAlarmNotifs 79 }

tnGenericTFecc1DayClearedNotif  NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Forward error correction counter exceeds Threshold Crossing
                 Alert value 1 day bin clear notification."
    ::= { tnGenericAlarmNotifs 80 }

tnGenericTrailTraceIdentifierMismatchRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Trail Trace Identifier (TTI) Mismatch raise notification."
    ::= { tnGenericAlarmNotifs 81 }

tnGenericTrailTraceIdentifierMismatchClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Trail Trace Identifier (TTI) Mismatch clear notification."
    ::= { tnGenericAlarmNotifs 82 }

tnGenericOduTrailTraceIdentifierMismatchRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "TTI Mismatch ODU out raise notification."
    ::= { tnGenericAlarmNotifs 83 }

tnGenericOduTrailTraceIdentifierMismatchClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "TTI Mismatch ODU out clear notification."
    ::= { tnGenericAlarmNotifs 84 }

tnGenericTcmTrailTraceIdentifierMismatchRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Trail Trace Identifier (TTI) Mismatch TCM raise notification."
    ::= { tnGenericAlarmNotifs 85 }

tnGenericTcmTrailTraceIdentifierMismatchClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Trail Trace Identifier (TTI) Mismatch TCM clear notification."
    ::= { tnGenericAlarmNotifs 86 }

tnGenericOpticsModuleUnknownRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optics Module Unknown raise notification."
    ::= { tnGenericAlarmNotifs 87 }

tnGenericOpticsModuleUnknownClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optics Module Unknown clear notification."
    ::= { tnGenericAlarmNotifs 88 }

tnGenericUruORaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Underlying Resource Unavailable Optical, raise notification."
    ::= { tnGenericAlarmNotifs 89 }

tnGenericUruOClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Underlying Resource Unavailable Optical, clear notification."
    ::= { tnGenericAlarmNotifs 90 }

tnGenericUruPRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Underlying Resource Unavailable Path, raise notification."
    ::= { tnGenericAlarmNotifs 91 }

tnGenericUruPClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Underlying Resource Unavailable Path, clear notification."
    ::= { tnGenericAlarmNotifs 92 }

tnGenericOduUruPRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Underlying Resource Unavailable Path, ODU raise notification."
    ::= { tnGenericAlarmNotifs 93 }

tnGenericOduUruPClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Underlying Resource Unavailable Path, ODU clear notification."
    ::= { tnGenericAlarmNotifs 94 }

tnGenericTcmUruPRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Underlying Resource Unavailable Path, TCM raise notification."
    ::= { tnGenericAlarmNotifs 95 }

tnGenericTcmUruPClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Underlying Resource Unavailable Path, TCM clear notification."
    ::= { tnGenericAlarmNotifs 96 }

tnGenericApsLockoutOfProtectionRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) lockout of protection raise
                 notification."
    ::= { tnGenericAlarmNotifs 97 }

tnGenericApsLockoutOfProtectionClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) lockout of protection clear
                 notification."
    ::= { tnGenericAlarmNotifs 98 }

tnGenericApsWorkingForceSwitchedBackToWorkingRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working force switched back
                 to working raise notification."
    ::= { tnGenericAlarmNotifs 99 }

tnGenericApsWorkingForceSwitchedBackToWorkingClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working force switched back
                 to working clear notification."
    ::= { tnGenericAlarmNotifs 100 }

tnGenericApsWorkingForceSwitchedToProtectRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working force switched to
                 protection raise notification."
    ::= { tnGenericAlarmNotifs 101 }

tnGenericApsWorkingForceSwitchedToProtectClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working force switched to
                 protection clear notification."
    ::= { tnGenericAlarmNotifs 102 }

tnGenericApsWorkingManualSwitchedBackToWorkingRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working manual switched
                 back to working raise notification."
    ::= { tnGenericAlarmNotifs 103 }

tnGenericApsWorkingManualSwitchedBackToWorkingClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working manual switched
                 back to working clear notification."
    ::= { tnGenericAlarmNotifs 104 }

tnGenericApsSwitchedToWorkRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) switched to working raise
                 notification."
    ::= { tnGenericAlarmNotifs 105 }

tnGenericApsSwitchedToWorkClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) switched to working clear
                 notification."
    ::= { tnGenericAlarmNotifs 106 }

tnGenericApsWorkingSwitchedToProtectRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working switched to protect
                 raise notification."
    ::= { tnGenericAlarmNotifs 107 }

tnGenericApsWorkingSwitchedToProtectClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working switched to protect
                 clear notification."
    ::= { tnGenericAlarmNotifs 108 }

tnGenericApsWorkingManualSwitchedToProtectRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working manual switched
                 to protect raise notification."
    ::= { tnGenericAlarmNotifs 109 }

tnGenericApsWorkingManualSwitchedToProtectClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch (APS) working manual switched
                 to protect clear notification."
    ::= { tnGenericAlarmNotifs 110 }

tnGenericWtrRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Wait to restore raise notification."
    ::= { tnGenericAlarmNotifs 111 }

tnGenericWtrClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Wait to restore clear notification."
    ::= { tnGenericAlarmNotifs 112 }

tnGenericTSesOdu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 15 Minute Bin - ODU raise notification."
    ::= { tnGenericAlarmNotifs 113 }

tnGenericTSesOdu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 15 Minute Bin - ODU clear notification."
    ::= { tnGenericAlarmNotifs 114 }

tnGenericTSesOdu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 1 Day Bin - ODU raise notification."
    ::= { tnGenericAlarmNotifs 115 }

tnGenericTSesOdu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 1 Day Bin - ODU clear notification."
    ::= { tnGenericAlarmNotifs 116 }

tnGenericTSesOtu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 15 Minute Bin - OTU raise notification."
    ::= { tnGenericAlarmNotifs 117 }

tnGenericTSesOtu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 15 Minute Bin - OTU clear notification."
    ::= { tnGenericAlarmNotifs 118 }

tnGenericTSesOtu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 1 Day Bin - OTU raise notification."
    ::= { tnGenericAlarmNotifs 119 }

tnGenericTSesOtu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 1 Day Bin - OTU clear notification."
    ::= { tnGenericAlarmNotifs 120 }

tnGenericTSesTcm15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 15 Minute Bin - TCM raise notification."
    ::= { tnGenericAlarmNotifs 121 }

tnGenericTSesTcm15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 15 Minute Bin - TCM clear notification."
    ::= { tnGenericAlarmNotifs 122 }

tnGenericTSesTcm1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 1 Day Bin - TCM raise notification."
    ::= { tnGenericAlarmNotifs 123 }

tnGenericTSesTcm1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second Threshold Crossing Alert Near End
                 1 Day Bin - TCM clear notification."
    ::= { tnGenericAlarmNotifs 124 }

tnGenericTUasOdu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 15 Minute Bin - ODU raise notification."
    ::= { tnGenericAlarmNotifs 125 }

tnGenericTUasOdu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 15 Minute Bin - ODU clear notification."
    ::= { tnGenericAlarmNotifs 126 }

tnGenericTUasOdu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 1 Day Bin - ODU raise notification."
    ::= { tnGenericAlarmNotifs 127 }

tnGenericTUasOdu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 1 Day Bin - ODU clear notification."
    ::= { tnGenericAlarmNotifs 128 }

tnGenericTUasOtu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 15 Minute Bin - OTU raise notification."
    ::= { tnGenericAlarmNotifs 129 }

tnGenericTUasOtu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 15 Minute Bin - OTU clear notification."
    ::= { tnGenericAlarmNotifs 130 }

tnGenericTUasOtu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 1 Day Bin - OTU raise notification."
    ::= { tnGenericAlarmNotifs 131 }

tnGenericTUasOtu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 1 Day Bin - OTU clear notification."
    ::= { tnGenericAlarmNotifs 132 }

tnGenericTUasTcm15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 15 Minute Bin - TCM raise notification."
    ::= { tnGenericAlarmNotifs 133 }

tnGenericTUasTcm15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 15 Minute Bin - TCM clear notification."
    ::= { tnGenericAlarmNotifs 134 }

tnGenericTUasTcm1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 1 Day Bin - TCM raise notification."
    ::= { tnGenericAlarmNotifs 135 }

tnGenericTUasTcm1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second Threshold Crossing Alert Near End
                 1 Day Bin - TCM clear notification."
    ::= { tnGenericAlarmNotifs 136 }

tnGenericApsBlockRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch Block raise notification."
    ::= { tnGenericAlarmNotifs 137 }

tnGenericApsBlockClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch Block clear notification."
    ::= { tnGenericAlarmNotifs 138 }

tnGenericApsLOSyncRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Protected Section Loss of Selector Synchronizations raise
                 notification."
    ::= { tnGenericAlarmNotifs 139 }

tnGenericApsLOSyncClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Protected Section Loss of Selector Synchronizations clear
                 notification."
    ::= { tnGenericAlarmNotifs 140 }

tnGenericApsLossOfServiceRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch Loss of Service raise
                 notification."
    ::= { tnGenericAlarmNotifs 141 }

tnGenericApsLossOfServiceClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Protection Switch Loss of Service clear
                 notification."
    ::= { tnGenericAlarmNotifs 142 }

tnGenericApsSuspendedRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "APS Mechanism interrupted raise notification."
    ::= { tnGenericAlarmNotifs 143 }

tnGenericApsSuspendedClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "APS Mechanism interrupted clear notification."
    ::= { tnGenericAlarmNotifs 144 }

tnGenericAuditBlockRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Audit Blocked raise notification."
    ::= { tnGenericAlarmNotifs 145 }

tnGenericAuditBlockClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Audit Blocked clear notification."
    ::= { tnGenericAlarmNotifs 146 }

tnGenericBreaker1BatteryFeedDownRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Power Input Fail raise notification."
    ::= { tnGenericAlarmNotifs 147 }

tnGenericBreaker1BatteryFeedDownClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Power Input Fail clear notification."
    ::= { tnGenericAlarmNotifs 148 }

tnGenericCabinAlarm1RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Cabin Alarm 1 raise notification."
    ::= { tnGenericAlarmNotifs 149 }

tnGenericCabinAlarm1ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Cabin Alarm 1 clear notification."
    ::= { tnGenericAlarmNotifs 150 }

tnGenericCabinAlarm2RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Cabin Alarm 2 raise notification."
    ::= { tnGenericAlarmNotifs 151 }

tnGenericCabinAlarm2ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Cabin Alarm 2 clear notification."
    ::= { tnGenericAlarmNotifs 152 }

tnGenericCabinAlarm3RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Cabin Alarm 3 raise notification."
    ::= { tnGenericAlarmNotifs 153 }

tnGenericCabinAlarm3ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Cabin Alarm 3 clear notification."
    ::= { tnGenericAlarmNotifs 154 }

tnGenericCabinAlarm4RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Cabin Alarm 4 raise notification."
    ::= { tnGenericAlarmNotifs 155 }

tnGenericCabinAlarm4ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Cabin Alarm 4 clear notification."
    ::= { tnGenericAlarmNotifs 156 }

tnGenericCardBootRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Card Booting raise notification."
    ::= { tnGenericAlarmNotifs 157 }

tnGenericCardBootClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Card Booting clear notification."
    ::= { tnGenericAlarmNotifs 158 }

tnGenericCardMissingRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Card Missing raise notification."
    ::= { tnGenericAlarmNotifs 159 }

tnGenericCardMissingClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Card Missing clear notification."
    ::= { tnGenericAlarmNotifs 160 }

tnGenericCardUnknownRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unknown Card raise notification."
    ::= { tnGenericAlarmNotifs 161 }

tnGenericCardUnknownClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unknown Card clear notification."
    ::= { tnGenericAlarmNotifs 162 }

tnGenericEqptDgrOchRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Equipment Degrade raise notification."
    ::= { tnGenericAlarmNotifs 163 }

tnGenericEqptDgrOchClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Equipment Degrade clear notification."
    ::= { tnGenericAlarmNotifs 164 }

tnGenericFrameAlarm1RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 1 raise notification."
    ::= { tnGenericAlarmNotifs 165 }

tnGenericFrameAlarm1ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 1 clear notification."
    ::= { tnGenericAlarmNotifs 166 }

tnGenericFrameAlarm2RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 2 raise notification."
    ::= { tnGenericAlarmNotifs 167 }

tnGenericFrameAlarm2ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 2 clear notification."
    ::= { tnGenericAlarmNotifs 168 }

tnGenericFrameAlarm3RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 3 raise notification."
    ::= { tnGenericAlarmNotifs 169 }

tnGenericFrameAlarm3ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 3 clear notification."
    ::= { tnGenericAlarmNotifs 170 }

tnGenericFrameAlarm4RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 4 raise notification."
    ::= { tnGenericAlarmNotifs 171 }

tnGenericFrameAlarm4ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 4 clear notification."
    ::= { tnGenericAlarmNotifs 172 }

tnGenericFrameAlarm5RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 5 raise notification."
    ::= { tnGenericAlarmNotifs 173 }

tnGenericFrameAlarm5ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 5 clear notification."
    ::= { tnGenericAlarmNotifs 174 }

tnGenericFrameAlarm6RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 6 raise notification."
    ::= { tnGenericAlarmNotifs 175 }

tnGenericFrameAlarm6ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 6 clear notification."
    ::= { tnGenericAlarmNotifs 176 }

tnGenericFrameAlarm7RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 7 raise notification."
    ::= { tnGenericAlarmNotifs 177 }

tnGenericFrameAlarm7ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 7 clear notification."
    ::= { tnGenericAlarmNotifs 178 }

tnGenericFrameAlarm8RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 8 raise notification."
    ::= { tnGenericAlarmNotifs 179 }

tnGenericFrameAlarm8ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 8 clear notification."
    ::= { tnGenericAlarmNotifs 180 }

tnGenericFrameAlarm9RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 9 raise notification."
    ::= { tnGenericAlarmNotifs 181 }

tnGenericFrameAlarm9ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 9 clear notification."
    ::= { tnGenericAlarmNotifs 182 }

tnGenericFrameAlarm10RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 10 raise notification."
    ::= { tnGenericAlarmNotifs 183 }

tnGenericFrameAlarm10ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 10 clear notification."
    ::= { tnGenericAlarmNotifs 184 }

tnGenericFrameAlarm11RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 11 raise notification."
    ::= { tnGenericAlarmNotifs 185 }

tnGenericFrameAlarm11ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 11 clear notification."
    ::= { tnGenericAlarmNotifs 186 }

tnGenericFrameAlarm12RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 12 raise notification."
    ::= { tnGenericAlarmNotifs 187 }

tnGenericFrameAlarm12ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Frame Alarm 12 clear notification."
    ::= { tnGenericAlarmNotifs 188 }

tnGenericInterShelfLossofCommsRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss of Communications raise notification."
    ::= { tnGenericAlarmNotifs 189 }

tnGenericInterShelfLossofCommsClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss of Communications clear notification."
    ::= { tnGenericAlarmNotifs 190 }

tnGenericInventoryErrModRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Inventory Error Module raise notification."
    ::= { tnGenericAlarmNotifs 191 }

tnGenericInventoryErrModClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Inventory Error Module clear notification."
    ::= { tnGenericAlarmNotifs 192 }

tnGenericLineFacilityLoopbackActiveRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Line Facility Loopback Active raise notification."
    ::= { tnGenericAlarmNotifs 193 }

tnGenericLineFacilityLoopbackActiveClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Line Facility Loopback Active clear notification."
    ::= { tnGenericAlarmNotifs 194 }

tnGenericLossOfFrameRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Frame raise notification."
    ::= { tnGenericAlarmNotifs 195 }

tnGenericLossOfFrameClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Frame clear notification."
    ::= { tnGenericAlarmNotifs 196 }

tnGenericOpticalPowerReceivedOutOfRangeRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optical Power Received Out of Range raise notification."
    ::= { tnGenericAlarmNotifs 197 }

tnGenericOpticalPowerReceivedOutOfRangeClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optical Power Received Out of Range clear notification."
    ::= { tnGenericAlarmNotifs 198 }

tnGenericSfpTempOORRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SFP Temperature Out Of Range raise notification."
    ::= { tnGenericAlarmNotifs 199 }

tnGenericSfpTempOORClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SFP Temperature Out Of Range clear notification."
    ::= { tnGenericAlarmNotifs 200 }

tnGenericSfpTrmtPwrOORRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optical Power Transmitted Out of Range raise notification."
    ::= { tnGenericAlarmNotifs 201 }

tnGenericSfpTrmtPwrOORClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optical Power Transmitted Out of Range clear notification."
    ::= { tnGenericAlarmNotifs 202 }

tnGenericSoftwareCompatibilityFailRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Software Compatibility Failure raise notification."
    ::= { tnGenericAlarmNotifs 203 }

tnGenericSoftwareCompatibilityFailClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Software Compatibility Failure clear notification."
    ::= { tnGenericAlarmNotifs 204 }

tnGenericSoftwareUpgradeFailureRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Software Upgrade Failure raise notification."
    ::= { tnGenericAlarmNotifs 205 }

tnGenericSoftwareUpgradeFailureClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Software Upgrade Failure clear notification."
    ::= { tnGenericAlarmNotifs 206 }

tnGenericTCvPcs15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CV-PCS 15Min TCA raise notification."
    ::= { tnGenericAlarmNotifs 207 }

tnGenericTCvPcs15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CV-PCS 15Min TCA clear notification."
    ::= { tnGenericAlarmNotifs 208 }

tnGenericTCvPcs1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CV-PCS 1Day TCA raise notification."
    ::= { tnGenericAlarmNotifs 209 }

tnGenericTCvPcs1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CV-PCS 1Day TCA clear notification."
    ::= { tnGenericAlarmNotifs 210 }

tnGenericTEsPcs15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "ES-PCS 15Min TCA raise notification."
    ::= { tnGenericAlarmNotifs 211 }

tnGenericTEsPcs15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "ES-PCS 15Min TCA clear notification."
    ::= { tnGenericAlarmNotifs 212 }

tnGenericTEsPcs1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "ES-PCS 1Day TCA raise notification."
    ::= { tnGenericAlarmNotifs 213 }

tnGenericTEsPcs1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "ES-PCS 1Day TCA clear notification."
    ::= { tnGenericAlarmNotifs 214 }

tnGenericTSefsPcs15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SEFS-PCS 15Min TCA raise notification."
    ::= { tnGenericAlarmNotifs 215 }

tnGenericTSefsPcs15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SEFS-PCS 15Min TCA clear notification."
    ::= { tnGenericAlarmNotifs 216 }

tnGenericTSefsPcs1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SEFS-PCS 1Day TCA raise notification."
    ::= { tnGenericAlarmNotifs 217 }

tnGenericTSefsPcs1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SEFS-PCS 1Day TCA clear notification."
    ::= { tnGenericAlarmNotifs 218 }

tnGenericTSesPcs15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SES-PCS 15Min TCA raise notification."
    ::= { tnGenericAlarmNotifs 219 }

tnGenericTSesPcs15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SES-PCS 15Min TCA clear notification."
    ::= { tnGenericAlarmNotifs 220 }

tnGenericTSesPcs1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SES-PCS 1Day TCA raise notification."
    ::= { tnGenericAlarmNotifs 221 }

tnGenericTSesPcs1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "SES-PCS 1Day TCA clear notification."
    ::= { tnGenericAlarmNotifs 222 }

tnGenericTxSquelchRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmit Squelched raise notification."
    ::= { tnGenericAlarmNotifs 223 }

tnGenericTxSquelchClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmit Squelched clear notification."
    ::= { tnGenericAlarmNotifs 224 }

tnGenericUserAlarm1RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 1 raise notification."
    ::= { tnGenericAlarmNotifs 225 }

tnGenericUserAlarm1ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 1 clear notification."
    ::= { tnGenericAlarmNotifs 226 }

tnGenericUserAlarm2RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 2 raise notification."
    ::= { tnGenericAlarmNotifs 227 }

tnGenericUserAlarm2ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 2 clear notification."
    ::= { tnGenericAlarmNotifs 228 }

tnGenericUserAlarm3RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 3 raise notification."
    ::= { tnGenericAlarmNotifs 229 }

tnGenericUserAlarm3ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 3 clear notification."
    ::= { tnGenericAlarmNotifs 230 }

tnGenericUserAlarm4RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 4 raise notification."
    ::= { tnGenericAlarmNotifs 231 }

tnGenericUserAlarm4ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 4 clear notification."
    ::= { tnGenericAlarmNotifs 232 }

tnGenericUserAlarm5RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 5 raise notification."
    ::= { tnGenericAlarmNotifs 233 }

tnGenericUserAlarm5ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 5 clear notification."
    ::= { tnGenericAlarmNotifs 234 }

tnGenericUserAlarm6RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 6 raise notification."
    ::= { tnGenericAlarmNotifs 235 }

tnGenericUserAlarm6ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 6 clear notification."
    ::= { tnGenericAlarmNotifs 236 }

tnGenericUserAlarm7RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 7 raise notification."
    ::= { tnGenericAlarmNotifs 237 }

tnGenericUserAlarm7ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 7 clear notification."
    ::= { tnGenericAlarmNotifs 238 }

tnGenericUserAlarm8RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 8 raise notification."
    ::= { tnGenericAlarmNotifs 239 }

tnGenericUserAlarm8ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 8 clear notification."
    ::= { tnGenericAlarmNotifs 240 }

tnGenericUserAlarm9RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 9 raise notification."
    ::= { tnGenericAlarmNotifs 241 }

tnGenericUserAlarm9ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 9 clear notification."
    ::= { tnGenericAlarmNotifs 242 }

tnGenericUserAlarm10RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 10 raise notification."
    ::= { tnGenericAlarmNotifs 243 }

tnGenericUserAlarm10ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 10 clear notification."
    ::= { tnGenericAlarmNotifs 244 }

tnGenericUserAlarm11RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 11 raise notification."
    ::= { tnGenericAlarmNotifs 245 }

tnGenericUserAlarm11ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 11 clear notification."
    ::= { tnGenericAlarmNotifs 246 }

tnGenericUserAlarm12RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 12 raise notification."
    ::= { tnGenericAlarmNotifs 247 }

tnGenericUserAlarm12ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 12 clear notification."
    ::= { tnGenericAlarmNotifs 248 }

tnGenericUserAlarm13RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 13 raise notification."
    ::= { tnGenericAlarmNotifs 249 }

tnGenericUserAlarm13ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 13 clear notification."
    ::= { tnGenericAlarmNotifs 250 }

tnGenericUserAlarm14RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 14 raise notification."
    ::= { tnGenericAlarmNotifs 251 }

tnGenericUserAlarm14ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 14 clear notification."
    ::= { tnGenericAlarmNotifs 252 }

tnGenericUserAlarm15RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 15 raise notification."
    ::= { tnGenericAlarmNotifs 253 }

tnGenericUserAlarm15ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 15 clear notification."
    ::= { tnGenericAlarmNotifs 254 }

tnGenericUserAlarm16RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 16 raise notification."
    ::= { tnGenericAlarmNotifs 255 }

tnGenericUserAlarm16ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 16 clear notification."
    ::= { tnGenericAlarmNotifs 256 }

tnGenericUserAlarm17RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 17 raise notification."
    ::= { tnGenericAlarmNotifs 257 }

tnGenericUserAlarm17ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 17 clear notification."
    ::= { tnGenericAlarmNotifs 258 }

tnGenericUserAlarm18RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 18 raise notification."
    ::= { tnGenericAlarmNotifs 259 }

tnGenericUserAlarm18ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 18 clear notification."
    ::= { tnGenericAlarmNotifs 260 }

tnGenericUserAlarm19RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 19 raise notification."
    ::= { tnGenericAlarmNotifs 261 }

tnGenericUserAlarm19ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 19 clear notification."
    ::= { tnGenericAlarmNotifs 262 }

tnGenericUserAlarm20RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 20 raise notification."
    ::= { tnGenericAlarmNotifs 263 }

tnGenericUserAlarm20ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 20 clear notification."
    ::= { tnGenericAlarmNotifs 264 }

tnGenericUserAlarm21RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 21 raise notification."
    ::= { tnGenericAlarmNotifs 265 }

tnGenericUserAlarm21ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 21 clear notification."
    ::= { tnGenericAlarmNotifs 266 }

tnGenericUserAlarm22RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 22 raise notification."
    ::= { tnGenericAlarmNotifs 267 }

tnGenericUserAlarm22ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 22 clear notification."
    ::= { tnGenericAlarmNotifs 268 }

tnGenericUserAlarm23RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 23 raise notification."
    ::= { tnGenericAlarmNotifs 269 }

tnGenericUserAlarm23ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 23 clear notification."
    ::= { tnGenericAlarmNotifs 270 }

tnGenericUserAlarm24RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 24 raise notification."
    ::= { tnGenericAlarmNotifs 271 }

tnGenericUserAlarm24ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 24 clear notification."
    ::= { tnGenericAlarmNotifs 272 }

tnGenericUserAlarm25RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 25 raise notification."
    ::= { tnGenericAlarmNotifs 273 }

tnGenericUserAlarm25ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 25 clear notification."
    ::= { tnGenericAlarmNotifs 274 }

tnGenericUserAlarm26RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 26 raise notification."
    ::= { tnGenericAlarmNotifs 275 }

tnGenericUserAlarm26ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 26 clear notification."
    ::= { tnGenericAlarmNotifs 276 }

tnGenericUserAlarm27RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 27 raise notification."
    ::= { tnGenericAlarmNotifs 277 }

tnGenericUserAlarm27ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 27 clear notification."
    ::= { tnGenericAlarmNotifs 278 }

tnGenericUserAlarm28RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 28 raise notification."
    ::= { tnGenericAlarmNotifs 279 }

tnGenericUserAlarm28ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 28 clear notification."
    ::= { tnGenericAlarmNotifs 280 }

tnGenericUserAlarm29RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 29 raise notification."
    ::= { tnGenericAlarmNotifs 281 }

tnGenericUserAlarm29ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 29 clear notification."
    ::= { tnGenericAlarmNotifs 282 }

tnGenericUserAlarm30RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 30 raise notification."
    ::= { tnGenericAlarmNotifs 283 }

tnGenericUserAlarm30ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 30 clear notification."
    ::= { tnGenericAlarmNotifs 284 }

tnGenericUserAlarm31RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 31 raise notification."
    ::= { tnGenericAlarmNotifs 285 }

tnGenericUserAlarm31ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 31 clear notification."
    ::= { tnGenericAlarmNotifs 286 }

tnGenericUserAlarm32RaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 32 raise notification."
    ::= { tnGenericAlarmNotifs 287 }

tnGenericUserAlarm32ClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "User Alarm 32 clear notification."
    ::= { tnGenericAlarmNotifs 288 }

tnGenericTFeBbeOdu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 15 Min Bin - ODU raise
                 notification."
    ::= { tnGenericAlarmNotifs 289 }

tnGenericTFeBbeOdu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 15 Min Bin - ODU clear
                 notification."
    ::= { tnGenericAlarmNotifs 290 }

tnGenericTFeBbeOdu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 1 Day Bin - ODU raise
                 notification."
    ::= { tnGenericAlarmNotifs 291 }

tnGenericTFeBbeOdu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 1 Day Bin - ODU clear
                 notification."
    ::= { tnGenericAlarmNotifs 292 }

tnGenericTFeEsOdu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 15 Minute Bin - ODU raise
                 notification."
    ::= { tnGenericAlarmNotifs 293 }

tnGenericTFeEsOdu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 15 Minute Bin - ODU clear
                 notification."
    ::= { tnGenericAlarmNotifs 294 }

tnGenericTFeEsOdu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 1 Day Bin - ODU raise
                 notification."
    ::= { tnGenericAlarmNotifs 295 }

tnGenericTFeEsOdu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 1 Day Bin - ODU clear
                 notification."
    ::= { tnGenericAlarmNotifs 296 }

tnGenericTFeSesOdu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 15 Minute Bin - ODU
                 raise notification."
    ::= { tnGenericAlarmNotifs 297 }

tnGenericTFeSesOdu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 15 Minute Bin - ODU
                 clear notification."
    ::= { tnGenericAlarmNotifs 298 }

tnGenericTFeSesOdu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 1 Day Bin - ODU raise
                 notification."
    ::= { tnGenericAlarmNotifs 299 }

tnGenericTFeSesOdu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 1 Day Bin - ODU clear
                 notification."
    ::= { tnGenericAlarmNotifs 300 }

tnGenericTFeUasOdu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 15 Minute Bin - ODU raise
                 notification."
    ::= { tnGenericAlarmNotifs 301 }

tnGenericTFeUasOdu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 15 Minute Bin - ODU clear
                 notification."
    ::= { tnGenericAlarmNotifs 302 }

tnGenericTFeUasOdu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 1 Day Bin - ODU raise
                 notification."
    ::= { tnGenericAlarmNotifs 303 }

tnGenericTFeUasOdu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 1 Day Bin - ODU clear
                 notification."
    ::= { tnGenericAlarmNotifs 304 }

tnGenericTFeBbeTcm15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 15 Min Bin - TCM raise
                 notification."
    ::= { tnGenericAlarmNotifs 305 }

tnGenericTFeBbeTcm15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 15 Min Bin - TCM clear
                 notification."
    ::= { tnGenericAlarmNotifs 306 }

tnGenericTFeBbeTcm1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 1 Day Bin - TCM raise
                 notification."
    ::= { tnGenericAlarmNotifs 307 }

tnGenericTFeBbeTcm1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 1 Day Bin - TCM clear
                 notification."
    ::= { tnGenericAlarmNotifs 308 }

tnGenericTFeEsTcm15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 15 Minute Bin - TCM raise
                 notification."
    ::= { tnGenericAlarmNotifs 309 }

tnGenericTFeEsTcm15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 15 Minute Bin - TCM clear
                 notification."
    ::= { tnGenericAlarmNotifs 310 }

tnGenericTFeEsTcm1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 1 Day Bin - TCM raise
                 notification."
    ::= { tnGenericAlarmNotifs 311 }

tnGenericTFeEsTcm1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 1 Day Bin - TCM clear
                 notification."
    ::= { tnGenericAlarmNotifs 312 }

tnGenericTFeSesTcm15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 15 Minute Bin - TCM raise
                 notification."
    ::= { tnGenericAlarmNotifs 313 }

tnGenericTFeSesTcm15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 15 Minute Bin - TCM clear
                 notification."
    ::= { tnGenericAlarmNotifs 314 }

tnGenericTFeSesTcm1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 1 Day Bin - TCM raise
                 notification."
    ::= { tnGenericAlarmNotifs 315 }

tnGenericTFeSesTcm1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 1 Day Bin - TCM clear
                 notification."
    ::= { tnGenericAlarmNotifs 316 }

tnGenericTFeUasTcm15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 15 Minute Bin - TCM raise
                 notification."
    ::= { tnGenericAlarmNotifs 317 }

tnGenericTFeUasTcm15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 15 Minute Bin - TCM clear
                 notification."
    ::= { tnGenericAlarmNotifs 318 }

tnGenericTFeUasTcm1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 1 Day Bin - TCM raise
                 notification."
    ::= { tnGenericAlarmNotifs 319 }

tnGenericTFeUasTcm1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 1 Day Bin - TCM clear
                 notification."
    ::= { tnGenericAlarmNotifs 320 }

tnGenericTFeBbeOtu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 15 Min Bin - OTU raise
                 notification."
    ::= { tnGenericAlarmNotifs 321 }

tnGenericTFeBbeOtu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 15 Min Bin - OTU clear
                 notification."
    ::= { tnGenericAlarmNotifs 322 }

tnGenericTFeBbeOtu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 1 Day Bin - OTU raise
                 notification."
    ::= { tnGenericAlarmNotifs 323 }

tnGenericTFeBbeOtu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Block Count TCA Far End 1 Day Bin - OTU clear
                 notification."
    ::= { tnGenericAlarmNotifs 324 }

tnGenericTFeEsOtu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 15 Minute Bin - OTU raise
                 notification."
    ::= { tnGenericAlarmNotifs 325 }

tnGenericTFeEsOtu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 15 Minute Bin - OTU clear
                 notification."
    ::= { tnGenericAlarmNotifs 326 }

tnGenericTFeEsOtu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 1 Day Bin - OTU raise
                 notification."
    ::= { tnGenericAlarmNotifs 327 }

tnGenericTFeEsOtu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Second TCA Far End 1 Day Bin - OTU clear
                 notification."
    ::= { tnGenericAlarmNotifs 328 }

tnGenericTFeSesOtu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 15 Minute Bin - OTU
                 raise notification."
    ::= { tnGenericAlarmNotifs 329 }

tnGenericTFeSesOtu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 15 Minute Bin - OTU
                 clear notification."
    ::= { tnGenericAlarmNotifs 330 }

tnGenericTFeSesOtu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 1 Day Bin - OTU raise
                 notification."
    ::= { tnGenericAlarmNotifs 331 }

tnGenericTFeSesOtu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Severely Errored Second TCA Far End 1 Day Bin - OTU clear
                 notification."
    ::= { tnGenericAlarmNotifs 332 }

tnGenericTFeUasOtu15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 15 Minute Bin - OTU raise
                 notification."
    ::= { tnGenericAlarmNotifs 333 }

tnGenericTFeUasOtu15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 15 Minute Bin - OTU clear
                 notification."
    ::= { tnGenericAlarmNotifs 334 }

tnGenericTFeUasOtu1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 1 Day Bin - OTU raise
                 notification."
    ::= { tnGenericAlarmNotifs 335 }

tnGenericTFeUasOtu1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unavailable Second TCA Far End 1 Day Bin - OTU clear
                 notification."
    ::= { tnGenericAlarmNotifs 336 }

tnGenericTPmonPortIfInPackets15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Valid received frames TCA 15 Min. Bin - Port raise
                 notification."
    ::= { tnGenericAlarmNotifs 337 }

tnGenericTPmonPortIfInPackets15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Valid received frames TCA 15 Min. Bin - Port clear
                 notification."
    ::= { tnGenericAlarmNotifs 338 }

tnGenericTPmonPortIfInPackets1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Valid received frames TCA 1 Day Bin - Port raise
                 notification."
    ::= { tnGenericAlarmNotifs 339 }

tnGenericTPmonPortIfInPackets1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Valid received frames TCA 1 Day Bin - Port clear
                 notification."
    ::= { tnGenericAlarmNotifs 340 }

tnGenericTPmonPortIfInOctets15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Octets valid Rx frames TCA 15 Min. Bin - Port raise
                 notification."
    ::= { tnGenericAlarmNotifs 341 }

tnGenericTPmonPortIfInOctets15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Octets valid Rx frames TCA 15 Min. Bin - Port clear
                 notification."
    ::= { tnGenericAlarmNotifs 342 }

tnGenericTPmonPortIfInOctets1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Octets valid Rx frames TCA 1 Day Bin - Port raise
                 notification."
    ::= { tnGenericAlarmNotifs 343 }

tnGenericTPmonPortIfInOctets1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Octets valid Rx frames TCA 1 Day Bin - Port clear
                 notification."
    ::= { tnGenericAlarmNotifs 344 }

tnGenericTPmonPortIfInDiscards15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Discarded Rx frames TCA 15 Min. Bin - Port raise
                 notification."
    ::= { tnGenericAlarmNotifs 345 }

tnGenericTPmonPortIfInDiscards15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Discarded Rx frames TCA 15 Min. Bin - Port clear
                 notification."
    ::= { tnGenericAlarmNotifs 346 }

tnGenericTPmonPortIfInDiscards1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Discarded Rx frames TCA 1 Day Bin - Port raise notification."
    ::= { tnGenericAlarmNotifs 347 }

tnGenericTPmonPortIfInDiscards1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Discarded Rx frames TCA 1 Day Bin - Port clear notification."
    ::= { tnGenericAlarmNotifs 348 }

tnGenericTPmonPortIfInErrors15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Rx frames TCA 15 Min. Bin - Port raise notification."
    ::= { tnGenericAlarmNotifs 349 }

tnGenericTPmonPortIfInErrors15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Rx frames TCA 15 Min. Bin - Port clear notification."
    ::= { tnGenericAlarmNotifs 350 }

tnGenericTPmonPortIfInErrors1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Rx frames TCA 1 Day Bin - Port raise notification."
    ::= { tnGenericAlarmNotifs 351 }

tnGenericTPmonPortIfInErrors1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Errored Rx frames TCA 1 Day Bin - Port clear notification."
    ::= { tnGenericAlarmNotifs 352 }

tnGenericTPmonPortIfOutPackets15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmitted frames TCA 15 Min. Bin - Port raise notification."
    ::= { tnGenericAlarmNotifs 353 }

tnGenericTPmonPortIfOutPackets15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmitted frames TCA 15 Min. Bin - Port clear notification."
    ::= { tnGenericAlarmNotifs 354 }

tnGenericTPmonPortIfOutPackets1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmitted frames TCA 1 Day Bin - Port raise notification."
    ::= { tnGenericAlarmNotifs 355 }

tnGenericTPmonPortIfOutPackets1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmitted frames TCA 1 Day Bin - Port clear notification."
    ::= { tnGenericAlarmNotifs 356 }

tnGenericTPmonPortIfOutOctets15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmitted octets/bytes TCA 15 Min. Bin - Port raise
                 notification."
    ::= { tnGenericAlarmNotifs 357 }

tnGenericTPmonPortIfOutOctets15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmitted octets/bytes TCA 15 Min. Bin - Port clear
                 notification."
    ::= { tnGenericAlarmNotifs 358 }

tnGenericTPmonPortIfOutOctets1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmitted octets/bytes TCA 1 Day Bin - Port raise
                 notification."
    ::= { tnGenericAlarmNotifs 359 }

tnGenericTPmonPortIfOutOctets1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Transmitted octets/bytes TCA 1 Day Bin - Port clear
                 notification."
    ::= { tnGenericAlarmNotifs 360 }

tnGenericTPmonSlmanFlr1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Near End Frame Loss Ratio 1 Day Bin
                 raise notification."
    ::= { tnGenericAlarmNotifs 361 }

tnGenericTPmonSlmanFlr1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Near End Frame Loss Ratio 1 Day Bin
                 clear notification."
    ::= { tnGenericAlarmNotifs 362 }

tnGenericTPmonSlmafFlr1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Far End Frame Loss Ratio 1 Day Bin
                 raise notification."
    ::= { tnGenericAlarmNotifs 363 }

tnGenericTPmonSlmafFlr1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Far End Frame Loss Ratio 1 Day Bin
                 clear notification."
    ::= { tnGenericAlarmNotifs 364 }

tnGenericTPmonSlmanflr15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Near End Frame Loss Ratio 15 Min.
                 Bin raise notification."
    ::= { tnGenericAlarmNotifs 365 }

tnGenericTPmonSlmanflr15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Near End Frame Loss Ratio 15 Min.
                 Bin clear notification."
    ::= { tnGenericAlarmNotifs 366 }

tnGenericTPmonSlmafflr15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Far End Frame Loss Ratio 15 Min. Bin
                raise notification."
    ::= { tnGenericAlarmNotifs 367 }

tnGenericTPmonSlmafflr15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Far End Frame Loss Ratio 15 Min. Bin
                 clear notification."
    ::= { tnGenericAlarmNotifs 368 }

tnGenericTPmonSlmnhli15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Near End High Loss Interval 15 Min. Bin raise
                 notification."
    ::= { tnGenericAlarmNotifs 369 }

tnGenericTPmonSlmnhli15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Near End High Loss Interval 15 Min. Bin clear
                 notification."
    ::= { tnGenericAlarmNotifs 370 }

tnGenericTPmonSlmfhli15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Far End High Loss Interval 15 Min. Bin raise
                 notification."
    ::= { tnGenericAlarmNotifs 371 }

tnGenericTPmonSlmfhli15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Far End High Loss Interval 15 Min. Bin clear
                 notification."
    ::= { tnGenericAlarmNotifs 372 }

tnGenericTPmonSlmnhli1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Near End High Loss Interval 1 Day Bin raise
                 notification."
    ::= { tnGenericAlarmNotifs 373 }

tnGenericTPmonSlmnhli1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Near End High Loss Interval 1 Day Bin clear
                 notification."
    ::= { tnGenericAlarmNotifs 374 }

tnGenericTPmonSlmfhli1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Far End High Loss Interval 1 Day Bin raise
                 notification."
    ::= { tnGenericAlarmNotifs 375 }

tnGenericTPmonSlmfhli1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Far End High Loss Interval 1 Day Bin clear
                 notification."
    ::= { tnGenericAlarmNotifs 376 }

tnGenericTPmonSlmxfflrContRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Far End High Loss Interval Continuous Bin raise
                 notification."
    ::= { tnGenericAlarmNotifs 377 }

tnGenericTPmonSlmxfflrContClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Far End High Loss Interval Continuous Bin clear
                 notification."
    ::= { tnGenericAlarmNotifs 378 }

tnGenericTPmonSlmanflrContRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Near End Frame Loss Ratio Continuous
                 Bin raise notification."
    ::= { tnGenericAlarmNotifs 379 }

tnGenericTPmonSlmanflrContClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Near End Frame Loss Ratio Continuous
                 Bin clear notification."
    ::= { tnGenericAlarmNotifs 380 }

tnGenericTPmonSlmafflrContRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Far End Frame Loss Ratio Continuous Bin
                 raise notification."
    ::= { tnGenericAlarmNotifs 381 }

tnGenericTPmonSlmafflrContClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Average Far End Frame Loss Ratio Continuous
                 Bin clear notification."
    ::= { tnGenericAlarmNotifs 382 }

tnGenericTPmonDmaBfd15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Round-trip Frame Delay 15 Min. Bin raise
                 notification."
    ::= { tnGenericAlarmNotifs 383 }

tnGenericTPmonDmaBfd15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Round-trip Frame Delay 15 Min. Bin clear
                 notification."
    ::= { tnGenericAlarmNotifs 384 }

tnGenericTPmonDmaBfd1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Round-trip Frame Delay 1 Day Bin raise
                 notification."
    ::= { tnGenericAlarmNotifs 385 }

tnGenericTPmonDmaBfd1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Round-trip Frame Delay 1 Day Bin clear
                 notification."
    ::= { tnGenericAlarmNotifs 386 }

tnGenericTPmonDmafFdv15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Far End Frame Delay Var. 15 Min. Bin
                 raise notification."
    ::= { tnGenericAlarmNotifs 387 }

tnGenericTPmonDmafFdv15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Far End Frame Delay Var. 15 Min. Bin
                 clear notification."
    ::= { tnGenericAlarmNotifs 388 }

tnGenericTPmonDmafFdv1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Far End Frame Delay Var. 1 Day Bin
                 raise notification."
    ::= { tnGenericAlarmNotifs 389 }

tnGenericTPmonDmafFdv1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Far End Frame Delay Var. 1 Day Bin
                 clear notification."
    ::= { tnGenericAlarmNotifs 390 }

tnGenericTPmonDmanFdv15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Near End Frame Delay Var. 15 Min. Bin
                 raise notification."
    ::= { tnGenericAlarmNotifs 391 }

tnGenericTPmonDmanFdv15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Near End Frame Delay Var. 15 Min.
                 Bin clear notification."
    ::= { tnGenericAlarmNotifs 392 }

tnGenericTPmonDmanFdv1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Near End Frame Delay Var. 1 Day Bin raise
                 notification."
    ::= { tnGenericAlarmNotifs 393 }

tnGenericTPmonDmanFdv1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Average Near End Frame Delay Var. 1 Day Bin clear
                 notification."
    ::= { tnGenericAlarmNotifs 394 }

tnGenericTPmonDmxBfd15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Round-trip Frame Delay 15 Min. Bin raise
                 notification."
    ::= { tnGenericAlarmNotifs 395 }

tnGenericTPmonDmxBfd15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Round-trip Frame Delay 15 Min. Bin clear
                 notification."
    ::= { tnGenericAlarmNotifs 396 }

tnGenericTPmonDmxBfd1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Round-trip Frame Delay 1 Day Bin raise
                 notification."
    ::= { tnGenericAlarmNotifs 397 }

tnGenericTPmonDmxBfd1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Round-trip Frame Delay 1 Day Bin clear
                 notification."
    ::= { tnGenericAlarmNotifs 398 }

tnGenericTPmonDmxfFdv15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Far End Frame Delay Var. 15 Min.
                 Bin raise notification."
    ::= { tnGenericAlarmNotifs 399 }

tnGenericTPmonDmxfFdv15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Far End Frame Delay Var. 15 Min.
                 Bin clear notification."
    ::= { tnGenericAlarmNotifs 400 }

tnGenericTPmonDmxfFdv1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Far End Frame Delay Var. 1 Day Bin raise
                 notification."
    ::= { tnGenericAlarmNotifs 401 }

tnGenericTPmonDmxfFdv1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Far End Frame Delay Var. 1 Day Bin clear
                 notification."
    ::= { tnGenericAlarmNotifs 402 }

tnGenericTPmonDmxnFdv15MinRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Near End Frame Delay Var. 15 Min.
                 Bin raise notification."
    ::= { tnGenericAlarmNotifs 403 }

tnGenericTPmonDmxnFdv15MinClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Near End Frame Delay Var. 15 Min.
                 Bin clear notification."
    ::= { tnGenericAlarmNotifs 404 }

tnGenericTPmonDmxnFdv1DayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Near End Frame Delay Var. 1 Day Bin raise
                 notification."
    ::= { tnGenericAlarmNotifs 405 }

tnGenericTPmonDmxnFdv1DayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA DM Maximum Near End Frame Delay Var. 1 Day Bin clear
                 notification."
    ::= { tnGenericAlarmNotifs 406 }

tnGenericLagLosRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Link Aggregation Group has a Loss of Signal raise
                 notification."
    ::= { tnGenericAlarmNotifs 407 }

tnGenericLagLosClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Link Aggregation Group has a Loss of Signal clear
                 notification."
    ::= { tnGenericAlarmNotifs 408 }

tnGenericMepLocRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss of Continuity, no timely reception of CCM frames raise
                 notification."
    ::= { tnGenericAlarmNotifs 409 }

tnGenericMepLocClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss of Continuity, no timely reception of CCM frames clear
                 notification."
    ::= { tnGenericAlarmNotifs 410 }

tnGenericUNLRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received with incorrect MEG level raise
                 notification."
    ::= { tnGenericAlarmNotifs 411 }

tnGenericUNLClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received with incorrect MEG level clear
                 notification."
    ::= { tnGenericAlarmNotifs 412 }

tnGenericMepMmgRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received with incorrect MEG ID raise
                 notification."
    ::= { tnGenericAlarmNotifs 413 }

tnGenericMepMmgClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received with incorrect MEG ID clear
                 notification."
    ::= { tnGenericAlarmNotifs 414 }

tnGenericUNMRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received with Unexpected MEP ID raise
                 notification."
    ::= { tnGenericAlarmNotifs 415 }

tnGenericUNMClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received with Unexpected MEP ID clear
                 notification."
    ::= { tnGenericAlarmNotifs 416 }

tnGenericUNPrRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received with Unexpected VLAN priority raise
                 notification."
    ::= { tnGenericAlarmNotifs 417 }

tnGenericUNPrClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received with Unexpected VLAN priority clear
                 notification."
    ::= { tnGenericAlarmNotifs 418 }

tnGenericRDIRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received RDI field set, remote MEP(s) in failure
                 raise notification."
    ::= { tnGenericAlarmNotifs 419 }

tnGenericRDIClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "CCM frames received RDI field set, remote MEP(s) in failure
                 clear notification."
    ::= { tnGenericAlarmNotifs 420 }

tnGenericUNPRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unexpected CCM Period, local and remote value do not match
                 raise notification."
    ::= { tnGenericAlarmNotifs 421 }

tnGenericUNPClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unexpected CCM Period, local and remote value do not match
                 clear notification."
    ::= { tnGenericAlarmNotifs 422 }

tnGenericNuatRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Near-End Unavailable Time Period raise notification."
    ::= { tnGenericAlarmNotifs 423 }

tnGenericNuatClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Near-End Unavailable Time Period clear notification."
    ::= { tnGenericAlarmNotifs 424 }

tnGenericFuatRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Far-End Unavailable Time Period raise notification."
    ::= { tnGenericAlarmNotifs 425 }

tnGenericFuatClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Far-End Unavailable Time Period clear notification."
    ::= { tnGenericAlarmNotifs 426 }

tnGenericAutoLaserOffDueToUpstreamFaultRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Laser Shutdown due to upstream condition raise
                 notification."
    ::= { tnGenericAlarmNotifs 427 }

tnGenericAutoLaserOffDueToUpstreamFaultClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Automatic Laser Shutdown due to upstream condition clear
                 notification."
    ::= { tnGenericAlarmNotifs 428 }

tnGenericLagProtLosRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Link Aggregation Groups (LAG) Protection LOS condition
                 raise notification."
    ::= { tnGenericAlarmNotifs 429 }

tnGenericLagProtLosClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Link Aggregation Groups (LAG) Protection LOS condition
                 clear notification."
    ::= { tnGenericAlarmNotifs 430 }

tnGenericMonitorExcRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Hardware monitoring capabilities exceeded condition raise
                 notification."
    ::= { tnGenericAlarmNotifs 431 }

tnGenericMonitorExcClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Hardware monitoring capabilities exceeded condition clear
                 notification."
    ::= { tnGenericAlarmNotifs 432 }

tnGenericEquipmentLedOnRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Equipment LED on condition raise notification."
    ::= { tnGenericAlarmNotifs 433 }

tnGenericEquipmentLedOnClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Equipment LED on condition clear notification."
    ::= { tnGenericAlarmNotifs 434 }

tnGenericUnitInitRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unit initializing condition raise notification."
    ::= { tnGenericAlarmNotifs 435 }

tnGenericUnitInitClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Unit initializing condition clear notification."
    ::= { tnGenericAlarmNotifs 436 }

tnGenericCardMismatchRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Card type mismatch raise notification."
    ::= { tnGenericAlarmNotifs 437 }

tnGenericCardMismatchClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Card type mismatch clear notification."
    ::= { tnGenericAlarmNotifs 438 }

tnGenericTPmonSlmxnflrContRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Maximum Near End Frame Loss Ratio Cont. Bin
                 raise notification."
    ::= { tnGenericAlarmNotifs 439 }

tnGenericTPmonSlmxnflrContClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PMON TCA SLM Maximum Near End Frame Loss Ratio Cont. Bin
                 clear notification."
    ::= { tnGenericAlarmNotifs 440 }

tnGenericOpticalOutputPowerUnachievableRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optical Output Power Unachievable raise notification."
    ::= { tnGenericAlarmNotifs 441 }

tnGenericOpticalOutputPowerUnachievableClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Optical Output Power Unachievable clear notification."
    ::= { tnGenericAlarmNotifs 442 }

tnGenericDiagnosticTerminalLoopbackActiveRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Diagnostic Terminal Loopback Active raise notification."
    ::= { tnGenericAlarmNotifs 443 }

tnGenericDiagnosticTerminalLoopbackActiveClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Diagnostic Terminal Loopback Active clear notification."
    ::= { tnGenericAlarmNotifs 444 }

tnGenericLocalFaultRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Local Fault condition present raise notification."
    ::= { tnGenericAlarmNotifs 445 }

tnGenericLocalFaultClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Local Fault condition present clear notification."
    ::= { tnGenericAlarmNotifs 446 }

tnGenericRemoteFailureIndicationRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Remote Failure condition present raise notification."
    ::= { tnGenericAlarmNotifs 447 }

tnGenericRemoteFailureIndicationClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Remote Failure condition present clear notification."
    ::= { tnGenericAlarmNotifs 448 }

tnGenericOduClientSignalFailureRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Client Signal Failure - ODUkP raise notification."
    ::= { tnGenericAlarmNotifs 477 }

tnGenericOduClientSignalFailureClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Client Signal Failure - ODUkP clear notification."
    ::= { tnGenericAlarmNotifs 478 }

tnGenericPRBSLSSRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PRBS LSS raise notification."
    ::= { tnGenericAlarmNotifs 479 }

tnGenericPRBSLSSClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "PRBS LSS clear notification."
    ::= { tnGenericAlarmNotifs 480 }

tnGenericCsfGfpRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "GFP Client Signal Failure raise notification."
    ::= { tnGenericAlarmNotifs 481 }

tnGenericCsfGfpClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "GFP Client Signal Failure clear notification."
    ::= { tnGenericAlarmNotifs 482 }

tnGenericGfpExmRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "GFP Extention Header Mismatch raise notification."
    ::= { tnGenericAlarmNotifs 483 }

tnGenericGfpExmClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "GFP Extention Header Mismatch clear notification."
    ::= { tnGenericAlarmNotifs 484 }

tnGenericGfpLofRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "GFP Loss Of Frame raise notification."
    ::= { tnGenericAlarmNotifs 485 }

tnGenericGfpLofClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "GFP Loss Of Frame clear notification."
    ::= { tnGenericAlarmNotifs 486 }

tnGenericGfpUpmRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "GFP User Payload Mismatch raise notification."
    ::= { tnGenericAlarmNotifs 487 }

tnGenericGfpUpmClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "GFP User Payload Mismatch clear notification."
    ::= { tnGenericAlarmNotifs 488 }

tnGenericLOFLOMRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Frame Loss Of Multiframe raise notification."
    ::= { tnGenericAlarmNotifs 489 }

tnGenericLOFLOMClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Loss Of Frame Loss Of Multiframe clear notification."
    ::= { tnGenericAlarmNotifs 490 }

tnGenericMsimRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Multiplex Structure Identifier Mismatch raise notification."
    ::= { tnGenericAlarmNotifs 491 }

tnGenericMsimClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Multiplex Structure Identifier Mismatch clear notification."
    ::= { tnGenericAlarmNotifs 492 }

tnGenericPayloadTypeMismatchRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Payload Type Mismatch raise notification."
    ::= { tnGenericAlarmNotifs 493 }

tnGenericPayloadTypeMismatchClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Payload Type Mismatch clear notification."
    ::= { tnGenericAlarmNotifs 494 }

tnGenericIntrusionRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Intrusion raise notification."
    ::= { tnGenericAlarmNotifs 495 }

tnGenericIntrusionClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Intrusion clear notification."
    ::= { tnGenericAlarmNotifs 496 }


tnGenericNtpOutOfSyncRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "NTP Out-Of-Sync raise notification."
    ::= { tnGenericAlarmNotifs 497 }

tnGenericNtpOutOfSyncClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "NTP Out-Of-Sync clear notification."
    ::= { tnGenericAlarmNotifs 498 }

tnGenericTxAutoLaserShutdownRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "ALS raise notification."
    ::= { tnGenericAlarmNotifs 499 }

tnGenericTxAutoLaserShutdownClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "ALS clear notification."
    ::= { tnGenericAlarmNotifs 500 }

tnGenericTBerPreFec15minRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Pre-FEC BER Threshold Crossing Alert 15min raise notification."
    ::= { tnGenericAlarmNotifs 501 }

tnGenericTBerPreFec15minClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Pre-FEC BER Threshold Crossing Alert 15min clear notification."
    ::= { tnGenericAlarmNotifs 502 }

tnGenericTBerPreFec1dayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Pre-FEC BER Threshold Crossing Alert 1day raise notification."
    ::= { tnGenericAlarmNotifs 503 }

tnGenericTBerPreFec1dayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Pre-FEC BER Threshold Crossing Alert 1day clear notification."
    ::= { tnGenericAlarmNotifs 504 }

tnGenericTBerPostFec15minRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Post-FEC BER Threshold Crossing Alert 15min raise notification."
    ::= { tnGenericAlarmNotifs 505 }

tnGenericTBerPostFec15minClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Post-FEC BER Threshold Crossing Alert 15min clear notification."
    ::= { tnGenericAlarmNotifs 506 }

tnGenericTBerPostFec1dayRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Post-FEC BER Threshold Crossing Alert 1day raise notification."
    ::= { tnGenericAlarmNotifs 507 }

tnGenericTBerPostFec1dayClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Post-FEC BER Threshold Crossing Alert 1day clear notification."
    ::= { tnGenericAlarmNotifs 508 }

tnGenericUruSRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Underlying Resource Unavailable Section raise notification."
    ::= { tnGenericAlarmNotifs 509 }

tnGenericUruSClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS      current
    DESCRIPTION "Underlying Resource Unavailable Section clear notification."
    ::= { tnGenericAlarmNotifs 510 }

tnGenericNeCertValidityWarnRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "NE certificate expiry warning raise notification."
    ::= { tnGenericAlarmNotifs 511 }

tnGenericNeCertValidityWarnClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "NE certificate expiry warning clear notification."
    ::= { tnGenericAlarmNotifs 512 }

tnGenericNeCertValidityExpRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "NE certificate expired raise notification."
    ::= { tnGenericAlarmNotifs 513 }

tnGenericNeCertValidityExpClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "NE certificate expired clear notification."
    ::= { tnGenericAlarmNotifs 514 }

tnGenericVoltageLowRaisedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Voltage Low raise notification."
    ::= { tnGenericAlarmNotifs 515 }

tnGenericVoltageLowClearedNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapDateAndTime,
        tnGenericTrapEntityType
    }
    STATUS current
    DESCRIPTION "Voltage Low clear notification."
    ::= { tnGenericAlarmNotifs 516 }

-------------------------------------------------------------------------------
-- Generic Event Notifications
-------------------------------------------------------------------------------

tnGenericPmBinsRolledOverNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the completion of a PM binning interval."
    ::= { tnGenericEventNotifs 1 }

tnGenericSecurityFileNameNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the name of a transferable file."
    ::= { tnGenericEventNotifs 2 }

tnGenericSecurityLoginNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies a remote login on the system."
    ::= { tnGenericEventNotifs 3 }

tnGenericSecurityLogoutNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies a remote log-out on the system."
    ::= { tnGenericEventNotifs 4 }

tnGenericSecurityAddAccountNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the addition of a user account on the system."
    ::= { tnGenericEventNotifs 5 }

tnGenericSecurityDeleteAccountNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the deletion of a user account on the system."
    ::= { tnGenericEventNotifs 6 }

tnGenericSecurityChangeAccountNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies a modification of a user account on the system."
    ::= { tnGenericEventNotifs 7 }

tnGenericSubgroupSelectNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the selected Link Aggregation Group (LAG) subgroup."
    ::= { tnGenericEventNotifs 8 }

tnGenericDot1agCfmDmTestCompleteNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the completion of an on-demand DM test."
    ::= { tnGenericEventNotifs 9 }

tnGenericDot1agCfmSlmTestCompleteNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the completion of an on-demand SLM test."
    ::= { tnGenericEventNotifs 10 }

tnGenericDot1agCfmLmTestCompleteNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the completion of an on-demand LM test."
    ::= { tnGenericEventNotifs 11 }

tnGenericSecurityExceededLoginAttemptsNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies exceeded login attempts of a user account."
    ::= { tnGenericEventNotifs 12 }

tnGenericSecurityLockAccountNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the locking of a user account."
    ::= { tnGenericEventNotifs 13 }

tnGenericSecurityUnlockAccountNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the unlocking of a user account."
    ::= { tnGenericEventNotifs 14 }

tnGenericSecurityUnauthAccessAttemptNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies an unauthorized access attempt."
    ::= { tnGenericEventNotifs 15 }

tnGenericSecurityEnableInterfaceNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the enabling of an interface."
    ::= { tnGenericEventNotifs 16 }

tnGenericSecurityDisableInterfaceNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the disabling of an interface."
    ::= { tnGenericEventNotifs 17 }

tnGenericDiscoverMeNotif NOTIFICATION-TYPE
    OBJECTS {
        tnGenericTrapSeqNumber,
        tnGenericTrapObject,
        tnGenericTrapObjectInstance,
        tnGenericTrapTime,
        tnGenericTrapCategory,
        tnGenericTrapDescr,
        tnGenericTrapData,
        tnGenericTrapDateAndTime
    }
    STATUS current
    DESCRIPTION "Notifies the existence of the system."
    ::= { tnGenericEventNotifs 18 }

-------------------------------------------------------------------------------
-- Generic Scalar Configuration Change Notifications
-------------------------------------------------------------------------------

tnGenericScalarChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Scalar object configuration change notification."
::= { tnGenericScalarNotifs 1 }

-------------------------------------------------------------------------------
-- Generic Interface (IF-MIB)  Configuration Change Notifications
-------------------------------------------------------------------------------

tnGenericIfConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Interface (IF-MIB, ifTable) configuration change
                 notification."
::= { tnGenericInterfaceNotifs 1 }

tnGenericIfOperStatusChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime
    }
    STATUS current
    DESCRIPTION "Interface operational status (IF-MIB, ifOperStatus) change
                 notification."
    ::= { tnGenericInterfaceNotifs 2 }

-------------------------------------------------------------------------------
-- Generic Optical Interface (OPT-IF-MIB) Configuration
-- Change Notifications
-------------------------------------------------------------------------------

tnGenericOptIfOTUkConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Optical interface OTUk (OPT-IF-MIB, optIfOTUkConfigTable)
                 configuration change notification."
::= { tnGenericOptIfNotifs 1 }

-------------------------------------------------------------------------------
-- Generic Access Port (TROPIC-ACCESSPORT-MIB) Configuration
-- Change Notifications
-------------------------------------------------------------------------------

tnGenericTnAccessPortConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Access port (TROPIC-ACCESSPORT-MIB, tnAccessPortTable)
                 configuration change notification."
::= { tnGenericTnAccessPortNotifs 1 }

tnGenericTnIfConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Interface (TROPIC-ACCESSPORT-MIB, tnIfTable)
                 configuration change notification."
::= { tnGenericTnAccessPortNotifs 2 }

-------------------------------------------------------------------------------
-- Generic Optical Port (TROPIC-OPTICALPORT-MIB) Configuration
-- Change Notifications
-------------------------------------------------------------------------------

tnGenericTnLoopbackPortConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Loopback port (TROPIC-OPTICALPORT-MIB, tnLoopbackPortTable)
                 configuration change notification."
::= { tnGenericTnOpticalPortNotifs 1 }

tnGenericTnDwdmCmnClientPortConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "DWDM Common Client port (TROPIC-OPTICALPORT-MIB,
                 tnDwdmCmnClientPortConfigTable) configuration change
                 notification."
::= { tnGenericTnOpticalPortNotifs 2 }

-------------------------------------------------------------------------------
-- Generic OTU/ODU (TROPIC-OTUODU-MIB) Configuration
-- Change Notifications
-------------------------------------------------------------------------------

tnGenericTnOtukConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "OTUk (TROPIC-OTUODU-MIB, tnOtukTable) configuration change
                 notification."
::= { tnGenericTnOtuOduNotifs 1 }

-------------------------------------------------------------------------------
-- Generic OTH (TROPIC-OTH-MIB) Configuration Change Notifications
-------------------------------------------------------------------------------

tnGenericTnOthOdukNimConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "ODUk NIM (TROPIC-OTH-MIB, tnOthOdukNimTable) configuration
                 change notification."
::= { tnGenericTnOthNotifs 1 }

tnGenericTnOthOdukTtpConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "ODUk TTP (TROPIC-OTH-MIB, tnOthOdukTtpTable) configuration
                 change notification."
::= { tnGenericTnOthNotifs 2 }

tnGenericTnOthOdukTConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "ODUkT (TROPIC-OTH-MIB, tnOthOdukTTable) configuration
                 change notification."
::= { tnGenericTnOthNotifs 3 }

tnGenericTnOthOdukTCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "ODUkT (TROPIC-OTH-MIB, tnOthOdukTTable) creation
                 notification."
::= { tnGenericTnOthNotifs 4 }

tnGenericTnOthOdukTDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "ODUkT (TROPIC-OTH-MIB, tnOthOdukTTable) deletion
                 notification."
::= { tnGenericTnOthNotifs 5 }

tnGenericTnOthOdukApsGroupConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "ODUk APS group (TROPIC-OTH-MIB, tnOthOdukApsGroupTable)
                 configuration change notification."
::= { tnGenericTnOthNotifs 6 }

tnGenericTnOthOdukXcConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "ODUk cross connect (TROPIC-OTH-MIB, tnOthOdukXcTable)
                 configuration change notification."
::= { tnGenericTnOthNotifs 7 }

tnGenericTnOthOdukApsGroupConvertNotif NOTIFICATION-TYPE
    OBJECTS {
        tnGenericTrapSeqNumber,
        tnGenericTrapObject,
        tnGenericTrapObjectInstance,
        tnGenericTrapTime,
        tnGenericTrapCategory,
        tnGenericTrapOthOdukApsAction,
        tnGenericTrapOthOdukApsFromedIfIndex,
        tnGenericTrapOthOdukApsFromedIfIndexLo,
        tnGenericTrapOthOdukApsFromingIfIndex,
        tnGenericTrapOthOdukApsFromingIfIndexLo,
        tnGenericTrapDateAndTime,
        tnGenericTrapConfigurationChangeCounter
    }
    STATUS      current
    DESCRIPTION "ODUk APS group (TROPIC-OTH-MIB, tnOthOdukApsGroupTable)
                 convert notification."
::= { tnGenericTnOthNotifs 8 }

tnGenericTnOthOdukXcCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "ODUk XC (TROPIC-OTH-MIB, tnOthOdukXcTable) creation
                 notification."
::= { tnGenericTnOthNotifs 9 }

tnGenericTnOthOdukXcDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "ODUk XC (TROPIC-OTH-MIB, tnOthOdukXcTable) deletion
                 notification."
::= { tnGenericTnOthNotifs 10 }

-------------------------------------------------------------------------------
-- Generic L1 service (TROPIC-L1SERVICE-MIB) Configuration Change
-- Notifications
-------------------------------------------------------------------------------

tnGenericTnNetIfConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Network interface for EEC (TROPIC-L1SERVICE-MIB, tnNetIfTable)
                 configuration change notification."
::= { tnGenericTnL1ServiceNotifs 1 }

tnGenericTnNetIfFacilityConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Network interface facility (TROPIC-L1SERVICE-MIB,
                 tnNetIfFacilityTable) configuration change notification."
::= { tnGenericTnL1ServiceNotifs 2 }

tnGenericTnNetIfFacilityCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "Network interface facility (TROPIC-L1SERVICE-MIB,
                 tnNetIfFacilityTable) creation notification."
::= { tnGenericTnL1ServiceNotifs 3 }

tnGenericTnNetIfFacilityDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "Network interface facility (TROPIC-L1SERVICE-MIB,
                 tnNetIfFacilityTable) deletion notification."
::= { tnGenericTnL1ServiceNotifs 4 }

tnGenericTnControlNetworkLinkConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Control Network Link (TROPIC-L1SERVICE-MIB, tnControlNetworkLinkTable)
                 configuration change notification."
::= { tnGenericTnL1ServiceNotifs 5 }

tnGenericTnControlNetworkLinkStateChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime
    }
    STATUS current
    DESCRIPTION "Control Network Link (TROPIC-L1SERVICE-MIB, tnControlNetworkLinkTable)
                 state change notification."
    ::= { tnGenericTnL1ServiceNotifs 6 }

-------------------------------------------------------------------------------
-- Generic Statistics (TROPIC-STATISTICS-MIB) Configuration Change
-- Notifications
-------------------------------------------------------------------------------

tnGenericTnStatsTCAProfileConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "TCA profile (TROPIC-STATISTICS-MIB, tnStatsTCAProfileTable)
                 configuration change notification."
::= { tnGenericTnStatisticsNotifs 1 }

tnGenericTnStatsTCAConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "TCA (TROPIC-STATISTICS-MIB, tnStatsTCATable)
                 configuration change notification."
::= { tnGenericTnStatisticsNotifs 2 }

tnGenericTnOtuStatsPortConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "OTUk statistics port (TROPIC-STATISTICS-MIB,
                 tnOtuStatsPortTable) configuration change notification."
::= { tnGenericTnStatisticsNotifs 3 }

tnGenericTnOdukStatsTcmConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "ODUk TCM statistics (TROPIC-STATISTICS-MIB,
                 tnOthOdukStatsTcmConfigTable) configuration change
                 notification."
::= { tnGenericTnStatisticsNotifs 4 }

tnGenericTnOdukStatsRxConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "ODUk RX statistics (TROPIC-STATISTICS-MIB,
                 tnOthOdukStatsRxConfigTable) configuration change
                 notification."
::= { tnGenericTnStatisticsNotifs 5 }

-------------------------------------------------------------------------------
-- Generic LAG (TN-LAG-MIB) Configuration Change
-- Notifications
-------------------------------------------------------------------------------

tnGenericTnLagPortConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "LAG port (TN-LAG-MIB, tnLagPortTableTable)
                 configuration change notification."
::= { tnGenericTnLagNotifs 1 }

tnGenericTnLagCommandConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "LAG command (TN-LAG-MIB, tnLagCommandTableTable)
                 configuration change notification."
::= { tnGenericTnLagNotifs 2 }

-------------------------------------------------------------------------------
-- Generic PMON (TN-PMON-MIB) Configuration Change
-- Notifications
-------------------------------------------------------------------------------

tnGenericTnPmonPolicyConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "PMON Policy (TN-PMON-MIB, tnPmonPolicyTable)
                 configuration change notification."
::= { tnGenericTnPmonNotifs 1 }

tnGenericTnPmonTcaConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "PMON TCA (TN-PMON-MIB, tnPmonTcaTable)
                 configuration change notification."
::= { tnGenericTnPmonNotifs 2 }

-------------------------------------------------------------------------------
-- Generic port (TN-PORT-MIB) Configuration Change
-- Notifications
-------------------------------------------------------------------------------

tnGenericTnPortEtherConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Ethernet Port (TN-PORT-MIB, tnPortEtherTable)
                 configuration change notification."
::= { tnGenericTnPortNotifs 1 }

-------------------------------------------------------------------------------
-- Generic CFM (IEEE8021-CFM-MIB) Configuration Change
-- Notifications
-------------------------------------------------------------------------------

tnGenericDot1agCfmMdConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "CFM Maintenance Domain (IEEE8021-CFM-MIB, dot1agCfmMdTable)
                 configuration change notification."
::= { tnGenericDot1agCfmNotifs 1 }

tnGenericDot1agCfmMdCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM Maintenance Domain (IEEE8021-CFM-MIB, dot1agCfmMdTable)
                 creation notification."
::= { tnGenericDot1agCfmNotifs 2 }

tnGenericDot1agCfmMdDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM Maintenance Domain (IEEE8021-CFM-MIB, dot1agCfmMdTable)
                 deletion notification."
::= { tnGenericDot1agCfmNotifs 3 }

tnGenericDot1agCfmMaNetConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "CFM Maintenance Association (IEEE8021-CFM-MIB,
                  dot1agCfmMaNetTable) configuration change notification."
::= { tnGenericDot1agCfmNotifs 4 }

tnGenericDot1agCfmMaNetCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM Maintenance Association (IEEE8021-CFM-MIB,
                 dot1agCfmMaNetTable) creation notification."
::= { tnGenericDot1agCfmNotifs 5 }

tnGenericDot1agCfmMaNetDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM Maintenance Association (IEEE8021-CFM-MIB,
                 dot1agCfmMaNetTable) deletion notification."
::= { tnGenericDot1agCfmNotifs 6 }

tnGenericDot1agCfmMaCompConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "CFM Maintenance Association component (IEEE8021-CFM-MIB,
                 dot1agCfmMaCompTable) configuration change notification."
::= { tnGenericDot1agCfmNotifs 7 }

tnGenericDot1agCfmMaCompCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM Maintenance Association component (IEEE8021-CFM-MIB,
                 dot1agCfmMaCompTable) creation notification."
::= { tnGenericDot1agCfmNotifs 8 }

tnGenericDot1agCfmMaCompDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM Maintenance Association component (IEEE8021-CFM-MIB,
                 dot1agCfmMaCompTable) deletion notification."
::= { tnGenericDot1agCfmNotifs 9 }


tnGenericDot1agCfmMaMepListCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM List of MEPIDs belonging to a Maintenance Association
                 (IEEE8021-CFM-MIB, dot1agCfmMaMepListTable) creation
                 notification."
::= { tnGenericDot1agCfmNotifs 10 }

tnGenericDot1agCfmMaMepListDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM List of MEPIDs belonging to a Maintenance Association
                 (IEEE8021-CFM-MIB, dot1agCfmMaMepListTable) deletion
                 notification."
::= { tnGenericDot1agCfmNotifs 11 }

tnGenericDot1agCfmMepConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "CFM Maintenance Association End Point (MEP)
                 (IEEE8021-CFM-MIB, dot1agCfmMepTable) configuration
                 change notification."
::= { tnGenericDot1agCfmNotifs 12 }

tnGenericDot1agCfmMepCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM Maintenance Association End Point (MEP)
                 (IEEE8021-CFM-MIB, dot1agCfmMepTable) creation
                 notification."
::= { tnGenericDot1agCfmNotifs 13 }

tnGenericDot1agCfmMepDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "CFM Maintenance Association End Point (MEP)
                 (IEEE8021-CFM-MIB, dot1agCfmMepTable) deletion
                 notification."
::= { tnGenericDot1agCfmNotifs 14 }

-------------------------------------------------------------------------------
-- Generic CFM (TN-IEEE8021-CFM-MIB) Configuration Change
-- Notifications
-------------------------------------------------------------------------------

tnGenericTnDot1agCfmMepConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "CFM Maintenance Association End Point (MEP)
                 (TN-IEEE8021-CFM-MIB, tnDot1agCfmMepTable) configuration
                 change notification."
::= { tnGenericTnDot1agCfmNotifs 1 }

tnGenericTnDot1agCfmMepSlmTWTestConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Two-way on-demand SLM test (TN-IEEE8021-CFM-MIB,
                 tnDot1agCfmMepSlmTWTestTable) configuration change
                 notification."
::= { tnGenericTnDot1agCfmNotifs 2 }

tnGenericTnDot1agCfmMepOndemandLmTestConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Two-way on-demand LM test (TN-IEEE8021-CFM-MIB,
                 tnDot1agCfmMepOndemandLmTestTable) configuration change
                 notification."
::= { tnGenericTnDot1agCfmNotifs 3 }

-------------------------------------------------------------------------------
-- Generic OAM TEST (TN-OAM-TEST-MIB) Configuration Change Notifications
-------------------------------------------------------------------------------
tnGenericTnOamPingCtlCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "OAM Ping control (TN-OAM-TEST-MIB, tnOamPingCtlTable)
                 creation notification."
::= { tnGenericTnOamTestNotifs 1 }

tnGenericTnOamPingCtlDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "OAM Ping control (TN-OAM-TEST-MIB, tnOamPingCtlTable)
                 deletion notification."
::= { tnGenericTnOamTestNotifs 2 }


tnGenericTnOamSaaCtlConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "OAM Service Assurance Agent (SAA) control (TN-OAM-TEST-MIB,
                 tnOamSaaCtlTable) configuration change notification."
::= { tnGenericTnOamTestNotifs 3 }

-------------------------------------------------------------------------------
-- Generic Radius Server Creation Change Notifications
-------------------------------------------------------------------------------
tnGenericRadiusServerCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "Radius server (TROPIC-EXPRSCALARS, tnRadiusServerTable)
                 creation notification."
::= { tnGenericRadiusNotifs 1 }

tnGenericRadiusServerDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "Radius server (TROPIC-EXPRSCALARS, tnRadiusServerTable)
                 deletion notification."
::= { tnGenericRadiusNotifs 2 }

tnGenericRadiusServerConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Radius server (TROPIC-EXPRSCALARS, tnRadiusServerTable)
                 configuration change notification."
::= { tnGenericRadiusNotifs 3 }

-------------------------------------------------------------------------------
-- Generic Syslog Server Creation Change Notifications
-------------------------------------------------------------------------------
tnGenericSyslogServerCreationNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "Syslog server (TROPIC-SYSTEM-MIB, tnSyslogServerTable)
                 creation notification."
::= { tnGenericSyslogNotifs 1 }

tnGenericSyslogServerDeletionNotif NOTIFICATION-TYPE
    OBJECTS {
        tnGenericTrapSeqNumber,
        tnGenericTrapObject,
        tnGenericTrapObjectInstance,
        tnGenericTrapTime,
        tnGenericTrapCategory,
        tnGenericTrapDateAndTime,
        tnGenericTrapConfigurationChangeCounter
    }
    STATUS      current
    DESCRIPTION "Syslog server (TROPIC-SYSTEM-MIB, tnSyslogServerTable)
                 deletion notification."
::= { tnGenericSyslogNotifs 2 }

tnGenericSyslogServerConfigChangeNotif NOTIFICATION-TYPE
    OBJECTS {
        tnGenericTrapSeqNumber,
        tnGenericTrapObject,
        tnGenericTrapObjectInstance,
        tnGenericTrapTime,
        tnGenericTrapCategory,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericTrapDateAndTime,
        tnGenericTrapConfigurationChangeCounter
    }
    STATUS      current
    DESCRIPTION "Syslog server (TROPIC-SYSTEM-MIB, tnSyslogServerTable)
                 configuration change notification."
::= { tnGenericSyslogNotifs 3 }

-------------------------------------------------------------------------------
-- Generic Transfer PM Discovery Notifications
-------------------------------------------------------------------------------
tnGenericTransferPMDiscoveryCreationNotif NOTIFICATION-TYPE
     OBJECTS {
         tnGenericTrapSeqNumber,
         tnGenericTrapObject,
         tnGenericTrapObjectInstance,
         tnGenericTrapTime,
         tnGenericTrapCategory,
         tnGenericTrapDateAndTime,
         tnGenericTrapConfigurationChangeCounter
     }
     STATUS      current
     DESCRIPTION "Transfer PM Discovery server (TROPIC-SYSTEM-MIB,
                  tnTransferPMDiscoveryTable) creation notification."
::= { tnGenericTransferPMDiscoveryNotifs 1 }

tnGenericTransferPMDiscoveryDeletionNotif NOTIFICATION-TYPE
     OBJECTS {
         tnGenericTrapSeqNumber,
         tnGenericTrapObject,
         tnGenericTrapObjectInstance,
         tnGenericTrapTime,
         tnGenericTrapCategory,
         tnGenericTrapDateAndTime,
         tnGenericTrapConfigurationChangeCounter
     }
     STATUS      current
     DESCRIPTION "Transfer PM Discovery server (TROPIC-SYSTEM-MIB,
                  tnTransferPMDiscoveryTable) deletion notification."
::= { tnGenericTransferPMDiscoveryNotifs 2 }

tnGenericTransferPMDiscoveryConfigChangeNotif NOTIFICATION-TYPE
     OBJECTS {
         tnGenericTrapSeqNumber,
         tnGenericTrapObject,
         tnGenericTrapObjectInstance,
         tnGenericTrapTime,
         tnGenericTrapCategory,
         tnGenericTrapObjectValueType,
         tnGenericTrapObjectCounter32Val,
         tnGenericTrapObjectUnsigned32Val,
         tnGenericTrapObjectTimeTicksVal,
         tnGenericTrapObjectInteger32Val,
         tnGenericTrapObjectOctetStringVal,
         tnGenericTrapObjectIpAddressVal,
         tnGenericTrapObjectOidVal,
         tnGenericTrapObjectCounter64Val,
         tnGenericTrapDateAndTime,
         tnGenericTrapConfigurationChangeCounter
     }
     STATUS      current
     DESCRIPTION "Transfer PM Discovery server (TROPIC-SYSTEM-MIB,
                  tnTransferPMDiscoveryTable) configuration change
                  notification."
::= { tnGenericTransferPMDiscoveryNotifs 3 }

-------------------------------------------------------------------------------
-- Conformance Group Definitions
-------------------------------------------------------------------------------

tnGenericTrapBufferGroup OBJECT-GROUP
    OBJECTS {
        tnGenericTrapType,
        tnGenericTrapObject,
        tnGenericTrapObjectInstance,
        tnGenericTrapTime,
        tnGenericTrapCategory,
        tnGenericTrapDescr,
        tnGenericTrapData,
        tnGenericTrapServiceAffecting,
        tnGenericTrapCondition,
        tnGenericTrapObjectValueType,
        tnGenericTrapObjectCounter32Val,
        tnGenericTrapObjectUnsigned32Val,
        tnGenericTrapObjectTimeTicksVal,
        tnGenericTrapObjectInteger32Val,
        tnGenericTrapObjectOctetStringVal,
        tnGenericTrapObjectIpAddressVal,
        tnGenericTrapObjectOidVal,
        tnGenericTrapObjectCounter64Val,
        tnGenericLastIssuedTrapNumber,
        tnGenericTrapNumberResetToBeHandled,
        tnGenericTrapDateAndTime,
        tnGenericTrapConfigurationChangeCounter,
        tnGenericTrapEntityType
    }
    STATUS         current
    DESCRIPTION    "Generic Trap Buffer group."
    ::= { tnGenericTrapBufferGroups 1 }

tnGenericTrapGroup OBJECT-GROUP
    OBJECTS {
        tnGenericTrapSeqNumber,
        tnGenericTrapOthOdukApsAction,
        tnGenericTrapOthOdukApsFromedIfIndex,
        tnGenericTrapOthOdukApsFromedIfIndexLo,
        tnGenericTrapOthOdukApsFromingIfIndex,
        tnGenericTrapOthOdukApsFromingIfIndexLo
    }
    STATUS  current
    DESCRIPTION
            "Generic Trap group."
    ::= { tnGenericTrapGroups 1 }

tnGenericConfigurationChangeNotifsGroup NOTIFICATION-GROUP
    NOTIFICATIONS {
        tnGenericConfigurationChangeNotif
    }
    STATUS         current
    DESCRIPTION    "Generic configuration change group."
    ::= { tnGenericTrapGroups 2 }

tnGenericStateChangeNotifsGroup NOTIFICATION-GROUP
    NOTIFICATIONS {
        tnGenericStateChangeNotif
    }
    STATUS         current
    DESCRIPTION    "Generic state change group."
    ::= { tnGenericTrapGroups 3 }

tnGenericTreeUpdateNotifsGroup NOTIFICATION-GROUP
    NOTIFICATIONS {
        tnGenericTreeUpdateNotif
    }
    STATUS         current
    DESCRIPTION    "Generic Tree update group."
    ::= { tnGenericTrapGroups 4 }

tnGenericAlarmNotifsGroup NOTIFICATION-GROUP
    NOTIFICATIONS {
        tnGenericBackwardDefectIndicationRaisedNotif,
        tnGenericBackwardDefectIndicationClearedNotif,
        tnGenericOduBackwardDefectIndicationRaisedNotif,
        tnGenericOduBackwardDefectIndicationClearedNotif,
        tnGenericTcmBackwardDefectIndicationRaisedNotif,
        tnGenericTcmBackwardDefectIndicationClearedNotif,
        tnGenericCommDownRaisedNotif,
        tnGenericCommDownClearedNotif,
        tnGenericSignalDegradeRaisedNotif,
        tnGenericSignalDegradeClearedNotif,
        tnGenericOduSignalDegradeRaisedNotif,
        tnGenericOduSignalDegradeClearedNotif,
        tnGenericTcmSignalDegradeRaisedNotif,
        tnGenericTcmSignalDegradeClearedNotif,
        tnGenericBoardEqptRaisedNotif,
        tnGenericBoardEqptClearedNotif,
        tnGenericEqptPortRaisedNotif,
        tnGenericEqptPortClearedNotif,
        tnGenericIntTempHighRaisedNotif,
        tnGenericIntTempHighClearedNotif,
        tnGenericLockedIndicationRaisedNotif,
        tnGenericLockedIndicationClearedNotif,
        tnGenericTcmLockedIndicationRaisedNotif,
        tnGenericTcmLockedIndicationClearedNotif,
        tnGenericDwLossOfFrameRaisedNotif,
        tnGenericDwLossOfFrameClearedNotif,
        tnGenericDwLossOfMultiFrameRaisedNotif,
        tnGenericDwLossOfMultiFrameClearedNotif,
        tnGenericLossOfSignalRaisedNotif,
        tnGenericLossOfSignalClearedNotif,
        tnGenericTcmLossofTandemConnectionRaisedNotif,
        tnGenericTcmLossofTandemConnectionClearedNotif,
        tnGenericInMaintenanceRaisedNotif,
        tnGenericInMaintenanceClearedNotif,
        tnGenericOpticsModuleMismatchRaisedNotif,
        tnGenericOpticsModuleMismatchClearedNotif,
        tnGenericOpenConnectionIndicationRaisedNotif,
        tnGenericOpenConnectionIndicationClearedNotif,
        tnGenericTcmOpenConnectionIndicationRaisedNotif,
        tnGenericTcmOpenConnectionIndicationClearedNotif,
        tnGenericReplUnitMissMODRaisedNotif,
        tnGenericReplUnitMissMODClearedNotif,
        tnGenericServerSignalFailureEgressRaisedNotif,
        tnGenericServerSignalFailureEgressClearedNotif,
        tnGenericServerSignalFailureRaisedNotif,
        tnGenericServerSignalFailureClearedNotif,
        tnGenericOduServerSignalFailureRaisedNotif,
        tnGenericOduServerSignalFailureClearedNotif,
        tnGenericTcmServerSignalFailureRaisedNotif,
        tnGenericTcmServerSignalFailureClearedNotif,
        tnGenericCardInitializingRaisedNotif,
        tnGenericCardInitializingClearedNotif,
        tnGenericTBbeOdu15MinRaisedNotif,
        tnGenericTBbeOdu15MinClearedNotif,
        tnGenericTBbeOdu1DayRaisedNotif,
        tnGenericTBbeOdu1DayClearedNotif,
        tnGenericTBbeOtu15MinRaisedNotif,
        tnGenericTBbeOtu15MinClearedNotif,
        tnGenericTBbeOtu1DayRaisedNotif,
        tnGenericTBbeOtu1DayClearedNotif,
        tnGenericTBbeTcm15MinRaisedNotif,
        tnGenericTBbeTcm15MinClearedNotif,
        tnGenericTBbeTcm1DayRaisedNotif,
        tnGenericTBbeTcm1DayClearedNotif,
        tnGenericTEsOdu15MinRaisedNotif,
        tnGenericTEsOdu15MinClearedNotif,
        tnGenericTEsOdu1DayRaisedNotif,
        tnGenericTEsOdu1DayClearedNotif,
        tnGenericTEsOtu15MinRaisedNotif,
        tnGenericTEsOtu15MinClearedNotif,
        tnGenericTEsOtu1DayRaisedNotif,
        tnGenericTEsOtu1DayClearedNotif,
        tnGenericTEsTcm15MinRaisedNotif,
        tnGenericTEsTcm15MinClearedNotif,
        tnGenericTEsTcm1DayRaisedNotif,
        tnGenericTEsTcm1DayClearedNotif,
        tnGenericTFecc15MinRaisedNotif,
        tnGenericTFecc15MinClearedNotif,
        tnGenericTFecc1DayRaisedNotif,
        tnGenericTFecc1DayClearedNotif,
        tnGenericTrailTraceIdentifierMismatchRaisedNotif,
        tnGenericTrailTraceIdentifierMismatchClearedNotif,
        tnGenericOduTrailTraceIdentifierMismatchRaisedNotif,
        tnGenericOduTrailTraceIdentifierMismatchClearedNotif,
        tnGenericTcmTrailTraceIdentifierMismatchRaisedNotif,
        tnGenericTcmTrailTraceIdentifierMismatchClearedNotif,
        tnGenericOpticsModuleUnknownRaisedNotif,
        tnGenericOpticsModuleUnknownClearedNotif,
        tnGenericUruORaisedNotif,
        tnGenericUruOClearedNotif,
        tnGenericUruPRaisedNotif,
        tnGenericUruPClearedNotif,
        tnGenericOduUruPRaisedNotif,
        tnGenericOduUruPClearedNotif,
        tnGenericTcmUruPRaisedNotif,
        tnGenericTcmUruPClearedNotif,
        tnGenericApsLockoutOfProtectionRaisedNotif,
        tnGenericApsLockoutOfProtectionClearedNotif,
        tnGenericApsWorkingForceSwitchedBackToWorkingRaisedNotif,
        tnGenericApsWorkingForceSwitchedBackToWorkingClearedNotif,
        tnGenericApsWorkingForceSwitchedToProtectRaisedNotif,
        tnGenericApsWorkingForceSwitchedToProtectClearedNotif,
        tnGenericApsWorkingManualSwitchedBackToWorkingRaisedNotif,
        tnGenericApsWorkingManualSwitchedBackToWorkingClearedNotif,
        tnGenericApsSwitchedToWorkRaisedNotif,
        tnGenericApsSwitchedToWorkClearedNotif,
        tnGenericApsWorkingSwitchedToProtectRaisedNotif,
        tnGenericApsWorkingSwitchedToProtectClearedNotif,
        tnGenericApsWorkingManualSwitchedToProtectRaisedNotif,
        tnGenericApsWorkingManualSwitchedToProtectClearedNotif,
        tnGenericWtrRaisedNotif,
        tnGenericWtrClearedNotif,
        tnGenericTSesOdu15MinRaisedNotif,
        tnGenericTSesOdu15MinClearedNotif,
        tnGenericTSesOdu1DayRaisedNotif,
        tnGenericTSesOdu1DayClearedNotif,
        tnGenericTSesOtu15MinRaisedNotif,
        tnGenericTSesOtu15MinClearedNotif,
        tnGenericTSesOtu1DayRaisedNotif,
        tnGenericTSesOtu1DayClearedNotif,
        tnGenericTSesTcm15MinRaisedNotif,
        tnGenericTSesTcm15MinClearedNotif,
        tnGenericTSesTcm1DayRaisedNotif,
        tnGenericTSesTcm1DayClearedNotif,
        tnGenericTUasOdu15MinRaisedNotif,
        tnGenericTUasOdu15MinClearedNotif,
        tnGenericTUasOdu1DayRaisedNotif,
        tnGenericTUasOdu1DayClearedNotif,
        tnGenericTUasOtu15MinRaisedNotif,
        tnGenericTUasOtu15MinClearedNotif,
        tnGenericTUasOtu1DayRaisedNotif,
        tnGenericTUasOtu1DayClearedNotif,
        tnGenericTUasTcm15MinRaisedNotif,
        tnGenericTUasTcm15MinClearedNotif,
        tnGenericTUasTcm1DayRaisedNotif,
        tnGenericTUasTcm1DayClearedNotif,
        tnGenericApsBlockRaisedNotif,
        tnGenericApsBlockClearedNotif,
        tnGenericApsLOSyncRaisedNotif,
        tnGenericApsLOSyncClearedNotif,
        tnGenericApsLossOfServiceRaisedNotif,
        tnGenericApsLossOfServiceClearedNotif,
        tnGenericApsSuspendedRaisedNotif,
        tnGenericApsSuspendedClearedNotif,
        tnGenericAuditBlockRaisedNotif,
        tnGenericAuditBlockClearedNotif,
        tnGenericBreaker1BatteryFeedDownRaisedNotif,
        tnGenericBreaker1BatteryFeedDownClearedNotif,
        tnGenericCabinAlarm1RaisedNotif,
        tnGenericCabinAlarm1ClearedNotif,
        tnGenericCabinAlarm2RaisedNotif,
        tnGenericCabinAlarm2ClearedNotif,
        tnGenericCabinAlarm3RaisedNotif,
        tnGenericCabinAlarm3ClearedNotif,
        tnGenericCabinAlarm4RaisedNotif,
        tnGenericCabinAlarm4ClearedNotif,
        tnGenericCardBootRaisedNotif,
        tnGenericCardBootClearedNotif,
        tnGenericCardMissingRaisedNotif,
        tnGenericCardMissingClearedNotif,
        tnGenericCardUnknownRaisedNotif,
        tnGenericCardUnknownClearedNotif,
        tnGenericEqptDgrOchRaisedNotif,
        tnGenericEqptDgrOchClearedNotif,
        tnGenericFrameAlarm1RaisedNotif,
        tnGenericFrameAlarm1ClearedNotif,
        tnGenericFrameAlarm2RaisedNotif,
        tnGenericFrameAlarm2ClearedNotif,
        tnGenericFrameAlarm3RaisedNotif,
        tnGenericFrameAlarm3ClearedNotif,
        tnGenericFrameAlarm4RaisedNotif,
        tnGenericFrameAlarm4ClearedNotif,
        tnGenericFrameAlarm5RaisedNotif,
        tnGenericFrameAlarm5ClearedNotif,
        tnGenericFrameAlarm6RaisedNotif,
        tnGenericFrameAlarm6ClearedNotif,
        tnGenericFrameAlarm7RaisedNotif,
        tnGenericFrameAlarm7ClearedNotif,
        tnGenericFrameAlarm8RaisedNotif,
        tnGenericFrameAlarm8ClearedNotif,
        tnGenericFrameAlarm9RaisedNotif,
        tnGenericFrameAlarm9ClearedNotif,
        tnGenericFrameAlarm10RaisedNotif,
        tnGenericFrameAlarm10ClearedNotif,
        tnGenericFrameAlarm11RaisedNotif,
        tnGenericFrameAlarm11ClearedNotif,
        tnGenericFrameAlarm12RaisedNotif,
        tnGenericFrameAlarm12ClearedNotif,
        tnGenericInterShelfLossofCommsRaisedNotif,
        tnGenericInterShelfLossofCommsClearedNotif,
        tnGenericInventoryErrModRaisedNotif,
        tnGenericInventoryErrModClearedNotif,
        tnGenericLineFacilityLoopbackActiveRaisedNotif,
        tnGenericLineFacilityLoopbackActiveClearedNotif,
        tnGenericLossOfFrameRaisedNotif,
        tnGenericLossOfFrameClearedNotif,
        tnGenericOpticalPowerReceivedOutOfRangeRaisedNotif,
        tnGenericOpticalPowerReceivedOutOfRangeClearedNotif,
        tnGenericSfpTempOORRaisedNotif,
        tnGenericSfpTempOORClearedNotif,
        tnGenericSfpTrmtPwrOORRaisedNotif,
        tnGenericSfpTrmtPwrOORClearedNotif,
        tnGenericSoftwareCompatibilityFailRaisedNotif,
        tnGenericSoftwareCompatibilityFailClearedNotif,
        tnGenericSoftwareUpgradeFailureRaisedNotif,
        tnGenericSoftwareUpgradeFailureClearedNotif,
        tnGenericTCvPcs15MinRaisedNotif,
        tnGenericTCvPcs15MinClearedNotif,
        tnGenericTCvPcs1DayRaisedNotif,
        tnGenericTCvPcs1DayClearedNotif,
        tnGenericTEsPcs15MinRaisedNotif,
        tnGenericTEsPcs15MinClearedNotif,
        tnGenericTEsPcs1DayRaisedNotif,
        tnGenericTEsPcs1DayClearedNotif,
        tnGenericTSefsPcs15MinRaisedNotif,
        tnGenericTSefsPcs15MinClearedNotif,
        tnGenericTSefsPcs1DayRaisedNotif,
        tnGenericTSefsPcs1DayClearedNotif,
        tnGenericTSesPcs15MinRaisedNotif,
        tnGenericTSesPcs15MinClearedNotif,
        tnGenericTSesPcs1DayRaisedNotif,
        tnGenericTSesPcs1DayClearedNotif,
        tnGenericTxSquelchRaisedNotif,
        tnGenericTxSquelchClearedNotif,
        tnGenericUserAlarm1RaisedNotif,
        tnGenericUserAlarm1ClearedNotif,
        tnGenericUserAlarm2RaisedNotif,
        tnGenericUserAlarm2ClearedNotif,
        tnGenericUserAlarm3RaisedNotif,
        tnGenericUserAlarm3ClearedNotif,
        tnGenericUserAlarm4RaisedNotif,
        tnGenericUserAlarm4ClearedNotif,
        tnGenericUserAlarm5RaisedNotif,
        tnGenericUserAlarm5ClearedNotif,
        tnGenericUserAlarm6RaisedNotif,
        tnGenericUserAlarm6ClearedNotif,
        tnGenericUserAlarm7RaisedNotif,
        tnGenericUserAlarm7ClearedNotif,
        tnGenericUserAlarm8RaisedNotif,
        tnGenericUserAlarm8ClearedNotif,
        tnGenericUserAlarm9RaisedNotif,
        tnGenericUserAlarm9ClearedNotif,
        tnGenericUserAlarm10RaisedNotif,
        tnGenericUserAlarm10ClearedNotif,
        tnGenericUserAlarm11RaisedNotif,
        tnGenericUserAlarm11ClearedNotif,
        tnGenericUserAlarm12RaisedNotif,
        tnGenericUserAlarm12ClearedNotif,
        tnGenericUserAlarm13RaisedNotif,
        tnGenericUserAlarm13ClearedNotif,
        tnGenericUserAlarm14RaisedNotif,
        tnGenericUserAlarm14ClearedNotif,
        tnGenericUserAlarm15RaisedNotif,
        tnGenericUserAlarm15ClearedNotif,
        tnGenericUserAlarm16RaisedNotif,
        tnGenericUserAlarm16ClearedNotif,
        tnGenericUserAlarm17RaisedNotif,
        tnGenericUserAlarm17ClearedNotif,
        tnGenericUserAlarm18RaisedNotif,
        tnGenericUserAlarm18ClearedNotif,
        tnGenericUserAlarm19RaisedNotif,
        tnGenericUserAlarm19ClearedNotif,
        tnGenericUserAlarm20RaisedNotif,
        tnGenericUserAlarm20ClearedNotif,
        tnGenericUserAlarm21RaisedNotif,
        tnGenericUserAlarm21ClearedNotif,
        tnGenericUserAlarm22RaisedNotif,
        tnGenericUserAlarm22ClearedNotif,
        tnGenericUserAlarm23RaisedNotif,
        tnGenericUserAlarm23ClearedNotif,
        tnGenericUserAlarm24RaisedNotif,
        tnGenericUserAlarm24ClearedNotif,
        tnGenericUserAlarm25RaisedNotif,
        tnGenericUserAlarm25ClearedNotif,
        tnGenericUserAlarm26RaisedNotif,
        tnGenericUserAlarm26ClearedNotif,
        tnGenericUserAlarm27RaisedNotif,
        tnGenericUserAlarm27ClearedNotif,
        tnGenericUserAlarm28RaisedNotif,
        tnGenericUserAlarm28ClearedNotif,
        tnGenericUserAlarm29RaisedNotif,
        tnGenericUserAlarm29ClearedNotif,
        tnGenericUserAlarm30RaisedNotif,
        tnGenericUserAlarm30ClearedNotif,
        tnGenericUserAlarm31RaisedNotif,
        tnGenericUserAlarm31ClearedNotif,
        tnGenericUserAlarm32RaisedNotif,
        tnGenericUserAlarm32ClearedNotif,
        tnGenericTFeBbeOdu15MinRaisedNotif,
        tnGenericTFeBbeOdu15MinClearedNotif,
        tnGenericTFeBbeOdu1DayRaisedNotif,
        tnGenericTFeBbeOdu1DayClearedNotif,
        tnGenericTFeEsOdu15MinRaisedNotif,
        tnGenericTFeEsOdu15MinClearedNotif,
        tnGenericTFeEsOdu1DayRaisedNotif,
        tnGenericTFeEsOdu1DayClearedNotif,
        tnGenericTFeSesOdu15MinRaisedNotif,
        tnGenericTFeSesOdu15MinClearedNotif,
        tnGenericTFeSesOdu1DayRaisedNotif,
        tnGenericTFeSesOdu1DayClearedNotif,
        tnGenericTFeUasOdu15MinRaisedNotif,
        tnGenericTFeUasOdu15MinClearedNotif,
        tnGenericTFeUasOdu1DayRaisedNotif,
        tnGenericTFeUasOdu1DayClearedNotif,
        tnGenericTFeBbeTcm15MinRaisedNotif,
        tnGenericTFeBbeTcm15MinClearedNotif,
        tnGenericTFeBbeTcm1DayRaisedNotif,
        tnGenericTFeBbeTcm1DayClearedNotif,
        tnGenericTFeEsTcm15MinRaisedNotif,
        tnGenericTFeEsTcm15MinClearedNotif,
        tnGenericTFeEsTcm1DayRaisedNotif,
        tnGenericTFeEsTcm1DayClearedNotif,
        tnGenericTFeSesTcm15MinRaisedNotif,
        tnGenericTFeSesTcm15MinClearedNotif,
        tnGenericTFeSesTcm1DayRaisedNotif,
        tnGenericTFeSesTcm1DayClearedNotif,
        tnGenericTFeUasTcm15MinRaisedNotif,
        tnGenericTFeUasTcm15MinClearedNotif,
        tnGenericTFeUasTcm1DayRaisedNotif,
        tnGenericTFeUasTcm1DayClearedNotif,
        tnGenericTFeBbeOtu15MinRaisedNotif,
        tnGenericTFeBbeOtu15MinClearedNotif,
        tnGenericTFeBbeOtu1DayRaisedNotif,
        tnGenericTFeBbeOtu1DayClearedNotif,
        tnGenericTFeEsOtu15MinRaisedNotif,
        tnGenericTFeEsOtu15MinClearedNotif,
        tnGenericTFeEsOtu1DayRaisedNotif,
        tnGenericTFeEsOtu1DayClearedNotif,
        tnGenericTFeSesOtu15MinRaisedNotif,
        tnGenericTFeSesOtu15MinClearedNotif,
        tnGenericTFeSesOtu1DayRaisedNotif,
        tnGenericTFeSesOtu1DayClearedNotif,
        tnGenericTFeUasOtu15MinRaisedNotif,
        tnGenericTFeUasOtu15MinClearedNotif,
        tnGenericTFeUasOtu1DayRaisedNotif,
        tnGenericTFeUasOtu1DayClearedNotif,
        tnGenericTPmonPortIfInPackets15MinRaisedNotif,
        tnGenericTPmonPortIfInPackets15MinClearedNotif,
        tnGenericTPmonPortIfInPackets1DayRaisedNotif,
        tnGenericTPmonPortIfInPackets1DayClearedNotif,
        tnGenericTPmonPortIfInOctets15MinRaisedNotif,
        tnGenericTPmonPortIfInOctets15MinClearedNotif,
        tnGenericTPmonPortIfInOctets1DayRaisedNotif,
        tnGenericTPmonPortIfInOctets1DayClearedNotif,
        tnGenericTPmonPortIfInDiscards15MinRaisedNotif,
        tnGenericTPmonPortIfInDiscards15MinClearedNotif,
        tnGenericTPmonPortIfInDiscards1DayRaisedNotif,
        tnGenericTPmonPortIfInDiscards1DayClearedNotif,
        tnGenericTPmonPortIfInErrors15MinRaisedNotif,
        tnGenericTPmonPortIfInErrors15MinClearedNotif,
        tnGenericTPmonPortIfInErrors1DayRaisedNotif,
        tnGenericTPmonPortIfInErrors1DayClearedNotif,
        tnGenericTPmonPortIfOutPackets15MinRaisedNotif,
        tnGenericTPmonPortIfOutPackets15MinClearedNotif,
        tnGenericTPmonPortIfOutPackets1DayRaisedNotif,
        tnGenericTPmonPortIfOutPackets1DayClearedNotif,
        tnGenericTPmonPortIfOutOctets15MinRaisedNotif,
        tnGenericTPmonPortIfOutOctets15MinClearedNotif,
        tnGenericTPmonPortIfOutOctets1DayRaisedNotif,
        tnGenericTPmonPortIfOutOctets1DayClearedNotif,
        tnGenericTPmonSlmanFlr1DayRaisedNotif,
        tnGenericTPmonSlmanFlr1DayClearedNotif,
        tnGenericTPmonSlmafFlr1DayRaisedNotif,
        tnGenericTPmonSlmafFlr1DayClearedNotif,
        tnGenericTPmonSlmanflr15MinRaisedNotif,
        tnGenericTPmonSlmanflr15MinClearedNotif,
        tnGenericTPmonSlmafflr15MinRaisedNotif,
        tnGenericTPmonSlmafflr15MinClearedNotif,
        tnGenericTPmonSlmnhli15MinRaisedNotif,
        tnGenericTPmonSlmnhli15MinClearedNotif,
        tnGenericTPmonSlmfhli15MinRaisedNotif,
        tnGenericTPmonSlmfhli15MinClearedNotif,
        tnGenericTPmonSlmnhli1DayRaisedNotif,
        tnGenericTPmonSlmnhli1DayClearedNotif,
        tnGenericTPmonSlmfhli1DayRaisedNotif,
        tnGenericTPmonSlmfhli1DayClearedNotif,
        tnGenericTPmonSlmxfflrContRaisedNotif,
        tnGenericTPmonSlmxfflrContClearedNotif,
        tnGenericTPmonSlmanflrContRaisedNotif,
        tnGenericTPmonSlmanflrContClearedNotif,
        tnGenericTPmonSlmafflrContRaisedNotif,
        tnGenericTPmonSlmafflrContClearedNotif,
        tnGenericTPmonDmaBfd15MinRaisedNotif,
        tnGenericTPmonDmaBfd15MinClearedNotif,
        tnGenericTPmonDmaBfd1DayRaisedNotif,
        tnGenericTPmonDmaBfd1DayClearedNotif,
        tnGenericTPmonDmafFdv15MinRaisedNotif,
        tnGenericTPmonDmafFdv15MinClearedNotif,
        tnGenericTPmonDmafFdv1DayRaisedNotif,
        tnGenericTPmonDmafFdv1DayClearedNotif,
        tnGenericTPmonDmanFdv15MinRaisedNotif,
        tnGenericTPmonDmanFdv15MinClearedNotif,
        tnGenericTPmonDmanFdv1DayRaisedNotif,
        tnGenericTPmonDmanFdv1DayClearedNotif,
        tnGenericTPmonDmxBfd15MinRaisedNotif,
        tnGenericTPmonDmxBfd15MinClearedNotif,
        tnGenericTPmonDmxBfd1DayRaisedNotif,
        tnGenericTPmonDmxBfd1DayClearedNotif,
        tnGenericTPmonDmxfFdv15MinRaisedNotif,
        tnGenericTPmonDmxfFdv15MinClearedNotif,
        tnGenericTPmonDmxfFdv1DayRaisedNotif,
        tnGenericTPmonDmxfFdv1DayClearedNotif,
        tnGenericTPmonDmxnFdv15MinRaisedNotif,
        tnGenericTPmonDmxnFdv15MinClearedNotif,
        tnGenericTPmonDmxnFdv1DayRaisedNotif,
        tnGenericTPmonDmxnFdv1DayClearedNotif,
        tnGenericLagLosRaisedNotif,
        tnGenericLagLosClearedNotif,
        tnGenericMepLocRaisedNotif,
        tnGenericMepLocClearedNotif,
        tnGenericUNLRaisedNotif,
        tnGenericUNLClearedNotif,
        tnGenericMepMmgRaisedNotif,
        tnGenericMepMmgClearedNotif,
        tnGenericUNMRaisedNotif,
        tnGenericUNMClearedNotif,
        tnGenericUNPrRaisedNotif,
        tnGenericUNPrClearedNotif,
        tnGenericRDIRaisedNotif,
        tnGenericRDIClearedNotif,
        tnGenericUNPRaisedNotif,
        tnGenericUNPClearedNotif,
        tnGenericNuatRaisedNotif,
        tnGenericNuatClearedNotif,
        tnGenericFuatRaisedNotif,
        tnGenericFuatClearedNotif,
        tnGenericAutoLaserOffDueToUpstreamFaultRaisedNotif,
        tnGenericAutoLaserOffDueToUpstreamFaultClearedNotif,
        tnGenericLagProtLosRaisedNotif,
        tnGenericLagProtLosClearedNotif,
        tnGenericMonitorExcRaisedNotif,
        tnGenericMonitorExcClearedNotif,
        tnGenericEquipmentLedOnRaisedNotif,
        tnGenericEquipmentLedOnClearedNotif,
        tnGenericUnitInitRaisedNotif,
        tnGenericUnitInitClearedNotif,
        tnGenericCardMismatchRaisedNotif,
        tnGenericCardMismatchClearedNotif,
        tnGenericTPmonSlmxnflrContRaisedNotif,
        tnGenericTPmonSlmxnflrContClearedNotif,
        tnGenericOpticalOutputPowerUnachievableRaisedNotif,
        tnGenericOpticalOutputPowerUnachievableClearedNotif,
        tnGenericDiagnosticTerminalLoopbackActiveRaisedNotif,
        tnGenericDiagnosticTerminalLoopbackActiveClearedNotif,
        tnGenericLocalFaultRaisedNotif,
        tnGenericLocalFaultClearedNotif,
        tnGenericRemoteFailureIndicationRaisedNotif,
        tnGenericRemoteFailureIndicationClearedNotif,
        tnGenericOduClientSignalFailureRaisedNotif,
        tnGenericOduClientSignalFailureClearedNotif,
        tnGenericPRBSLSSRaisedNotif,
        tnGenericPRBSLSSClearedNotif,
        tnGenericCsfGfpRaisedNotif,
        tnGenericCsfGfpClearedNotif,
        tnGenericGfpExmRaisedNotif,
        tnGenericGfpExmClearedNotif,
        tnGenericGfpLofRaisedNotif,
        tnGenericGfpLofClearedNotif,
        tnGenericGfpUpmRaisedNotif,
        tnGenericGfpUpmClearedNotif,
        tnGenericLOFLOMRaisedNotif,
        tnGenericLOFLOMClearedNotif,
        tnGenericMsimRaisedNotif,
        tnGenericMsimClearedNotif,
        tnGenericPayloadTypeMismatchRaisedNotif,
        tnGenericPayloadTypeMismatchClearedNotif,
        tnGenericIntrusionRaisedNotif,
        tnGenericIntrusionClearedNotif,
        tnGenericNtpOutOfSyncRaisedNotif,
        tnGenericNtpOutOfSyncClearedNotif,
        tnGenericTxAutoLaserShutdownRaisedNotif,
        tnGenericTxAutoLaserShutdownClearedNotif,
        tnGenericTBerPreFec15minRaisedNotif,
        tnGenericTBerPreFec15minClearedNotif,
        tnGenericTBerPreFec1dayRaisedNotif,
        tnGenericTBerPreFec1dayClearedNotif,
        tnGenericTBerPostFec15minRaisedNotif,
        tnGenericTBerPostFec15minClearedNotif,
        tnGenericTBerPostFec1dayRaisedNotif,
        tnGenericTBerPostFec1dayClearedNotif,
        tnGenericUruSRaisedNotif,
        tnGenericUruSClearedNotif,
        tnGenericNeCertValidityWarnRaisedNotif,
        tnGenericNeCertValidityWarnClearedNotif,
        tnGenericNeCertValidityExpRaisedNotif,
        tnGenericNeCertValidityExpClearedNotif,
        tnGenericVoltageLowRaisedNotif,
        tnGenericVoltageLowClearedNotif }

    STATUS         current
    DESCRIPTION    "Generic alarm notifications group."
    ::= { tnGenericAlarmGroups 1 }

tnGenericEventNotifsGroup NOTIFICATION-GROUP
    NOTIFICATIONS {
        tnGenericPmBinsRolledOverNotif,
        tnGenericSecurityFileNameNotif,
        tnGenericSecurityLoginNotif,
        tnGenericSecurityLogoutNotif,
        tnGenericSecurityAddAccountNotif,
        tnGenericSecurityDeleteAccountNotif,
        tnGenericSecurityChangeAccountNotif,
        tnGenericSubgroupSelectNotif,
        tnGenericDot1agCfmDmTestCompleteNotif,
        tnGenericDot1agCfmSlmTestCompleteNotif,
        tnGenericDot1agCfmLmTestCompleteNotif,
        tnGenericSecurityExceededLoginAttemptsNotif,
        tnGenericSecurityLockAccountNotif,
        tnGenericSecurityUnlockAccountNotif,
        tnGenericSecurityUnauthAccessAttemptNotif,
        tnGenericSecurityEnableInterfaceNotif,
        tnGenericSecurityDisableInterfaceNotif,
        tnGenericDiscoverMeNotif }
    STATUS         current
    DESCRIPTION    "Generic event notifications group."
    ::= { tnGenericEventGroups 1 }

tnGenericScalarConfigChangeNotifGroup NOTIFICATION-GROUP
    NOTIFICATIONS {
        tnGenericScalarChangeNotif
    }
    STATUS         current
    DESCRIPTION    "Generic scalar configuration change
                    notifications group."
    ::= { tnGenericScalarGroups 1 }

tnGenericInterfaceConfigChangeNotifGroup NOTIFICATION-GROUP
    NOTIFICATIONS {
        tnGenericIfConfigChangeNotif
    }
    STATUS         current
    DESCRIPTION    "Generic interface (IF-MIB) configuration change
                    notifications group."
    ::= { tnGenericInterfaceGroups 1 }

tnGenericInterfaceStateChangeNotifGroup NOTIFICATION-GROUP
    NOTIFICATIONS {
        tnGenericIfOperStatusChangeNotif
    }
    STATUS         current
    DESCRIPTION    "Generic interface (IF-MIB) state change notifications
                    group."
    ::= { tnGenericInterfaceGroups 2 }

tnGenericOptIfConfigChangeNotifGroup NOTIFICATION-GROUP
    NOTIFICATIONS {
        tnGenericOptIfOTUkConfigChangeNotif
    }
    STATUS         current
    DESCRIPTION    "Generic optical interface (OPT-IF-MIB) configuration
                    change notifications group."
    ::= { tnGenericOptIfGroups 1 }

tnGenericTnAccessPortConfigChangeNotifGroup NOTIFICATION-GROUP
    NOTIFICATIONS {
        tnGenericTnAccessPortConfigChangeNotif,
        tnGenericTnIfConfigChangeNotif
    }
    STATUS         current
    DESCRIPTION    "Generic access port (TROPIC-ACCESSPORT-MIB) configuration
                    change notifications group."
    ::= { tnGenericTnAccessPortGroups 1 }

tnGenericTnOpticalPortConfigChangeNotifGroup NOTIFICATION-GROUP
    NOTIFICATIONS {
        tnGenericTnLoopbackPortConfigChangeNotif,
        tnGenericTnDwdmCmnClientPortConfigChangeNotif
    }
    STATUS         current
    DESCRIPTION    "Generic optical port (TROPIC-OPTICALPORT-MIB)
                    configuration change notifications group."
    ::= { tnGenericTnOpticalPortGroups 1 }

tnGenericTnOtuOduConfigChangeNotifGroup NOTIFICATION-GROUP
    NOTIFICATIONS {
        tnGenericTnOtukConfigChangeNotif
    }
    STATUS         current
    DESCRIPTION    "Generic OTU/ODU (TROPIC-OTUODU-MIB) configuration change
                    notifications group."
    ::= { tnGenericTnOtuOduGroups 1 }

tnGenericTnOthConfigChangeNotifGroup NOTIFICATION-GROUP
    NOTIFICATIONS {
        tnGenericTnOthOdukNimConfigChangeNotif,
        tnGenericTnOthOdukTtpConfigChangeNotif,
        tnGenericTnOthOdukTConfigChangeNotif,
        tnGenericTnOthOdukApsGroupConfigChangeNotif,
        tnGenericTnOthOdukXcConfigChangeNotif,
        tnGenericTnOthOdukApsGroupConvertNotif
    }
    STATUS         current
    DESCRIPTION    "Generic OTH (TROPIC-OTH-MIB) configuration change
                    notifications group."
    ::= { tnGenericTnOthGroups 1 }

tnGenericTnOthCreDelNotifGroup NOTIFICATION-GROUP
    NOTIFICATIONS {
        tnGenericTnOthOdukTCreationNotif,
        tnGenericTnOthOdukTDeletionNotif,
        tnGenericTnOthOdukXcCreationNotif,
        tnGenericTnOthOdukXcDeletionNotif
    }
    STATUS         current
    DESCRIPTION    "Generic OTH (TROPIC-OTH-MIB) creation and deletion
                    notifications group."
    ::= { tnGenericTnOthGroups 2 }

tnGenericTnL1ServiceConfigChangeNotifGroup NOTIFICATION-GROUP
    NOTIFICATIONS {
        tnGenericTnNetIfConfigChangeNotif,
        tnGenericTnNetIfFacilityConfigChangeNotif,
        tnGenericTnControlNetworkLinkConfigChangeNotif
    }
    STATUS         current
    DESCRIPTION    "Generic L1 service (TROPIC-L1SERVICE-MIB) configuration
                    change notifications group."
    ::= { tnGenericTnL1ServiceGroups 1 }

tnGenericTnL1ServiceCreDelNotifGroup NOTIFICATION-GROUP
    NOTIFICATIONS {
        tnGenericTnNetIfFacilityCreationNotif,
        tnGenericTnNetIfFacilityDeletionNotif
    }
    STATUS         current
    DESCRIPTION    "Generic L1 service (TROPIC-L1SERVICE-MIB) creation
                    and deletion notifications group."
    ::= { tnGenericTnL1ServiceGroups 2 }

tnGenericTnL1ServiceStateChangeNotifGroup NOTIFICATION-GROUP
    NOTIFICATIONS {
         tnGenericTnControlNetworkLinkStateChangeNotif
    }
    STATUS         current
    DESCRIPTION    "Generic L1 service (TROPIC-L1SERVICE-MIB) state
                    change notifications group."
    ::= { tnGenericTnL1ServiceGroups 3 }

tnGenericTnStatisticsConfigChangeNotifGroup NOTIFICATION-GROUP
    NOTIFICATIONS {
        tnGenericTnStatsTCAProfileConfigChangeNotif,
        tnGenericTnStatsTCAConfigChangeNotif,
        tnGenericTnOtuStatsPortConfigChangeNotif,
        tnGenericTnOdukStatsTcmConfigChangeNotif,
        tnGenericTnOdukStatsRxConfigChangeNotif
    }
    STATUS         current
    DESCRIPTION    "Generic statistics (TROPIC-STATISTICS-MIB) configuration
                    change notifications group."
    ::= { tnGenericTnStatisticsGroups 1 }

tnGenericTnLagConfigChangeNotifGroup NOTIFICATION-GROUP
    NOTIFICATIONS {
        tnGenericTnLagPortConfigChangeNotif,
        tnGenericTnLagCommandConfigChangeNotif
    }
    STATUS         current
    DESCRIPTION    "Generic LAG (TN-LAG-MIB) configuration
                    change notifications group."
    ::= { tnGenericTnLagGroups 1 }

tnGenericTnPmonConfigChangeNotifGroup NOTIFICATION-GROUP
    NOTIFICATIONS {
        tnGenericTnPmonPolicyConfigChangeNotif,
        tnGenericTnPmonTcaConfigChangeNotif
    }
    STATUS         current
    DESCRIPTION    "Generic PMON (TN-PMON-MIB) configuration
                    change notifications group."
    ::= { tnGenericTnPmonGroups 1 }

tnGenericTnPortConfigChangeNotifGroup NOTIFICATION-GROUP
    NOTIFICATIONS {
        tnGenericTnPortEtherConfigChangeNotif
    }
    STATUS         current
    DESCRIPTION    "Generic port (TN-PORT-MIB) configuration
                    change notifications group."
    ::= { tnGenericTnPortGroups 1 }

tnGenericDot1agCfmConfigChangeNotifGroup NOTIFICATION-GROUP
    NOTIFICATIONS {
        tnGenericDot1agCfmMdConfigChangeNotif,
        tnGenericDot1agCfmMaNetConfigChangeNotif,
        tnGenericDot1agCfmMaCompConfigChangeNotif,
        tnGenericDot1agCfmMepConfigChangeNotif
    }
    STATUS         current
    DESCRIPTION    "Generic CFM (IEEE8021-CFM-MIB) configuration
                    change notifications group."
    ::= { tnGenericDot1agCfmGroups 1 }

tnGenericDot1agCfmCreDelNotifGroup NOTIFICATION-GROUP
    NOTIFICATIONS {
        tnGenericDot1agCfmMdCreationNotif,
        tnGenericDot1agCfmMdDeletionNotif,
        tnGenericDot1agCfmMaNetCreationNotif,
        tnGenericDot1agCfmMaNetDeletionNotif,
        tnGenericDot1agCfmMaCompCreationNotif,
        tnGenericDot1agCfmMaCompDeletionNotif,
        tnGenericDot1agCfmMaMepListCreationNotif,
        tnGenericDot1agCfmMaMepListDeletionNotif,
        tnGenericDot1agCfmMepCreationNotif,
        tnGenericDot1agCfmMepDeletionNotif
    }
    STATUS         current
    DESCRIPTION    "Generic CFM (IEEE8021-CFM-MIB) creation and deletion
                    notifications group."
    ::= { tnGenericDot1agCfmGroups 2 }

tnGenericTnDot1agCfmConfigChangeNotifGroup NOTIFICATION-GROUP
    NOTIFICATIONS {
        tnGenericTnDot1agCfmMepConfigChangeNotif,
        tnGenericTnDot1agCfmMepSlmTWTestConfigChangeNotif,
        tnGenericTnDot1agCfmMepOndemandLmTestConfigChangeNotif
    }
    STATUS         current
    DESCRIPTION    "Generic CFM (TN-IEEE8021-CFM-MIB) configuration
                    change notifications group."
    ::= { tnGenericTnDot1agCfmGroups 1 }

tnGenericTnOamTestConfigChangeNotifGroup NOTIFICATION-GROUP
    NOTIFICATIONS {
        tnGenericTnOamSaaCtlConfigChangeNotif
    }
    STATUS         current
    DESCRIPTION    "Generic OAM test (TN-OAM-TEST-MIB) configuration
                    change notifications group."
    ::= { tnGenericTnOamTestGroups 1 }

tnGenericTnOamTestCreDelNotifGroup NOTIFICATION-GROUP
    NOTIFICATIONS {
        tnGenericTnOamPingCtlCreationNotif,
        tnGenericTnOamPingCtlDeletionNotif
    }
    STATUS         current
    DESCRIPTION    "Generic OAM test (TN-OAM-TEST-MIB) creation and deletion
                    notifications group."
    ::= { tnGenericTnOamTestGroups 2 }

tnGenericRadiusNotifGroup NOTIFICATION-GROUP
    NOTIFICATIONS {
        tnGenericRadiusServerCreationNotif,
        tnGenericRadiusServerDeletionNotif,
        tnGenericRadiusServerConfigChangeNotif
    }
    STATUS         current
    DESCRIPTION    "Generic Radius (TROPIC-EXPRSCALARS) notifications group."
    ::= { tnGenericRadiusGroups 1 }

tnGenericSyslogNotifGroup NOTIFICATION-GROUP
    NOTIFICATIONS {
        tnGenericSyslogServerCreationNotif,
        tnGenericSyslogServerDeletionNotif,
        tnGenericSyslogServerConfigChangeNotif
    }
    STATUS         current
    DESCRIPTION    "Generic Syslog (TROPIC-SYSTEM-MIB) notifications group."
    ::= { tnGenericSyslogGroups 1 }

tnGenericTransferPMDiscoveryNotifGroup NOTIFICATION-GROUP
     NOTIFICATIONS {
         tnGenericTransferPMDiscoveryCreationNotif,
         tnGenericTransferPMDiscoveryDeletionNotif,
         tnGenericTransferPMDiscoveryConfigChangeNotif
     }
     STATUS         current
     DESCRIPTION    "Generic Transfer PM Discovery (TROPIC-SYSTEM-MIB)
                     notifications group."
     ::= { tnGenericTransferPMDiscoveryGroups 1 }

-------------------------------------------------------------------------------
-- Compliance Statements
-------------------------------------------------------------------------------

tnGenericTrapCompliance MODULE-COMPLIANCE
    STATUS         current
    DESCRIPTION    "Generic trap compliance."
    MODULE
    GROUP          tnGenericTrapGroup
    DESCRIPTION    "tnGenericTrapGroup is optional."

    GROUP          tnGenericConfigurationChangeNotifsGroup
    DESCRIPTION    "tnGenericConfigurationChangeNotifsGroup is optional."

    GROUP          tnGenericStateChangeNotifsGroup
    DESCRIPTION    "tnGenericStateChangeNotifsGroup is optional."

    GROUP          tnGenericTreeUpdateNotifsGroup
    DESCRIPTION    "tnGenericTreeUpdateNotifsGroup is optional."
    ::= { tnGenericTrapCompliances 1 }

tnGenericTrapBufferCompliance MODULE-COMPLIANCE
    STATUS         current
    DESCRIPTION    "Generic Trap Buffer compliance."
    MODULE
    MANDATORY-GROUPS {
        tnGenericTrapBufferGroup
    }
    ::= { tnGenericTrapBufferCompliances 1 }

tnGenericAlarmCompliance MODULE-COMPLIANCE
    STATUS         current
    DESCRIPTION    "Generic Alarm compliance."
    MODULE
    GROUP          tnGenericAlarmNotifsGroup
    DESCRIPTION    "tnGenericAlarmNotifsGroup is optional."
    ::= { tnGenericAlarmCompliances 1 }

tnGenericEventCompliance MODULE-COMPLIANCE
    STATUS         current
    DESCRIPTION    "Generic Event compliance."
    MODULE
    GROUP          tnGenericEventNotifsGroup
    DESCRIPTION    "tnGenericEventNotifsGroup is optional."
    ::= { tnGenericEventCompliances 1 }

tnGenericScalarCompliance MODULE-COMPLIANCE
    STATUS         current
    DESCRIPTION    "Generic scalar change notification
                    compliance."
    MODULE
    GROUP          tnGenericScalarConfigChangeNotifGroup
    DESCRIPTION    "tnGenericScalarConfigChangeNotifGroup is optional."
    ::= { tnGenericScalarCompliances 1 }

tnGenericInterfaceCompliance MODULE-COMPLIANCE
    STATUS         current
    DESCRIPTION    "Generic interface (IF-MIB) change notification
                    compliance."
    MODULE
    GROUP          tnGenericInterfaceConfigChangeNotifGroup
    DESCRIPTION    "tnGenericInterfaceConfigChangeNotifGroup is optional."

    GROUP          tnGenericInterfaceStateChangeNotifGroup
    DESCRIPTION    "tnGenericInterfaceStateChangeNotifGroup is optional."
    ::= { tnGenericInterfaceCompliances 1 }

tnGenericOptIfCompliance MODULE-COMPLIANCE
    STATUS         current
    DESCRIPTION    "Generic optical interface (OPT-IF-MIB) change
                    notification compliance."
    MODULE
    GROUP          tnGenericOptIfConfigChangeNotifGroup
    DESCRIPTION    "tnGenericOptIfConfigChangeNotifGroup is optional."
    ::= { tnGenericOptIfCompliances 1 }

tnGenericTnAccessPortCompliance MODULE-COMPLIANCE
    STATUS         current
    DESCRIPTION    "Generic access port (TROPIC-ACCESSPORT-MIB) change
                    notification compliance."
    MODULE
    GROUP          tnGenericTnAccessPortConfigChangeNotifGroup
    DESCRIPTION    "tnGenericTnAccessPortConfigChangeNotifGroup is optional."
    ::= { tnGenericTnAccessPortCompliances 1 }

tnGenericTnOpticalPortCompliance MODULE-COMPLIANCE
    STATUS         current
    DESCRIPTION    "Generic optical port (TROPIC-OPTICALPORT-MIB) change
                    notification compliance."
    MODULE
    GROUP          tnGenericTnOpticalPortConfigChangeNotifGroup
    DESCRIPTION    "tnGenericTnOpticalPortConfigChangeNotifGroup is optional."
    ::= { tnGenericTnOpticalPortCompliances 1 }

tnGenericTnOtuOduCompliance MODULE-COMPLIANCE
    STATUS         current
    DESCRIPTION    "Generic OTU/ODU (TROPIC-OTUODU-MIB) change
                    notification compliance."
    MODULE
    GROUP          tnGenericTnOtuOduConfigChangeNotifGroup
    DESCRIPTION    "tnGenericTnOtuOduConfigChangeNotifGroup is optional."
    ::= { tnGenericTnOtuOduCompliances 1 }

tnGenericTnOthCompliance MODULE-COMPLIANCE
    STATUS         current
    DESCRIPTION    "Generic OTH (TROPIC-OTH-MIB) change
                    notification compliance."
    MODULE
    GROUP          tnGenericTnOthConfigChangeNotifGroup
    DESCRIPTION    "tnGenericTnOthConfigChangeNotifGroup is optional."

    GROUP          tnGenericTnOthCreDelNotifGroup
    DESCRIPTION    "tnGenericTnOthCreDelNotifGroup is optional."
    ::= { tnGenericTnOthCompliances 1 }

tnGenericTnL1ServiceCompliance MODULE-COMPLIANCE
    STATUS         current
    DESCRIPTION    "Generic L1 service (TROPIC-L1SERVICE-MIB) change
                    notification compliance."
    MODULE
    GROUP          tnGenericTnL1ServiceConfigChangeNotifGroup
    DESCRIPTION    "tnGenericTnL1ServiceConfigChangeNotifGroup is optional."

    GROUP          tnGenericTnL1ServiceCreDelNotifGroup
    DESCRIPTION    "tnGenericTnL1ServiceCreDelNotifGroup is optional."

    GROUP          tnGenericTnL1ServiceStateChangeNotifGroup
    DESCRIPTION    "tnGenericTnL1ServiceStateChangeNotifGroup is optional."
    ::= { tnGenericTnL1ServiceCompliances 1 }

tnGenericTnStatisticsCompliance MODULE-COMPLIANCE
    STATUS         current
    DESCRIPTION    "Generic statistics (TROPIC-STATISTICS-MIB) change
                    notification compliance."
    MODULE
    GROUP          tnGenericTnStatisticsConfigChangeNotifGroup
    DESCRIPTION    "tnGenericTnStatisticsConfigChangeNotifGroup is optional."
    ::= { tnGenericTnStatisticsCompliances 1 }

tnGenericTnLagCompliance MODULE-COMPLIANCE
    STATUS         current
    DESCRIPTION    "Generic LAG (TN-LAG-MIB) change
                    notification compliance."
    MODULE
    GROUP          tnGenericTnLagConfigChangeNotifGroup
    DESCRIPTION    "tnGenericTnLagConfigChangeNotifGroup is optional."
    ::= { tnGenericTnLagCompliances 1 }

tnGenericTnPmonCompliance MODULE-COMPLIANCE
    STATUS         current
    DESCRIPTION    "Generic PMON (TN-PMON-MIB) change
                    notification compliance."
    MODULE
    GROUP          tnGenericTnPmonConfigChangeNotifGroup
    DESCRIPTION    "tnGenericTnPmonConfigChangeNotifGroup is optional."
    ::= { tnGenericTnPmonCompliances 1 }

tnGenericTnPortCompliance MODULE-COMPLIANCE
    STATUS         current
    DESCRIPTION    "Generic port (TN-PORT-MIB) change
                    notification compliance."
    MODULE
    GROUP          tnGenericTnPortConfigChangeNotifGroup
    DESCRIPTION    "tnGenericTnPortConfigChangeNotifGroup is optional."
    ::= { tnGenericTnPortCompliances 1 }

tnGenericDot1agCfmCompliance MODULE-COMPLIANCE
    STATUS         current
    DESCRIPTION    "Generic CFM (IEEE8021-CFM-MIB) change
                    notification compliance."
    MODULE
    GROUP          tnGenericDot1agCfmConfigChangeNotifGroup
    DESCRIPTION    "tnGenericDot1agCfmConfigChangeNotifGroup is optional."

    GROUP          tnGenericDot1agCfmCreDelNotifGroup
    DESCRIPTION    "tnGenericDot1agCfmCreDelNotifGroup is optional."
    ::= { tnGenericDot1agCfmCompliances 1 }

tnGenericTnDot1agCfmCompliance MODULE-COMPLIANCE
    STATUS         current
    DESCRIPTION    "Generic CFM (TN-IEEE8021-CFM-MIB) change
                    notification compliance."
    MODULE
    GROUP          tnGenericTnDot1agCfmConfigChangeNotifGroup
    DESCRIPTION    "tnGenericTnDot1agCfmConfigChangeNotifGroup is optional."
    ::= { tnGenericTnDot1agCfmCompliances 1 }

tnGenericTnOamTestCompliance MODULE-COMPLIANCE
    STATUS         current
    DESCRIPTION    "Generic OAM TEST (TN-OAM-TEST-MIB) change
                    notification compliance."
    MODULE
    GROUP          tnGenericTnOamTestConfigChangeNotifGroup
    DESCRIPTION    "tnGenericTnOamTestConfigChangeNotifGroup is optional."

    GROUP          tnGenericTnOamTestCreDelNotifGroup
    DESCRIPTION    "tnGenericTnOamTestCreDelNotifGroup is optional."
    ::= { tnGenericTnOamTestCompliances 1 }

tnGenericRadiusCompliance MODULE-COMPLIANCE
    STATUS         current
    DESCRIPTION    "Generic Radius (TROPIC-EXPRSCALARS) compliance."
    MODULE
    GROUP          tnGenericRadiusNotifGroup
    DESCRIPTION    "tnGenericRadiusNotifGroup is optional."
    ::= { tnGenericRadiusCompliances 1 }

tnGenericSyslogCompliance MODULE-COMPLIANCE
    STATUS         current
    DESCRIPTION    "Generic Syslog (TROPIC-SYSTEM-MIB) compliance."
    MODULE
    GROUP          tnGenericSyslogNotifGroup
    DESCRIPTION    "tnGenericSyslogNotifGroup is optional."
    ::= { tnGenericSyslogCompliances 1 }

tnGenericTransferPMDiscoveryCompliance MODULE-COMPLIANCE
     STATUS         current
     DESCRIPTION    "Generic Transfer PM Discovery (TROPIC-SYSTEM-MIB) compliance."
     MODULE
     GROUP          tnGenericTransferPMDiscoveryNotifGroup
     DESCRIPTION "tnGenericTransferPMDiscoveryNotifGroup is optional."
     ::= { tnGenericTransferPMDiscoveryCompliances 1 }

END -- DEFINITION OF TROPIC-GENERIC-NOTIFICATION-MIB
