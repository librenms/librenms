TROPIC-SYSTEM-MIB DEFINITIONS ::= BEGIN

-- (c) Copyright 2023 Nokia Networks.  All rights reserved.
-- This software is the confidential and proprietary property of
-- Nokia and may only be used in accordance with the terms of the
-- license agreement provided with this software.

IMPORTS
      SnmpAdminString                         FROM SNMP-FRAMEWORK-MIB
      OBJECT-TYPE, MODULE-IDENTITY,
      IpAddress,
      Unsigned32, Integer32, Counter32        FROM SNMPv2-SMI
      MODULE-COMPLIANCE, OBJECT-GROUP         FROM SNMPv2-CONF
      TEXTUAL-CONVENTION,
      DateAndTime, TruthValue, RowStatus,
      MacAddress                              FROM SNMPv2-TC
      ifIndex                                 FROM IF-MIB
      InetAddressType, InetAddress,
      InetAddressIPv6,
      InetAddressPrefixLength                 FROM INET-ADDRESS-MIB
      AluWdmEnabledDisabled,
      TropicResetType,
      AluWdmTransferProtocol,
      AluWdmNewTransferProtocol,
      AluWdmCardCapacity,
      TropicOperationalStateType,
      TropicAdminStateType,
      TropicSourceIpModeValue,
      TnCommand,
      AluWdmDisabledEnabled                   FROM TROPIC-TC
      TnSwitchID,
      TmnxEnabledDisabled                     FROM TN-TC-MIB
      snmpTargetAddrEntry                     FROM SNMP-TARGET-MIB
      tnNetIfIndex,tnEthIfIndex               FROM TROPIC-L1SERVICE-MIB
      tnSystemModules, tnSystemMIB            FROM TROPIC-GLOBAL-REG;

  tnSystemMibModule MODULE-IDENTITY
      LAST-UPDATED    "202304071200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION "The system MIB for Nokia network elements."

      REVISION    "202304071200Z"
      DESCRIPTION "Added the following scalar to tnSysBasics:
                   tnSysBgpAdminDistance."

      REVISION    "202303171200Z"
      DESCRIPTION "Added the following to tnSysBgpPeerTable:
                   tnSysBgpPeerStatsInetAddressType
                   tnSysBgpPeerStatsIp
                   tnSysBgpPeerStatsInetAddress."

      REVISION    "202303031200Z"
      DESCRIPTION "1) Changed SYNTAX of the following from (1..80) to (0..80):
                      tnSysBgpPeerSecurityKey.
                   2) Added DEFVAL for the following attribute:
                      tnSysBgpPeerSecurityKey."

      REVISION    "202302171200Z"
      DESCRIPTION "1) Added the following scalar to tnSysBasics:
                      tnSysKeyStoreCertExpiration
                      tnSysNumOspfV2AreaIndependentLsas
                      tnSysNumOspfV3AreaIndependentLsas.
                   2) Added the following scalar to tnSysSsl:
                      tnSysSslCertExpiration."

      REVISION    "202302101200Z"
      DESCRIPTION "1) Added the following to tnSysBgpPeerTable:
                      tnSysBgpStatsIpv4PrefixInCount
                      tnSysBgpStatsIpv6PrefixInCount
                      tnSysBgpStatsIpv4PrefixOutCount
                      tnSysBgpStatsIpv6PrefixOutCount.
                   2) Modified the following DESCRIPTION:
                      tnSshKexAlgType."

      REVISION    "202301131200Z"
      DESCRIPTION "1) Added the following to tnSanListAuthTable:
                      tnSanListProfileDescription.
                   2) Added the following table:
                      tnSshProfileTable."

      REVISION    "202301061200Z"
      DESCRIPTION "Added the following to tnTlsProfileTable:
                   tnTlsProfileDescription."

      REVISION    "202212231200Z"
      DESCRIPTION "1) Added the following Textual Convention:
                      NokiaSysBgpMaxPrefixAction.
                   2) Added the following to tnSysBgpPeerTable:
                      tnSysBgpMaxPrefixIpv4Limit
                      tnSysBgpMaxPrefixIpv4Threshold
                      tnSysBgpMaxPrefixIpv4Action
                      tnSysBgpMaxPrefixIpv6Limit
                      tnSysBgpMaxPrefixIpv6Threshold
                      tnSysBgpMaxPrefixIpv6Action."

      REVISION    "202211251200Z"
      DESCRIPTION "Added the following to tnSyslogFacility and tnSyslogServerFacility:
                   all(21)
                   to
                   logAlert(23)."

      REVISION    "202210141200Z"
      DESCRIPTION "Added the following scalar to tnSysBasics:
                   tnSysPower."

      REVISION    "202209301200Z"
      DESCRIPTION "Added the following scalar to tnSysBasics:
                   tnSysPerformanceCPUStatsPercentages."

      REVISION    "202209231200Z"
      DESCRIPTION "1) Added the following scalars to tnSysBasics:
                      tnSysPerformanceMemoryTotal
                      tnSysPerformanceMemoryUsed
                      tnSysPerformanceMemoryUsedPercentage
                      tnSysPerformanceTime.
                   2) Added the following to tnSysIpAclRxAction and tnSysIpAclIpv6RxAction:
                      dropAndlog(3).
                   3) Added the following scalar to tnSysIpAclSysDefault:
                      tnSysIpAclClearCounter.
                   4) Changed SYNTAX of the following from (1..24) to (1..31):
                      tnSysDebugTransferShelfNum.
                   5) Added the following scalar to tnSysIpAclIpv6SysDefault:
                      tnSysIpAclIPv6ClearCounter."

      REVISION    "202208261200Z"
      DESCRIPTION "Added the following scalar to tnSysBasics:
                   tnSysMultiShelfAvailableList."

      REVISION    "202208191200Z"
      DESCRIPTION "Added the following scalar to tnSysBasics:
                   tnSysProtocolIpMode."

      REVISION    "202207291200Z"
      DESCRIPTION "1) Added the following scalars to tnSysBasics:
                      tnSysHwIfMode
                      tnSysIpAclNextIndex
                      tnSysIpv6AclNextIndex
                      tnSysDHCPClass.
                   2) Added the following tables:
                      tnSysIpAclTable
                      tnSysIpv6AclTable."

      REVISION    "202207221200Z"
      DESCRIPTION "Added the following scalar to tnSysBasics:
                   tnSysKeyLicense."

      REVISION    "202207151200Z"
      DESCRIPTION "Added the following scalars to tnSysBasics:
                   tnSysOtcWaitTimeAfterPowerChange
                   tnSysDHCPClassName
                   tnSysDHCPMatchString."

      REVISION    "202207081200Z"
      DESCRIPTION "Changed SYNTAX of the following from SIZE(0..127) to SIZE(0..512):
                   tnSysKeyStoreCertSubjectAlternativeName."

      REVISION    "202207011200Z"
      DESCRIPTION "Added the following scalars to tnSysBasics:
                   tnSysOcspSourceIpMode
                   tnSysDnsSourceIpMode."

      REVISION    "202205271200Z"
      DESCRIPTION "Added the following scalar to tnSysLinux:
                   tnSysLinuxRootUserPort."

      REVISION    "202202111200Z"
      DESCRIPTION "Added the following table:
                   tnTransferPMDiscoveryTable."

      REVISION    "202202041200Z"
      DESCRIPTION "Added the following table:
                   tnSysDnsServerTable."

      REVISION    "202201281200Z"
      DESCRIPTION "Added the following scalar to tnSysBasics:
                   tnSysNmsIpVerifyState."

      REVISION    "202201071200Z"
      DESCRIPTION "1) Added the following to tnSyslogServerProtocol:
                      tls(3).
                   2) Added the following to tnSyslogServerTable:
                      tnSyslogServerType
                      tnSyslogServerDomain."

      REVISION    "202112311200Z"
      DESCRIPTION "Added the following table:
                   tnOcspProfileTable."

      REVISION    "202112241200Z"
      DESCRIPTION "Added the following table:
                   tnSysNmsIpListTable."

      REVISION    "202112031200Z"
      DESCRIPTION "Added the following scalar to tnSysBasics:
                   tnSysUSBInstall."

      REVISION    "202111261200Z"
      DESCRIPTION "Added the following scalar to tnSysBasics:
                   tnSysCustomerLifeCycleState."

      REVISION    "202110151200Z"
      DESCRIPTION "Added the following scalar to tnSysSsl:
                   tnSysSslCertVerification."

      REVISION    "202110011200Z"
      DESCRIPTION "1) Added the following scalars to tnSysBasics:
                      tnSysVersionPatchId
                      tnSysVersionPatchDescr.
                   2) Added the following table:
                      tnSanListAuthTable."

      REVISION    "202109241200Z"
      DESCRIPTION "Added the following table:
                   tnCsrSanListTable."

      REVISION    "202109101200Z"
      DESCRIPTION "1) Added the following scalar to tnSysDiscovery:
                      tnSysDiscoveryTransferTraps.
                   2) Changed SYNTAX from (SIZE(0..31)) to (SIZE(0..32))
                      for the following:
                      tnSysKeyStoreTransServerUserId.
                   3) Changed SYNTAX from (SIZE(0..31)) to (SIZE(0..256))
                      for the following:
                      tnSysKeyStoreTransServerPassword.
                   4) Added the following to tnSysKeyStoreCertRepositoryIndex:
                      trustAnchorInstalledOfSystem(4)
                      trustAnchorDownLoadedOfSystem(5).
                   5) Added the following table:
                      tnSanListTable."

      REVISION    "202109031200Z"
      DESCRIPTION "1) Added the following to tnSysKeyStoreNameIndex:
                      system(4).
                   2) Added the following to tnTlsProfileTable:
                      tnTlsProfileMutualAuth."

      REVISION    "202108271200Z"
      DESCRIPTION "Added the following scalar to tnSysBasics:
                   tnSysNmsUserName."

      REVISION    "202108201200Z"
      DESCRIPTION "Added the following scalar to tnSysBasics:
                   tnSysDelayReboot."

      REVISION    "202108061200Z"
      DESCRIPTION "Added the following scalar to tnSysBasics:
                   tnSysDelayResetNE."

      REVISION    "202107161200Z"
      DESCRIPTION "Added the following scalar to tnSysTrapThrottling:
                   tnSysTrapThrottlingState."

      REVISION    "202107021200Z"
      DESCRIPTION "1) Added the following scalar to tnSysBasics:
                      tnSysFeatureAutoTurnUp.
                   2) Added the following to tnSysHealthCareCheckCommand:
                      abort(3).
                   3) Added the following to tnSysHealthCareTransferCommand:
                      abort(3).
                   4) Added the following scalars to tnSysHealthCare:
                      tnSysHealthCareLastOperation
                      tnSysHealthCareSetCriteriaTcId
                      tnSysHealthCareSetCriteria
                      tnSysHealthCareDeleteCriteriaTcId
                      tnSysHealthCareDeleteCriteria
                      tnSysHealthCareApplyCriteriaCommand.
                   5) Added tnSysTrapThrottling scalars."

      REVISION    "202106111200Z"
      DESCRIPTION "Added the following scalar to tnSysBasics:
                   tnSysNtpSourceIpMode."

      REVISION    "202105281200Z"
      DESCRIPTION "Added the following scalar to tnSysBasics:
                   tnSysAutoTurnUpActiveTemplateForce."

      REVISION    "202105141200Z"
      DESCRIPTION "Added the following scalar to tnSysLinux:
                   tnSysLinuxSecurityCommit."

      REVISION    "202105071200Z"
      DESCRIPTION "1) Added the following scalars to tnSysDiscovery:
                      tnSysDiscoveryPrevious15minBinFilesTransfer
                      tnSysDiscoveryPrevious1dayBinFilesTransfer
                      tnSysDiscoveryTransferTimeOffset.
                   2) Added the following to tnSnmpTargetAddrTable:
                      tnSnmpTargetAddrDisableTrap."

      REVISION    "202104231200Z"
      DESCRIPTION "Added the following scalar to tnSysLinux:
                   tnSysLinuxRootUserLocalStatus."

      REVISION    "202104161200Z"
      DESCRIPTION "1) Added tnSysHealthCare scalars.
                   2) Added the following tables:
                      tnSshCiphersTable
                      tnSshHostKeyTable
                      tnSshMacsTable
                      tnSshKexTable
                      tnSshPubKeyTable
                      tnTlsProfileTable."

      REVISION    "202104021200Z"
      DESCRIPTION "Added tnTransferSysLog scalars."

      REVISION    "202103261200Z"
      DESCRIPTION "Added the following tables:
                   tnSysNESshKeyTable
                   tnNESshKeyTable."

      REVISION    "202103191200Z"
      DESCRIPTION "Added the following tables:
                   tnHostKeyTable
                   tnSshPrivKeyTable."

      REVISION    "202102261200Z"
      DESCRIPTION "Added the following scalars to tnSysLinux:
                   tnSysLinuxSmsUserId
                   tnSysLinuxSmsUserPassword
                   tnSysLinuxSmsPasswordStatus
                   tnSysLinuxSmsUserStatus."

      REVISION    "202102191200Z"
      DESCRIPTION "Added tnPctObjs scalars."

      REVISION    "202102051200Z"
      DESCRIPTION "Added the following scalar to tnSysBasics:
                   tnSysAuthRejectOption."

      REVISION    "202101221200Z"
      DESCRIPTION "Added the following scalar to tnSysBasics:
                   tnSysAuthenticationOrder."

      REVISION    "202012041200Z"
      DESCRIPTION "Added the following to tnSysLicenseMgr:
                   tnSysLicenseMgrNextRefreshTime."

      REVISION    "202011061200Z"
      DESCRIPTION "Added the following table:
                   tnLicenseEntitlementTable."

      REVISION    "202010231200Z"
      DESCRIPTION "Added the following to tnSysOtdrScanTransfer:
                   tnSysOtdrScanTransferPort."

      REVISION    "202010091200Z"
      DESCRIPTION "Added the following scalar to tnSysBasics:
                   tnSysAutoTurnUpActiveTemplate."

      REVISION    "202008281200Z"
      DESCRIPTION "Marked the following as obsolete:
                   tnSysBackupAndRestoreType."

      REVISION    "202008071200Z"
      DESCRIPTION "Added the following scalars to tnSysBasics:
                   tnSysTacacsSourceIpMode
                   tnSysRadiusSourceIpMode
                   tnSysFtpSourceIpMode
                   tnSysSftpSourceIpMode
                   tnSysHttpSourceIpMode
                   tnSysHttpsSourceIpMode
                   tnSysSnmpSourceIpMode
                   tnSysSyslogSourceIpMode
                   tnSysSshSourceIpMode."

      REVISION    "202007241200Z"
      DESCRIPTION "Changed SYNTAX of tnSysNodeTemplate from SIZE(0..32) to
                   SIZE(0..64)."

      REVISION    "202005291200Z"
      DESCRIPTION "Marked the following as obsolete:
                   tnSysNodeLatitude
                   tnSysNodeLongitude."

      REVISION    "202005011200Z"
      DESCRIPTION "Added the following scalar to tnSysBasics:
                   tnSysShelfAltitude."

      REVISION    "202004101200Z"
      DESCRIPTION "1) Changed SYNTAX from (SIZE(0..255)) to (SIZE(0..256))
                      for the following:
                      tnSysUserlabel.
                   2) Added the following scalars to tnSysBasics:
                      tnSysPrompt
                      tnSysPromptType."

      REVISION    "202004031200Z"
      DESCRIPTION "Added the following scalars to tnSysBasics:
                   tnSysMultiShelfConfigList
                   tnSysMultiShelfUnknownList
                   tnSysMultiShelfMissingList."

      REVISION    "202003271200Z"
      DESCRIPTION "Added the following table:
                   tnSyslogServerTable."

      REVISION    "202003201200Z"
      DESCRIPTION "Added the following scalar to tnSysBasics:
                   tnSysMultiShelfMode."

      REVISION    "202003061200Z"
      DESCRIPTION "1) Added the following scalar to tnSysBasics:
                      tnSysMDCli.
                   2) Changed SYNTAX of the following from
                      AluWdmTransferProtocol to AluWdmNewTransferProtocol:
                      tnSysDiscoveryServerProtocol.
                   3) Added the following scalar to tnSysDiscovery:
                      tnSysDiscoveryPort.
                   4) Added the following to tnSysOtdrScanResultsTransfer:
                      tnSysOtdrScanResultsTransferRemoveFileFromNE."

      REVISION    "202002281200Z"
      DESCRIPTION "1) Added the following scalars to tnSysBasics:
                      tnSysNodeIdLabel
                      tnSysNodeNumber
                      tnSysNodeCLLI
                      tnSysNodeTemplate
                      tnSysNodeLatitude
                      tnSysNodeLongitude
                      tnSysCustomerApplicationMode.
                   2) Added the following scalar to tnSysDiscoverMe:
                      tnSysDiscoverMeTraps."

      REVISION    "202002211200Z"
      DESCRIPTION "1) Changed SYNTAX of the following from
                      AluWdmTransferProtocol to AluWdmNewTransferProtocol:
                      tnNeDiscoveryServerProtocol.
                   2) Added the following to tnNeDiscoveryTable:
                      tnNeDiscoveryPort."

      REVISION    "202002071200Z"
      DESCRIPTION "1) Marked the following as obsolete:
                      tnSysNFMTPublicKey.
                   2) Added the following scalar to tnSysBackupAndRestore:
                      tnSysBackupAndRestoreFallBackTimeStamp."

      REVISION    "202001311200Z"
      DESCRIPTION "1) Added the following scalars to tnSysBasics:
                      tnSysBgpAsn
                      tnSysBgpLocalRouterId.
                   2) Added the following table:
                      tnSysBgpPeerTable."

      REVISION    "202001241200Z"
      DESCRIPTION "1) Changed SYNTAX of the following from INTEGER to
                      AluWdmNewTransferProtocol:
                      tnSysSslCertTransferProtocol.
                   2) Added the following scalar to tnSysSsl:
                      tnSysSslCertTransferPort."

      REVISION    "202001171200Z"
      DESCRIPTION "Fixed MIB compile issues."

      REVISION    "202001031200Z"
      DESCRIPTION "Added the following to tnSysBackupAndRestoreCommand:
                   backupToLocal(5)."

      REVISION    "201912061200Z"
      DESCRIPTION "Added the following scalar to tnSysBasics:
                   tnSysAlmProfName."

      REVISION    "201911221200Z"
      DESCRIPTION "1) Added the following to tnSysDebugTransfer:
                      tnSysDebugTransferPort.
                   2) Added the following to tnSysOtdrScanResultsTransfer:
                      tnSysOtdrScanResultsTransferPort."

      REVISION    "201911151200Z"
      DESCRIPTION "1) Added the following scalars to tnSysBasics:
                      tnSysShelfLatitude
                      tnSysShelfLongitude.
                   2) Changed SYNTAX of the following from AluWdmTransferProtocol
                      to AluWdmNewTransferProtocol:
                      tnSysTransferLogProtocol
                      tnSysDebugTransferProtocol
                      tnSysOtdrScanResultsTransferProtocol.
                   3) Changed SYNTAX of the following to use AluWdmNewTransferProtocol:
                      tnSysBackupAndRestoreProtocol."

      REVISION    "201911011200Z"
      DESCRIPTION "1) Changed SYNTAX of the following from TruthValue to INTEGER:
                      tnSysIpAclPatternTcpEstablish
                      tnSysIpAclIpv6PatternTcpEstablish.
                   2) Added the following to tnSysIpAclPatternTcpEstablish and
                      tnSysIpAclIpv6PatternTcpEstablish:
                      true(1)
                      to
                      local(3)."

      REVISION    "201910111200Z"
      DESCRIPTION "Added the following to tnSysDebugTransferIncludeInDumps:
                   occ(3)."

      REVISION    "201908301200Z"
      DESCRIPTION "Added the following scalars to tnSysBasics:
                   tnSysSyncMode
                   tnSysPMMode."

      REVISION    "201907191200Z"
      DESCRIPTION "1) Added the following scalar to tnSysBackupAndRestore:
                      tnSysBackupAndRestorePort.
                   2) Added the following scalar to tnSysTransferLog:
                      tnSysTransferLogPort.
                   3) Added the following to tnSysKeyStoreCertInfoTable:
                      tnSysKeyStoreCertSHA256Fingerprint."

      REVISION    "201907121200Z"
      DESCRIPTION "Added the following to tnLicenseEntityTable:
                   tnLicenseEntityEntitlementNeeded."

      REVISION    "201907051200Z"
      DESCRIPTION "Modified the range from (SIZE(0..50)) to (SIZE(0..255))
                   for the following attribute:
                   tnSysBtInterfaceDescription."

      REVISION    "201906281200Z"
      DESCRIPTION "Changed SYNTAX of tnSysBackupAndRestoreProtocol from
                   AluWdmTransferProtocol to INTEGER."

      REVISION    "201906211200Z"
      DESCRIPTION "1) Changed SYNTAX of the following from Unsigned32 (1..4) to
                      Unsigned32 (1..8):
                      tnSysNtpServerIndex.
                   2) Changed SYNTAX of the following from Unsigned32 (1..3) to
                      Unsigned32 (1..8):
                      tnSysNtpServerIdStatsIndex."

      REVISION    "201906141200Z"
      DESCRIPTION "1) Added the following scalar to tnSysBasics:
                      tnSysNFMTPublicKey.
                   2) Added the following to tnSysKeyStoreTransServerCommand:
                      clear(7).
                   3) Added the following to tnSysKeyStoreServiceTable:
                      tnSysKeyStoreTransServerURI.
                   4) Added the following to tnSysKeyStoreCertInfoTable:
                      tnSysKeyStoreCertKeyUsage
                      tnSysKeyStoreCertSubjectAlternativeName
                      tnSysKeyStoreCertExtendedKeyUsage
                      tnSysKeyStoreCertBasicConstraints."

      REVISION    "201906071200Z"
      DESCRIPTION "1) Added the following scalar:
                      tnSysSshEcdsaKeyModulus.
                   2) Added the following to tnSshKeyTable:
                      tnSshEcdsaPublicKey
                      tnSshEcdsaPublicKey1
                      tnSshEd25519PublicKey
                      tnSshEd25519PublicKey1."

      REVISION    "201905311200Z"
      DESCRIPTION "1) Added the following to tnSysSshKeyType:
                      ecdsa(3)
                      to
                      all(5).
                   2) Added the following to tnSshKeyTable:
                      tnSshPublicKey1.
                   3) Added the following to tnSshKeyTypeIndex:
                      ecdsa(3)
                      ed25519(4).
                   4) Change SYNTAX of the following from 0..1024 to 0..2048:
                      tnSshPublicKey.
                   5) Added the following tables:
                      tnSysKeyStoreServiceTable
                      tnSysKeyStoreCertInfoTable."

      REVISION    "201905171200Z"
      DESCRIPTION "1) Added the following scalars:
                      tnSysBackupAndRestoreLocalInfo,
                      tnSysBackupAndRestoreType,
                      tnSysBackupAndRestoreLocalDelete.
                   2) Marked the following in tnSysLicenseMgrPrimaryServerStatus
                      and tnSysLicenseMgrSecondaryServerStatus as obsolete:
                      unknown(1),
                      standBy(3),
                   3) Added the following to tnSysLicenseMgrPrimaryServerStatus
                      and tnSysLicenseMgrSecondaryServerStatus:
                      notConnected(4)."

      REVISION    "201905031200Z"
      DESCRIPTION "1) Changed MAX-ACCESS of the following in
                      tnSysOtdrScanSystemProfileTable from read-only
                      to read-create:
                      tnSysOtdrScanSystemProfileDescription
                      tnSysOtdrScanSystemProfilePulseLength
                      tnSysOtdrScanSystemProfileRange
                      tnSysOtdrScanSystemProfileResolution
                      tnSysOtdrScanSystemProfileAvgTime
                   2) Changed MAX-ACCESS of the following in
                      tnSysOtdrScanSystemProfileMTable from read-only
                      to read-create:
                      tnSysOtdrScanSystemProfileMDescription
                      tnSysOtdrScanSystemProfileMPulseLength
                      tnSysOtdrScanSystemProfileMRange
                      tnSysOtdrScanSystemProfileMResolution
                      tnSysOtdrScanSystemProfileMAvgTime."

      REVISION    "201904261200Z"
      DESCRIPTION "1) Added the following scalars to tnSysBasics:
                      tnSysClusterV3SecurityUser.
                   2) Added the following to tnNeDiscoveryDeltaFileFlag:
                      syncTrapEnable(19)
                      to
                      syncTrapTransfer(21)."

      REVISION    "201904191200Z"
      DESCRIPTION "1) Added the following to tnSysOtdrScansystemProfileTable:
                      tnSysOtdrScanSystemProfileEventThreshold
                      tnSysOtdrScanSystemProfileIOR.
                   2) Added the following to tnSysOtdrScansystemProfileMTable
                      tnSysOtdrScanSystemProfileMEventThreshold
                      tnSysOtdrScanSystemProfileMIOR.
                   3) Changed SYNTAX of the following from Integer32 (1..4) to
                      Integer32 (1..9):
                      tnSysOtdrScanSystemProfileId.
                   4) Changed SYNTAX of the following from Integer32 (1..4) to
                      Integer32 (1..7):
                      tnSysOtdrScanSystemProfileMId."

      REVISION    "201904051200Z"
      DESCRIPTION "1) Added the following scalar to tnSysBasics:
                      tnSysDebug.
                   2) Added the following to tnNeDiscoveryTable:
                      tnNeDiscoveryDeltaSyncStatus."

      REVISION    "201903291200Z"
      DESCRIPTION "1) Added the following to tnNeDiscoveryDeltaFileFlag:
                      syncDisable(13)
                      to
                      pgSyncTransfer(18).
                   2) Added the following to tnSysLicenseMgr:
                      tnSysLicenseMgrLastRefresh
                      tnSysLicenseMgrCertStatus."

      REVISION    "201903151200Z"
      DESCRIPTION "Updated DEFVAL of following from tftp to ftp:
                   tnSysBackupAndRestoreProtocol
                   tnSysLicenseInvProtocol
                   tnSysDiscoveryServerProtocol."

      REVISION    "201902151200Z"
      DESCRIPTION "1) Added the following to tnNeDiscoveryTable:
                      tnNeDiscoveryDeltaFileFlag.
                   2) Mark the following as deprecated:
                      tnNeDiscoveryDeltaFilename."

      REVISION    "201902081200Z"
      DESCRIPTION "1) Added the following to tnSysSshKeyType:
                      rsa(2).
                   2) Updated the default value and description of the following:
                      tnSysSshKeyType."

      REVISION    "201901251200Z"
      DESCRIPTION "1) Added the following scalars to tnSysBasics:
                      tnSysLMEnabled
                      tnSysAlienChannelLicensingEnabled.
                   2) Added the following to tnSysLicenseMgr:
                      tnSysLicenseMgrTimeOut
                      tnSysLicenseMgrRetries."

      REVISION    "201812211200Z"
      DESCRIPTION "Added the following table:
                   tnLicenseEntityTable."

      REVISION    "201812141200Z"
      DESCRIPTION "Added the following scalar to tnSysBasics:
                   tnSysTL1Enable."

      REVISION    "201812061200Z"
      DESCRIPTION "1) Marked the following as obsolete:
                      tnSysDataDumpInfo
                      tnSysDataDump.
                   2) Added the following to tnSysLicenseMgr:
                      tnSysLicenseMgrExpiration."

      REVISION    "201811301200Z"
      DESCRIPTION "1) Added the following to tnNeDiscoveryTable:
                      tnNeDiscoveryDeltaFilename.
                   2) Added the following scalar:
                      tnSysDebugTransferIncludeInDumps.
                   3) Added the following to tnSysLicenseMgr:
                      tnSysLicenseMgrPrimaryServerStatus
                      tnSysLicenseMgrSecondaryServerStatus."

      REVISION    "201810261200Z"
      DESCRIPTION "Added the following scalars to tnSysLicenseMgr:
                   tnSysLicenseMgrKeepAliveTimer
                   tnSysLicenseMgrPrimaryServerIp
                   tnSysLicenseMgrPrimaryServerInetAddressType
                   tnSysLicenseMgrPrimaryServerInetAddress
                   tnSysLicenseMgrSecondaryServerIp
                   tnSysLicenseMgrSecondaryServerInetAddressType
                   tnSysLicenseMgrSecondaryServerInetAddress."

      REVISION    "201810121200Z"
      DESCRIPTION "Added the following to tnSysOtdrScanResultsTransfer:
                   tnSysOtdrScanResultsTransferRemoteInetAddressType
                   tnSysOtdrScanResultsTransferRemoteInetAddress."

      REVISION    "201810101200Z"
      DESCRIPTION "Added the following scalars to tnSysLinux:
                   tnSysLinuxRootUserStatus
                   tnSysLinuxApplUserStatus
                   tnSysLinuxLoginInactivityTimeOut."

      REVISION    "201809281200Z"
      DESCRIPTION "1) Added the following to tnSysOtdrScanResultsTransfer:
                      tnSysOtdrScanResultsLastTransferTimestamp.
                   2) Added the following scalar:
                      tnSyslogProtocol."

      REVISION    "201809211200Z"
      DESCRIPTION "Added the following scalars to tnSysOtdrScanResultsTransfer:
                   tnSysOtdrScanResultsTransferRemoteHostIp
                   tnSysOtdrScanResultsTransferProtocol
                   tnSysOtdrScanResultsTransferUserId
                   tnSysOtdrScanResultsTransferPassword
                   tnSysOtdrScanResultsTransferRemotePath
                   tnSysOtdrScanResultsTransferCommand
                   tnSysOtdrScanResultsTransferFilename
                   tnSysOtdrScanResultsTransferRecentSuccessFile
                   tnSysOtdrScanResultsTransferStatus."

      REVISION    "201809141200Z"
      DESCRIPTION "1) Updated the description of the following:
                      tnSysSslKeyModulus.
                   2) Updated the default value and description of the following:
                      tnSysSshKeyModulus."

      REVISION    "201809071200Z"
      DESCRIPTION "Added the following to tnSysBtInterface:
                   tnSysBtInterfaceMacAddress."

      REVISION    "201808311200Z"
      DESCRIPTION "Added the following scalars to tnSysBtInterface:
                   tnSysBtInterfaceDescription
                   tnSysBtInterfaceIpAddr
                   tnSysBtInterfaceIpSubMask
                   tnSysBtInterfaceAdminState
                   tnSysBtInterfaceLinkIntegrityStatus
                   tnSysBtInterfaceDHCPServer
                   tnSysBtInterfaceDHCPRange
                   tnSysBtInterfaceNodeSerialNum."

      REVISION    "201804271200Z"
      DESCRIPTION "1) Updated the default value and description of the following:
                      tnSysSslKeyModulus.
                   2) Updated the description of the following:
                      tnSysSshKeyModulus."

      REVISION    "201803021200Z"
      DESCRIPTION "Added the following table:
                   tnSysIpv6AclEthIfFilterTable."

      REVISION    "201802231200Z"
      DESCRIPTION "Updated the contact info."

      REVISION    "201802161200Z"
      DESCRIPTION "Added the following table:
                   tnSysIpAclEthIfFilterTable."

      REVISION    "201801261200Z"
      DESCRIPTION "Added the following scalars to tnSysLinux:
                   tnSysLinuxRootPasswordStatus
                   tnSysLinuxApplPasswordStatus."

      REVISION    "201712131200Z"
      DESCRIPTION "1) Added the following to tnSysIpAclIpv6PatternAction and
                      tnSysIpAclPatternAction:
                      log(3).
                   2) Added the following to tnSysIpAclIpv6InterfaceTable:
                      tnSysIpAclIpv6InterfaceFilterLog.
                   3) Added the following to tnSysIpAclInterfaceTable:
                      tnSysIpAclInterfaceFilterLog."

      REVISION    "201712081200Z"
      DESCRIPTION "Added the following scalars to tnSysBasics:
                   tnSysNetWorkTraceV3SecurityUser
                   tnSysScotV3SecurityUser."

      REVISION    "201712011200Z"
      DESCRIPTION "Added the following scalar:
                   tnSysDebugTransferScratchDir."

      REVISION    "201709081200Z"
      DESCRIPTION "Added the following scalar to tnSysBasics:
                   tnSysUnkeyedDanglingOchAddDropEnabled."

      REVISION    "201707071200Z"
      DESCRIPTION "Fixed MIB compile issues."

      REVISION    "201704281200Z"
      DESCRIPTION "Added the following table:
                   tnSysOtdrScanSystemProfileMTable."

      REVISION    "201704131200Z"
      DESCRIPTION "1) Added the following to tnSysIpAclPatternTable:
                      tnSysIpAclPatternSrcPortRangeEnd
                      tnSysIpAclPatternDestPortRangeEnd.
                   2) Added the following to tnSysIpAclIpv6PatternTable:
                      tnSysIpAclIpv6PatternSrcPortRangeEnd
                      tnSysIpAclIpv6PatternDestPortRangeEnd."

      REVISION    "201704071200Z"
      DESCRIPTION "Added the following scalars to tnSysFileInitialization:
                   tnSysFileInitializationRoot
                   tnSysFileInitializationUserId
                   tnSysFileInitializationPassword
                   tnSysFileInitializationFilename
                   tnSysFileInitializationInetAddressType
                   tnSysFileInitializationInetAddress."

      REVISION    "201703031200Z"
      DESCRIPTION "Added the following scalar to tnSysBasics:
                   tnSysOpenAgentControl."

      REVISION    "201702241200Z"
      DESCRIPTION "Added the following scalar to tnSysBasics:
                   tnSysUserlabel."

      REVISION    "201702171200Z"
      DESCRIPTION "Added the following scalars to tnSysSsl:
                   tnSysSslCertTransferInetAddressType
                   tnSysSslCertTransferInetAddress."

      REVISION    "201702101200Z"
      DESCRIPTION "1) Added the following scalars to tnSysControlNetwork:
                      tnSysOcsIp1Password,
                      tnSysOcsIp2Password,
                      tnSysOcsIp3Password,
                      tnSysConfiguredSnmpSourceIPv6,
                      tnSysConfiguredRadiusSourceIPv6.
                   2) Added the following scalars to tnSysNtp:
                      tnSysNtpServerCurrentInetAddressType,
                      tnSysNtpServerCurrentInetAddress.
                   3) Changed SYNTAX  from (SIZE(1..16)) to (SIZE(1..48))
                      for the following:
                      tnSysNtpServerIdStatsIp
                      tnSysNtpServerIdStatsRefId."

      REVISION    "201702031200Z"
      DESCRIPTION "1) Added the following scalars to tnSysOtdrScanTransfer:
                      tnSysOtdrScanTransferInetAddressType
                      tnSysOtdrScanTransferInetAddress.
                   2) Added the following to tnClusterTable:
                      tnClusterInetAddressType
                      tnClusterInetAddress."

      REVISION    "201701271200Z"
      DESCRIPTION "1) Added the following scalar to tnSysIpAclSysDefault:
                      tnSysIpAclCfgRestoreToDefault.
                   2) Added the following tables:
                      tnSysIpAclIpv6PatternTable
                      tnSysIpAclIpv6FilterTable
                      tnSysIpAclIpv6InterfaceTable
                      tnSysIpv6AclNetIfFilterTable.
                   3) Added the following scalars to tnSysIpAclIpv6SysDefault:
                      tnSysIpAclIpv6RxAction
                      tnSysIpAclIpv6TxAction
                      tnSysIpAclIpv6SnmpCfgEnable
                      tnSysIpAclIpv6CfgRestoreToDefault."

      REVISION    "201701201200Z"
      DESCRIPTION "1) Added the following scalars:
                      tnSysDiscoveryServerInetAddressType,
                      tnSysDiscoveryServerInetAddress.
                   2) Added the tnSysIpAclIpv6SysDefault node.
                   3) Added the following to tnNeDiscoveryTable:
                      tnNeDiscoveryServerInetAddressType,
                      tnNeDiscoveryServerInetAddress."

      REVISION    "201701131200Z"
      DESCRIPTION "Added the following scalar:
                   tnSysCNLinkPhysicalIfIndex."

      REVISION    "201612281200Z"
      DESCRIPTION "Added the following scalars:
                   tnSysLicenseInvLastOperPercentCompleted,
                   tnSysLicenseInvLastUploadFileName,
                   tnSysLicenseInvFileLastUploadStatus,
                   tnSysLicenseInvFileLastUploadTimeStamp."

      REVISION    "201612211200Z"
      DESCRIPTION "Changed the units of tnSysFilterCheckTime to seconds."

      REVISION    "201612051200Z"
      DESCRIPTION "Added the following scalars:
                   tnSyslogInetAddress,
                   tnSyslogInetAddressType,
                   tnSysNtpServerInetAddress,
                   tnSysNtpServerInetAddressType."

      REVISION    "201611291200Z"
      DESCRIPTION "Added the following scalar:
                   tnSysFilterCheckTime."

      REVISION    "201611281200Z"
      DESCRIPTION "Added the following scalars:
                   tnSysTransferLogRemoteHostInetAddressType,
                   tnSysTransferLogRemoteHostInetAddress,
                   tnSysBackupAndRestoreRemoteHostInetAddressType,
                   tnSysBackupAndRestoreRemoteHostInetAddress,
                   tnSysLicenseInvPathInetAddressType,
                   tnSysLicenseInvPathInetAddress,
                   tnSysDebugTransferRemoteInetAddressType,
                   tnSysDebugTransferRemoteInetAddress,
                   tnSysConfiguredInetAddressType,
                   tnSysConfiguredInetAddress,
                   tnSysConfiguredPrefixLength."

      REVISION    "201611221200Z"
      DESCRIPTION "Added the following scalar:
                   tnSysFlexGridClusterOcsAddDropEnabled."

      REVISION    "201611181200Z"
      DESCRIPTION "Added tnSysLinux attributes."

      REVISION    "201611161200Z"
      DESCRIPTION "Updated the contact info."

      REVISION    "201611071200Z"
      DESCRIPTION "Added the following scalar:
                   tnSysSlotMigrationControl."

      REVISION    "201610201200Z"
      DESCRIPTION "Added the following scalar:
                   tnSysPMStreamingServerControl."

      REVISION    "201609271200Z"
      DESCRIPTION "1) Changed SYNTAX of tnSysOtdrScanSystemProfileId from (SIZE(1..16))
                      to (SIZE(1..4)).
                   2) Updated values and default value of tnSysOtdrScanSystemProfileRange."

      REVISION    "201609161200Z"
      DESCRIPTION "1) Added tnSysDataDump attributes.
                   2) Added the following scalar:
                      tnSysFmRead."

      REVISION    "201609091200Z"
      DESCRIPTION "1) Added the following to tnSysDebugTransfer:
                      tnSysDebugTransferPercentCompleted.
                   2) Made the following to read-only:
                      tnSysDebugTransferRecentSuccessFile
                      tnSysDebugTransferFilename
                      tnSysDebugTransferTimestamp."

      REVISION    "201607291200Z"
      DESCRIPTION "Added tnSysLicenseInv attributes."

      REVISION    "201607251200Z"
      DESCRIPTION "Added the following to tnSysDebugTransfer:
                   tnSysDebugTransferFilename
                   tnSysDebugTransferRecentSuccessFile
                   tnSysDebugTransferTimestamp
                   tnSysDebugTransferShelfNum."

      REVISION    "201606231200Z"
      DESCRIPTION "Added the following scalar:
                   tnSysPMFineGranularityControl."

      REVISION    "201606151200Z"
      DESCRIPTION "Added the following to tnSnmpTargetAddrTable:
                   tnSnmpTargetAddrTrapGroupId."

      REVISION    "201604011200Z"
      DESCRIPTION "Added the following scalars:
                   tnSysDisplayShelfLabel."

      REVISION    "201603301200Z"
      DESCRIPTION "1) Added the following to tnSysSecureMode:
                      anssi(5).
                   2) Added the following to tnSysSecurityMode:
                      anssi(4)."

      REVISION    "201603041200Z"
      DESCRIPTION "Added the following scalars:
                   tnSysLoopbackIpAddress1,
                   tnSysLoopbackIp1SubnetMask."

      REVISION    "201603021200Z"
      DESCRIPTION "Added the following scalars:
                   tnSysPmFetchBulkShelfNum."

      REVISION    "201602261200Z"
      DESCRIPTION "Added the following scalars:
                   tnSysConfiguredLoopbackIp1
                   tnSysConfiguredLoopbackIp1SubnetMask
                   tnSysConfiguredSnmpSource1
                   tnSysConfiguredRadiusSource1."

      REVISION    "201602011200Z"
      DESCRIPTION "Added tnSysPmFetchBulk attributes."

      REVISION    "201601271200Z"
      DESCRIPTION "Changed the range of tnSysThermalShutdownAutotimer:
                   From (0..3600) To (-1..3600)."

      REVISION    "201512171200Z"
      DESCRIPTION "Added the following scalars:
                   tnSysConfiguredRadiusSource."

      REVISION    "201512101200Z"
      DESCRIPTION "Added the following to tnSysBasics:
                   tnSysThermalShutdownAutotimer."

      REVISION    "201512031200Z"
      DESCRIPTION "Added the following scalars:
                   tnSysOcs1LinkStatus
                   tnSysOcs2LinkStatus
                   tnSysOcs3LinkStatus."

      REVISION    "201511171200Z"
      DESCRIPTION "Added the following scalars:
                   tnSysConfiguredOcs2IpAddress
                   tnSysConfiguredOcs3IpAddress."

      REVISION    "201509301200Z"
      DESCRIPTION "Added the following to tnClusterTable:
                   tnClusterlinkStatus."

      REVISION    "201509161200Z"
      DESCRIPTION "Added the following to tnSysBasics:
                   tnSysAltitude."

      REVISION    "201507131200Z"
      DESCRIPTION "Added the following table:
                   tnClusterTable."

      REVISION    "201507121200Z"
      DESCRIPTION "1) Changed the SYNTAX and removed the DEFVAL of the following:
                      tnClusterRowStatus.
                   2) Changed the MAX-ACCESS of the following:
                      tnClusterFarEndNode."

      REVISION    "201502201200Z"
      DESCRIPTION "1) Added the following table:
                      tnSshKeyTable.
                   2) Updated the default value and description
                      for tnSysSshKeyModulus."

      REVISION    "201404231200Z"
      DESCRIPTION "1) Added the following to tnSysBasics:
                      tnSysOtdrListOfFileNames
                      tnSysOtdrFileCounts.
                   2) Added the following to tnSysOtdrScanTransfer:
                      tnSysOtdrScanTransferRemoteHostIp
                      tnSysOtdrScanTransferCommand
                      tnSysOtdrScanTransferRemotePath
                      tnSysOtdrScanTransferStatus
                      tnSysOtdrScanTransferFilename
                      tnSysOtdrScanTransferProtocol
                      tnSysOtdrScanTransferUserId
                      tnSysOtdrScanTransferPassword."

      REVISION    "201403301200Z"
      DESCRIPTION "1) Changed SYNTAX of the following from (SIZE(0..255))
                      to (SIZE(0..128)):
                      tnSysDiscoveryServerUserId
                      tnSysDiscoveryServerPassword
                      tnSysBackupAndRestoreRemotePath
                      tnSysBackupAndRestoreUserId
                      tnSysBackupAndRestorePassword
                      tnSysFtpServerUserId
                      tnSysFtpServerPassword
                      tnNeDiscoveryServerUserId
                      tnNeDiscoveryServerPassword.
                   2) Changed SYNTAX of the following from (SIZE(0..255))
                      to (SIZE(0..32)):
                      tnSysTransferLogUserId
                      tnSysTransferLogPassword."

      REVISION    "201403041200Z"
      DESCRIPTION "Added the following table:
                   tnSysOtdrScanSystemProfileTable."

      REVISION    "201402261200Z"
      DESCRIPTION "1) Marked the following as obsolete:
                      tnSysOperationPercentCompleted
                      tnSysLastOperationTimeStamp
                      tnSysBackupAndRestoreRemotePort
                      tnSysFeatureNetworkElementFaultCorrelation.
                   2) Added DEFVAL to attributes."

      REVISION    "201311201200Z"
      DESCRIPTION "Added the following table:
                   tnNeDiscoveryTable."

      REVISION    "201304191200Z"
      DESCRIPTION "Added the following to tnSysLoggingCLI and
                   tnSysLoggingSNMP:
                   level6Read(11),  -- crypto
                   level6Write(12)  -- crypto."

      REVISION    "201304171200Z"
      DESCRIPTION "1) Added the following to tnSysTransferLogType:
                      ualPartial(8).
                   2) Added the following to tnSysTransferLogLastCommand:
                      ualPartial(5).
                   3) Added the following scalars:
                      tnSysTransferLogWindowStart
                      tnSysTransferLogWindowStop."

      REVISION    "201303201200Z"
      DESCRIPTION "1) Changed DESCRIPTION of tnSysDiscoveryMask from
                      stage2(1), -- links       (unsupported)
                      to
                      stage2(1), -- ftp discovery.
                   2) Added the following scalar:
                      tnSysFipsSquelchMode."

      REVISION    "201303061200Z"
      DESCRIPTION "1) Added the following to tnSysSecureMode:
                      fips(4).
                   2) Added the following to tnSysSecurityMode:
                      fips(3)."

      REVISION    "201301311200Z"
      DESCRIPTION "Added the following table:
                   tnSysIpAclNetIfFilterTable."

      REVISION    "201301201200Z"
      DESCRIPTION "1) Added the following to tnSysIpAclPatternTable:
                      tnSysIpAclPatternSystemDefault.
                   2) Added the following to tnSysIpAclFilterTable:
                      tnSysIpAclFilterSystemDefault.
                   3) Added the following to tnSysIpAclInterfaceTable:
                      tnSysIpAclInterfaceSystemDefault."

      REVISION    "201301161200Z"
      DESCRIPTION "1) Added tnSysNtpServerAuthenticationTable.
                   2) Added the following to tnSysNtpServerTable:
                      tnSysNtpServerKeyIndex.
                   3) Added the following to tnSysNtpServerIdStatsTable:
                      tnSysNtpServerIdStatsKeyIndex."

      REVISION    "201205181200Z"
      DESCRIPTION "Marked the following as obsolete:
                   tnSysNtpDrift
                   tnSysNtpTimeOffset."

      REVISION    "201202161200Z"
      DESCRIPTION "Added the following scalar:
                   tnSysSwitchId."

      REVISION    "201201121200Z"
      DESCRIPTION "Added the following scalars:
                   tnSysFtpServerEnabled
                   tnSysFtpServerUserId
                   tnSysFtpServerPassword."

      REVISION    "201110241200Z"
      DESCRIPTION "Added the following scalar:
                   tnSysIpAclPatternSrcPort."

      REVISION    "201109301200Z"
      DESCRIPTION "Added the following scalars:
                   tnSysConfiguredOcsIpAddress
                   tnSysFeatureFastServiceSetup."

      REVISION    "201108121200Z"
      DESCRIPTION "1) Updated description of the following attributes:
                      tnSysDiscoveryServerPassword
                      tnSysBackupAndRestorePassword
                      tnSysSslCertTransferRemotePassword
                      tnSysTransferLogPassword.
                   2) Marked the following NTP scalars as obsolete:
                      tnSysNtpTimeOffsetHours
                      tnSysNtpTimeOffsetMinutes
                      tnSysNtpTimeOffsetTimeZone
                      tnSysNtpScale
                      tnSysNtpDaylightSavingsTimeConfigured."

      REVISION    "201106211200Z"
      DESCRIPTION "1) Added the following scalars:
                      tnSysTimeOffsetTimeZone.
                      tnSysLastOperationTimeStamp
                      tnSysOperationPercentCompleted.
                   2) Marked the following NTP scalars as deprecated:
                      tnSysNtpTimeOffsetHours
                      tnSysNtpTimeOffsetMinutes
                      tnSysNtpTimeOffsetTimeZone
                      tnSysNtpScale
                      tnSysNtpDaylightSavingsTimeConfigured."

      REVISION    "201106031200Z"
      DESCRIPTION "1) Added the following attributes:
                      tnSysFirstLevelControllerCapacity
                      tnSysMatrix0CompactCapacity
                      tnSysUniversalMatrixFirstLevelControllerCapacity.
                   2) Added status strings for tnSysBackupAndRestoreStatus."

      REVISION    "201105231200Z"
      DESCRIPTION "1) Added tnSysEquipmentControllerCapacity.
                   2) Added DEFVAL for the following attributes:
                      tnSysRingID, 0
                      tnSysNetworkElementID, 0
                      tnSysAINSDebounceTime, 600
                      tnSysWavelengthTrackerWaveKeySpace, 0."

      REVISION    "201104251200Z"
      DESCRIPTION "1) Added tnSysNtpClockMode.
                   2) Added tnSysNtpServerIdStatsTable."

      REVISION    "201103281200Z"
      DESCRIPTION "Added tnSysTransferLog attributes."

      REVISION    "201103171200Z"
      DESCRIPTION "Added the following tables:
                   tnSysIpAclSysDefault,
                   tnSysIpAclPatternTable,
                   tnSysIpAclFilterTable,
                   tnSysIpAclInterfaceTable."

      REVISION    "201103151200Z"
      DESCRIPTION "1) Marked tnSysSslCertTransferStatus as obsolete.
                   2) Updated range of tnSysSslKeyModulus to (512, 2048).
                   3) Defined AluWdmSslOperationStatus.
                   4) Added the following SSL attributes:
                      tnSysSslCsrUploadStatus,
                      tnSysSslCertDownloadStatus,
                      tnSysSslCertInstallStatus,
                      tnSysSslCsrGenerationStatus."

      REVISION    "201011111200Z"
      DESCRIPTION "Added tnSysName."

      REVISION    "201010181200Z"
      DESCRIPTION "Marked the following as obsolete:
                   tnSysDiscoveryTFTPServer
                   tnSysDiscoveryNMSMask
                   tnSysFeatureWavelengthTracker."

      REVISION    "201006221200Z"
      DESCRIPTION "Added tnSysSecurity attributes."

      REVISION    "201001111200Z"
      DESCRIPTION "Updated description for tnSysConfiguredSnmpSource."

      REVISION    "201001071200Z"
      DESCRIPTION "Added tnSysConfiguredSnmpSource."

      REVISION    "200907221200Z"
      DESCRIPTION "Added tnSysTemperatureInCelsius."

      REVISION    "200905051200Z"
      DESCRIPTION "Added tnSysExtendedTemperatureRange for PSS-1 ETR."

      REVISION    "200904301200Z"
      DESCRIPTION "1) Marked tnSysMinPasswordLength and
                      tnSysMaxPasswordLength as obsolete.
                   2) Moved recently defined security related MIB
                      attributes from tnSysBasics to tnUserMgmtGlobal
                      (in TROPIC-USERMGMT-MIB)."

      REVISION    "200904281200Z"
      DESCRIPTION "1) Defined tnSysNtpDriftString and tnSysNtpTimeOffsetString
                      to replace tnSysNtpDrift and tnSysNtpTimeOffset,
                      respectively.
                   2) Marked the following as deprecated:
                      tnSysNtpDrift
                      tnSysNtpTimeOffset."

      REVISION    "200904081200Z"
      DESCRIPTION "Added security MIB attributes to tnSysBasics."

      REVISION    "200904071200Z"
      DESCRIPTION "Updated description and added range values to Security
                   MIB attributes."

      REVISION    "200903031200Z"
      DESCRIPTION "Used AluWdmEnabledDisabled common enum in TROPIC-TC."

      REVISION    "200902271200Z"
      DESCRIPTION "Used AluWdmEnabledDisabled common enum in SNMPv2-TC."

      REVISION    "200810141200Z"
      DESCRIPTION "Added restoreForceFromRemote(4) to
                   tnSysBackupAndRestoreCommand."

      REVISION    "200810101200Z"
      DESCRIPTION "Change size of tnSysNtpTimeOffsetTimeZone from
                   (0..10) to (0..128)."

      REVISION    "200805291200Z"
      DESCRIPTION "Updated the tnSysNtpServerIndex description."

      REVISION    "200804051200Z"
      DESCRIPTION "Added tnSysBackupAndRestoreRemotePort."

      REVISION    "200802161200Z"
      DESCRIPTION "1) Added the backup and restore file CRC attribute.
                   2) Updated the system MIB description.
                   3) Increased the backup and restore path to 255
                      characters.
                   4) Added date to the backup and restore timestamp
                      attribute description."

      ::= { tnSystemModules 1 }

  tnSystemConf                  OBJECT IDENTIFIER ::= { tnSystemMIB 1 }
  tnSystemGroups                OBJECT IDENTIFIER ::= { tnSystemConf 1 }
  tnSystemCompliances           OBJECT IDENTIFIER ::= { tnSystemConf 2 }
  tnSystemObjs                  OBJECT IDENTIFIER ::= { tnSystemMIB 2 }
  tnSysBasics                   OBJECT IDENTIFIER ::= { tnSystemObjs 1 }
  tnSysControlNetwork           OBJECT IDENTIFIER ::= { tnSystemObjs 2 }
  tnSysRedundancy               OBJECT IDENTIFIER ::= { tnSystemObjs 3 }
  tnSysDiscovery                OBJECT IDENTIFIER ::= { tnSystemObjs 4 }
  tnSysLogging                  OBJECT IDENTIFIER ::= { tnSystemObjs 5 }
  tnSysBackupAndRestore         OBJECT IDENTIFIER ::= { tnSystemObjs 6 }
  tnSysNtp                      OBJECT IDENTIFIER ::= { tnSystemObjs 7 }
  tnSysNtpServers               OBJECT IDENTIFIER ::= { tnSystemObjs 8 }
  tnSnmpTargetAddresses         OBJECT IDENTIFIER ::= { tnSystemObjs 9 }
  tnSyslog                      OBJECT IDENTIFIER ::= { tnSystemObjs 10 }
  tnSysTiming                   OBJECT IDENTIFIER ::= { tnSystemObjs 11 }
  tnSysFeatures                 OBJECT IDENTIFIER ::= { tnSystemObjs 12 }
  tnSysFaultCorrelation         OBJECT IDENTIFIER ::= { tnSystemObjs 13 }
  tnSysErrorHandling            OBJECT IDENTIFIER ::= { tnSystemObjs 14 }
  tnSysSecurity                 OBJECT IDENTIFIER ::= { tnSystemObjs 15 }
  tnSysSsh                      OBJECT IDENTIFIER ::= { tnSysSecurity 2 }
  tnSysSsl                      OBJECT IDENTIFIER ::= { tnSysSecurity 3 }
  tnSysTransferLog              OBJECT IDENTIFIER ::= { tnSystemObjs 16 }
  tnSysAccessControlList        OBJECT IDENTIFIER ::= { tnSystemObjs 17 }
  tnSysIpAclSysDefault          OBJECT IDENTIFIER ::= { tnSysAccessControlList 1 }
  tnSysNtpServerIdStats         OBJECT IDENTIFIER ::= { tnSystemObjs 18 }
  tnSysFtpServer                OBJECT IDENTIFIER ::= { tnSystemObjs 19 }
  tnSysNtpServerAuthentication  OBJECT IDENTIFIER ::= { tnSystemObjs 20 }
  tnNeDiscovery                 OBJECT IDENTIFIER ::= { tnSystemObjs 21 }
  tnSysOtdrScan                 OBJECT IDENTIFIER ::= { tnSystemObjs 22 }
  tnSysOtdrScanSystemProfile    OBJECT IDENTIFIER ::= { tnSysOtdrScan 1 }
  tnSysOtdrScanTransfer         OBJECT IDENTIFIER ::= { tnSysOtdrScan 2 }
  tnSysKey                      OBJECT IDENTIFIER ::= { tnSysSecurity 4 }
  tnClusterObjs                 OBJECT IDENTIFIER ::= { tnSystemObjs 23 }
  tnSysPmFetchBulk              OBJECT IDENTIFIER ::= { tnSystemObjs 24 }
  tnSysDebugTransfer            OBJECT IDENTIFIER ::= { tnSystemObjs 25 }
  tnSysLicenseInv               OBJECT IDENTIFIER ::= { tnSystemObjs 26 }
--  obsolete
--  tnSysDataDump                 OBJECT IDENTIFIER ::= { tnSystemObjs 27 }
  tnSysLinux                    OBJECT IDENTIFIER ::= { tnSystemObjs 28 }
  tnSysIpAclIpv6SysDefault      OBJECT IDENTIFIER ::= { tnSystemObjs 29 }
  tnSysFileInitialization       OBJECT IDENTIFIER ::= { tnSystemObjs 30 }
  tnSysBtInterface              OBJECT IDENTIFIER ::= { tnSystemObjs 31 }
  tnSysLicenseMgr               OBJECT IDENTIFIER ::= { tnSystemObjs 32 }
  tnLicenseObjs                 OBJECT IDENTIFIER ::= { tnSystemObjs 33 }
  tnSysKeyStore                 OBJECT IDENTIFIER ::= { tnSystemObjs 34 }
  tnSysOtdrScanSystemProfileM   OBJECT IDENTIFIER ::= { tnSysOtdrScan 3 }
  tnSysOtdrScanResultsTransfer  OBJECT IDENTIFIER ::= { tnSysOtdrScan 4 }
  tnSysBgp                      OBJECT IDENTIFIER ::= { tnSystemObjs 35 }
  tnSysDiscoverMe               OBJECT IDENTIFIER ::= { tnSystemObjs 36 }
  tnSyslogServer                OBJECT IDENTIFIER ::= { tnSystemObjs 37 }
  tnPctObjs                     OBJECT IDENTIFIER ::= { tnSystemObjs 38 }
  tnKeyObjs                     OBJECT IDENTIFIER ::= { tnSystemObjs 39 }
  tnTransferSysLog              OBJECT IDENTIFIER ::= { tnSystemObjs 40 }
  tnSysHealthCare               OBJECT IDENTIFIER ::= { tnSystemObjs 41 }
  tnSysTrapThrottling           OBJECT IDENTIFIER ::= { tnSystemObjs 42 }
  tnSysNmsObjs                  OBJECT IDENTIFIER ::= { tnSystemObjs 43 }
  tnSysDnsServer                OBJECT IDENTIFIER ::= { tnSystemObjs 44 }
  tnTransferPMDiscovery         OBJECT IDENTIFIER ::= { tnSystemObjs 45 }

--------------------------------------------------------------------------------
-- Type Definitions
--------------------------------------------------------------------------------
    TropicSysTimingReferenceQuality ::= TEXTUAL-CONVENTION
        STATUS         current
        DESCRIPTION    "."
        SYNTAX         INTEGER {
                         unknown(1),
                         prs(2),       -- SONET, Stratum 1 Traceable
                         stu(3),       -- SONET, Synchronized - Traceability Unknown
                         st2(4),       -- SONET, Stratum 2 Traceable
                         tnc(5),       -- SONET, Transit Node Clock Traceable
                         st3e(6),      -- SONET, Stratum 3E Traceable
                         st3(7),       -- SONET, Stratum 3 Traceable
                         smc(8),       -- SONET, SONET Minimum Clock Traceable
                         st4(9),       -- SONET, Stratum 4 Traceable
                         dus(10),      -- SONET, DON'T USE for Synchronization
                         prc(11),      -- SDH, PRC Clock G.811
                         ssua(12),     -- SDH, Type I or V SSU clock G.812
                         ssub(13),     -- SDH, Type VI SSU clock G.812
                         sec(14),      -- SDH, SEC clock G.813 option 1
                         dnu(15)       -- SDH, DON'T USE for Synchronization
                       }

    TropicSysTimingReferenceTimingMode ::= TEXTUAL-CONVENTION
        STATUS         current
        DESCRIPTION    "."
        SYNTAX         INTEGER {
                         unknown(1),
                         external(2),
                         line(3),
                         through(4),
                         loop(5),
                         local(6)
                       }

    AluWdmSslOperationStatus ::= TEXTUAL-CONVENTION
        STATUS         current
        DESCRIPTION    "SSL operation status."
        SYNTAX         INTEGER {
                         completed(1),
                         inProgress(2),
                         failed(3),
                         none(4)
                       }

    AluWdmTransferStatus ::= TEXTUAL-CONVENTION
        STATUS         current
        DESCRIPTION    "This attribute indicates the status of the
                        previously executed transfer command operation."
        SYNTAX         INTEGER {
                         none(1),
                         completed(2),
                         inProgress(3),
                         failure(4),
                         failTimeout(5)
                       }

    AluWdmOcsLinkStatus ::= TEXTUAL-CONVENTION
        STATUS         current
        DESCRIPTION    "OCS node link status."
        SYNTAX         INTEGER {
                         up(1),
                         down(2),
                         notConnected(3)
                       }

    NokiaSysBgpMaxPrefixAction ::= TEXTUAL-CONVENTION
        STATUS         current
        DESCRIPTION    "."
        SYNTAX         INTEGER {
                         disabled(1),
                         alarmOnly(2),
                         tearDown(3),
                         restartInterval(4)
                       }

--------------------------------------------------------------------------------
-- Object Definitions
--------------------------------------------------------------------------------

--------------------------------------------------------------------------------
--  Basics
--------------------------------------------------------------------------------
    tnSysDescr OBJECT-TYPE
        SYNTAX         SnmpAdminString (SIZE(0..255))
        MAX-ACCESS     read-write
        STATUS         current
        DESCRIPTION    "System's Description."
        DEFVAL         { "" }
        ::= { tnSysBasics 1 }

    tnSysTelnetPort OBJECT-TYPE
        SYNTAX         Unsigned32 (1..65535)
        MAX-ACCESS     read-only
        STATUS         current
        DESCRIPTION    "System's Telnet Port."
        DEFVAL         { 23 }
        ::= { tnSysBasics 2 }

    tnSysHttpPort OBJECT-TYPE
        SYNTAX         Unsigned32 (1..65535)
        MAX-ACCESS     read-only
        STATUS         current
        DESCRIPTION    "System's Http Port."
        DEFVAL         { 80 }
        ::= { tnSysBasics 3 }

    tnSysDateAndTime OBJECT-TYPE
        SYNTAX         DateAndTime
        MAX-ACCESS     read-write
        STATUS         current
        DESCRIPTION    "System's Date and Time."
        ::= { tnSysBasics 4 }

    tnSysReset OBJECT-TYPE
        SYNTAX         TropicResetType
        MAX-ACCESS     read-write
        STATUS         current
        DESCRIPTION    "System reset."
        DEFVAL         { noCmd }
        ::= { tnSysBasics 5 }

    tnSysMIBVersion OBJECT-TYPE
        SYNTAX         SnmpAdminString (SIZE(0..255))
        MAX-ACCESS     read-only
        STATUS         current
        DESCRIPTION    "The current version of the Nokia
                        proprietary MIBs."
        ::= { tnSysBasics 6 }

    tnSysRingID OBJECT-TYPE
        SYNTAX         Unsigned32
        MAX-ACCESS     read-only
        STATUS         current
        DESCRIPTION    "Current configurable range: 0 to 62."
        DEFVAL         { 0 }
        ::= { tnSysBasics 7 }

    tnSysNetworkElementID OBJECT-TYPE
        SYNTAX         Unsigned32
        MAX-ACCESS     read-write
        STATUS         current
        DESCRIPTION    "Current configurable range: 0 to 30."
        DEFVAL         { 0 }
        ::= { tnSysBasics 8 }

    tnSysAINSDebounceTime OBJECT-TYPE
        SYNTAX         Unsigned32
        UNITS          "seconds"
        MAX-ACCESS     read-write
        STATUS         current
        DESCRIPTION    "This attribute must be set in multiples of 60s.

                        Current configurable range: 1m to 96h 0m."
        DEFVAL         { 600 }
        ::= { tnSysBasics 9 }

    tnSysSonetSdhMode OBJECT-TYPE
        SYNTAX         INTEGER {
                         sonet(1),
                         sdh(2)
                       }
        MAX-ACCESS     read-write
        STATUS         current
        DESCRIPTION    "Sonet/SDH Mode."
        DEFVAL         { sonet }
        ::= { tnSysBasics 10 }

    tnSysAlarmReportingControl OBJECT-TYPE
        SYNTAX         INTEGER {
                         unknown(1),
                         released(2),
                         indefiniteInhibition(3)
                       }
        MAX-ACCESS     read-write
        STATUS         current
        DESCRIPTION    "Alarm reporting control."
        DEFVAL         { indefiniteInhibition }
        ::= { tnSysBasics 11 }

    tnSysWavelengthTrackerWaveKeySpace OBJECT-TYPE
        SYNTAX         Unsigned32
        MAX-ACCESS     read-write
        STATUS         current
        DESCRIPTION    "Current configurable range: 0 to 255."
        DEFVAL         { 0 }
        ::= { tnSysBasics 12 }

    tnSysSecureMode OBJECT-TYPE
        SYNTAX         INTEGER {
                         unknown(1),
                         nonSecure(2),
                         secure(3),
                         fips(4),
                         anssi(5)
                       }
        MAX-ACCESS     read-only
        STATUS         current
        DESCRIPTION    "Secure mode inherited from 1696R.  For 1830
                        secure mode, use tnSysSecurityMode."
        DEFVAL         { nonSecure }
        ::= { tnSysBasics 13 }

--    obsolete
--    tnSysMinPasswordLength OBJECT-TYPE ::= { tnSysBasics 14 }
--    tnSysMaxPasswordLength OBJECT-TYPE ::= { tnSysBasics 15 }

    tnSysExtendedTemperatureRange OBJECT-TYPE
        SYNTAX         TruthValue
        MAX-ACCESS     read-write
        STATUS         current
        DESCRIPTION    "Extended temperature range for 1830 PSS-1."
        DEFVAL         { true }
        ::= { tnSysBasics 16 }

    tnSysTemperatureInCelsius OBJECT-TYPE
        SYNTAX         TruthValue
        MAX-ACCESS     read-write
        STATUS         current
        DESCRIPTION    "."
        DEFVAL         { true }
        ::= { tnSysBasics 17 }

    tnSysName OBJECT-TYPE
        SYNTAX         SnmpAdminString (SIZE(0..255))
        MAX-ACCESS     read-write
        STATUS         current
        DESCRIPTION    "This is to replace sysName, so that the system ID
                        may have characters outside of those supported by
                        DisplayString."
        DEFVAL         { "" }
        ::= { tnSysBasics 18 }

    tnSysEquipmentControllerCapacity OBJECT-TYPE
        SYNTAX         AluWdmCardCapacity
        MAX-ACCESS     read-write
        STATUS         current
        DESCRIPTION    "The capacity of the storage medium of the
                        Equipment Controller cards in the node."
        DEFVAL         { unknownCapacity }
        ::= { tnSysBasics 19 }

    tnSysFirstLevelControllerCapacity OBJECT-TYPE
        SYNTAX         AluWdmCardCapacity
        MAX-ACCESS     read-write
        STATUS         current
        DESCRIPTION    "The capacity of the storage medium of the
                        First Level Controller cards in the node."
        DEFVAL         { unknownCapacity }
        ::= { tnSysBasics 20 }

    tnSysMatrix0CompactCapacity OBJECT-TYPE
        SYNTAX         AluWdmCardCapacity
        MAX-ACCESS     read-write
        STATUS         current
        DESCRIPTION    "The capacity of the storage medium of the
                        Matrix0 Compact cards in the node."
        DEFVAL         { unknownCapacity }
        ::= { tnSysBasics 21 }

    tnSysUniversalMatrixFirstLevelControllerCapacity OBJECT-TYPE
        SYNTAX         AluWdmCardCapacity
        MAX-ACCESS     read-write
        STATUS         current
        DESCRIPTION    "The capacity of the storage medium of the
                        Universal Matrix First Level Controller
                        cards in the node."
        DEFVAL         { unknownCapacity }
        ::= { tnSysBasics 22 }

    tnSysTimeOffsetTimeZone OBJECT-TYPE
        SYNTAX         SnmpAdminString (SIZE(0..128))
        MAX-ACCESS     read-write
        STATUS         current
        DESCRIPTION    "."
        ::= { tnSysBasics 23 }

--    obsolete
--    tnSysOperationPercentCompleted OBJECT-TYPE ::= { tnSysBasics 24 }
--    tnSysLastOperationTimeStamp    OBJECT-TYPE ::= { tnSysBasics 25 }

    tnSysSwitchId OBJECT-TYPE
        SYNTAX         TnSwitchID
        MAX-ACCESS     not-accessible
        STATUS         current
        DESCRIPTION    "An identifier that uniquely identifies a switching
                        domain on the PSS."
        ::= { tnSysBasics 26 }

    tnSysFipsSquelchMode OBJECT-TYPE
        SYNTAX         INTEGER {
                         nonFips(1),
                         fips(2)
                       }
        MAX-ACCESS     read-write
        STATUS         current
        DESCRIPTION    "FIPS Squelch mode.  If set to FIPS, it causes
                        transmission loss on all encrypted links if
                        FIPS selftest fails."
        DEFVAL         { nonFips }
        ::= { tnSysBasics 27 }

    tnSysOtdrListOfFileNames OBJECT-TYPE
        SYNTAX         SnmpAdminString (SIZE(0..2047))
        MAX-ACCESS     read-only
        STATUS         current
        DESCRIPTION    "This contains a list of all the OTDR file names
                        that are stored on NE.  The maximum number of
                        files is 32.  The file names are separated by
                        newlines.  The format of a file name is:

                        Filenamewhichis34charslong_sh_sl_pt_yyyymmdd_hr-min-sec

                        Here is an example:

                        profile1_1_6_1_20140416_21-20-3."
        ::= { tnSysBasics 28 }

    tnSysOtdrFileCounts OBJECT-TYPE
        SYNTAX         Unsigned32
        MAX-ACCESS     read-only
        STATUS         current
        DESCRIPTION    "This returns the number of files under OTDR."
        ::= { tnSysBasics 29 }

    tnSysAltitude OBJECT-TYPE
        SYNTAX         Unsigned32 (0..8000)
        UNITS          "meters"
        MAX-ACCESS     read-write
        STATUS         current
        DESCRIPTION    "This is used for FAN control and for filter clogging rate calculation."
        DEFVAL         { 0 }
        ::= { tnSysBasics 30 }

    tnSysThermalShutdownAutotimer OBJECT-TYPE
        SYNTAX         Integer32 (-1..3600)
        UNITS          "seconds"
        MAX-ACCESS     read-write
        STATUS         current
        DESCRIPTION    "Configures the time when the mode of thermal is automatically restarted."
        DEFVAL         { 900 }
        ::= { tnSysBasics 31 }

    tnSysDisplayShelfLabel OBJECT-TYPE
        SYNTAX         TruthValue
        MAX-ACCESS     read-write
        STATUS         current
        DESCRIPTION    "."
        DEFVAL         { false }
        ::= { tnSysBasics 32 }

    tnSysPMFineGranularityControl OBJECT-TYPE
        SYNTAX         INTEGER {
                         enable(1),
                         disable(2)
                       }
        MAX-ACCESS     read-write
        STATUS         current
        DESCRIPTION    "Enables network element for fine granularity
                        PM operation."
        DEFVAL         { disable }
        ::= { tnSysBasics 33 }

    tnSysFmRead OBJECT-TYPE
        SYNTAX         TruthValue
        MAX-ACCESS     read-write
        STATUS         current
        DESCRIPTION    "Enables System Ready notification."
        DEFVAL         { false }
        ::= { tnSysBasics 34 }

    tnSysPMStreamingServerControl OBJECT-TYPE
        SYNTAX         INTEGER {
                         enable(1),
                         disable(2)
                       }
        MAX-ACCESS     read-write
        STATUS         current
        DESCRIPTION    "Enables network element for streaming server control
                        PM operation."
        DEFVAL         { disable }
        ::= { tnSysBasics 35 }

    tnSysSlotMigrationControl OBJECT-TYPE
        SYNTAX         INTEGER {
                         noCmd(1),
                         activate(2),
                         clear(3)
                       }
        MAX-ACCESS     read-write
        STATUS         current
        DESCRIPTION    "Slot Migration Control."
        DEFVAL         { noCmd }
        ::= { tnSysBasics 36 }

    tnSysFlexGridClusterOcsAddDropEnabled OBJECT-TYPE
        SYNTAX         TruthValue
        MAX-ACCESS     read-write
        STATUS         current
        DESCRIPTION    "Enables the OCS/Cluster flex."
        DEFVAL         { false }
        ::= { tnSysBasics 37 }

    tnSysFilterCheckTime OBJECT-TYPE
        SYNTAX         Unsigned32
        UNITS          "seconds"
        MAX-ACCESS     read-write
        STATUS         current
        DESCRIPTION    "Time in seconds when the filter check is executed everyday."
        DEFVAL         { 0 }
        ::= { tnSysBasics 38 }

    tnSysCNLinkPhysicalIfIndex OBJECT-TYPE
        SYNTAX         SnmpAdminString (SIZE(0..168))
        MAX-ACCESS     read-write
        STATUS         current
        DESCRIPTION    "."
        ::= { tnSysBasics 39 }

    tnSysUserlabel OBJECT-TYPE
        SYNTAX         SnmpAdminString (SIZE(0..256))
        MAX-ACCESS     read-write
        STATUS         current
        DESCRIPTION    "User Label NE identifier."
        DEFVAL         { "" }
        ::= { tnSysBasics 40 }

    tnSysOpenAgentControl OBJECT-TYPE
        SYNTAX         INTEGER {
                         enable(1),
                         disable(2)
                       }
        MAX-ACCESS     read-write
        STATUS         current
        DESCRIPTION    "Enable/Disable the OpenAgent functionality on the NE."
        DEFVAL         { disable }
        ::= { tnSysBasics 41 }

    tnSysUnkeyedDanglingOchAddDropEnabled OBJECT-TYPE
        SYNTAX         TruthValue
        MAX-ACCESS     read-write
        STATUS         current
        DESCRIPTION    "Indicates if the unkeyed dangling optical channel add/drop
                        capability is enabled.  If false, unkeyed OCh add/drop
                        cross-connections to SFD channel ports, PSC add/drop ports
                        and MCS add/drop ports are not allowed."
        DEFVAL         { false }
        ::= { tnSysBasics 42 }

    tnSysNetWorkTraceV3SecurityUser OBJECT-TYPE
        SYNTAX         INTEGER {
                         compatibilityMode(1),
                         maintenanceMode(2),
                         secureMode(3)
                       }
        MAX-ACCESS     read-write
        STATUS         current
        DESCRIPTION    "Network trace V3 SecurityUser."
        DEFVAL         { compatibilityMode }
        ::= { tnSysBasics 43 }

    tnSysScotV3SecurityUser OBJECT-TYPE
        SYNTAX         INTEGER {
                         maintenanceMode(1),
                         secureMode(2)
                       }
        MAX-ACCESS     read-write
        STATUS         current
        DESCRIPTION    "PowerM V3 SecurityUser."
        DEFVAL         { maintenanceMode }
        ::= { tnSysBasics 44 }

    tnSysTL1Enable OBJECT-TYPE
        SYNTAX         TruthValue
        MAX-ACCESS     read-write
        STATUS         current
        DESCRIPTION    "Enable/Disable the TL1 connectivity on the NE."
        DEFVAL         { false }
        ::= { tnSysBasics 45 }

    tnSysLMEnabled OBJECT-TYPE
        SYNTAX         TruthValue
        MAX-ACCESS     read-write
        STATUS         current
        DESCRIPTION    "Enable/Disable the CLM Functionality."
        DEFVAL         { true }
        ::= { tnSysBasics 46 }

    tnSysAlienChannelLicensingEnabled OBJECT-TYPE
        SYNTAX         TruthValue
        MAX-ACCESS     read-write
        STATUS         current
        DESCRIPTION    "Enable/Disable the Alien channel licensing."
        DEFVAL         { true }
        ::= { tnSysBasics 47 }

    tnSysDebug OBJECT-TYPE
        SYNTAX         TruthValue
        MAX-ACCESS     read-write
        STATUS         current
        DESCRIPTION    "Enable/Disable the access to debug port on network
                        element."
        DEFVAL         { false }
        ::= { tnSysBasics 48 }

    tnSysClusterV3SecurityUser OBJECT-TYPE
        SYNTAX         INTEGER {
                         compatibilityMode(1),
                         secureMode(2)
                       }
        MAX-ACCESS     read-write
        STATUS         current
        DESCRIPTION    "Cluster V3 SecurityUser.
                          compatibilityMode - In Compatibility mode the Cluster
                                              NE-to-NE Communication allow
                                              communication with authentication
                                              and privacy, but with fixed
                                              passwords.  The compatibility mode
                                              shall be used when not all NEs in a
                                              cluster running a release supporting
                                              the Cluster NE-to-NE Communication
                                              in the secure mode.  This ensures
                                              communication while upgrade (or
                                              downgrade) scenarios.  If all NEs in
                                              a cluster supporting the secure mode
                                              then the secure mode should be used.

                          secureMode -        The secure mode uses authentication
                                              and privacy with configurable
                                              passwords only.  Secure mode is the
                                              recommended mode during normal
                                              operation.  Switching to secure mode
                                              while not all network elements are
                                              upgraded to a release supporting
                                              Cluster NE-to-NE Communication security,
                                              or while passwords are not set on all
                                              network elements leads to communication
                                              interruptions."
        DEFVAL         { compatibilityMode }
        ::= { tnSysBasics 49 }

--    obsolete
--    tnSysNFMTPublicKey OBJECT-TYPE ::= { tnSysBasics 50 }

    tnSysSyncMode OBJECT-TYPE
        SYNTAX         INTEGER {
                         ansi(1),
                         etsi(2)
                       }
        MAX-ACCESS     read-write
        STATUS         current
        DESCRIPTION    "etsi/ansi Mode for Synchronization."
        DEFVAL         { etsi }
        ::= { tnSysBasics 51 }

    tnSysPMMode OBJECT-TYPE
        SYNTAX         INTEGER {
                         ansi(1),
                         etsi(2)
                       }
        MAX-ACCESS     read-write
        STATUS         current
        DESCRIPTION    "etsi/ansi Mode for PM."
        DEFVAL         { ansi }
        ::= { tnSysBasics 52 }

    tnSysShelfLatitude OBJECT-TYPE
        SYNTAX         SnmpAdminString (SIZE(0..32))
        MAX-ACCESS     read-write
        STATUS         current
        DESCRIPTION    "Shelf latitude.
                        Free format to store the latitude part of GPS coordinates."
        DEFVAL         { "" }
        ::= { tnSysBasics 53 }

    tnSysShelfLongitude OBJECT-TYPE
        SYNTAX         SnmpAdminString (SIZE(0..32))
        MAX-ACCESS     read-write
        STATUS         current
        DESCRIPTION    "Shelf longitude.
                        Free format to store the longitude part of GPS
                        coordinates."
        DEFVAL         { "" }
        ::= { tnSysBasics 54 }

    tnSysAlmProfName OBJECT-TYPE
        SYNTAX         OCTET STRING (SIZE(1..40))
        MAX-ACCESS     read-write
        STATUS         current
        DESCRIPTION    "."
        ::= { tnSysBasics 55 }

    tnSysBgpAsn OBJECT-TYPE
        SYNTAX         Unsigned32
        MAX-ACCESS     read-write
        STATUS         current
        DESCRIPTION    "Autonomous System Number which will enable BGP on the
                        NE.  Setting the ASN to 0 to disable BGP on the NE.
                        Any ASN can be used, but the following ASNs will be for
                        private use (RFC 6996)
                        64512      - 65534      (16-bit ASN)
                        4200000000 - 4294967294 (32-bit ASN)."
        DEFVAL         { 0 }
        ::= { tnSysBasics 56 }

    tnSysBgpLocalRouterId OBJECT-TYPE
        SYNTAX         IpAddress
        MAX-ACCESS     read-only
        STATUS         current
        DESCRIPTION    "."
        DEFVAL         { '00000000'H }
        ::= { tnSysBasics 57 }

    tnSysNodeIdLabel OBJECT-TYPE
        SYNTAX         SnmpAdminString (SIZE(0..63))
        MAX-ACCESS     read-write
        STATUS         current
        DESCRIPTION    "."
        DEFVAL         { "" }
        ::= { tnSysBasics 58 }

    tnSysNodeNumber OBJECT-TYPE
        SYNTAX         Integer32
        MAX-ACCESS     read-write
        STATUS         current
        DESCRIPTION    "."
        DEFVAL         { 0 }
        ::= { tnSysBasics 59 }

    tnSysNodeCLLI OBJECT-TYPE
        SYNTAX         SnmpAdminString (SIZE(0..11))
        MAX-ACCESS     read-write
        STATUS         current
        DESCRIPTION    "."
        DEFVAL         { "" }
        ::= { tnSysBasics 60 }

    tnSysNodeTemplate OBJECT-TYPE
        SYNTAX         SnmpAdminString (SIZE(0..64))
        MAX-ACCESS     read-write
        STATUS         current
        DESCRIPTION    "."
        DEFVAL         { "" }
        ::= { tnSysBasics 61 }

--    obsolete
--    tnSysNodeLatitude  OBJECT-TYPE ::= { tnSysBasics 62 }
--    tnSysNodeLongitude OBJECT-TYPE ::= { tnSysBasics 63 }

    tnSysCustomerApplicationMode OBJECT-TYPE
        SYNTAX         INTEGER {
                         uninitialized(1),
                         unknown(2),
                         generic(3),
                         openRoadm(4)
                       }
        MAX-ACCESS     read-write
        STATUS         current
        DESCRIPTION    "."
        DEFVAL         { uninitialized }
        ::= { tnSysBasics 64 }

    tnSysMDCli OBJECT-TYPE
        SYNTAX         INTEGER {
                         unknown(1),
                         enable(2),
                         disable(3)
                       }
        MAX-ACCESS     read-write
        STATUS         current
        DESCRIPTION    "Enable/Disable the MDCLI functionality."
        DEFVAL         { unknown }
        ::= { tnSysBasics 65 }

    tnSysMultiShelfMode OBJECT-TYPE
        SYNTAX         INTEGER {
                         learnModeNone(1),
                         learnModeFinal(2),
                         learnModeLearn(3),
                         learnModeAuto(4),
                         learnModeManual(5),
                         learnModeMax(6)
                       }
        MAX-ACCESS     read-write
        STATUS         current
        DESCRIPTION    "."
        DEFVAL         { learnModeNone }
        ::= { tnSysBasics 66 }

    tnSysMultiShelfConfigList OBJECT-TYPE
        SYNTAX         SnmpAdminString (SIZE(0..1600))
        MAX-ACCESS     read-only
        STATUS         current
        DESCRIPTION    "."
        DEFVAL         { "" }
        ::= { tnSysBasics 67 }

    tnSysMultiShelfUnknownList OBJECT-TYPE
        SYNTAX         SnmpAdminString (SIZE(0..1600))
        MAX-ACCESS     read-only
        STATUS         current
        DESCRIPTION    "."
        DEFVAL         { "" }
        ::= { tnSysBasics 68 }

    tnSysMultiShelfMissingList OBJECT-TYPE
        SYNTAX         SnmpAdminString (SIZE(0..1600))
        MAX-ACCESS     read-only
        STATUS         current
        DESCRIPTION    "."
        DEFVAL         { "" }
        ::= { tnSysBasics 69 }

    tnSysPrompt OBJECT-TYPE
        SYNTAX         SnmpAdminString (SIZE(0..256))
        MAX-ACCESS     read-write
        STATUS         current
        DESCRIPTION    "."
        DEFVAL         { "" }
        ::= { tnSysBasics 70 }

    tnSysPromptType OBJECT-TYPE
        SYNTAX         INTEGER {
                         tid(1),
                         userLabel(2),
                         promptText(3),
                         unknown(4)
                       }
        MAX-ACCESS     read-write
        STATUS         current
        DESCRIPTION    "."
        ::= { tnSysBasics 71 }

    tnSysShelfAltitude OBJECT-TYPE
        SYNTAX         SnmpAdminString (SIZE(0..32))
        MAX-ACCESS     read-write
        STATUS         current
        DESCRIPTION    "Shelf altitude. Free format to store
                        the altitude part of GPS coordinates."
        DEFVAL         { "" }
        ::= { tnSysBasics 72 }

    tnSysTacacsSourceIpMode OBJECT-TYPE
        SYNTAX         TropicSourceIpModeValue
        MAX-ACCESS     read-write
        STATUS         current
        DESCRIPTION    "."
        DEFVAL         { any }
        ::= { tnSysBasics 73 }

    tnSysRadiusSourceIpMode OBJECT-TYPE
        SYNTAX         TropicSourceIpModeValue
        MAX-ACCESS     read-write
        STATUS         current
        DESCRIPTION    "."
        DEFVAL         { any }
        ::= { tnSysBasics 74 }

    tnSysFtpSourceIpMode OBJECT-TYPE
        SYNTAX         TropicSourceIpModeValue
        MAX-ACCESS     read-write
        STATUS         current
        DESCRIPTION    "."
        DEFVAL         { any }
        ::= { tnSysBasics 75 }

    tnSysSftpSourceIpMode OBJECT-TYPE
        SYNTAX         TropicSourceIpModeValue
        MAX-ACCESS     read-write
        STATUS         current
        DESCRIPTION    "."
        DEFVAL         { any }
        ::= { tnSysBasics 76 }

    tnSysHttpSourceIpMode OBJECT-TYPE
        SYNTAX         TropicSourceIpModeValue
        MAX-ACCESS     read-write
        STATUS         current
        DESCRIPTION    "."
        DEFVAL         { any }
        ::= { tnSysBasics 77 }

    tnSysHttpsSourceIpMode OBJECT-TYPE
        SYNTAX         TropicSourceIpModeValue
        MAX-ACCESS     read-write
        STATUS         current
        DESCRIPTION    "."
        DEFVAL         { any }
        ::= { tnSysBasics 78 }

    tnSysSnmpSourceIpMode OBJECT-TYPE
        SYNTAX         TropicSourceIpModeValue
        MAX-ACCESS     read-write
        STATUS         current
        DESCRIPTION    "."
        DEFVAL         { any }
        ::= { tnSysBasics 79 }

    tnSysSyslogSourceIpMode OBJECT-TYPE
        SYNTAX         TropicSourceIpModeValue
        MAX-ACCESS     read-write
        STATUS         current
        DESCRIPTION    "."
        DEFVAL         { any }
        ::= { tnSysBasics 80 }

    tnSysSshSourceIpMode OBJECT-TYPE
        SYNTAX         TropicSourceIpModeValue
        MAX-ACCESS     read-write
        STATUS         current
        DESCRIPTION    "."
        DEFVAL         { any }
        ::= { tnSysBasics 81 }

    tnSysAutoTurnUpActiveTemplate OBJECT-TYPE
        SYNTAX         SnmpAdminString (SIZE(0..256))
        MAX-ACCESS     read-write
        STATUS         current
        DESCRIPTION    "."
        DEFVAL         { "" }
        ::= { tnSysBasics 82 }

    tnSysAuthenticationOrder OBJECT-TYPE
        SYNTAX         Unsigned32
        MAX-ACCESS     read-write
        STATUS         current
        DESCRIPTION    "."
        ::= { tnSysBasics 83 }

    tnSysAuthRejectOption OBJECT-TYPE
        SYNTAX         INTEGER {
                         denyRjectMode(1),
                         denyRetryMode(2)
                       }
        MAX-ACCESS     read-write
        STATUS         current
        DESCRIPTION    "."
        DEFVAL         { denyRjectMode }
        ::= { tnSysBasics 84 }

    tnSysAutoTurnUpActiveTemplateForce OBJECT-TYPE
        SYNTAX         TruthValue
        MAX-ACCESS     read-write
        STATUS         current
        DESCRIPTION    "."
        ::= { tnSysBasics 85 }

    tnSysNtpSourceIpMode OBJECT-TYPE
        SYNTAX         TropicSourceIpModeValue
        MAX-ACCESS     read-write
        STATUS         current
        DESCRIPTION    "."
        DEFVAL         { any }
        ::= { tnSysBasics 86 }

    tnSysFeatureAutoTurnUp OBJECT-TYPE
        SYNTAX         AluWdmDisabledEnabled
        MAX-ACCESS     read-write
        STATUS         current
        DESCRIPTION    "Configure to enabled before automation line(s) can be
                          enabled.
                        Configure to disabled after all automation line(s) have
                          been disabled."
        DEFVAL         { disabled }
        ::= { tnSysBasics 87 }

    tnSysDelayResetNE OBJECT-TYPE
        SYNTAX         Integer32
        MAX-ACCESS     read-write
        STATUS         current
        DESCRIPTION    "For Transient Condition:
                        UsrColdResetPend (cleared automatically when controller
                        comes back up active)."
        ::= { tnSysBasics 88 }

    tnSysDelayReboot OBJECT-TYPE
        SYNTAX         TruthValue
        MAX-ACCESS     read-write
        STATUS         current
        DESCRIPTION    "Minimize the number of (warm) reboots during initial
                        configuration (non-ZTP)."
        ::= { tnSysBasics 89 }

    tnSysNmsUserName OBJECT-TYPE
        SYNTAX         SnmpAdminString (SIZE(0..64))
        MAX-ACCESS     read-write
        STATUS         current
        DESCRIPTION    "The Nms user name."
        ::= { tnSysBasics 90 }

    tnSysVersionPatchId OBJECT-TYPE
        SYNTAX         Integer32
        MAX-ACCESS     read-only
        STATUS         current
        DESCRIPTION    "."
        ::= { tnSysBasics 91 }

    tnSysVersionPatchDescr OBJECT-TYPE
        SYNTAX         SnmpAdminString (SIZE(0..2048))
        MAX-ACCESS     read-only
        STATUS         current
        DESCRIPTION    "."
        ::= { tnSysBasics 92 }

    tnSysCustomerLifeCycleState OBJECT-TYPE
        SYNTAX         SnmpAdminString (SIZE(0..45))
        MAX-ACCESS     read-write
        STATUS         current
        DESCRIPTION    "."
        DEFVAL         { "" }
        ::= { tnSysBasics 93 }

    tnSysUSBInstall OBJECT-TYPE
        SYNTAX         TruthValue
        MAX-ACCESS     read-write
        STATUS         current
        DESCRIPTION    "true  - to change boot order from USB port first and allow
                                SW installation from USB port.
                        false - to disable the USB port access for SW installation
                                and to change the boot order to SSD first."
        DEFVAL         { false }
        ::= { tnSysBasics 94 }

    tnSysNmsIpVerifyState OBJECT-TYPE
        SYNTAX         TruthValue
        MAX-ACCESS     read-write
        STATUS         current
        DESCRIPTION    "."
        ::= { tnSysBasics 95 }

    tnSysOcspSourceIpMode OBJECT-TYPE
        SYNTAX         TropicSourceIpModeValue
        MAX-ACCESS     read-write
        STATUS         current
        DESCRIPTION    "Online Certificate Status Protocol IP Mode."
        DEFVAL         { any }
        ::= { tnSysBasics 96 }

    tnSysDnsSourceIpMode OBJECT-TYPE
        SYNTAX         TropicSourceIpModeValue
        MAX-ACCESS     read-write
        STATUS         current
        DESCRIPTION    "Domain Name System IP Mode."
        DEFVAL         { any }
        ::= { tnSysBasics 97 }

    tnSysOtcWaitTimeAfterPowerChange OBJECT-TYPE
        SYNTAX         Unsigned32 (60..3600)
        UNITS          "seconds"
        MAX-ACCESS     read-only
        STATUS         current
        DESCRIPTION    "This attribute indicates how long the NMS shall wait after
                        changing the output power of an external transponder
                        managed with optical terminal control."
        DEFVAL         { 600 }
        ::= { tnSysBasics 98 }

    tnSysDHCPClassName OBJECT-TYPE
        SYNTAX         SnmpAdminString (SIZE(0..32))
        MAX-ACCESS     read-write
        STATUS         current
        DESCRIPTION    "DHCP Class Name."
        DEFVAL         { "" }
        ::= { tnSysBasics 99 }

    tnSysDHCPMatchString OBJECT-TYPE
        SYNTAX         SnmpAdminString (SIZE(0..512))
        MAX-ACCESS     read-write
        STATUS         current
        DESCRIPTION    "DHCP Match String."
        DEFVAL         { "" }
        ::= { tnSysBasics 100 }

    tnSysKeyLicense OBJECT-TYPE
        SYNTAX         SnmpAdminString (SIZE(0..256))
        MAX-ACCESS     read-write
        STATUS         current
        DESCRIPTION    "Unique anti-theft license key stored on the NE."
        DEFVAL         { "" }
        ::= { tnSysBasics 101 }

    tnSysHwIfMode OBJECT-TYPE
        SYNTAX         INTEGER {
                         nomate(1),
                         mate100g(2)
                       }
        MAX-ACCESS     read-write
        STATUS         current
        DESCRIPTION    "This parameter is used to select the variants of hardware
                        interface assignments.  The configuration operation is
                        allowed only when the impacted ports (port speed is changed
                        after config) have the interface type='unassigned'.
                        nomate   - the system has X1-X6 and C1-C24 ports - default
                                   value.
                        mate100g - the system has X1-X6, C1-C24, M1(t24ps1), and M1
                                   (t24ps2) ports.  In this mode, C10-C15 allows
                                   only the interface type with the port rate equal
                                   or lower than 10Gbps

                        When changing from nomate to mate100g, C10-C15 must have the
                        interface type='unassigned';
                        When changing from mate100g to nomate, C10-C15, M1 (t24ps1)
                        and M1 (t24ps2) must have the interface type='unassigned'"
        DEFVAL         { nomate }
        ::= { tnSysBasics 102 }

    tnSysIpAclNextIndex OBJECT-TYPE
        SYNTAX         Integer32
        MAX-ACCESS     read-only
        STATUS         current
        DESCRIPTION    "This parameter indicates the next available SNMP index for
                        a IPACL rule to be created in tnSysIpAclTable.  If there
                        is no available index, zero shall be used."
        ::= { tnSysBasics 103 }

    tnSysIpv6AclNextIndex OBJECT-TYPE
        SYNTAX         Integer32
        MAX-ACCESS     read-only
        STATUS         current
        DESCRIPTION    "This parameter indicates the next available SNMP index for
                        a IPACL rule to be created in tnSysIpv6AclTable.  If there
                        is no available index, zero shall be used."
        ::= { tnSysBasics 104 }

    tnSysDHCPClass OBJECT-TYPE
        SYNTAX         INTEGER {
                         add(1),
                         delete(2)
                       }
        MAX-ACCESS     read-write
        STATUS         current
        DESCRIPTION    "."
        ::= { tnSysBasics 105 }

    tnSysProtocolIpMode OBJECT-TYPE
        SYNTAX         TropicSourceIpModeValue
        MAX-ACCESS     read-write
        STATUS         current
        DESCRIPTION    "."
        DEFVAL         { any }
        ::= { tnSysBasics 106 }

    tnSysMultiShelfAvailableList OBJECT-TYPE
        SYNTAX         SnmpAdminString (SIZE(0..1600))
        MAX-ACCESS     read-only
        STATUS         current
        DESCRIPTION    "."
        ::= { tnSysBasics 107 }

    tnSysPerformanceMemoryTotal OBJECT-TYPE
        SYNTAX         Integer32
        MAX-ACCESS     read-only
        STATUS         current
        DESCRIPTION    "."
        ::= { tnSysBasics 108 }

    tnSysPerformanceMemoryUsed OBJECT-TYPE
        SYNTAX         Integer32
        MAX-ACCESS     read-only
        STATUS         current
        DESCRIPTION    "."
        ::= { tnSysBasics 109 }

    tnSysPerformanceMemoryUsedPercentage OBJECT-TYPE
        SYNTAX         Integer32
        MAX-ACCESS     read-only
        STATUS         current
        DESCRIPTION    "."
        ::= { tnSysBasics 110 }

    tnSysPerformanceTime OBJECT-TYPE
        SYNTAX         SnmpAdminString (SIZE(0..32))
        MAX-ACCESS     read-only
        STATUS         current
        DESCRIPTION    "."
        ::= { tnSysBasics 111 }

    tnSysPerformanceCPUStatsPercentages OBJECT-TYPE
        SYNTAX         SnmpAdminString (SIZE(0..255))
        MAX-ACCESS     read-only
        STATUS         current
        DESCRIPTION    "Format:
                        utilization%-user%-system%-nice%-I/O Wait%-Irq%-SoftIrq%-Idle%.
                        Example: 4.68-1.92-2.70-0.00-0.00-0.06-0.00-95.32"
        ::= { tnSysBasics 112 }

    tnSysPower OBJECT-TYPE
        SYNTAX         INTEGER {
                         powerOn(1),
                         powerOff(2)
                       }
        MAX-ACCESS     read-write
        STATUS         current
        DESCRIPTION    "Power state of the system."
        DEFVAL         { powerOn }
        ::= { tnSysBasics 113 }

    tnSysKeyStoreCertExpiration OBJECT-TYPE
        SYNTAX         Unsigned32
        MAX-ACCESS     read-write
        STATUS         current
        DESCRIPTION    "."
        ::= { tnSysBasics 114 }

    tnSysNumOspfV2AreaIndependentLsas OBJECT-TYPE
        SYNTAX         Unsigned32
        MAX-ACCESS     read-only
        STATUS         current
        DESCRIPTION    "."
        ::= { tnSysBasics 115 }

    tnSysNumOspfV3AreaIndependentLsas OBJECT-TYPE
        SYNTAX         Unsigned32
        MAX-ACCESS     read-only
        STATUS         current
        DESCRIPTION    "."
        ::= { tnSysBasics 116 }

    tnSysBgpAdminDistance OBJECT-TYPE
        SYNTAX         Unsigned32
        MAX-ACCESS     read-write
        STATUS         current
        DESCRIPTION    "."
        DEFVAL         { 20 }
        ::= { tnSysBasics 117 }

-------------------------------------------------------------------------------
--  Control Network
--------------------------------------------------------------------------------
    tnSysIpAddress OBJECT-TYPE
        SYNTAX         IpAddress
        MAX-ACCESS     read-only
        STATUS         current
        DESCRIPTION    "System's IP Address."
        DEFVAL         { 'AC100101'H }
        ::= { tnSysControlNetwork 1 }

    tnSysSubnetMask OBJECT-TYPE
        SYNTAX         IpAddress
        MAX-ACCESS     read-only
        STATUS         current
        DESCRIPTION    "Subnet Mask."
        DEFVAL         { 'FFFFFFFF'H }
        ::= { tnSysControlNetwork 2 }

    tnSysConfiguredIpAddress OBJECT-TYPE
        SYNTAX         IpAddress
        MAX-ACCESS     read-write
        STATUS         current
        DESCRIPTION    "."
        DEFVAL         { 'AC100101'H }
        ::= { tnSysControlNetwork 3 }

    tnSysConfiguredSubnetMask OBJECT-TYPE
        SYNTAX         IpAddress
        MAX-ACCESS     read-write
        STATUS         current
        DESCRIPTION    "."
        DEFVAL         { 'FFFFFFFF'H }
        ::= { tnSysControlNetwork 4 }

    tnSysConfiguredSnmpSource OBJECT-TYPE
        SYNTAX         TruthValue
        MAX-ACCESS     read-write
        STATUS         current
        DESCRIPTION    "When set to false, SNMP requests can be made
                        using any of the NEs interface IP addresses or
                        Loopback IP address.  The source IP address in
                        SNMP trap/reply messages shall be the interface
                        IP address on which the packet leaves the NE.
                        Hence it is the SNMP clients responsibility to
                        be able to associate an NE with multiple IP
                        addresses.

                        When set to true, SNMP requests can be made
                        using ONLY the NEs Loopback IP address.  The
                        source IP address in SNMP trap/reply messages
                        shall be fixed as the Loopback IP.  Hence SNMP
                        clients need only have a single association to
                        the NEs Loopback IP address."
        DEFVAL         { false }
        ::= { tnSysControlNetwork 5 }

    tnSysConfiguredOcsIpAddress OBJECT-TYPE
        SYNTAX         IpAddress
        MAX-ACCESS     read-write
        STATUS         current
        DESCRIPTION    "Optical Cross-connect System (OCS) IP address.

                        R9.0:
                        We now support two OCS Nodes(WDMx2OCS) and this mib is
                        meant for OCS node."
        DEFVAL         { '00000000'H }
        ::= { tnSysControlNetwork 6 }

    tnSysConfiguredOcs2IpAddress OBJECT-TYPE
        SYNTAX         IpAddress
        MAX-ACCESS     read-write
        STATUS         current
        DESCRIPTION    "Optical Cross-connect System (OCS) IP address.

                        R9.0:
                        we now support upto three OCS Nodes(WDMx3OCS) and
                        this attribute is meant for 2nd OCS node."
        DEFVAL         { '00000000'H }
        ::= { tnSysControlNetwork 7 }

    tnSysConfiguredOcs3IpAddress OBJECT-TYPE
        SYNTAX         IpAddress
        MAX-ACCESS     read-write
        STATUS         current
        DESCRIPTION    "Optical Cross-connect System (OCS) IP address.

                        R9.0:
                        we now support upto three OCS Nodes(WDMx3OCS) and
                        this mib is meant for 3rd OCS node."
        DEFVAL         { '00000000'H }
        ::= { tnSysControlNetwork 8 }

    tnSysOcs1LinkStatus OBJECT-TYPE
        SYNTAX         AluWdmOcsLinkStatus
        MAX-ACCESS     read-only
        STATUS         current
        DESCRIPTION    "Shows the link status of 1st Optical Cross-connect
                        System(OCS)."
        ::= { tnSysControlNetwork 9 }

    tnSysOcs2LinkStatus OBJECT-TYPE
        SYNTAX         AluWdmOcsLinkStatus
        MAX-ACCESS     read-only
        STATUS         current
        DESCRIPTION    "Shows the link status of 2nd Optical Cross-connect
                        System(OCS)."
        ::= { tnSysControlNetwork 10 }

    tnSysOcs3LinkStatus OBJECT-TYPE
        SYNTAX         AluWdmOcsLinkStatus
        MAX-ACCESS     read-only
        STATUS         current
        DESCRIPTION    "Shows the link status of 3rd Optical Cross-connect
                        System(OCS)."
        ::= { tnSysControlNetwork 11 }

    tnSysConfiguredRadiusSource OBJECT-TYPE
        SYNTAX         TruthValue
        MAX-ACCESS     read-write
        STATUS         current
        DESCRIPTION    "When set to true, the radius client will only use
                        the Loopback IP."
        DEFVAL         { false }
        ::= { tnSysControlNetwork 12 }

    tnSysConfiguredLoopbackIp1 OBJECT-TYPE
        SYNTAX         IpAddress
        MAX-ACCESS     read-write
        STATUS         current
        DESCRIPTION    "."
        DEFVAL         { '00000000'H }
        ::= { tnSysControlNetwork 13 }

    tnSysConfiguredLoopbackIp1SubnetMask OBJECT-TYPE
        SYNTAX         IpAddress
        MAX-ACCESS     read-write
        STATUS         current
        DESCRIPTION    "."
        DEFVAL         { '00000000'H }
        ::= { tnSysControlNetwork 14 }

    tnSysConfiguredSnmpSource1 OBJECT-TYPE
        SYNTAX         TruthValue
        MAX-ACCESS     read-write
        STATUS         current
        DESCRIPTION    "When set to false, SNMP requests can be made
                        using any of the NEs interface IP addresses or
                        Loopback IP address.  The source IP address in
                        SNMP trap/reply messages shall be the interface
                        IP address on which the packet leaves the NE.
                        Hence it is the SNMP clients responsibility to
                        be able to associate an NE with multiple IP
                        addresses.

                        When set to true, SNMP requests can be made
                        using ONLY the NEs Loopback IP1 address.  The
                        source IP address in SNMP trap/reply messages
                        shall be fixed as the Loopback IP1.  Hence SNMP
                        clients need only have a single association to
                        the NEs Loopback IP1 address."
        DEFVAL         { false }
        ::= { tnSysControlNetwork 15 }

    tnSysConfiguredRadiusSource1 OBJECT-TYPE
        SYNTAX         TruthValue
        MAX-ACCESS     read-write
        STATUS         current
        DESCRIPTION    "When set to true, the radius client will only use
                        the Loopback IP1."
        DEFVAL         { false }
        ::= { tnSysControlNetwork 16 }

    tnSysLoopbackIpAddress1 OBJECT-TYPE
        SYNTAX         IpAddress
        MAX-ACCESS     read-only
        STATUS         current
        DESCRIPTION    "."
        DEFVAL         { '00000000'H }
        ::= { tnSysControlNetwork 17 }

    tnSysLoopbackIp1SubnetMask OBJECT-TYPE
        SYNTAX         IpAddress
        MAX-ACCESS     read-only
        STATUS         current
        DESCRIPTION    "."
        DEFVAL         { '00000000'H }
        ::= { tnSysControlNetwork 18 }

    tnSysConfiguredInetAddressType OBJECT-TYPE
        SYNTAX         InetAddressType
        MAX-ACCESS     read-write
        STATUS         current
        DESCRIPTION    "The value specifies the type of Internet address
                        stored in tnSysConfiguredInetAddress."
        DEFVAL         { unknown }
        ::= { tnSysControlNetwork 19 }

    tnSysConfiguredInetAddress OBJECT-TYPE
        SYNTAX         InetAddress
        MAX-ACCESS     read-write
        STATUS         current
        DESCRIPTION    "Indicates the IPv6 address of the Loopback IP"
        DEFVAL         { ''H }
        ::= { tnSysControlNetwork 20 }

    tnSysConfiguredPrefixLength OBJECT-TYPE
        SYNTAX         InetAddressPrefixLength
        MAX-ACCESS     read-write
        STATUS         current
        DESCRIPTION    "Prefix length of the IPV6 of the Loopback."
        DEFVAL         { 0 }
        ::= { tnSysControlNetwork 21 }

    tnSysOcsIp1Password OBJECT-TYPE
        SYNTAX         SnmpAdminString (SIZE(0..255))
        MAX-ACCESS     read-write
        STATUS         current
        DESCRIPTION    "The password used to access OCS NE.

                        When read, this attribute will return an empty
                        string if the password has not been set and
                        '********' if it has been set."
        DEFVAL         { "" }
        ::= { tnSysControlNetwork 22 }

    tnSysOcsIp2Password OBJECT-TYPE
        SYNTAX         SnmpAdminString (SIZE(0..255))
        MAX-ACCESS     read-write
        STATUS         current
        DESCRIPTION    "The password used to access OCS NE.

                        When read, this attribute will return an empty
                        string if the password has not been set and
                        '********' if it has been set."
        DEFVAL         { "" }
        ::= { tnSysControlNetwork 23 }

    tnSysOcsIp3Password OBJECT-TYPE
        SYNTAX         SnmpAdminString (SIZE(0..255))
        MAX-ACCESS     read-write
        STATUS         current
        DESCRIPTION    "The password used to access OCS NE.

                        When read, this attribute will return an empty
                        string if the password has not been set and
                        '********' if it has been set."
        DEFVAL         { "" }
        ::= { tnSysControlNetwork 24 }

    tnSysConfiguredSnmpSourceIPv6 OBJECT-TYPE
        SYNTAX         TruthValue
        MAX-ACCESS     read-write
        STATUS         current
        DESCRIPTION    "When set to false, SNMP requests can be made
                        using any of the NEs interface IP addresses or
                        Loopback IPv6 address.  The source IP address in
                        SNMP trap/reply messages shall be the interface
                        IP address on which the packet leaves the NE.
                        Hence it is the SNMP clients responsibility to
                        be able to associate an NE with multiple IP
                        addresses.

                        When set to true, SNMP requests can be made
                        using ONLY the NEs Loopback IPv6 address.  The
                        source IP address in SNMP trap/reply messages
                        shall be fixed as the Loopback IP.  Hence SNMP
                        clients need only have a single association to
                        the NEs Loopback IPv6 address."
        DEFVAL         { false }
        ::= { tnSysControlNetwork 25 }

    tnSysConfiguredRadiusSourceIPv6 OBJECT-TYPE
        SYNTAX         TruthValue
        MAX-ACCESS     read-write
        STATUS         current
        DESCRIPTION    "When set to true, the radius client will only use
                        the Loopback IPv6."
        DEFVAL         { false }
        ::= { tnSysControlNetwork 26 }

--------------------------------------------------------------------------------
--  Redundancy
--------------------------------------------------------------------------------
    tnSysRedundancyDbSynchState OBJECT-TYPE
        SYNTAX         INTEGER {
                         notSynched(1),
                         synched(2),
                         synching(3),
                         unSynchable(4),
                         synchFailure(5),
                         schemaTesting(6)
                       }
        MAX-ACCESS     read-only
        STATUS         current
        DESCRIPTION    "."
        DEFVAL         { notSynched }
        ::= { tnSysRedundancy 1 }

    tnSysRedundancyDbResynch OBJECT-TYPE
        SYNTAX         TnCommand
        MAX-ACCESS     read-write
        STATUS         current
        DESCRIPTION    "."
        DEFVAL         { noCmd }
        ::= { tnSysRedundancy 2 }

    tnSysRedundancyDbAudit OBJECT-TYPE
        SYNTAX         TnCommand
        MAX-ACCESS     read-write
        STATUS         current
        DESCRIPTION    "."
        DEFVAL         { noCmd }
        ::= { tnSysRedundancy 3 }

    tnSysRedundancyDbClear OBJECT-TYPE
        SYNTAX         INTEGER {
                         noCmd(1),
                         execute(2),
                         executeAndClearSonetSdhMode(3)
                       }
        MAX-ACCESS     read-write
        STATUS         current
        DESCRIPTION    "."
        DEFVAL         { noCmd }
        ::= { tnSysRedundancy 4 }

    tnSysRedundancyActiveCCSlot OBJECT-TYPE
        SYNTAX         Unsigned32
        MAX-ACCESS     read-only
        STATUS         current
        DESCRIPTION    "."
        DEFVAL         { 1 }
        ::= { tnSysRedundancy 5 }

    tnSysRedundancyDbInvalid OBJECT-TYPE
        SYNTAX         TruthValue
        MAX-ACCESS     read-only
        STATUS         current
        DESCRIPTION    "."
        DEFVAL         { false }
        ::= { tnSysRedundancy 6 }

    tnSysRedundancyMateCCReadyToProtect OBJECT-TYPE
        SYNTAX         TruthValue
        MAX-ACCESS     read-only
        STATUS         current
        DESCRIPTION    "."
        DEFVAL         { false }
        ::= { tnSysRedundancy 7 }

--------------------------------------------------------------------------------
--  System Discovery
--------------------------------------------------------------------------------
--    obsolete
--    tnSysDiscoveryTFTPServer OBJECT-TYPE ::= { tnSysDiscovery 1 }

    tnSysDiscoveryFilename OBJECT-TYPE
        SYNTAX         SnmpAdminString (SIZE(0..255))
        MAX-ACCESS     read-write
        STATUS         current
        DESCRIPTION    "."
        DEFVAL         { "./remote-file" }
        ::= { tnSysDiscovery 2 }

    tnSysDiscoveryMask OBJECT-TYPE
        SYNTAX         BITS {
                         stage1(0), -- equipment   (unsupported)
                         stage2(1), -- ftp discovery
                         stage3(2), -- alarms      (alarm config)
                         stage4(3), -- alarms      (active alarms)
                         stage5(4), -- statistics  (binned counts)
                         stage6(5), -- statistics  (raw counts)
                         stage7(6)  -- statistics  (TCAs)
                       }
        MAX-ACCESS     read-write
        STATUS         current
        DESCRIPTION    "For a newly commissioned network element, the
                        default bit set is stage5."
        DEFVAL         { { stage5 } }
        ::= { tnSysDiscovery 3 }

    tnSysDiscoveryControl OBJECT-TYPE
        SYNTAX         INTEGER {
                         noCmd(1),
                         start(2),
                         abort(3)
                       }
        MAX-ACCESS     read-write
        STATUS         current
        DESCRIPTION    "Controls the Discovery, i.e., starts or aborts it."
        DEFVAL         { noCmd }
        ::= { tnSysDiscovery 4 }

    tnSysDiscoveryStatus OBJECT-TYPE
        SYNTAX         INTEGER {
                         idle(1),
                         inProgress(2),
                         completedSuccessfully(3),
                         failed(4),
                         aborted(5)
                       }
        MAX-ACCESS     read-only
        STATUS         current
        DESCRIPTION    "."
        DEFVAL         { idle }
        ::= { tnSysDiscovery 5 }

    tnSysDiscoveryErrorCode OBJECT-TYPE
        SYNTAX         INTEGER {
                         noError(1),
                         unknown(2),
                         timeout(3),
                         serverError(4),
                         networkError(5),
                         fileSystemError(6),
                         statsBinsRolled(7)
                       }
        MAX-ACCESS     read-only
        STATUS         current
        DESCRIPTION    "."
        DEFVAL         { noError }
        ::= { tnSysDiscovery 6 }

--    obsolete
--    tnSysDiscoveryNMSMask OBJECT-TYPE ::= { tnSysDiscovery 7 }

    tnSysDiscoveryBinnedStatsInterval OBJECT-TYPE
        SYNTAX         Unsigned32
        MAX-ACCESS     read-write
        STATUS         current
        DESCRIPTION    "."
        DEFVAL         { 0 }
        ::= { tnSysDiscovery 8 }

    tnSysDiscoveryBinnedStatsBin OBJECT-TYPE
        SYNTAX         Unsigned32
        MAX-ACCESS     read-write
        STATUS         current
        DESCRIPTION    "."
        DEFVAL         { 0 }
        ::= { tnSysDiscovery 9 }

    tnSysDiscoveryServerProtocol OBJECT-TYPE
        SYNTAX         AluWdmNewTransferProtocol
        MAX-ACCESS     read-write
        STATUS         current
        DESCRIPTION    "This attributes indicates the server protocol."
        DEFVAL         { ftp }
        ::= { tnSysDiscovery 10 }

    tnSysDiscoveryServerIp OBJECT-TYPE
        SYNTAX         IpAddress
        MAX-ACCESS     read-write
        STATUS         current
        DESCRIPTION    "."
        DEFVAL         { '00000000'H }
        ::= { tnSysDiscovery 11 }

    tnSysDiscoveryServerUserId OBJECT-TYPE
        SYNTAX         SnmpAdminString (SIZE(0..128))
        MAX-ACCESS     read-write
        STATUS         current
        DESCRIPTION    "The userId used to access the server."
        DEFVAL         { "" }
        ::= { tnSysDiscovery 12 }

    tnSysDiscoveryServerPassword OBJECT-TYPE
        SYNTAX         SnmpAdminString (SIZE(0..128))
        MAX-ACCESS     read-write
        STATUS         current
        DESCRIPTION    "The password used to access the server.

                        When read, this attribute will return an empty
                        string if the password has not been set and
                        '********' if it has been set."
        DEFVAL         { "" }
        ::= { tnSysDiscovery 13 }

    tnSysDiscoveryServerInetAddressType OBJECT-TYPE
        SYNTAX         InetAddressType
        MAX-ACCESS     read-write
        STATUS         current
        DESCRIPTION    "The value specifies the type of Internet address
                        stored in tnSysDiscoveryServerInetAddress."
        DEFVAL         { unknown }
        ::= { tnSysDiscovery 14 }

    tnSysDiscoveryServerInetAddress OBJECT-TYPE
        SYNTAX         InetAddress
        MAX-ACCESS     read-write
        STATUS         current
        DESCRIPTION    "Indicates the IPv6 address of the log server."
        DEFVAL         { ''H }
        ::= { tnSysDiscovery 15 }

    tnSysDiscoveryPort OBJECT-TYPE
        SYNTAX         Unsigned32 (1..65535)
        MAX-ACCESS     read-write
        STATUS         current
        DESCRIPTION    "."
        DEFVAL         { 21 }
        ::= { tnSysDiscovery 16 }

    tnSysDiscoveryPrevious15minBinFilesTransfer OBJECT-TYPE
        SYNTAX         Unsigned32
        MAX-ACCESS     read-write
        STATUS         current
        DESCRIPTION    "Indicates the number of previous 15 min bin files
                        that needs to be transferred."
        DEFVAL         { 0 }
        ::= { tnSysDiscovery 17 }

    tnSysDiscoveryPrevious1dayBinFilesTransfer OBJECT-TYPE
        SYNTAX         Unsigned32
        MAX-ACCESS     read-write
        STATUS         current
        DESCRIPTION    "Indicates the number of previous 1 day bin files
                        that needs to be transferred."
        DEFVAL         { 0 }
        ::= { tnSysDiscovery 18 }

    tnSysDiscoveryTransferTimeOffset OBJECT-TYPE
        SYNTAX         Unsigned32 (0..899)
        MAX-ACCESS     read-write
        STATUS         current
        DESCRIPTION    "Indicates the file transfer time offset in seconds."
        DEFVAL         { 0 }
        ::= { tnSysDiscovery 19 }

    tnSysDiscoveryTransferTraps OBJECT-TYPE
        SYNTAX         TruthValue
        MAX-ACCESS     read-write
        STATUS         current
        DESCRIPTION    "Indicates whether the file transfer is triggered by
                        the NE sending traps."
        DEFVAL         { true }
        ::= { tnSysDiscovery 20 }

--------------------------------------------------------------------------------
--  Logging
--------------------------------------------------------------------------------
    tnSysLoggingCLI OBJECT-TYPE
        SYNTAX         BITS {
                         disableAllLogging(0),
                         level1Read(1),
                         level1Write(2),
                         level2Read(3),   -- admin
                         level2Write(4),  -- admin
                         level3Read(5),   -- provisioner
                         level3Write(6),  -- provisioner
                         level4Read(7),   -- service
                         level4Write(8),  -- service
                         level5Read(9),   -- observer
                         level5Write(10), -- observer
                         level6Read(11),  -- crypto
                         level6Write(12)  -- crypto
                       }
        MAX-ACCESS     read-write
        STATUS         current
        DESCRIPTION    "Each bit represents whether the appropriate
                        logging is activated for each CLI security
                        level."
        ::= { tnSysLogging 1 }

    tnSysLoggingSNMP OBJECT-TYPE
        SYNTAX         BITS {
                         disableAllLogging(0),
                         level1Read(1),   -- nms
                         level1Write(2),  -- nms
                         level2Read(3),   -- admin
                         level2Write(4),  -- admin
                         level3Read(5),   -- provisioner
                         level3Write(6),  -- provisioner
                         level4Read(7),   -- service
                         level4Write(8),  -- service
                         level5Read(9),   -- observer
                         level5Write(10), -- observer
                         level6Read(11),  -- crypto
                         level6Write(12)  -- crypto
                       }
        MAX-ACCESS     read-write
        STATUS         current
        DESCRIPTION    "Each bit represents whether the appropriate
                        logging is activated for each SNMP security
                        level."
        ::= { tnSysLogging 2 }

--------------------------------------------------------------------------------
--  Backup And Restore
--------------------------------------------------------------------------------
    tnSysBackupAndRestoreCommand OBJECT-TYPE
        SYNTAX         INTEGER {
                         noCmd(1),
                         backupToRemote(2),
                         restoreFromRemote(3),
                         restoreForceFromRemote(4),
                         backupToLocal(5)
                       }
        MAX-ACCESS     read-write
        STATUS         current
        DESCRIPTION    "."
        DEFVAL         { noCmd }
        ::= { tnSysBackupAndRestore 1 }

    tnSysBackupAndRestoreRemoteHostIp OBJECT-TYPE
        SYNTAX         IpAddress
        MAX-ACCESS     read-write
        STATUS         current
        DESCRIPTION    "."
        DEFVAL         { '00000000'H }
        ::= { tnSysBackupAndRestore 2 }

    tnSysBackupAndRestoreRemotePath OBJECT-TYPE
        SYNTAX         SnmpAdminString (SIZE(0..128))
        MAX-ACCESS     read-write
        STATUS         current
        DESCRIPTION    "."
        DEFVAL         { "" }
        ::= { tnSysBackupAndRestore 3 }

    tnSysBackupAndRestoreStatus OBJECT-TYPE
        SYNTAX         SnmpAdminString (SIZE(0..255))
        MAX-ACCESS     read-only
        STATUS         current
        DESCRIPTION    "This attribute indicates the status of the
                        previously executed tnSysBackupAndRestoreCommand
                        operation.  Here are the status strings:

                        * Success
                        * Failed - no such record instance
                        * Failed - timed out
                        * Failed - invalid record size
                        * Failed - invalid record type
                        * Remote backup in progress
                        * Remote restore in progress
                        * Failed - remote path exceeds the max length
                            of 127 characters
                        * Failed - for restore the remote path must
                            specify a file
                        * Failed - restored database was corrupt or
                            was created on a different node
                        * Failed - cannot backup or restore while
                            operation already in progress
                        * Failed - backup or restore failed to complete
                            due to a reset
                        * Failed - restored database missing GMRE
                            database (forced to override)
                        * Failed - local error
                        * Failed - network error
                        * Failed - Remote server error
                        * Failed - invalid database backup file
                        * Failed - Invalid remote server IP address not set
                        * Failed - Error
                        * Failed - Authorization failed
                        * Failed - File permission(s) failed
                        * Failed - <Unknown database error code>"
        DEFVAL         { "" }
        ::= { tnSysBackupAndRestore 4 }

    tnSysBackupAndRestoreLastBackupFilename OBJECT-TYPE
        SYNTAX         SnmpAdminString (SIZE(0..255))
        MAX-ACCESS     read-only
        STATUS         current
        DESCRIPTION    "This attribute indicates the filename for the
                        last backup performed on the node.  If none
                        exists, this attribute will return an empty
                        string.  If a backup is in progress, this
                        attribute will return an empty string."
        DEFVAL         { "" }
        ::= { tnSysBackupAndRestore 5 }

    tnSysBackupAndRestoreLastCommand OBJECT-TYPE
        SYNTAX         INTEGER {
                         noCommand(1),
                         unknown(2),
                         backupToRemote(3),
                         restoreFromRemote(4)
                       }
        MAX-ACCESS     read-only
        STATUS         current
        DESCRIPTION    "This is the last backup and restore command
                        executed.  If the last operation is unknown,
                        the value of this attribute will be unknown.
                        If a backup and restore command has not been
                        executed since the last node reset, the value
                        of this attribute will be noCommand."
        DEFVAL         { noCommand }
        ::= { tnSysBackupAndRestore 6 }

    tnSysBackupAndRestorePercentCompleted OBJECT-TYPE
        SYNTAX         Unsigned32
        MAX-ACCESS     read-only
        STATUS         current
        DESCRIPTION    "The percent completion of the previously
                        executed operation."
        DEFVAL         { 0 }
        ::= { tnSysBackupAndRestore 7 }

    tnSysBackupAndRestoreLastBackupFileTimeStamp OBJECT-TYPE
        SYNTAX         Unsigned32
        MAX-ACCESS     read-only
        STATUS         current
        DESCRIPTION    "The date and time when the last backup was completed."
        DEFVAL         { 0 }
        ::= { tnSysBackupAndRestore 8 }

    tnSysBackupAndRestoreProtocol OBJECT-TYPE
        SYNTAX         AluWdmNewTransferProtocol
        MAX-ACCESS     read-write
        STATUS         current
        DESCRIPTION    "This attributes indicates the database Backup and restore
                        protocol."
        DEFVAL         { ftp }
        ::= { tnSysBackupAndRestore 9 }

    tnSysBackupAndRestoreUserId OBJECT-TYPE
        SYNTAX         SnmpAdminString (SIZE(0..128))
        MAX-ACCESS     read-write
        STATUS         current
        DESCRIPTION    "The userId used to access the backup and restore server."
        DEFVAL         { "" }
        ::= { tnSysBackupAndRestore 10 }

    tnSysBackupAndRestorePassword OBJECT-TYPE
        SYNTAX         SnmpAdminString (SIZE(0..128))
        MAX-ACCESS     read-write
        STATUS         current
        DESCRIPTION    "The password used to access the backup and restore server.

                        When read, this attribute will return an empty
                        string if the password has not been set and
                        '********' if it has been set."
        DEFVAL         { "" }
        ::= { tnSysBackupAndRestore 11 }

    tnSysBackupAndRestoreLastBackupFileCrc OBJECT-TYPE
        SYNTAX         SnmpAdminString
        MAX-ACCESS     read-only
        STATUS         current
        DESCRIPTION    "32-bit Cyclic Redundancy Code calculated over
                        the backed-up data."
        DEFVAL         { "" }
        ::= { tnSysBackupAndRestore 12 }

--    obsolete
--    tnSysBackupAndRestoreRemotePort OBJECT-TYPE ::= { tnSysBackupAndRestore 13 }

    tnSysBackupAndRestoreRemoteHostInetAddressType OBJECT-TYPE
        SYNTAX         InetAddressType
        MAX-ACCESS     read-write
        STATUS         current
        DESCRIPTION    "The value specifies the type of Internet address
                        stored in tnSysBackupAndRestoreRemoteHostInetAddress."
        DEFVAL         { unknown }
        ::= { tnSysBackupAndRestore 14 }

    tnSysBackupAndRestoreRemoteHostInetAddress OBJECT-TYPE
        SYNTAX         InetAddress
        MAX-ACCESS     read-write
        STATUS         current
        DESCRIPTION    "Indicates the IPv6 address of the backup server."
        DEFVAL         { ''H }
        ::= { tnSysBackupAndRestore 15 }

    tnSysBackupAndRestoreLocalInfo OBJECT-TYPE
        SYNTAX         SnmpAdminString
        MAX-ACCESS     read-only
        STATUS         current
        DESCRIPTION    "Database local backup information."
        DEFVAL         { "" }
        ::= { tnSysBackupAndRestore 16 }

--    obsolete
--    tnSysBackupAndRestoreType OBJECT-TYPE ::= { tnSysBackupAndRestore 17 }

    tnSysBackupAndRestoreLocalDelete OBJECT-TYPE
        SYNTAX         INTEGER {
                         noCmd(1),
                         execute(2)
                       }
        MAX-ACCESS     read-write
        STATUS         current
        DESCRIPTION    "Delete local database backup."
        DEFVAL         { noCmd }
        ::= { tnSysBackupAndRestore 18 }

    tnSysBackupAndRestorePort OBJECT-TYPE
        SYNTAX         Unsigned32 (1..65535)
        MAX-ACCESS     read-write
        STATUS         current
        DESCRIPTION    "This attributes indicates the database
                        port."
        DEFVAL         { 21 }
        ::= { tnSysBackupAndRestore 19 }

    tnSysBackupAndRestoreFallBackTimeStamp OBJECT-TYPE
        SYNTAX         Unsigned32
        MAX-ACCESS     read-only
        STATUS         current
        DESCRIPTION    "return the creation time of the Fallback DB."
        DEFVAL         { 0 }
        ::= { tnSysBackupAndRestore 20 }

--------------------------------------------------------------------------------
-- NTP - Network Time Protocol
--------------------------------------------------------------------------------
    tnSysNtpEnable OBJECT-TYPE
        SYNTAX         TruthValue
        MAX-ACCESS     read-write
        STATUS         current
        DESCRIPTION    "To enable or disable NTP client."
        DEFVAL         { false }
        ::= { tnSysNtp 1 }

--    obsolete
--    tnSysNtpTimeOffsetHours    OBJECT-TYPE ::= { tnSysNtp 2 }
--    tnSysNtpTimeOffsetMinutes  OBJECT-TYPE ::= { tnSysNtp 3 }
--    tnSysNtpTimeOffsetTimeZone OBJECT-TYPE ::= { tnSysNtp 4 }
--    tnSysNtpDrift              OBJECT-TYPE ::= { tnSysNtp 5 }
--    tnSysNtpTimeOffset         OBJECT-TYPE ::= { tnSysNtp 6 }
--    tnSysNtpScale              OBJECT-TYPE ::= { tnSysNtp 7 }

    tnSysNtpSynched OBJECT-TYPE
        SYNTAX         TruthValue
        MAX-ACCESS     read-only
        STATUS         current
        DESCRIPTION    "."
        DEFVAL         { false }
        ::= { tnSysNtp 8 }

    tnSysNtpServerCurrentIpAddress OBJECT-TYPE
        SYNTAX         IpAddress
        MAX-ACCESS     read-only
        STATUS         current
        DESCRIPTION    "."
        DEFVAL         { '00000000'H }
        ::= { tnSysNtp 9 }

--    obsolete
--    tnSysNtpDaylightSavingsTimeConfigured OBJECT-TYPE ::= { tnSysNtp 10 }

    tnSysNtpDriftString OBJECT-TYPE
        SYNTAX         OCTET STRING
        MAX-ACCESS     read-only
        STATUS         current
        DESCRIPTION    "."
        ::= { tnSysNtp 11 }

    tnSysNtpTimeOffsetString OBJECT-TYPE
        SYNTAX         OCTET STRING
        MAX-ACCESS     read-only
        STATUS         current
        DESCRIPTION    "."
        ::= { tnSysNtp 12 }

    tnSysNtpClockMode OBJECT-TYPE
        SYNTAX         INTEGER {
                         freeRun(1),
                         holdOver(2),
                         sync(3),
                         syncRed(4)
                       }
        MAX-ACCESS     read-only
        STATUS         current
        DESCRIPTION    "NTP clock mode."
        DEFVAL         { freeRun }
        ::= { tnSysNtp 13 }

    tnSysNtpServerCurrentInetAddressType OBJECT-TYPE
        SYNTAX         InetAddressType
        MAX-ACCESS     read-write
        STATUS         current
        DESCRIPTION    "The value specifies the type of Internet address
                        stored tnSysNtpServerCurrentInetAddress."
        DEFVAL         { unknown }
        ::= { tnSysNtp 14 }

    tnSysNtpServerCurrentInetAddress OBJECT-TYPE
        SYNTAX         InetAddress
        MAX-ACCESS     read-write
        STATUS         current
        DESCRIPTION    "Indicates the IPv6 address NTP server."
        DEFVAL         { ''H }
        ::= { tnSysNtp 15 }

--------------------------------------------------------------------------------
-- NTP Servers
--------------------------------------------------------------------------------
    tnSysNtpServerTable OBJECT-TYPE
        SYNTAX         SEQUENCE OF TnSysNtpServerEntry
        MAX-ACCESS     not-accessible
        STATUS         current
        DESCRIPTION    "."
        ::= { tnSysNtpServers 1 }

    tnSysNtpServerEntry OBJECT-TYPE
        SYNTAX         TnSysNtpServerEntry
        MAX-ACCESS     not-accessible
        STATUS         current
        DESCRIPTION    "."
        INDEX { tnSysNtpServerIndex }
        ::= { tnSysNtpServerTable 1 }

    TnSysNtpServerEntry ::= SEQUENCE {
        tnSysNtpServerIndex               Unsigned32,
        tnSysNtpServerIpAddress           IpAddress,
        tnSysNtpServerRowStatus           RowStatus,
        tnSysNtpServerKeyIndex            Unsigned32,
        tnSysNtpServerInetAddress         InetAddress,
        tnSysNtpServerInetAddressType     InetAddressType
    }

    tnSysNtpServerIndex OBJECT-TYPE
        SYNTAX         Unsigned32 (1..8)
        MAX-ACCESS     not-accessible
        STATUS         current
        DESCRIPTION    "For the 1830 PSS-32, the maximum number of
                        supported servers is 8."
        ::= { tnSysNtpServerEntry 1 }

    tnSysNtpServerIpAddress OBJECT-TYPE
        SYNTAX         IpAddress
        MAX-ACCESS     read-create
        STATUS         current
        DESCRIPTION    "This attribute is configurable only when the
                        row status has been set to createAndGo."
        ::= { tnSysNtpServerEntry 2 }

    tnSysNtpServerRowStatus OBJECT-TYPE
        SYNTAX         RowStatus
        MAX-ACCESS     read-create
        STATUS         current
        DESCRIPTION    "."
        ::= { tnSysNtpServerEntry 3 }

    tnSysNtpServerKeyIndex OBJECT-TYPE
        SYNTAX         Unsigned32 (0..65535)
        MAX-ACCESS     read-create
        STATUS         current
        DESCRIPTION    "."
        ::= { tnSysNtpServerEntry 4 }

    tnSysNtpServerInetAddress OBJECT-TYPE
        SYNTAX         InetAddress
        MAX-ACCESS     read-create
        STATUS         current
        DESCRIPTION    "Indicates the IPv6 address of the NTP Server."
        DEFVAL         { ''H }
        ::= { tnSysNtpServerEntry 5 }

    tnSysNtpServerInetAddressType OBJECT-TYPE
        SYNTAX         InetAddressType
        MAX-ACCESS     read-create
        STATUS         current
        DESCRIPTION    "The value specifies the type of Internet address
                        stored in tnSysNtpServerInetAddress."
        DEFVAL         { unknown }
        ::= { tnSysNtpServerEntry 6 }

--------------------------------------------------------------------------------
--  SNMP Target Addresses
--------------------------------------------------------------------------------
    tnSnmpTargetAddrTable OBJECT-TYPE
        SYNTAX         SEQUENCE OF TnSnmpTargetAddrEntry
        MAX-ACCESS     not-accessible
        STATUS         current
        DESCRIPTION    "."
        ::= { tnSnmpTargetAddresses 1 }

    tnSnmpTargetAddrEntry OBJECT-TYPE
        SYNTAX         TnSnmpTargetAddrEntry
        MAX-ACCESS     not-accessible
        STATUS         current
        DESCRIPTION    "."
        AUGMENTS    { snmpTargetAddrEntry }
        ::= { tnSnmpTargetAddrTable 1 }

    TnSnmpTargetAddrEntry ::= SEQUENCE {
        tnSnmpTargetAddrNmsStationGroupId     Unsigned32,
        tnSnmpTargetAddrTrapGroupId           INTEGER,
        tnSnmpTargetAddrDisableTrap           Unsigned32
    }

    tnSnmpTargetAddrNmsStationGroupId OBJECT-TYPE
        SYNTAX         Unsigned32
        MAX-ACCESS     read-create
        STATUS         current
        DESCRIPTION    "."
        ::= { tnSnmpTargetAddrEntry 1 }

    tnSnmpTargetAddrTrapGroupId OBJECT-TYPE
        SYNTAX         INTEGER {
                         allOtherData(1),
                         pmData(2)
                       }
        MAX-ACCESS     read-create
        STATUS         current
        DESCRIPTION    "."
        DEFVAL         { allOtherData }
        ::= { tnSnmpTargetAddrEntry 2 }

    tnSnmpTargetAddrDisableTrap OBJECT-TYPE
        SYNTAX         Unsigned32
        MAX-ACCESS     read-create
        STATUS         current
        DESCRIPTION    "Indicates the destination based trap disable mechanism
                        feature is on."
        ::= { tnSnmpTargetAddrEntry 3 }

--------------------------------------------------------------------------------
--  Syslog
--------------------------------------------------------------------------------
    tnSyslogIpAddress OBJECT-TYPE
        SYNTAX         IpAddress
        MAX-ACCESS     read-write
        STATUS         current
        DESCRIPTION    "."
        DEFVAL         { '00000000'H }
        ::= { tnSyslog 1 }

    tnSyslogPort OBJECT-TYPE
        SYNTAX         Unsigned32 (1..65535)
        MAX-ACCESS     read-write
        STATUS         current
        DESCRIPTION    "."
        DEFVAL         { 514 }
        ::= { tnSyslog 2 }

    tnSyslogFacility OBJECT-TYPE
        SYNTAX         INTEGER {
                         kern(1),
                         user(2),
                         mail(3),
                         daemon(4),
                         auth(5),
                         syslog(6),
                         lpr(7),
                         news(8),
                         uucp(9),
                         cron(10),
                         authPriv(11),
                         ftp(12),
                         local0(13),
                         local1(14),
                         local2(15),
                         local3(16),
                         local4(17),
                         local5(18),
                         local6(19),
                         local7(20),
                         all(21),
                         logAudit(22),
                         logAlert(23)
                       }
        MAX-ACCESS     read-write
        STATUS         current
        DESCRIPTION    "."
        DEFVAL         { local0 }
        ::= { tnSyslog 3 }

    tnSyslogPriority OBJECT-TYPE
        SYNTAX         INTEGER {
                         emergency(1),
                         alert(2),
                         critical(3),
                         error(4),
                         warning(5),
                         notice(6),
                         info(7),
                         debug(8)
                       }
        MAX-ACCESS     read-write
        STATUS         current
        DESCRIPTION    "."
        DEFVAL         { debug }
        ::= { tnSyslog 4 }

    tnSyslogEnabled OBJECT-TYPE
        SYNTAX         TruthValue
        MAX-ACCESS     read-write
        STATUS         current
        DESCRIPTION    "."
        DEFVAL         { false }
        ::= { tnSyslog 5 }

    tnSyslogInetAddress OBJECT-TYPE
        SYNTAX         InetAddress
        MAX-ACCESS     read-write
        STATUS         current
        DESCRIPTION    "Indicates the IPv6 address of the Syslog Server."
        DEFVAL         { ''H }
        ::= { tnSyslog 6 }

    tnSyslogInetAddressType OBJECT-TYPE
        SYNTAX         InetAddressType
        MAX-ACCESS     read-write
        STATUS         current
        DESCRIPTION    "The value specifies the type of Internet address
                        stored in tnSyslogInetAddress."
        DEFVAL         { unknown }
        ::= { tnSyslog 7 }

    tnSyslogProtocol OBJECT-TYPE
        SYNTAX         INTEGER {
                         udp(1),
                         tcp(2)
                       }
        MAX-ACCESS     read-write
        STATUS         current
        DESCRIPTION    "Syslog Transmission Protocol."
        DEFVAL         { udp }
        ::= { tnSyslog 8 }

--------------------------------------------------------------------------------
--  System Timing
--------------------------------------------------------------------------------
    tnSysTimingPrimaryReference OBJECT-TYPE
        SYNTAX         Unsigned32
        MAX-ACCESS     read-write
        STATUS         current
        DESCRIPTION    "."
        DEFVAL         { 0 }
        ::= { tnSysTiming 1 }

    tnSysTimingSecondaryReference OBJECT-TYPE
        SYNTAX         Unsigned32
        MAX-ACCESS     read-write
        STATUS         current
        DESCRIPTION    "."
        DEFVAL         { 0 }
        ::= { tnSysTiming 2 }

    tnSysTimingLastSwitchTime OBJECT-TYPE
        SYNTAX         Unsigned32
        MAX-ACCESS     read-only
        STATUS         current
        DESCRIPTION    "."
        DEFVAL         { 0 }
        ::= { tnSysTiming 3 }

    tnSysTimingControl OBJECT-TYPE
        SYNTAX         INTEGER {
                         noCmd(1),
                         forceToPrimary(2),
                         forceToSecondary(3),
                         manualToPrimary(4),
                         manualToSecondary(5),
                         clear(6)
                       }
        MAX-ACCESS     read-write
        STATUS         current
        DESCRIPTION    "."
        DEFVAL         { clear }
        ::= { tnSysTiming 4 }

    tnSysTimingPrimaryReferenceStatus OBJECT-TYPE
        SYNTAX         INTEGER {
                         unknown(1),
                         ok(2),
                         manual(3),
                         forced(4),
                         failed(5),
                         failedLOS(6),
                         failedLOF(7),
                         failedLOC(8),
                         failedFreqOffset(9),
                         failedAIS(10),
                         failedSSM(11),
                         qualifying(12)
                       }
        MAX-ACCESS     read-only
        STATUS         current
        DESCRIPTION    "."
        DEFVAL         { unknown }
        ::= { tnSysTiming 5 }

    tnSysTimingSecondaryReferenceStatus OBJECT-TYPE
        SYNTAX         INTEGER {
                         unknown(1),
                         ok(2),
                         manual(3),
                         forced(4),
                         failed(5),
                         failedLOS(6),
                         failedLOF(7),
                         failedLOC(8),
                         failedFreqOffset(9),
                         failedAIS(10),
                         failedSSM(11),
                         qualifying(12)
                       }
        MAX-ACCESS     read-only
        STATUS         current
        DESCRIPTION    "."
        DEFVAL         { unknown }
        ::= { tnSysTiming 6 }

    tnSysTimingPrimaryReferenceQuality OBJECT-TYPE
        SYNTAX         TropicSysTimingReferenceQuality
        MAX-ACCESS     read-only
        STATUS         current
        DESCRIPTION    "."
        DEFVAL         { unknown }
        ::= { tnSysTiming 7 }

    tnSysTimingSecondaryReferenceQuality OBJECT-TYPE
        SYNTAX         TropicSysTimingReferenceQuality
        MAX-ACCESS     read-only
        STATUS         current
        DESCRIPTION    "."
        DEFVAL         { unknown }
        ::= { tnSysTiming 8 }

    tnSysTimingPrimaryReferenceTimingMode OBJECT-TYPE
        SYNTAX         TropicSysTimingReferenceTimingMode
        MAX-ACCESS     read-only
        STATUS         current
        DESCRIPTION    "."
        DEFVAL         { unknown }
        ::= { tnSysTiming 9 }

    tnSysTimingSecondaryReferenceTimingMode OBJECT-TYPE
        SYNTAX         TropicSysTimingReferenceTimingMode
        MAX-ACCESS     read-only
        STATUS         current
        DESCRIPTION    "."
        DEFVAL         { unknown }
        ::= { tnSysTiming 10 }

    tnSysTimingActiveReference OBJECT-TYPE
        SYNTAX         INTEGER {
                         none(1),
                         primary(2),
                         secondary(3)
                       }
        MAX-ACCESS     read-only
        STATUS         current
        DESCRIPTION    "."
        DEFVAL         { none }
        ::= { tnSysTiming 11 }

    tnSysTimingClockingMode OBJECT-TYPE
        SYNTAX         INTEGER {
                         unknown(1),
                         normal(2),
                         fastStart(3),
                         holdOver(4),
                         freeRun(5)
                       }
        MAX-ACCESS     read-only
        STATUS         current
        DESCRIPTION    "."
        DEFVAL         { unknown }
        ::= { tnSysTiming 12 }

    tnSysTimingSwitchingMode OBJECT-TYPE
        SYNTAX         INTEGER {
                         unknown(1),
                         revertive(2),
                         nonRevertive(3)
                       }
        MAX-ACCESS     read-write
        STATUS         current
        DESCRIPTION    "."
        DEFVAL         { nonRevertive }
        ::= { tnSysTiming 13 }

    tnSysTimingFreeRunSuppressAlarms OBJECT-TYPE
        SYNTAX         TruthValue
        MAX-ACCESS     read-write
        STATUS         current
        DESCRIPTION    "."
        DEFVAL         { false }
        ::= { tnSysTiming 14 }

    tnSysTimingDs1FramingMode OBJECT-TYPE
        SYNTAX         INTEGER {
                         unknown(1),
                         sf(2),
                         esf(3)
                       }
        MAX-ACCESS     read-write
        STATUS         current
        DESCRIPTION    "."
        DEFVAL         { esf }
        ::= { tnSysTiming 15 }

    tnSysTimingDs1LineCoding OBJECT-TYPE
        SYNTAX         INTEGER {
                         unknown(1),
                         ami(2),
                         b8zs(3)
                       }
        MAX-ACCESS     read-write
        STATUS         current
        DESCRIPTION    "."
        DEFVAL         { b8zs }
        ::= { tnSysTiming 16 }

    tnSysTimingDs1SsmProcessing OBJECT-TYPE
        SYNTAX         AluWdmEnabledDisabled
        MAX-ACCESS     read-write
        STATUS         current
        DESCRIPTION    "."
        DEFVAL         { enabled }
        ::= { tnSysTiming 17 }

    tnSysTimingBitsAClockQuality OBJECT-TYPE
        SYNTAX         TropicSysTimingReferenceQuality
        MAX-ACCESS     read-write
        STATUS         current
        DESCRIPTION    "."
        DEFVAL         { unknown }
        ::= { tnSysTiming 18 }

    tnSysTimingBitsBClockQuality OBJECT-TYPE
        SYNTAX         TropicSysTimingReferenceQuality
        MAX-ACCESS     read-write
        STATUS         current
        DESCRIPTION    "."
        DEFVAL         { unknown }
        ::= { tnSysTiming 19 }

    tnSysTimingActiveLineTimingCable OBJECT-TYPE
        SYNTAX         INTEGER {
                         unknown(1),
                         notApplicable(2),
                         none(3),
                         a(4),
                         b(5)
                       }
        MAX-ACCESS     read-only
        STATUS         current
        DESCRIPTION    "."
        DEFVAL         { unknown }
        ::= { tnSysTiming 20 }

    tnSysTimingBitSourceType OBJECT-TYPE
        SYNTAX         INTEGER {
                         unknown(1),
                         ds1(2),
                         e1(3)
                       }
        MAX-ACCESS     read-write
        STATUS         current
        DESCRIPTION    "."
        DEFVAL         { ds1 }
        ::= { tnSysTiming 21 }

    tnSysTimingBitsAModuleType OBJECT-TYPE
        SYNTAX         INTEGER {
                         unknown(1),
                         ds1(2),
                         e1(3)
                       }
        MAX-ACCESS     read-only
        STATUS         current
        DESCRIPTION    "."
        DEFVAL         { ds1 }
        ::= { tnSysTiming 22 }

    tnSysTimingBitsBModuleType OBJECT-TYPE
        SYNTAX         INTEGER {
                         unknown(1),
                         ds1(2),
                         e1(3)
                       }
        MAX-ACCESS     read-only
        STATUS         current
        DESCRIPTION    "."
        DEFVAL         { ds1 }
        ::= { tnSysTiming 23 }

--------------------------------------------------------------------------------
--  System Features
--------------------------------------------------------------------------------
--    obsolete
--    tnSysFeatureWavelengthTracker              OBJECT-TYPE ::= { tnSysFeatures 1 }
--    tnSysFeatureNetworkElementFaultCorrelation OBJECT-TYPE ::= { tnSysFeatures 2 }

    tnSysFeatureAutoTopology OBJECT-TYPE
        SYNTAX         TruthValue
        MAX-ACCESS     read-write
        STATUS         current
        DESCRIPTION    "."
        DEFVAL         { false }
        ::= { tnSysFeatures 3 }

    tnSysFeaturePauseFlowControl OBJECT-TYPE
        SYNTAX         INTEGER {
                         manual(1),
                         negotiated(2)
                       }
        MAX-ACCESS     read-write
        STATUS         current
        DESCRIPTION    "."
        DEFVAL         { negotiated }
        ::= { tnSysFeatures 4 }

    tnSysFeatureIpUtilitiesRestricted OBJECT-TYPE
        SYNTAX         TruthValue
        MAX-ACCESS     read-write
        STATUS         current
        DESCRIPTION    "."
        DEFVAL         { false }
        ::= { tnSysFeatures 5 }

    tnSysFeatureFastServiceSetup OBJECT-TYPE
        SYNTAX         TruthValue
        MAX-ACCESS     read-write
        STATUS         current
        DESCRIPTION    "Enables or disables fast service setup feature."
        DEFVAL         { false }
        ::= { tnSysFeatures 6 }

--------------------------------------------------------------------------------
--  System Fault Correlation
--------------------------------------------------------------------------------
    tnSysFaultCorrelationTransientSuppression OBJECT-TYPE
        SYNTAX         AluWdmEnabledDisabled
        MAX-ACCESS     read-write
        STATUS         current
        DESCRIPTION    "This attribute always returns a value of
                        disabled.  Sets are not supported."
        ::= { tnSysFaultCorrelation 1 }

--------------------------------------------------------------------------------
--  System Error Handling
--------------------------------------------------------------------------------
    tnSysSetRequestErrorMessage OBJECT-TYPE
        SYNTAX         SnmpAdminString (SIZE(0..128))
        MAX-ACCESS     read-write
        STATUS         current
        DESCRIPTION    "If this attribute is set to any value and it
                        is the first attribute in a multi-set request
                        varbind list and one of the other attributes
                        in the multi-set request varbind list failed
                        to set, the response PDU will contain an error
                        message.  The error message will be the value
                        of attribute tnSysSetRequestErrorMessage in the
                        response PDU.  If there are no set failures,
                        the value of tnSysSetRequestErrorMessage in the
                        response PDU will be unchanged.

                        When read, this attribute will return an empty
                        string."
        DEFVAL         { "" }
        ::= { tnSysErrorHandling 1 }

--------------------------------------------------------------------------------
--  Security Mode
--------------------------------------------------------------------------------
    tnSysSecurityMode OBJECT-TYPE
        SYNTAX         INTEGER {
                         normal(1),
                         encrypted(2),
                         fips(3),
                         anssi(4)
                       }
        MAX-ACCESS     read-write
        STATUS         current
        DESCRIPTION    "Security mode for 1830."
        DEFVAL         { normal }
        ::= { tnSysSecurity 1 }

--------------------------------------------------------------------------------
--  SSH
--------------------------------------------------------------------------------
    tnSysSshKeyType OBJECT-TYPE
        SYNTAX         INTEGER {
                         dsa(1),
                         rsa(2),
                         ecdsa(3),
                         ed25519(4),
                         all(5)
                       }
        MAX-ACCESS     read-write
        STATUS         current
        DESCRIPTION    "The secure shell key type.  Only RSA key
                        generation is supported in the current release.

                        Current configurable value: rsa."
        DEFVAL         { rsa }
        ::= { tnSysSsh 1 }

    tnSysSshKeyModulus OBJECT-TYPE
        SYNTAX         Unsigned32
        MAX-ACCESS     read-write
        STATUS         current
        DESCRIPTION    "The secure shell modulus.  This is used for RSA
                        key generation.

                        Current supported range: 2048 to 4096."
        DEFVAL         { 2048 }
        ::= { tnSysSsh 2 }

    tnSysSshPublicKey OBJECT-TYPE
        SYNTAX         OCTET STRING (SIZE(0..500))
        MAX-ACCESS     read-only
        STATUS         current
        DESCRIPTION    "The secure shell public key."
        DEFVAL         { "" }
        ::= { tnSysSsh 3 }

    tnSysSshKeyCommand OBJECT-TYPE
        SYNTAX         INTEGER {
                         noCmd(1),
                         generate(2),
                         delete(3)
                       }
        MAX-ACCESS     read-write
        STATUS         current
        DESCRIPTION    "Secure key command.  Note that the value
                        retrieved from this attribute is always noCmd."
        DEFVAL         { noCmd }
        ::= { tnSysSsh 4 }

    tnSysSshKeyGenerationStatus OBJECT-TYPE
        SYNTAX         INTEGER {
                         completed(1),
                         inProgress(2),
                         failed(3)
                       }
        MAX-ACCESS     read-only
        STATUS         current
        DESCRIPTION    "Status of the secure key generation."
        DEFVAL         { completed }
        ::= { tnSysSsh 5 }

    tnSysSshEcdsaKeyModulus OBJECT-TYPE
        SYNTAX         Unsigned32
        MAX-ACCESS     read-write
        STATUS         current
        DESCRIPTION    "."
        ::= { tnSysSsh 6 }

--------------------------------------------------------------------------------
-- SSH KEY SCALAR
--------------------------------------------------------------------------------
    tnSshKeyAttributeTotal OBJECT-TYPE
        SYNTAX         Integer32
        MAX-ACCESS     read-only
        STATUS         current
        DESCRIPTION    "Total no of attributes in tnSshKeyTable."
        ::= { tnSysKey 1 }

--------------------------------------------------------------------------------
-- SSH KEY TABLE
--------------------------------------------------------------------------------
    tnSshKeyTable OBJECT-TYPE
        SYNTAX         SEQUENCE OF TnSshKeyEntry
        MAX-ACCESS     not-accessible
        STATUS         current
        DESCRIPTION    "."
        ::= { tnSysKey 2 }

    tnSshKeyEntry OBJECT-TYPE
        SYNTAX         TnSshKeyEntry
        MAX-ACCESS     not-accessible
        STATUS         current
        DESCRIPTION    "."
        INDEX { tnSshKeyTypeIndex }
        ::= { tnSshKeyTable 1 }

    TnSshKeyEntry ::= SEQUENCE {
        tnSshKeyTypeIndex          INTEGER,
        tnSshPublicKey             OCTET STRING,
        tnSshPublicKey1            OCTET STRING,
        tnSshEcdsaPublicKey        OCTET STRING,
        tnSshEcdsaPublicKey1       OCTET STRING,
        tnSshEd25519PublicKey      OCTET STRING,
        tnSshEd25519PublicKey1     OCTET STRING
    }

    tnSshKeyTypeIndex OBJECT-TYPE
        SYNTAX         INTEGER {
                         dsa(1),
                         rsa(2),
                         ecdsa(3),
                         ed25519(4)
                       }
        MAX-ACCESS     not-accessible
        STATUS         current
        DESCRIPTION    "The secure shell key type."
        ::= { tnSshKeyEntry 1 }

    tnSshPublicKey OBJECT-TYPE
        SYNTAX         OCTET STRING (SIZE(0..2048))
        MAX-ACCESS     read-only
        STATUS         current
        DESCRIPTION    "The secure shell public key."
        DEFVAL         { "" }
        ::= { tnSshKeyEntry 2 }

    tnSshPublicKey1 OBJECT-TYPE
        SYNTAX         OCTET STRING (SIZE(0..2048))
        MAX-ACCESS     read-only
        STATUS         current
        DESCRIPTION    "The secure shell public key1."
        DEFVAL         { "" }
        ::= { tnSshKeyEntry 3 }

    tnSshEcdsaPublicKey OBJECT-TYPE
        SYNTAX         OCTET STRING (SIZE(0..2048))
        MAX-ACCESS     read-only
        STATUS         current
        DESCRIPTION    "The secure Ecdsa public key."
        DEFVAL         { "" }
        ::= { tnSshKeyEntry 4 }

    tnSshEcdsaPublicKey1 OBJECT-TYPE
        SYNTAX         OCTET STRING (SIZE(0..2048))
        MAX-ACCESS     read-only
        STATUS         current
        DESCRIPTION    "The secure Ecdsa public key1."
        DEFVAL         { "" }
        ::= { tnSshKeyEntry 5 }

    tnSshEd25519PublicKey OBJECT-TYPE
        SYNTAX         OCTET STRING (SIZE(0..2048))
        MAX-ACCESS     read-only
        STATUS         current
        DESCRIPTION    "The secure Ed25519 public key."
        DEFVAL         { "" }
        ::= { tnSshKeyEntry 6 }

    tnSshEd25519PublicKey1 OBJECT-TYPE
        SYNTAX         OCTET STRING (SIZE(0..2048))
        MAX-ACCESS     read-only
        STATUS         current
        DESCRIPTION    "The secure Ed25519 public key1."
        DEFVAL         { "" }
        ::= { tnSshKeyEntry 7 }

--------------------------------------------------------------------------------
--  SSL
--------------------------------------------------------------------------------
    tnSysSslKeyType OBJECT-TYPE
        SYNTAX         INTEGER {
                         dsa(1),
                         rsa(2)
                       }
        MAX-ACCESS     read-write
        STATUS         current
        DESCRIPTION    "The SSL key type.  Only RSA key generation is
                        supported in the current release.

                        Current configurable value: rsa."
        DEFVAL         { rsa }
        ::= { tnSysSsl 1 }

    tnSysSslKeyModulus OBJECT-TYPE
        SYNTAX         Unsigned32 (512..4096)
        MAX-ACCESS     read-write
        STATUS         current
        DESCRIPTION    "The SSL key modulus.
                        Pre-R3.6 range:  (512, 4096)
                        R3.6 range:      (512, 2048)
                        Post-R11.0 range:(512, 4096)
                        R11.1 range:     (2048, 4096)."
        DEFVAL         { 2048 }
        ::= { tnSysSsl 2 }

    tnSysSslPublicKey OBJECT-TYPE
        SYNTAX         OCTET STRING (SIZE(0..2000))
        MAX-ACCESS     read-only
        STATUS         current
        DESCRIPTION    "The SSL public key."
        ::= { tnSysSsl 3 }

    tnSysSslKeyCommand OBJECT-TYPE
        SYNTAX         INTEGER {
                         noCmd(1),
                         generate(2)
                       }
        MAX-ACCESS     read-write
        STATUS         current
        DESCRIPTION    "SSL key command.  Note that the value retrieved
                        from this attribute is always noCmd."
        DEFVAL         { noCmd }
        ::= { tnSysSsl 4 }

    tnSysSslKeyGenerationStatus OBJECT-TYPE
        SYNTAX         AluWdmSslOperationStatus
        MAX-ACCESS     read-only
        STATUS         current
        DESCRIPTION    "Status of the SSL key generation."
        DEFVAL         { completed }
        ::= { tnSysSsl 5 }

    tnSysSslCertTransferCommand OBJECT-TYPE
        SYNTAX         INTEGER {
                         noCmd(1),
                         uploadReq(2),
                         downloadCert(3)
                       }
        MAX-ACCESS     read-write
        STATUS         current
        DESCRIPTION    "Command to upload SSL CSR or download certificate."
        DEFVAL         { noCmd }
        ::= { tnSysSsl 6 }

--    obsolete
--    tnSysSslCertTransferStatus OBJECT-TYPE ::= { tnSysSsl 7 }

    tnSysSslCertTransferProtocol OBJECT-TYPE
        SYNTAX         AluWdmNewTransferProtocol
        MAX-ACCESS     read-write
        STATUS         current
        DESCRIPTION    "The protocol used for SSL CSR and certificate
                        file transfers."
        DEFVAL         { ftp }
        ::= { tnSysSsl 8 }

    tnSysSslCertTransferRemoteIp OBJECT-TYPE
        SYNTAX         IpAddress
        MAX-ACCESS     read-write
        STATUS         current
        DESCRIPTION    "The server IP address for SSL CSR and
                        certificate file transfers."
        DEFVAL         { '00000000'H }
        ::= { tnSysSsl 9 }

    tnSysSslCertTransferRemotePath OBJECT-TYPE
        SYNTAX         SnmpAdminString (SIZE(0..255))
        MAX-ACCESS     read-write
        STATUS         current
        DESCRIPTION    "The path on server for SSL CSR and certificate
                        file transfers."
        DEFVAL         { "" }
        ::= { tnSysSsl 10 }

    tnSysSslCertTransferRemoteUserId OBJECT-TYPE
        SYNTAX         SnmpAdminString
        MAX-ACCESS     read-write
        STATUS         current
        DESCRIPTION    "The userId used for SSL CSR and certificate
                        file transfers."
        DEFVAL         { "" }
        ::= { tnSysSsl 11 }

    tnSysSslCertTransferRemotePassword OBJECT-TYPE
        SYNTAX         SnmpAdminString
        MAX-ACCESS     read-write
        STATUS         current
        DESCRIPTION    "The password used for SSL CSR and certificate
                        file transfers.

                        When read, this attribute will return an empty
                        string if the password has not been set and
                        '********' if it has been set."
        DEFVAL         { "" }
        ::= { tnSysSsl 12 }

    tnSysSslCsrCommand OBJECT-TYPE
        SYNTAX         INTEGER {
                         noCmd(1),
                         generate(2)
                       }
        MAX-ACCESS     read-write
        STATUS         current
        DESCRIPTION    "Command to generate SSL certificate signing
                        request (CSR)."
        DEFVAL         { noCmd }
        ::= { tnSysSsl 13 }

    tnSysSslCsrCountry OBJECT-TYPE
        SYNTAX         SnmpAdminString (SIZE(2))
        MAX-ACCESS     read-write
        STATUS         current
        DESCRIPTION    "The SSL CSR subject country."
        DEFVAL         { "IT" }
        ::= { tnSysSsl 14 }

    tnSysSslCsrState OBJECT-TYPE
        SYNTAX         SnmpAdminString (SIZE(0..128))
        MAX-ACCESS     read-write
        STATUS         current
        DESCRIPTION    "The SSL CSR subject state."
        DEFVAL         { "Italy" }
        ::= { tnSysSsl 15 }

    tnSysSslCsrLocality OBJECT-TYPE
        SYNTAX         SnmpAdminString (SIZE(0..128))
        MAX-ACCESS     read-write
        STATUS         current
        DESCRIPTION    "The SSL CSR subject locality."
        DEFVAL         { "Milan" }
        ::= { tnSysSsl 16 }

    tnSysSslCsrOrganization OBJECT-TYPE
        SYNTAX         SnmpAdminString (SIZE(0..64))
        MAX-ACCESS     read-write
        STATUS         current
        DESCRIPTION    "The SSL CSR subject organization."
        DEFVAL         { "Nokia" }
        ::= { tnSysSsl 17 }

    tnSysSslCsrOrganizationUnit OBJECT-TYPE
        SYNTAX         SnmpAdminString (SIZE(0..64))
        MAX-ACCESS     read-write
        STATUS         current
        DESCRIPTION    "The SSL CSR subject organization unit."
        DEFVAL         { "Optics Division" }
        ::= { tnSysSsl 18 }

    tnSysSslCsrCommonName OBJECT-TYPE
        SYNTAX         SnmpAdminString (SIZE(0..64))
        MAX-ACCESS     read-write
        STATUS         current
        DESCRIPTION    "The SSL CSR subject common name."
        DEFVAL         { "1830 Domain" }
        ::= { tnSysSsl 19 }

    tnSysSslCsrEmailAddress OBJECT-TYPE
        SYNTAX         SnmpAdminString
        MAX-ACCESS     read-write
        STATUS         current
        DESCRIPTION    "The SSL CSR subject email address."
        DEFVAL         { "" }
        ::= { tnSysSsl 20 }

    tnSysSslCertCommand OBJECT-TYPE
        SYNTAX         INTEGER {
                         noCmd(1),
                         install(2)
                       }
        MAX-ACCESS     read-write
        STATUS         current
        DESCRIPTION    "Command to install SSL certificate."
        DEFVAL         { noCmd }
        ::= { tnSysSsl 21 }

    tnSysSslCertSignatureAlgorithm OBJECT-TYPE
        SYNTAX         SnmpAdminString
        MAX-ACCESS     read-only
        STATUS         current
        DESCRIPTION    "The SSL certificate signature algorithm."
        DEFVAL         { "md5WithRSAEncryption" }
        ::= { tnSysSsl 22 }

    tnSysSslCertValidity OBJECT-TYPE
        SYNTAX         SnmpAdminString
        MAX-ACCESS     read-only
        STATUS         current
        DESCRIPTION    "The SSL certificate validity."
        DEFVAL         { "Apr 14 06:03:04 2011 GMT - Apr 11 06:03:04 2021 GMT" }
        ::= { tnSysSsl 23 }

    tnSysSslCsrUploadStatus OBJECT-TYPE
        SYNTAX         AluWdmSslOperationStatus
        MAX-ACCESS     read-only
        STATUS         current
        DESCRIPTION    "Status of the SSL CSR file transfer."
        DEFVAL         { none }
        ::= { tnSysSsl 24 }

    tnSysSslCertDownloadStatus OBJECT-TYPE
        SYNTAX         AluWdmSslOperationStatus
        MAX-ACCESS     read-only
        STATUS         current
        DESCRIPTION    "Status of the SSL certificate file transfer."
        DEFVAL         { none }
        ::= { tnSysSsl 25 }

    tnSysSslCertInstallStatus OBJECT-TYPE
        SYNTAX         AluWdmSslOperationStatus
        MAX-ACCESS     read-only
        STATUS         current
        DESCRIPTION    "Status of the SSL certificate install."
        DEFVAL         { completed }
        ::= { tnSysSsl 26 }

    tnSysSslCsrGenerationStatus OBJECT-TYPE
        SYNTAX         INTEGER {
                         completed(1),
                         inProgress(2),
                         failed(3),
                         none(4),
                         editing(5)
                       }
        MAX-ACCESS     read-only
        STATUS         current
        DESCRIPTION    "Status of the SSL CSR Generation."
        DEFVAL         { none }
        ::= { tnSysSsl 27 }

    tnSysSslCertTransferInetAddressType OBJECT-TYPE
        SYNTAX         InetAddressType
        MAX-ACCESS     read-write
        STATUS         current
        DESCRIPTION    "The value specifies the type of Internet address
                        stored in SSL CSR"
        DEFVAL         { unknown }
        ::= { tnSysSsl 28 }

    tnSysSslCertTransferInetAddress OBJECT-TYPE
        SYNTAX         InetAddress
        MAX-ACCESS     read-write
        STATUS         current
        DESCRIPTION    "Indicates the IPv6 address of SSL CSR and
                        certificate file transfers."
        DEFVAL         { ''H }
        ::= { tnSysSsl 29 }

    tnSysSslCertTransferPort OBJECT-TYPE
        SYNTAX         Unsigned32 (1..65535)
        MAX-ACCESS     read-write
        STATUS         current
        DESCRIPTION    "."
        DEFVAL         { 21 }
        ::= { tnSysSsl 30 }

    tnSysSslCertVerification OBJECT-TYPE
        SYNTAX         TruthValue
        MAX-ACCESS     read-write
        STATUS         current
        DESCRIPTION    "Specifies that the X.509v3 certificate will be verified
                        before installation. This means verification of validaity,
                        chain of trust (issuer of certificate), basicConstraints,
                        (extended) key purpose, revocation status."
        DEFVAL         { false }
        ::= { tnSysSsl 31 }

    tnSysSslCertExpiration  OBJECT-TYPE
        SYNTAX         Unsigned32
        MAX-ACCESS     read-write
        STATUS         current
        DESCRIPTION    "."
        ::= { tnSysSsl 32 }

--------------------------------------------------------------------------------
-- System Transfer Log
--------------------------------------------------------------------------------
    tnSysTransferLogCommand OBJECT-TYPE
        SYNTAX         INTEGER {
                         noCmd(1),
                         transferToRfs(2)
                       }
        MAX-ACCESS     read-write
        STATUS         current
        DESCRIPTION    "."
        DEFVAL         { noCmd }
        ::= { tnSysTransferLog 1 }

    tnSysTransferLogRemoteHostIp OBJECT-TYPE
        SYNTAX         IpAddress
        MAX-ACCESS     read-write
        STATUS         current
        DESCRIPTION    "."
        DEFVAL         { '00000000'H }
        ::= { tnSysTransferLog 2 }

    tnSysTransferLogRemotePath OBJECT-TYPE
        SYNTAX         SnmpAdminString (SIZE(0..255))
        MAX-ACCESS     read-write
        STATUS         current
        DESCRIPTION    "."
        DEFVAL         { "" }
        ::= { tnSysTransferLog 3 }

    tnSysTransferLogType OBJECT-TYPE
        SYNTAX         INTEGER {
                         none(1),
                         snmp(2),
                         ual(3),
                         alarm(4),
                         user(5),
                         secu(6),
                         other(7),
                         ualPartial(8)
                       }
        MAX-ACCESS     read-write
        STATUS         current
        DESCRIPTION    "This attribute indicates the log type to be
                        transferred to remote file server."
        DEFVAL         { none }
        ::= { tnSysTransferLog 4 }

    tnSysTransferLogStatus OBJECT-TYPE
        SYNTAX         AluWdmTransferStatus
        MAX-ACCESS     read-only
        STATUS         current
        DESCRIPTION    "This attribute indicates the status of the
                        previously executed tnSysTransferLogCommand
                        operation."
        DEFVAL         { none }
        ::= { tnSysTransferLog 5 }

    tnSysTransferLogLastLogFilename OBJECT-TYPE
        SYNTAX         SnmpAdminString (SIZE(0..255))
        MAX-ACCESS     read-only
        STATUS         current
        DESCRIPTION    "This attribute indicates the filename for the
                        last transfer performed on the node.  If none
                        exists or a transfer is in progress, this
                        attribute will return an empty string."
        DEFVAL         { "" }
        ::= { tnSysTransferLog 6 }

    tnSysTransferLogLastCommand OBJECT-TYPE
        SYNTAX         INTEGER {
                         noCommand(1),
                         unknown(2),
                         ual(3),
                         snmp(4),
                         ualPartial(5)
                       }
        MAX-ACCESS     read-only
        STATUS         current
        DESCRIPTION    "This is the last transfer log command executed.
                        If the last operation is unknown, the value of
                        this attribute will be unknown.  If a transfer
                        log command has not been executed since the
                        last node reset, the value of this attribute
                        will be noCommand."
        DEFVAL         { noCommand }
        ::= { tnSysTransferLog 7 }

    tnSysTransferLogLastFileTimeStamp OBJECT-TYPE
        SYNTAX         Unsigned32
        MAX-ACCESS     read-only
        STATUS         current
        DESCRIPTION    "The date and time when the last file was
                        completed."
        DEFVAL         { 0 }
        ::= { tnSysTransferLog 8 }

    tnSysTransferLogProtocol OBJECT-TYPE
        SYNTAX         AluWdmNewTransferProtocol
        MAX-ACCESS     read-write
        STATUS         current
        DESCRIPTION    "This attributes indicates the transfer log
                        protocol."
        DEFVAL         { ftp }
        ::= { tnSysTransferLog 9 }

    tnSysTransferLogUserId OBJECT-TYPE
        SYNTAX         SnmpAdminString (SIZE(0..32))
        MAX-ACCESS     read-write
        STATUS         current
        DESCRIPTION    "The userId used to access the RFS."
        DEFVAL         { "" }
        ::= { tnSysTransferLog 10 }

    tnSysTransferLogPassword OBJECT-TYPE
        SYNTAX         SnmpAdminString (SIZE(0..32))
        MAX-ACCESS     read-write
        STATUS         current
        DESCRIPTION    "The password used to access the RFS.

                        When read, this attribute will return an empty
                        string if the password has not been set and
                        '********' if it has been set."
        DEFVAL         { "" }
        ::= { tnSysTransferLog 11 }

    tnSysTransferLogWindowStart OBJECT-TYPE
        SYNTAX         Unsigned32
        MAX-ACCESS     read-write
        STATUS         current
        DESCRIPTION    "The start time of partial log time window,
                        measured in total time ticks (seconds) from the
                        year 1970."
        DEFVAL         { 0 }
        ::= { tnSysTransferLog 12 }

    tnSysTransferLogWindowStop OBJECT-TYPE
        SYNTAX         Unsigned32
        MAX-ACCESS     read-write
        STATUS         current
        DESCRIPTION    "The stop time of partial log time window,
                        measured in total time ticks (seconds) from the
                        year 1970."
        DEFVAL         { 0 }
        ::= { tnSysTransferLog 13 }

    tnSysTransferLogRemoteHostInetAddressType OBJECT-TYPE
        SYNTAX         InetAddressType
        MAX-ACCESS     read-write
        STATUS         current
        DESCRIPTION    "The value specifies the type of Internet address
                        stored in tnSysTransferLogRemoteHostInetAddress."
        DEFVAL         { unknown }
        ::= { tnSysTransferLog 14 }

    tnSysTransferLogRemoteHostInetAddress OBJECT-TYPE
        SYNTAX         InetAddress
        MAX-ACCESS     read-write
        STATUS         current
        DESCRIPTION    "Indicates the IPv6 address of the log server."
        DEFVAL         { ''H }
        ::= { tnSysTransferLog 15 }

    tnSysTransferLogPort OBJECT-TYPE
        SYNTAX         Unsigned32 (1..65535)
        MAX-ACCESS     read-write
        STATUS         current
        DESCRIPTION    "This attributes indicates the transfer log
                        port."
        DEFVAL         { 21 }
        ::= { tnSysTransferLog 16 }

--------------------------------------------------------------------------------
-- IP Access Control List (ACL) System Default
--------------------------------------------------------------------------------
    tnSysIpAclRxAction OBJECT-TYPE
        SYNTAX         INTEGER {
                         pass(1),
                         block(2),
                         dropAndlog(3)
                       }
        MAX-ACCESS     read-write
        STATUS         current
        DESCRIPTION    "Default action to be taken on received (incoming)
                        packets where ACL is enabled but no pattern
                        matches or no action is explicitly defined."
        DEFVAL         { pass }
        ::= { tnSysIpAclSysDefault 1 }

    tnSysIpAclTxAction OBJECT-TYPE
        SYNTAX         INTEGER {
                         pass(1),
                         block(2)
                       }
        MAX-ACCESS     read-write
        STATUS         current
        DESCRIPTION    "Default action to be taken on transmitted
                        (outgoing) packets where ACL is enabled but no
                        pattern matches or no action is explicitly
                        defined."
        DEFVAL         { pass }
        ::= { tnSysIpAclSysDefault 2 }

    tnSysIpAclSnmpCfgEnable OBJECT-TYPE
        SYNTAX         TruthValue
        MAX-ACCESS     read-write
        STATUS         current
        DESCRIPTION    "Indicates whether or not ACL configuration is
                        supported via SNMP."
        DEFVAL         { false }
        ::= { tnSysIpAclSysDefault 3 }

    tnSysIpAclCfgRestoreToDefault OBJECT-TYPE
        SYNTAX         TruthValue
        MAX-ACCESS     read-write
        STATUS         current
        DESCRIPTION    "If setting to true, it will restore acl_ipv4
                        config to system default."
        DEFVAL         { false }
        ::= { tnSysIpAclSysDefault 4 }

   tnSysIpAclClearCounter OBJECT-TYPE
        SYNTAX         TruthValue
        MAX-ACCESS     read-write
        STATUS         current
        DESCRIPTION    "Clear IPACL counter to zero."
        DEFVAL         { false }
        ::= { tnSysIpAclSysDefault 5 }

--------------------------------------------------------------------------------
-- IP Access Control List (ACL) Pattern Scalars
--------------------------------------------------------------------------------
    tnSysIpAclPatternAttributeTotal OBJECT-TYPE
        SYNTAX         Integer32
        MAX-ACCESS     read-only
        STATUS         current
        DESCRIPTION    "."
        ::= { tnSysAccessControlList 2 }

--------------------------------------------------------------------------------
-- IP Access Control List (ACL) Pattern
--------------------------------------------------------------------------------
    tnSysIpAclPatternTable OBJECT-TYPE
        SYNTAX         SEQUENCE OF TnSysIpAclPatternEntry
        MAX-ACCESS     not-accessible
        STATUS         current
        DESCRIPTION    "Table of IP ACL pattern.  An ACL pattern is a
                        set of packet field descriptors that can be
                        tested against a packet.  For a pattern to
                        match, each of its field descriptors must fit
                        the data in the packet."
        ::= { tnSysAccessControlList 3 }

    tnSysIpAclPatternEntry OBJECT-TYPE
        SYNTAX         TnSysIpAclPatternEntry
        MAX-ACCESS     not-accessible
        STATUS         current
        DESCRIPTION    "."
        INDEX { tnSysIpAclPatternID }
        ::= { tnSysIpAclPatternTable 1 }

    TnSysIpAclPatternEntry ::= SEQUENCE {
        tnSysIpAclPatternID               SnmpAdminString,
        tnSysIpAclPatternAction           INTEGER,
        tnSysIpAclPatternICMPERROR        TruthValue,
        tnSysIpAclPatternSrcAddr          IpAddress,
        tnSysIpAclPatternSrcPrefix        IpAddress,
        tnSysIpAclPatternDestAddr         IpAddress,
        tnSysIpAclPatternDestPrefix       IpAddress,
        tnSysIpAclPatternDestPort         Integer32,
        tnSysIpAclPatternIpProtocol       OCTET STRING,
        tnSysIpAclPatternIpFragment       TruthValue,
        tnSysIpAclPatternIcmpType         Integer32,
        tnSysIpAclPatternIcmpCode         Integer32,
        tnSysIpAclPatternTcpEstablish     INTEGER,
        tnSysIpAclPatternRowStatus        RowStatus,
        tnSysIpAclPatternSrcPort          Integer32,
        tnSysIpAclPatternSystemDefault    TruthValue,
        tnSysIpAclPatternSrcPortRangeEnd  Integer32,
        tnSysIpAclPatternDestPortRangeEnd Integer32
    }

    tnSysIpAclPatternID OBJECT-TYPE
        SYNTAX         SnmpAdminString (SIZE(1..30))
        MAX-ACCESS     not-accessible
        STATUS         current
        DESCRIPTION    "The identifier of the ACL pattern to be created.
                        It could be either an integer in the range of
                        (1-4000) or a string of up to 30 case-sensitive
                        alphanumeric characters, where the first character
                        is always a letter, which is selected by the user
                        to uniquely identify the pattern in subsequent
                        provisioning requests."
        ::= { tnSysIpAclPatternEntry 1 }

    tnSysIpAclPatternAction OBJECT-TYPE
        SYNTAX         INTEGER {
                         pass(1),
                         block(2),
                         log(3)
                       }
        MAX-ACCESS     read-create
        STATUS         current
        DESCRIPTION    "Action to be taken on packets matching the
                        specified ACL pattern.  Valid values are:
                        pass  - allow the packet if it matches all the
                                pattern descriptors;
                        block - disallow the packet if it doesn't match
                                all the pattern descriptors.
                        log   - log the packet if it matches all the
                                pattern descriptors."
        ::= { tnSysIpAclPatternEntry 2 }

    tnSysIpAclPatternICMPERROR OBJECT-TYPE
        SYNTAX         TruthValue
        MAX-ACCESS     read-create
        STATUS         current
        DESCRIPTION    "ICMP error reporting behavior for blocked
                        packets.  If no icmpError value is specified,
                        the behavior will be determined by the system
                        default setting.  Valid values are:
                        true  - send ICMP error for blocked packets
                        false - do not send ICMP error for blocked
                                packets."
        DEFVAL         { false }
        ::= { tnSysIpAclPatternEntry 3 }

    tnSysIpAclPatternSrcAddr OBJECT-TYPE
        SYNTAX         IpAddress
        MAX-ACCESS     read-create
        STATUS         current
        DESCRIPTION    "Source IP address.  It can be specified
                        explicitly to match only packets that originate
                        from a particular address or can be used along
                        with the SrcPrefix parameter to specify a range
                        of supported originating IP addresses."
        ::= { tnSysIpAclPatternEntry 4 }

    tnSysIpAclPatternSrcPrefix OBJECT-TYPE
        SYNTAX         IpAddress
        MAX-ACCESS     read-create
        STATUS         current
        DESCRIPTION    "Source IP mask prefix.  It's the reverse of a
                        subnet mask, where 0 indicates a position that
                        must be matched and 1 indicates a position that
                        does not matter.  If the SrcAddr is specified
                        and the SrcPrefix is unspecified (0.0.0.0), the
                        originating IP address of the packet must match
                        the SrcAddr exactly.  Otherwise, the pattern
                        will allow packets whose originating IP is within
                        the range implied by the source IP and subnet
                        mask.  This parameter is not valid  unless the
                        SrcAddr is also specified."
        DEFVAL         { '00000000'H }
        ::= { tnSysIpAclPatternEntry 5 }

    tnSysIpAclPatternDestAddr OBJECT-TYPE
        SYNTAX         IpAddress
        MAX-ACCESS     read-create
        STATUS         current
        DESCRIPTION    "Destination IP address.  It can be specified
                        explicitly to match only packets that originate
                        from a particular address or can be used along
                        with the DestPrefix parameter to specify a range
                        of supported destination IP addresses."
        ::= { tnSysIpAclPatternEntry 6 }

    tnSysIpAclPatternDestPrefix OBJECT-TYPE
        SYNTAX         IpAddress
        MAX-ACCESS     read-create
        STATUS         current
        DESCRIPTION    "Destination IP Mask Prefix.  It's the reverse
                        of a subnet mask, where 0 indicates a position
                        that must be matched and 1 indicates a position
                        that does not matter.  If the DestAddr is
                        specified and the DestPrefix is unspecified
                        (0.0.0.0), the originating IP address of the
                        packet must match the DestAddr exactly.  Otherwise,
                        the pattern will allow packets whose originating
                        IP is within the range implied by the source IP
                        and subnet mask.  This parameter is not valid
                        unless the DestAddr is also specified."
        DEFVAL         { '00000000'H }
        ::= { tnSysIpAclPatternEntry 7 }

    tnSysIpAclPatternDestPort OBJECT-TYPE
        SYNTAX         Integer32 (0..65535)
        MAX-ACCESS     read-create
        STATUS         current
        DESCRIPTION    "TCP/UDP destination port.When rangeEnd not zero,
                        it is used as range start. It is applicable only
                        when the IP Protocol is TCP or UDP.  Some of the
                        commonly used ports are:
                        20    FTP-Data    TCP  File Transfer Protocol [Data]
                        21    FTP         TCP  File Transfer Protocol [Control]
                        23    Telnet      TCP  Telnet
                        69    TFTP        UDP  Trivial File Transfer Protocol
                        123   NTP         UDP  Network Time Protocol
                        161   SNMP        UDP  SNMP
                        162   SNMPTRAP    UDP  SNMPTRAP
                        3082  TL1-Raw     TCP  TL-1 [Raw]
                        3083  TL1-Telnet  TCP  TL-1 [User Interface]"
        ::= { tnSysIpAclPatternEntry 8 }

    tnSysIpAclPatternIpProtocol OBJECT-TYPE
        SYNTAX         OCTET STRING
        MAX-ACCESS     read-create
        STATUS         current
        DESCRIPTION    "IP Protocol.  It can be specified by explicit
                        protocol number (Integer, 0 to 255) or by keyword.
                        Some common protocol types are listed below:
                        ICMP              - IP protocol is ICMP (1)
                        IPIP              - IP protocol is IPIP (4)
                        TCP               - IP protocol is TCP (6)
                        UDP               - IP protocol is UDP (17)
                        RSVP              - IP protocol is RSVP (46)
                        GRE               - IP protocol is GRE (47)
                        OSPF              - IP protocol is OSPF (89)
                        <other protocol>  - Specify IP protocol number: 0 to 255"
        ::= { tnSysIpAclPatternEntry 9 }

    tnSysIpAclPatternIpFragment OBJECT-TYPE
        SYNTAX         TruthValue
        MAX-ACCESS     read-create
        STATUS         current
        DESCRIPTION    "IP Fragmentation.  True means that the filtering
                        is done on all fragments, not just on the initial
                        one (assuming the following ones are ok).  Valid
                        values are:
                        true  - pattern is an IP
                        false - pattern is not an IP fragment."
        DEFVAL         { false }
        ::= { tnSysIpAclPatternEntry 10 }

    tnSysIpAclPatternIcmpType OBJECT-TYPE
        SYNTAX         Integer32 (0..255)
        MAX-ACCESS     read-create
        STATUS         current
        DESCRIPTION    "ICMP Type identifier.  It is applicable only
                        when IPPROTOCOL is ICMP.  If specified, the
                        pattern will match only packets with this exact
                        ICMP type.  Some of the most commonly used ICMP
                        types are:
                        0         Echo Reply [RFC792]
                        3         Destination Unreachable[RFC792]
                        5         Redirect[RFC792]
                        9         Router Advertisement[RFC1256]
                        42-255    Reserved."
        ::= { tnSysIpAclPatternEntry 11 }

    tnSysIpAclPatternIcmpCode OBJECT-TYPE
        SYNTAX         Integer32 (0..255)
        MAX-ACCESS     read-create
        STATUS         current
        DESCRIPTION    "ICMP code field.  It is applicable only when IP
                        protocol is ICMP and is used along with certain
                        ICMP types to further specify the message type.
                        It must also specify the ICMP type when setting
                        this parameter.  If specified, the pattern will
                        only match packets with this exact ICMP code
                        value.  For example, there are a few ICMPCODEs
                        associated with the ICMPTYPE Redirect [RFC792]:
                        0  Redirect Datagram for the Network (or subnet)
                        1  Redirect Datagram for the Host
                        2  Redirect Datagram for the Type of Service
                           and Network
                        3  Redirect Datagram for the Type of Service and
                           Host."
        ::= { tnSysIpAclPatternEntry 12 }

    tnSysIpAclPatternTcpEstablish OBJECT-TYPE
        SYNTAX         INTEGER {
                         true(1),
                         false(2),
                         local(3)
                       }
        MAX-ACCESS     read-create
        STATUS         current
        DESCRIPTION    "TCP established flag.  It matches a packet depending on
                        whether the TCP flags in the IP header correspond to the
                        established state.  It is applicable only when IP Protocol
                        is TCP.  Valid values are:
                        true  - TCP flags correspond to established state
                        false - TCP flags do not correspond to established state
                        local - TCP flags correspond to established state only for
                                destination to local NE."
        ::= { tnSysIpAclPatternEntry 13 }

    tnSysIpAclPatternRowStatus OBJECT-TYPE
        SYNTAX         RowStatus
        MAX-ACCESS     read-create
        STATUS         current
        DESCRIPTION    "The status of pattern.
                        Set to 4 (createAndGo) to add pattern.
                        Set to 6 (destroy) to remove the pattern."
        ::= { tnSysIpAclPatternEntry 14 }

    tnSysIpAclPatternSrcPort OBJECT-TYPE
        SYNTAX         Integer32 (0..65535)
        MAX-ACCESS     read-create
        STATUS         current
        DESCRIPTION    "TCP/UDP source port. When rangeEnd not zero,
                        it is used as range start. It is applicable only
                        when the IP Protocol is TCP or UDP.  Some of the
                        commonly used ports are:

                        20    FTP-Data    TCP  File Transfer Protocol [Data]
                        21    FTP         TCP  File Transfer Protocol [Control]
                        23    Telnet      TCP  Telnet
                        69    TFTP        UDP  Trivial File Transfer Protocol
                        123   NTP         UDP  Network Time Protocol
                        161   SNMP        UDP  SNMP
                        162   SNMPTRAP    UDP  SNMPTRAP
                        3082  TL1-Raw     TCP  TL-1 [Raw]
                        3083  TL1-Telnet  TCP  TL-1 [User Interface]"
        ::= { tnSysIpAclPatternEntry 15 }

    tnSysIpAclPatternSystemDefault OBJECT-TYPE
        SYNTAX         TruthValue
        MAX-ACCESS     read-only
        STATUS         current
        DESCRIPTION    "Indicates if ACL pattern is added by the system
                        or a user.  Valid values are:
                          true  - ACL pattern is added by the system.
                          false - ACL pattern is added by the user."
        ::= { tnSysIpAclPatternEntry 16 }

    tnSysIpAclPatternSrcPortRangeEnd OBJECT-TYPE
        SYNTAX         Integer32 (0..65535)
        MAX-ACCESS     read-create
        STATUS         current
        DESCRIPTION    "TCP/UDP source port range end."
        ::= { tnSysIpAclPatternEntry 17 }

    tnSysIpAclPatternDestPortRangeEnd OBJECT-TYPE
        SYNTAX         Integer32 (0..65535)
        MAX-ACCESS     read-create
        STATUS         current
        DESCRIPTION    "TCP/UDP destination port range end."
        ::= { tnSysIpAclPatternEntry 18 }

--------------------------------------------------------------------------------
-- IP Access Control List (ACL) Filter Scalar
--------------------------------------------------------------------------------
    tnSysIpAclFilterAttributeTotal OBJECT-TYPE
        SYNTAX         Integer32
        MAX-ACCESS     read-only
        STATUS         current
        DESCRIPTION    "."
        ::= { tnSysAccessControlList 4 }

--------------------------------------------------------------------------------
-- IP Access Control List (ACL) Filter
--------------------------------------------------------------------------------
    tnSysIpAclFilterTable OBJECT-TYPE
        SYNTAX         SEQUENCE OF TnSysIpAclFilterEntry
        MAX-ACCESS     not-accessible
        STATUS         current
        DESCRIPTION    "An ACL filter is an ordered list of patterns.
                        A filter consists of a sorted list of (index,
                        pattern) pairs, where the index indicates the
                        relative position on the list and the pattern
                        indicates the pattern identifier.  Up to 100
                        filters may be defined on the system, and each
                        filter may contain up to 256 (index, pattern)
                        pairs."
        ::= { tnSysAccessControlList 5 }

    tnSysIpAclFilterEntry OBJECT-TYPE
        SYNTAX         TnSysIpAclFilterEntry
        MAX-ACCESS     not-accessible
        STATUS         current
        DESCRIPTION    "."
        INDEX { tnSysIpAclFilterID,
                tnSysIpAclFilterPatternIndex }
        ::= { tnSysIpAclFilterTable 1 }

    TnSysIpAclFilterEntry ::= SEQUENCE {
        tnSysIpAclFilterID               SnmpAdminString,
        tnSysIpAclFilterPatternIndex     Integer32,
        tnSysIpAclFilterPatternID        SnmpAdminString,
        tnSysIpAclFilterStatCount        Counter32,
        tnSysIpAclFilterRowStatus        RowStatus,
        tnSysIpAclFilterSystemDefault    TruthValue
    }

    tnSysIpAclFilterID OBJECT-TYPE
        SYNTAX         SnmpAdminString (SIZE(1..30))
        MAX-ACCESS     not-accessible
        STATUS         current
        DESCRIPTION    "Identifier for the ACL filter being defined.
                        It could be either an integer in the range of
                        (100-199) or a string of up to 30 case-sensitive
                        alphanumeric characters, where the first
                        character is always a letter, which uniquely
                        identifies the filter being defined."
        ::= { tnSysIpAclFilterEntry 1 }

    tnSysIpAclFilterPatternIndex OBJECT-TYPE
        SYNTAX         Integer32 (0..256)
        MAX-ACCESS     not-accessible
        STATUS         current
        DESCRIPTION    "The values of 1 to 256 represent the insertion
                        point for the specified pattern on the filter
                        list.  If there is already a pattern defined at
                        the specified index, the new pattern entry will
                        replace the previous one.  The value of 0
                        represents user input filterID without giving
                        the pattern index.  Front end users will use 0
                        for setting."
        ::= { tnSysIpAclFilterEntry 2 }

    tnSysIpAclFilterPatternID OBJECT-TYPE
        SYNTAX         SnmpAdminString (SIZE(0..30))
        MAX-ACCESS     read-create
        STATUS         current
        DESCRIPTION    "The identifier of the ACL pattern being added
                        to or removed from the specified filter.  It
                        could be either an integer in the range of
                        (1-4000) or a string of up to 30 case-sensitive
                        alphanumeric characters, where the first
                        character is always a letter, which is selected
                        by the user to uniquely identify the pattern in
                        subsequent provisioning requests."
        ::= { tnSysIpAclFilterEntry 3 }

    tnSysIpAclFilterStatCount OBJECT-TYPE
        SYNTAX         Counter32
        MAX-ACCESS     read-only
        STATUS         current
        DESCRIPTION    "Packet match counter.  It is incremented whenever
                        a packet matches the specified ACL pattern in the
                        filter.  This counter will be incremented
                        regardless of the provisioned action on that
                        pattern."
        ::= { tnSysIpAclFilterEntry 4 }

    tnSysIpAclFilterRowStatus OBJECT-TYPE
        SYNTAX         RowStatus
        MAX-ACCESS     read-create
        STATUS         current
        DESCRIPTION    "Action to take on the specified filter.  The
                        operator could add or remove a pattern from a
                        specified filter.  Set to 4 (createAndGo) to
                        add pattern in the filter.  Set to 6 (destroy)
                        to remove the pattern in the filter."
        ::= { tnSysIpAclFilterEntry 5 }

    tnSysIpAclFilterSystemDefault OBJECT-TYPE
        SYNTAX         TruthValue
        MAX-ACCESS     read-only
        STATUS         current
        DESCRIPTION    "Indicates if ACL filter is added by the system
                        or a user.  Valid values are:
                          true  - ACL filter is added by the system.
                          false - ACL filter is added by a user."
        ::= { tnSysIpAclFilterEntry 6 }

--------------------------------------------------------------------------------
-- IP Access Control List (ACL) Interface
--------------------------------------------------------------------------------
    tnSysIpAclInterfaceAttributeTotal OBJECT-TYPE
        SYNTAX         Integer32
        MAX-ACCESS     read-only
        STATUS         current
        DESCRIPTION    "."
        ::= { tnSysAccessControlList 6 }

--------------------------------------------------------------------------------
-- IP Access Control List (ACL) Interface
--------------------------------------------------------------------------------
    tnSysIpAclInterfaceTable OBJECT-TYPE
        SYNTAX         SEQUENCE OF TnSysIpAclInterfaceEntry
        MAX-ACCESS     not-accessible
        STATUS         current
        DESCRIPTION    "The IP ACL interface table is used to associate
                        or disassociate filters with particular physical
                        network interfaces (but not logical sub-interfaces).
                        Two filters may be associated with each interface,
                        one receive and one transmit.  The receive and
                        transmit filters on an interface may be
                        independently enabled and disabled on that
                        interface without disassociating the specific
                        filter numbers."
        ::= { tnSysAccessControlList 7 }

    tnSysIpAclInterfaceEntry OBJECT-TYPE
        SYNTAX         TnSysIpAclInterfaceEntry
        MAX-ACCESS     not-accessible
        STATUS         current
        DESCRIPTION    "."
        INDEX { ifIndex,
                tnSysIpAclInterfaceFilterDir }
        ::= { tnSysIpAclInterfaceTable 1 }

    TnSysIpAclInterfaceEntry ::= SEQUENCE {
        tnSysIpAclInterfaceFilterDir           INTEGER,
        tnSysIpAclInterfaceFilterID            SnmpAdminString,
        tnSysIpAclInterfaceFilterEnable        INTEGER,
        tnSysIpAclInterfaceFilterRowStatus     RowStatus,
        tnSysIpAclInterfaceSystemDefault       TruthValue,
        tnSysIpAclInterfaceFilterLog           INTEGER
    }

    tnSysIpAclInterfaceFilterDir OBJECT-TYPE
        SYNTAX         INTEGER {
                         rx(1),
                         tx(2)
                       }
        MAX-ACCESS     not-accessible
        STATUS         current
        DESCRIPTION    "Direction on the specified network interface
                        to which the IP ACL filter will be associated."
        ::= { tnSysIpAclInterfaceEntry 1 }

    tnSysIpAclInterfaceFilterID OBJECT-TYPE
        SYNTAX         SnmpAdminString (SIZE(0..30))
        MAX-ACCESS     read-create
        STATUS         current
        DESCRIPTION    "Identifier for the ACL filter being associated
                        with the specified interface and direction.  It
                        could be either an integer in the range of
                        (100-199) or a string of up to 30 case-sensitive
                        alphanumeric characters, where the first character
                        is always a letter, representing an existing ACL
                        Filter."
        ::= { tnSysIpAclInterfaceEntry 2 }

    tnSysIpAclInterfaceFilterEnable OBJECT-TYPE
        SYNTAX         INTEGER {
                         enable(1),
                         disable(2)
                       }
        MAX-ACCESS     read-create
        STATUS         current
        DESCRIPTION    "Enable or disable the IP ACL filter associated
                        with the specified interface and direction."
        DEFVAL         { disable }
        ::= { tnSysIpAclInterfaceEntry 3 }

    tnSysIpAclInterfaceFilterRowStatus OBJECT-TYPE
        SYNTAX         RowStatus
        MAX-ACCESS     read-create
        STATUS         current
        DESCRIPTION    "The status of Interface Filter.  Set to 4
                        (createAndGo) to add filter in the interface.
                        Set to 6 (destroy) to remove the filter in
                        the interface."
        ::= { tnSysIpAclInterfaceEntry 4 }

    tnSysIpAclInterfaceSystemDefault OBJECT-TYPE
        SYNTAX         TruthValue
        MAX-ACCESS     read-only
        STATUS         current
        DESCRIPTION    "Indicates if ACL interface added by the system
                        or a user.  Valid values are:
                          true  - ACL interface is added by the system.
                          false - ACL interface is added by a user."
        ::= { tnSysIpAclInterfaceEntry 5 }

    tnSysIpAclInterfaceFilterLog OBJECT-TYPE
        SYNTAX         INTEGER {
                         enable(1),
                         disable(2)
                       }
        MAX-ACCESS     read-create
        STATUS         current
        DESCRIPTION    "Enable or disable the IP ACL filter logging
                        on specified interface and direction."
        DEFVAL         { disable }
        ::= { tnSysIpAclInterfaceEntry 6 }

--------------------------------------------------------------------------------
-- IP Access Control List (ACL) Network Interface
--------------------------------------------------------------------------------
    tnSysIpAclNetIfFilterAttributeTotal OBJECT-TYPE
        SYNTAX         Integer32
        MAX-ACCESS     read-only
        STATUS         current
        DESCRIPTION    "."
        ::= { tnSysAccessControlList 8 }

--------------------------------------------------------------------------------
-- IP Access Control List (ACL) Network Interface
--------------------------------------------------------------------------------
    tnSysIpAclNetIfFilterTable OBJECT-TYPE
        SYNTAX         SEQUENCE OF TnSysIpAclNetIfFilterEntry
        MAX-ACCESS     not-accessible
        STATUS         current
        DESCRIPTION    "The IP ACL NetIf table is used to associate or
                        disassociate filters with particular NetIf.  Two
                        filters may be associated with each NetIf, one
                        receive and one transmit.  The receive and transmit
                        filters on an NetIf may be independently enabled
                        and disabled on that NetIf without disassociating
                        the specific filter numbers."
        ::= { tnSysAccessControlList 9 }

    tnSysIpAclNetIfFilterEntry OBJECT-TYPE
        SYNTAX         TnSysIpAclNetIfFilterEntry
        MAX-ACCESS     not-accessible
        STATUS         current
        DESCRIPTION    "."
        INDEX { tnNetIfIndex,
                tnSysIpAclNetIfFilterDir}
        ::= { tnSysIpAclNetIfFilterTable 1 }

    TnSysIpAclNetIfFilterEntry ::= SEQUENCE {
        tnSysIpAclNetIfFilterDir            INTEGER,
        tnSysIpAclNetIfFilterRowStatus      RowStatus,
        tnSysIpAclNetIfFilterID             SnmpAdminString,
        tnSysIpAclNetIfFilterEnable         INTEGER,
        tnSysIpAclNetIfFilterSystemDefault  TruthValue
    }

    tnSysIpAclNetIfFilterDir OBJECT-TYPE
        SYNTAX         INTEGER {
                         rx(1),
                         tx(2)
                       }
        MAX-ACCESS     not-accessible
        STATUS         current
        DESCRIPTION    "Direction on the specified NetIf to which the IP
                        ACL filter will be associated."
        ::= { tnSysIpAclNetIfFilterEntry 1 }

    tnSysIpAclNetIfFilterRowStatus OBJECT-TYPE
        SYNTAX         RowStatus
        MAX-ACCESS     read-create
        STATUS         current
        DESCRIPTION    "The status of NetIf  Filter.  Set to 4 (createAndGo)
                        to add filter in the interface.
                        Set to 6 (destroy) to remove the filter in
                        the interface."
        ::= { tnSysIpAclNetIfFilterEntry 2 }

    tnSysIpAclNetIfFilterID OBJECT-TYPE
        SYNTAX         SnmpAdminString (SIZE(0..30))
        MAX-ACCESS     read-create
        STATUS         current
        DESCRIPTION    "Identifier for the ACL filter being associated
                        with the specified NetIf  and direction.  It
                        could be either an integer in the range of
                        (100-199) or a string of up to 30 case-sensitive
                        alphanumeric characters, where the first character
                        is always a letter, representing an existing ACL
                        Filter."
        ::= { tnSysIpAclNetIfFilterEntry 3 }

    tnSysIpAclNetIfFilterEnable OBJECT-TYPE
        SYNTAX         INTEGER {
                         enable(1),
                         disable(2)
                       }
        MAX-ACCESS     read-create
        STATUS         current
        DESCRIPTION    "Enable or disable the IP ACL filter associated
                        with the specified NetIf  and direction."
        DEFVAL         { disable }
        ::= { tnSysIpAclNetIfFilterEntry 4 }

    tnSysIpAclNetIfFilterSystemDefault OBJECT-TYPE
        SYNTAX         TruthValue
        MAX-ACCESS     read-only
        STATUS         current
        DESCRIPTION    "Indicates if ACL NetIf is added by the system
                        or a user.  Valid values are:
                          true  - ACL interface is added by the system.
                          false - ACL interface is added by a user."
        ::= { tnSysIpAclNetIfFilterEntry 5 }

--------------------------------------------------------------------------------
-- IPV6 Access Control List (ACL) Pattern Scalars
--------------------------------------------------------------------------------
    tnSysIpAclIpv6PatternAttributeTotal OBJECT-TYPE
        SYNTAX         Integer32
        MAX-ACCESS     read-only
        STATUS         current
        DESCRIPTION    "."
        ::= { tnSysAccessControlList 10 }

--------------------------------------------------------------------------------
-- IPV6 Access Control List (ACL) Pattern
--------------------------------------------------------------------------------
    tnSysIpAclIpv6PatternTable OBJECT-TYPE
        SYNTAX         SEQUENCE OF TnSysIpAclIpv6PatternEntry
        MAX-ACCESS     not-accessible
        STATUS         current
        DESCRIPTION    "Table of IPV6 ACL pattern.  An ACL pattern is a
                        set of packet field descriptors that can be
                        tested against a packet.  For a pattern to
                        match, each of its field descriptors must fit
                        the data in the packet."
        ::= { tnSysAccessControlList 11 }

    tnSysIpAclIpv6PatternEntry OBJECT-TYPE
        SYNTAX         TnSysIpAclIpv6PatternEntry
        MAX-ACCESS     not-accessible
        STATUS         current
        DESCRIPTION    "."
        INDEX { tnSysIpAclIpv6PatternID }
        ::= { tnSysIpAclIpv6PatternTable 1 }

    TnSysIpAclIpv6PatternEntry ::= SEQUENCE {
        tnSysIpAclIpv6PatternID               SnmpAdminString,
        tnSysIpAclIpv6PatternAction           INTEGER,
        tnSysIpAclIpv6PatternICMPV6ERROR      TruthValue,
        tnSysIpAclIpv6PatternSrcAddr          InetAddressIPv6,
        tnSysIpAclIpv6PatternSrcPrefixLen     InetAddressPrefixLength,
        tnSysIpAclIpv6PatternDestAddr         InetAddressIPv6,
        tnSysIpAclIpv6PatternDestPrefixLen    InetAddressPrefixLength,
        tnSysIpAclIpv6PatternIpProtocol       OCTET STRING,
        tnSysIpAclIpv6PatternIcmpType         Integer32,
        tnSysIpAclIpv6PatternIcmpCode         Integer32,
        tnSysIpAclIpv6PatternSrcPort          Integer32,
        tnSysIpAclIpv6PatternDestPort         Integer32,
        tnSysIpAclIpv6PatternIpFragment       TruthValue,
        tnSysIpAclIpv6PatternTcpEstablish     INTEGER,
        tnSysIpAclIpv6PatternSystemDefault    TruthValue,
        tnSysIpAclIpv6PatternRowStatus        RowStatus,
        tnSysIpAclIpv6PatternSrcPortRangeEnd  Integer32,
        tnSysIpAclIpv6PatternDestPortRangeEnd Integer32
      }

    tnSysIpAclIpv6PatternID OBJECT-TYPE
        SYNTAX         SnmpAdminString (SIZE(1..30))
        MAX-ACCESS     not-accessible
        STATUS         current
        DESCRIPTION    "The identifier of theIpv6 ACL pattern to be created.
                        It could be either an integer in the range of
                        (1-4000) or a string of up to 30 case-sensitive
                        alphanumeric characters, where the first character
                        is always a letter, which is selected by the user
                        to uniquely identify the pattern in subsequent
                        provisioning requests."
        ::= { tnSysIpAclIpv6PatternEntry 1 }

    tnSysIpAclIpv6PatternAction OBJECT-TYPE
        SYNTAX         INTEGER {
                       pass(1),
                       block(2),
                       log(3)
                       }
        MAX-ACCESS     read-create
        STATUS         current
        DESCRIPTION    "Action to be taken on packets matching the
                        specified Ipv6ACL pattern.  Valid values are:
                        pass  - allow the packet if it matches all the
                        pattern descriptors;
                        block - disallow the packet if it doesn't match
                        all the pattern descriptors.
                        log   - log the packet if it matches all the
                        pattern descriptors."
        ::= { tnSysIpAclIpv6PatternEntry 2 }

    tnSysIpAclIpv6PatternICMPV6ERROR OBJECT-TYPE
        SYNTAX         TruthValue
        MAX-ACCESS     read-create
        STATUS         current
        DESCRIPTION    "ICMPV6 error reporting behavior for blocked
                        packets.  If no icmpV6Error value is specified,
                        the behavior will be determined by the system
                        default setting.  Valid values are:
                        true  - send ICMPV6 error for blocked packets
                        false - do not send ICMPV6 error for blocked
                        packets."
        DEFVAL         { false }
        ::= { tnSysIpAclIpv6PatternEntry 3 }

    tnSysIpAclIpv6PatternSrcAddr OBJECT-TYPE
        SYNTAX         InetAddressIPv6
        MAX-ACCESS     read-create
        STATUS         current
        DESCRIPTION    "Source IPV6 address.  It can be specified
                        explicitly to match only packets that originate
                        from a particular address or can be used along
                        with the SrcPrefixLen parameter to specify a range
                        of supported originating IPV6 addresses."
        ::= { tnSysIpAclIpv6PatternEntry 4 }

    tnSysIpAclIpv6PatternSrcPrefixLen OBJECT-TYPE
        SYNTAX         InetAddressPrefixLength
        MAX-ACCESS     read-create
        STATUS         current
        DESCRIPTION    "Denotes the length of source IPV6 address prefix.
                        A value of n corresponds to an IP address maskthat
                        has n contiguous1-bits from the most significant
                        bit (MSB), with all other bits set to 0"
        ::= { tnSysIpAclIpv6PatternEntry 5 }

    tnSysIpAclIpv6PatternDestAddr OBJECT-TYPE
        SYNTAX         InetAddressIPv6
        MAX-ACCESS     read-create
        STATUS         current
        DESCRIPTION    "Destination IPV6 address.  It can be specified
                        explicitly to match only packets that originate
                        from a particular address or can be used along
                        with the DestPrefixLen parameter to specify a range
                        of supported destination IPV6 addresses."
        ::= { tnSysIpAclIpv6PatternEntry 6 }

    tnSysIpAclIpv6PatternDestPrefixLen OBJECT-TYPE
        SYNTAX         InetAddressPrefixLength
        MAX-ACCESS     read-create
        STATUS         current
        DESCRIPTION    "Denotes the length of destination IPV6 address prefix.
                        A value of n corresponds to an IP address maskthat
                        has n contiguous1-bits from the most significant
                        bit (MSB), with all other bits set to 0"
        ::= { tnSysIpAclIpv6PatternEntry 7 }

    tnSysIpAclIpv6PatternIpProtocol OBJECT-TYPE
        SYNTAX         OCTET STRING
        MAX-ACCESS     read-create
        STATUS         current
        DESCRIPTION    "IP Protocol.  It can be specified by explicit
                        protocol number (Integer, 0 to 255) or by keyword.
                        Some common protocol types are listed below:
                        ICMPv6  - IP protocol is ICMPv6 (58)
                        IPIP    - IP protocol is IPIP (41)
                        TCP     - IP protocol is TCP (6)
                        UDP     - IP protocol is UDP (17)
                        RSVP    - IP protocol is RSVP (46)
                        GRE     - IP protocol is GRE (47)
                        OSPFv3  - IP protocol is OSPFv3 (89)
                        <other protocol>  - Specify IP protocol number: 0 to 255"
        ::= { tnSysIpAclIpv6PatternEntry 8 }

    tnSysIpAclIpv6PatternIcmpType OBJECT-TYPE
        SYNTAX         Integer32 (0..255)
        MAX-ACCESS     read-create
        STATUS         current
        DESCRIPTION    "ICMPV6 Type identifier. If specified, the
                        pattern will match only packets with this exact
                        ICMPV6 type.  Some of the most commonly used ICMP
                        types are:
                        1    Destination Unreachable [RFC2463]
                        2    Packet Too Big
                        3    Time Exceeded
                        4    Parameter Problem
                        128  Echo Request(IPv6 pingcommand)
                        129  Echo Reply
                        133-137  Neighbor Discovery."
        ::= { tnSysIpAclIpv6PatternEntry 9 }

    tnSysIpAclIpv6PatternIcmpCode OBJECT-TYPE
        SYNTAX         Integer32 (0..255)
        MAX-ACCESS     read-create
        STATUS         current
        DESCRIPTION    "ICMPV6code field.  It is used along with certain
                        ICMPV6 types to further specify the message type.
                        For example, some of the codes used with
                        ICMPv6 Type 1 (Destination Unreachable) are
                        0       no route to destination
                        1       communication with destination administratively prohibited
                        2       beyond scope of source address
                        3       address unreachable
                        4       port unreachable
                        5       source address failed ingress/egress policy
                        6       reject route to destination
                        7       Error in Source Routing Header
                        If specified, the pattern will only match packets with
                        this exact ICMPV6 codevalue. [RFC2463]"
        ::= { tnSysIpAclIpv6PatternEntry 10 }

    tnSysIpAclIpv6PatternSrcPort OBJECT-TYPE
        SYNTAX         Integer32 (0..65535)
        MAX-ACCESS     read-create
        STATUS         current
        DESCRIPTION    "TCP/UDP source port. When rangeEnd not zero,
                        it is used as range start."
        ::= { tnSysIpAclIpv6PatternEntry 11 }

    tnSysIpAclIpv6PatternDestPort OBJECT-TYPE
        SYNTAX         Integer32 (0..65535)
        MAX-ACCESS     read-create
        STATUS         current
        DESCRIPTION    "TCP/UDP destination port. When rangeEnd not zero,
                        it is used as range start."
        ::= { tnSysIpAclIpv6PatternEntry 12 }

    tnSysIpAclIpv6PatternIpFragment OBJECT-TYPE
        SYNTAX         TruthValue
        MAX-ACCESS     read-create
        STATUS         current
        DESCRIPTION    "IP Fragmentation.  True means that the filtering
                        is done on all fragments, not just on the initial
                        one (assuming the following ones are ok).  Valid
                        values are:
                        true  - pattern is an IP
                        false - pattern is not an IP fragment."
        DEFVAL         { false }
        ::= { tnSysIpAclIpv6PatternEntry 13 }

    tnSysIpAclIpv6PatternTcpEstablish OBJECT-TYPE
        SYNTAX         INTEGER {
                         true(1),
                         false(2),
                         local(3)
                       }
        MAX-ACCESS     read-create
        STATUS         current
        DESCRIPTION    "TCP established flag.  It matches a packet depending on
                        whether the TCP flags in the IP header correspond to the
                        established state.  Valid values are:
                        true  - TCP flags correspond to established state
                        false - TCP flags do not correspond to established
                        local - TCP flags correspond to established state
                                only for destination to local NE."
        ::= { tnSysIpAclIpv6PatternEntry 14 }

    tnSysIpAclIpv6PatternSystemDefault OBJECT-TYPE
        SYNTAX         TruthValue
        MAX-ACCESS     read-only
        STATUS         current
        DESCRIPTION    "Indicates if ACLIPV6 pattern is added by the system
                        or a user.  Valid values are:
                        true  - ACL pattern is added by the system.
                        false - ACL pattern is added by the user."
        ::= { tnSysIpAclIpv6PatternEntry 15 }

    tnSysIpAclIpv6PatternRowStatus OBJECT-TYPE
        SYNTAX         RowStatus
        MAX-ACCESS     read-create
        STATUS         current
        DESCRIPTION    "The status of pattern.
                        Set to 4 (createAndGo) to add pattern.
                        Set to 6 (destroy) to remove the pattern."
        ::= { tnSysIpAclIpv6PatternEntry 16 }

    tnSysIpAclIpv6PatternSrcPortRangeEnd OBJECT-TYPE
        SYNTAX         Integer32 (0..65535)
        MAX-ACCESS     read-create
        STATUS         current
        DESCRIPTION    "TCP/UDP source port range end."
        ::= { tnSysIpAclIpv6PatternEntry 17 }

    tnSysIpAclIpv6PatternDestPortRangeEnd OBJECT-TYPE
        SYNTAX         Integer32 (0..65535)
        MAX-ACCESS     read-create
        STATUS         current
        DESCRIPTION    "TCP/UDP destination port range end."
        ::= { tnSysIpAclIpv6PatternEntry 18 }

--------------------------------------------------------------------------------
-- IPV6 Access Control List (ACL) Filter Scalar
--------------------------------------------------------------------------------
    tnSysIpAclIpv6FilterAttributeTotal OBJECT-TYPE
        SYNTAX         Integer32
        MAX-ACCESS     read-only
        STATUS         current
        DESCRIPTION    "."
        ::= { tnSysAccessControlList 12  }

--------------------------------------------------------------------------------
-- IPV6 Access Control List (ACL) Filter
--------------------------------------------------------------------------------
    tnSysIpAclIpv6FilterTable OBJECT-TYPE
        SYNTAX         SEQUENCE OF TnSysIpAclIpv6FilterEntry
        MAX-ACCESS     not-accessible
        STATUS         current
        DESCRIPTION    "An ACL filter is an ordered list of patterns.
                        A filter consists of a sorted list of (index,
                        pattern) pairs, where the index indicates the
                        relative position on the list and the pattern
                        indicates the pattern identifier.  Up to 100
                        filters may be defined on the system, and each
                        filter may contain up to 256 (index, pattern)
                        pairs."
        ::= { tnSysAccessControlList 13 }

    tnSysIpAclIpv6FilterEntry OBJECT-TYPE
        SYNTAX         TnSysIpAclIpv6FilterEntry
        MAX-ACCESS     not-accessible
        STATUS         current
        DESCRIPTION    "."
        INDEX { tnSysIpAclIpv6FilterID,
                tnSysIpAclIpv6FilterPatternIndex }
        ::= { tnSysIpAclIpv6FilterTable 1 }

    TnSysIpAclIpv6FilterEntry ::= SEQUENCE {
        tnSysIpAclIpv6FilterID               SnmpAdminString,
        tnSysIpAclIpv6FilterPatternIndex     Integer32,
        tnSysIpAclIpv6FilterPatternID        SnmpAdminString,
        tnSysIpAclIpv6FilterStatCount        Counter32,
        tnSysIpAclIpv6FilterRowStatus        RowStatus,
        tnSysIpAclIpv6FilterSystemDefault    TruthValue
    }
    tnSysIpAclIpv6FilterID OBJECT-TYPE
        SYNTAX         SnmpAdminString (SIZE(1..30))
        MAX-ACCESS     not-accessible
        STATUS         current
        DESCRIPTION    "Identifier for the ACL filter being defined.
                        It could be either an integer in the range of
                        (100-199) or a string of up to 30 case-sensitive
                        alphanumeric characters, where the first
                        character is always a letter, which uniquely
                        identifies the filter being defined."
        ::= { tnSysIpAclIpv6FilterEntry 1 }

    tnSysIpAclIpv6FilterPatternIndex OBJECT-TYPE
        SYNTAX         Integer32 (0..256)
        MAX-ACCESS     not-accessible
        STATUS         current
        DESCRIPTION    "The values of 1 to 256 represent the insertion
                        point for the specified pattern on the filter
                        list.  If there is already a pattern defined at
                        the specified index, the new pattern entry will
                        replace the previous one.  The value of 0
                        represents user input filterID without giving
                        the pattern index.  Front end users will use 0
                        for setting."
        ::= { tnSysIpAclIpv6FilterEntry 2 }

    tnSysIpAclIpv6FilterPatternID OBJECT-TYPE
        SYNTAX         SnmpAdminString (SIZE(0..30))
        MAX-ACCESS     read-create
        STATUS         current
        DESCRIPTION    "The identifier of the ACL pattern being added
                        to or removed from the specified filter.  It
                        could be either an integer in the range of
                        (1-4000) or a string of up to 30 case-sensitive
                        alphanumeric characters, where the first
                        character is always a letter, which is selected
                        by the user to uniquely identify the pattern in
                        subsequent provisioning requests."
        ::= { tnSysIpAclIpv6FilterEntry 3 }

    tnSysIpAclIpv6FilterStatCount OBJECT-TYPE
        SYNTAX         Counter32
        MAX-ACCESS     read-only
        STATUS         current
        DESCRIPTION    "Packet match counter.  It is incremented whenever
                        a packet matches the specified ACL pattern in the
                        filter.  This counter will be incremented
                        regardless of the provisioned action on that
                        pattern."
        ::= { tnSysIpAclIpv6FilterEntry 4 }

    tnSysIpAclIpv6FilterRowStatus OBJECT-TYPE
        SYNTAX         RowStatus
        MAX-ACCESS     read-create
        STATUS         current
        DESCRIPTION    "Action to take on the specified filter.  The
                        operator could add or remove a pattern from a
                        specified filter.  Set to 4 (createAndGo) to
                        add pattern in the filter.  Set to 6 (destroy)
                        to remove the pattern in the filter."
        ::= { tnSysIpAclIpv6FilterEntry 5 }

    tnSysIpAclIpv6FilterSystemDefault OBJECT-TYPE
        SYNTAX         TruthValue
        MAX-ACCESS     read-only
        STATUS         current
        DESCRIPTION    "Indicates if ACL filter is added by the system
                        or a user.  Valid values are:
                          true  - ACL filter is added by the system.
                          false - ACL filter is added by a user."
        ::= { tnSysIpAclIpv6FilterEntry 6 }

--------------------------------------------------------------------------------
-- IPV6 Access Control List (ACL) Interface
--------------------------------------------------------------------------------
    tnSysIpAclIpv6InterfaceAttributeTotal OBJECT-TYPE
        SYNTAX         Integer32
        MAX-ACCESS     read-only
        STATUS         current
        DESCRIPTION    "."
        ::= { tnSysAccessControlList 14 }

--------------------------------------------------------------------------------
-- IPV6 Access Control List (ACL) Interface
--------------------------------------------------------------------------------
    tnSysIpAclIpv6InterfaceTable OBJECT-TYPE
        SYNTAX         SEQUENCE OF TnSysIpAclIpv6InterfaceEntry
        MAX-ACCESS     not-accessible
        STATUS         current
        DESCRIPTION    "The IP ACL interface table is used to associate
                        or disassociate filters with particular physical
                        network interfaces (but not logical sub-interfaces).
                        Two filters may be associated with each interface,
                        one receive and one transmit.  The receive and
                        transmit filters on an interface may be
                        independently enabled and disabled on that
                        interface without disassociating the specific
                        filter numbers."
        ::= { tnSysAccessControlList 15 }

    tnSysIpAclIpv6InterfaceEntry OBJECT-TYPE
        SYNTAX         TnSysIpAclIpv6InterfaceEntry
        MAX-ACCESS     not-accessible
        STATUS         current
        DESCRIPTION    "."
        INDEX { ifIndex,
                tnSysIpAclIpv6InterfaceFilterDir }
        ::= { tnSysIpAclIpv6InterfaceTable 1 }

    TnSysIpAclIpv6InterfaceEntry ::= SEQUENCE {
        tnSysIpAclIpv6InterfaceFilterDir           INTEGER,
        tnSysIpAclIpv6InterfaceFilterID            SnmpAdminString,
        tnSysIpAclIpv6InterfaceFilterEnable        INTEGER,
        tnSysIpAclIpv6InterfaceFilterRowStatus     RowStatus,
        tnSysIpAclIpv6InterfaceSystemDefault       TruthValue,
        tnSysIpAclIpv6InterfaceFilterLog           INTEGER
    }

    tnSysIpAclIpv6InterfaceFilterDir OBJECT-TYPE
        SYNTAX         INTEGER {
                         rx(1),
                         tx(2)
                       }
        MAX-ACCESS     not-accessible
        STATUS         current
        DESCRIPTION    "Direction on the specified network interface
                        to which the IP ACL filter will be associated."
        ::= { tnSysIpAclIpv6InterfaceEntry 1 }

    tnSysIpAclIpv6InterfaceFilterID OBJECT-TYPE
        SYNTAX         SnmpAdminString (SIZE(0..30))
        MAX-ACCESS     read-create
        STATUS         current
        DESCRIPTION    "Identifier for the ACL filter being associated
                        with the specified interface and direction.  It
                        could be either an integer in the range of
                        (100-199) or a string of up to 30 case-sensitive
                        alphanumeric characters, where the first character
                        is always a letter, representing an existing ACL
                        Filter."
        ::= { tnSysIpAclIpv6InterfaceEntry 2 }

    tnSysIpAclIpv6InterfaceFilterEnable OBJECT-TYPE
        SYNTAX         INTEGER {
                         enable(1),
                         disable(2)
                       }
        MAX-ACCESS     read-create
        STATUS         current
        DESCRIPTION    "Enable or disable the IP ACL filter associated
                        with the specified interface and direction."
        DEFVAL         { disable }
        ::= { tnSysIpAclIpv6InterfaceEntry 3 }

    tnSysIpAclIpv6InterfaceFilterRowStatus OBJECT-TYPE
        SYNTAX         RowStatus
        MAX-ACCESS     read-create
        STATUS         current
        DESCRIPTION    "The status of Interface Filter.  Set to 4
                        (createAndGo) to add filter in the interface.
                        Set to 6 (destroy) to remove the filter in
                        the interface."
        ::= { tnSysIpAclIpv6InterfaceEntry 4 }

    tnSysIpAclIpv6InterfaceSystemDefault OBJECT-TYPE
        SYNTAX         TruthValue
        MAX-ACCESS     read-only
        STATUS         current
        DESCRIPTION    "Indicates if ACL interface added by the system
                        or a user.  Valid values are:
                          true  - ACL interface is added by the system.
                          false - ACL interface is added by a user."
        ::= { tnSysIpAclIpv6InterfaceEntry 5 }

    tnSysIpAclIpv6InterfaceFilterLog OBJECT-TYPE
        SYNTAX         INTEGER {
                         enable(1),
                         disable(2)
                       }
        MAX-ACCESS     read-create
        STATUS         current
        DESCRIPTION    "Enable or disable the IPV6 ACL filter logging
                        on specified interface and direction."
        DEFVAL         { disable }
        ::= { tnSysIpAclIpv6InterfaceEntry 6 }

--------------------------------------------------------------------------------
-- IPV6 Access Control List (ACL) Network Interface
--------------------------------------------------------------------------------
    tnSysIpv6AclNetIfFilterAttributeTotal OBJECT-TYPE
        SYNTAX         Integer32
        MAX-ACCESS     read-only
        STATUS         current
        DESCRIPTION    "."
        ::= { tnSysAccessControlList 16 }

--------------------------------------------------------------------------------
-- IPV6 Access Control List (ACL) Network Interface
--------------------------------------------------------------------------------
    tnSysIpv6AclNetIfFilterTable OBJECT-TYPE
        SYNTAX         SEQUENCE OF TnSysIpv6AclNetIfFilterEntry
        MAX-ACCESS     not-accessible
        STATUS         current
        DESCRIPTION    "The IP ACL NetIf table is used to associate or
                        disassociate filters with particular NetIf.  Two
                        filters may be associated with each NetIf, one
                        receive and one transmit.  The receive and transmit
                        filters on an NetIf may be independently enabled
                        and disabled on that NetIf without disassociating
                        the specific filter numbers."
        ::= { tnSysAccessControlList 17 }

    tnSysIpv6AclNetIfFilterEntry OBJECT-TYPE
        SYNTAX         TnSysIpv6AclNetIfFilterEntry
        MAX-ACCESS     not-accessible
        STATUS         current
        DESCRIPTION    "."
        INDEX { tnNetIfIndex,
                tnSysIpv6AclNetIfFilterDir}
        ::= { tnSysIpv6AclNetIfFilterTable 1 }

    TnSysIpv6AclNetIfFilterEntry ::= SEQUENCE {
        tnSysIpv6AclNetIfFilterDir            INTEGER,
        tnSysIpv6AclNetIfFilterRowStatus      RowStatus,
        tnSysIpv6AclNetIfFilterID             SnmpAdminString,
        tnSysIpv6AclNetIfFilterEnable         INTEGER,
        tnSysIpv6AclNetIfFilterSystemDefault  TruthValue
    }

    tnSysIpv6AclNetIfFilterDir OBJECT-TYPE
        SYNTAX         INTEGER {
                         rx(1),
                         tx(2)
                       }
        MAX-ACCESS     not-accessible
        STATUS         current
        DESCRIPTION    "Direction on the specified NetIf to which the IP
                        ACL filter will be associated."
        ::= { tnSysIpv6AclNetIfFilterEntry 1 }

    tnSysIpv6AclNetIfFilterRowStatus OBJECT-TYPE
        SYNTAX         RowStatus
        MAX-ACCESS     read-create
        STATUS         current
        DESCRIPTION    "The status of NetIf  Filter.  Set to 4 (createAndGo)
                        to add filter in the interface.
                        Set to 6 (destroy) to remove the filter in
                        the interface."
        ::= { tnSysIpv6AclNetIfFilterEntry 2 }

    tnSysIpv6AclNetIfFilterID OBJECT-TYPE
        SYNTAX         SnmpAdminString (SIZE(0..30))
        MAX-ACCESS     read-create
        STATUS         current
        DESCRIPTION    "Identifier for the ACL filter being associated
                        with the specified NetIf  and direction.  It
                        could be either an integer in the range of
                        (100-199) or a string of up to 30 case-sensitive
                        alphanumeric characters, where the first character
                        is always a letter, representing an existing ACL
                        Filter."
        ::= { tnSysIpv6AclNetIfFilterEntry 3 }

    tnSysIpv6AclNetIfFilterEnable OBJECT-TYPE
        SYNTAX         INTEGER {
                         enable(1),
                         disable(2)
                       }
        MAX-ACCESS     read-create
        STATUS         current
        DESCRIPTION    "Enable or disable the IP ACL filter associated
                        with the specified NetIf  and direction."
        DEFVAL         { disable }
        ::= { tnSysIpv6AclNetIfFilterEntry 4 }

    tnSysIpv6AclNetIfFilterSystemDefault OBJECT-TYPE
        SYNTAX         TruthValue
        MAX-ACCESS     read-only
        STATUS         current
        DESCRIPTION    "Indicates if ACL NetIf is added by the system
                        or a user.  Valid values are:
                          true  - ACL interface is added by the system.
                          false - ACL interface is added by a user."
        ::= { tnSysIpv6AclNetIfFilterEntry 5 }

--------------------------------------------------------------------------------
-- IP Access Control List (ACL) Ethernet IBM Interface Scalars
--------------------------------------------------------------------------------
    tnSysIpAclEthIfFilterAttributeTotal OBJECT-TYPE
        SYNTAX         Integer32
        MAX-ACCESS     read-only
        STATUS         current
        DESCRIPTION    "."
        ::= { tnSysAccessControlList 18 }

--------------------------------------------------------------------------------
-- IP Access Control List (ACL) Ethernet IBM Interface
--------------------------------------------------------------------------------
    tnSysIpAclEthIfFilterTable OBJECT-TYPE
        SYNTAX         SEQUENCE OF TnSysIpAclEthIfFilterEntry
        MAX-ACCESS     not-accessible
        STATUS         current
        DESCRIPTION    "The IP ACL EthIf table is used to associate or
                        disassociate filters with particular EthIf.  Two
                        filters may be associated with each EthIf, one
                        receive and one transmit.  The receive and transmit
                        filters on an EthIf may be independently enabled
                        and disabled on that EthIf without disassociating
                        the specific filter numbers."
        ::= { tnSysAccessControlList 19 }

    tnSysIpAclEthIfFilterEntry OBJECT-TYPE
        SYNTAX         TnSysIpAclEthIfFilterEntry
        MAX-ACCESS     not-accessible
        STATUS         current
        DESCRIPTION    "."
        INDEX { tnEthIfIndex,
                tnSysIpAclEthIfFilterDir}
        ::= { tnSysIpAclEthIfFilterTable 1 }

    TnSysIpAclEthIfFilterEntry ::= SEQUENCE {
        tnSysIpAclEthIfFilterDir               INTEGER,
        tnSysIpAclEthIfFilterRowStatus         RowStatus,
        tnSysIpAclEthIfFilterID                SnmpAdminString,
        tnSysIpAclEthIfFilterEnable            INTEGER,
        tnSysIpAclEthIfFilterSystemDefault     TruthValue
    }

    tnSysIpAclEthIfFilterDir OBJECT-TYPE
        SYNTAX         INTEGER {
                         rx(1),
                         tx(2)
                       }
        MAX-ACCESS     not-accessible
        STATUS         current
        DESCRIPTION    "Direction on the specified EthIf to which the IP
                        ACL filter will be associated."
        ::= { tnSysIpAclEthIfFilterEntry 1 }

    tnSysIpAclEthIfFilterRowStatus OBJECT-TYPE
        SYNTAX         RowStatus
        MAX-ACCESS     read-create
        STATUS         current
        DESCRIPTION    "The status of EthIf  Filter.  Set to 4 (createAndGo)
                        to add filter in the interface.
                        Set to 6 (destroy) to remove the filter in
                        the interface."
        ::= { tnSysIpAclEthIfFilterEntry 2 }

    tnSysIpAclEthIfFilterID OBJECT-TYPE
        SYNTAX         SnmpAdminString (SIZE(0..30))
        MAX-ACCESS     read-create
        STATUS         current
        DESCRIPTION    "Identifier for the ACL filter being associated
                        with the specified EthIf  and direction.  It
                        could be either an integer in the range of
                        (100-199) or a string of up to 30 case-sensitive
                        alphanumeric characters, where the first character
                        is always a letter, representing an existing ACL
                        Filter."
        ::= { tnSysIpAclEthIfFilterEntry 3 }

    tnSysIpAclEthIfFilterEnable OBJECT-TYPE
        SYNTAX         INTEGER {
                         enable(1),
                         disable(2)
                       }
        MAX-ACCESS     read-create
        STATUS         current
        DESCRIPTION    "Enable or disable the IP ACL filter associated
                        with the specified EthIf  and direction."
        DEFVAL         { disable }
        ::= { tnSysIpAclEthIfFilterEntry 4 }

    tnSysIpAclEthIfFilterSystemDefault OBJECT-TYPE
        SYNTAX         TruthValue
        MAX-ACCESS     read-only
        STATUS         current
        DESCRIPTION    "Indicates if ACL EthIf is added by the system
                        or a user.  Valid values are:
                          true  - ACL interface is added by the system.
                          false - ACL interface is added by a user."
        ::= { tnSysIpAclEthIfFilterEntry 5 }

--------------------------------------------------------------------------------
-- IPv6 Access Control List (ACL) Ethernet IBM Interface Scalars
--------------------------------------------------------------------------------
    tnSysIpv6AclEthIfFilterAttributeTotal OBJECT-TYPE
        SYNTAX         Integer32
        MAX-ACCESS     read-only
        STATUS         current
        DESCRIPTION    "."
        ::= { tnSysAccessControlList 20 }

--------------------------------------------------------------------------------
-- IPv6 Access Control List (ACL) Ethernet IBM Interface
--------------------------------------------------------------------------------
    tnSysIpv6AclEthIfFilterTable OBJECT-TYPE
        SYNTAX         SEQUENCE OF TnSysIpv6AclEthIfFilterEntry
        MAX-ACCESS     not-accessible
        STATUS         current
        DESCRIPTION    "The IPV6 ACL EthIf table is used to associate or
                        disassociate filters with particular EthIf.  Two
                        filters may be associated with each EthIf, one
                        receive and one transmit.  The receive and transmit
                        filters on an EthIf may be independently enabled
                        and disabled on that EthIf without disassociating
                        the specific filter numbers."
        ::= { tnSysAccessControlList 21 }

    tnSysIpv6AclEthIfFilterEntry OBJECT-TYPE
        SYNTAX         TnSysIpv6AclEthIfFilterEntry
        MAX-ACCESS     not-accessible
        STATUS         current
        DESCRIPTION    "."
        INDEX { tnEthIfIndex,
                tnSysIpv6AclEthIfFilterDir }
        ::= { tnSysIpv6AclEthIfFilterTable 1 }

    TnSysIpv6AclEthIfFilterEntry ::= SEQUENCE {
        tnSysIpv6AclEthIfFilterDir            INTEGER,
        tnSysIpv6AclEthIfFilterRowStatus      RowStatus,
        tnSysIpv6AclEthIfFilterID             SnmpAdminString,
        tnSysIpv6AclEthIfFilterEnable         INTEGER,
        tnSysIpv6AclEthIfFilterSystemDefault  TruthValue
    }

    tnSysIpv6AclEthIfFilterDir OBJECT-TYPE
        SYNTAX         INTEGER {
                         rx(1),
                         tx(2)
                       }
        MAX-ACCESS     not-accessible
        STATUS         current
        DESCRIPTION    "Direction on the specified EthIf to which the IP
                        ACL filter will be associated."
        ::= { tnSysIpv6AclEthIfFilterEntry 1 }

    tnSysIpv6AclEthIfFilterRowStatus OBJECT-TYPE
        SYNTAX         RowStatus
        MAX-ACCESS     read-create
        STATUS         current
        DESCRIPTION    "The status of EthIf  Filter.  Set to 4 (createAndGo)
                        to add filter in the interface.
                        Set to 6 (destroy) to remove the filter in the
                        interface."
        ::= { tnSysIpv6AclEthIfFilterEntry 2 }

    tnSysIpv6AclEthIfFilterID OBJECT-TYPE
        SYNTAX         SnmpAdminString (SIZE(0..30))
        MAX-ACCESS     read-create
        STATUS         current
        DESCRIPTION    "Identifier for the ACL filter being associated with
                        the specified EthIf and direction.  It could be
                        either an integer in the range of (100-199) or a
                        string of up to 30 case-sensitive alphanumeric
                        characters, where the first character is always a
                        letter, representing an existing ACL Filter."
        ::= { tnSysIpv6AclEthIfFilterEntry 3 }

    tnSysIpv6AclEthIfFilterEnable OBJECT-TYPE
        SYNTAX         INTEGER {
                         enable(1),
                         disable(2)
                       }
        MAX-ACCESS     read-create
        STATUS         current
        DESCRIPTION    "Enable or disable the IPV6 ACL filter associated
                        with the specified EthIf and direction."
        DEFVAL         { disable }
        ::= { tnSysIpv6AclEthIfFilterEntry 4 }

    tnSysIpv6AclEthIfFilterSystemDefault OBJECT-TYPE
        SYNTAX         TruthValue
        MAX-ACCESS     read-only
        STATUS         current
        DESCRIPTION    "Indicates if ACL EthIf is added by the system
                        or a user.  Valid values are:
                          true  - ACL interface is added by the system.
                          false - ACL interface is added by a user."
        ::= { tnSysIpv6AclEthIfFilterEntry 5 }

--------------------------------------------------------------------------------
-- IP Access Control List (ACL) Ipv4 Scalar
--------------------------------------------------------------------------------
    tnSysIpAclAttributeTotal OBJECT-TYPE
        SYNTAX         Integer32
        MAX-ACCESS     read-only
        STATUS         current
        DESCRIPTION    "This parameter indicates the total IPACL rules can be
                        supported in tnSysIpAclTable."
        ::= { tnSysAccessControlList 22 }

--------------------------------------------------------------------------------
-- IP Access Control List (ACL) Ipv4
--------------------------------------------------------------------------------
    tnSysIpAclTable OBJECT-TYPE
        SYNTAX         SEQUENCE OF TnSysIpAclEntry
        MAX-ACCESS     not-accessible
        STATUS         current
        DESCRIPTION    "Table of IP ACL rule.  An ACL rule is a set of packet
                        field descriptors that can be tested against a packet.
                        For a rule to match, each of its field descriptors must
                        fit the data in the packet."
        ::= { tnSysAccessControlList 23 }

    tnSysIpAclEntry OBJECT-TYPE
        SYNTAX         TnSysIpAclEntry
        MAX-ACCESS     not-accessible
        STATUS         current
        DESCRIPTION    "."
        INDEX { tnSysIpAclIndex }
        ::= { tnSysIpAclTable 1 }

    TnSysIpAclEntry ::= SEQUENCE {
        tnSysIpAclIndex                   Integer32,
        tnSysIpAclDesc                    SnmpAdminString,
        tnSysIpAclAccessID                SnmpAdminString,
        tnSysIpAclInterface               Unsigned32,
        tnSysIpAclAction                  INTEGER,
        tnSysIpAclSrcPort                 SnmpAdminString,
        tnSysIpAclDestPort                SnmpAdminString,
        tnSysIpAclIcmpType                Integer32,
        tnSysIpAclIcmpCode                Integer32,
        tnSysIpAclIpProtocol              OCTET STRING,
        tnSysIpAclSrcAddr                 IpAddress,
        tnSysIpAclSrcPrefix               Integer32,
        tnSysIpAclDestAddr                IpAddress,
        tnSysIpAclDestPrefix              Integer32,
        tnSysIpAclIpFragment              TruthValue,
        tnSysIpAclTcpEstablish            INTEGER,
        tnSysIpAclStatCount               Counter32,
        tnSysIpAclAdminState              INTEGER
    }

    tnSysIpAclIndex OBJECT-TYPE
        SYNTAX         Integer32
        MAX-ACCESS     not-accessible
        STATUS         current
        DESCRIPTION    "The values of 1 to 512 represent the index of IPACL.
                        Default is the number of existing rules + 1, or a number
                        between 1 and the number of existing rules (in this case
                        existing rules after indes will be shifted to index + 1).
                        For modify: an index of an existing rule.
                        For delete: a delete will shift existing rules after
                            index to index - 1.
                        The maximum number of ACL rules is 512.
                        The valid index range is from 1 to 512.
                        If index is not provided by CLI/NMS when a new rule is
                            added, index 65535 shall be used, NE SW will add a
                            new rule using the index with the number of existing
                            rules + 1."
        ::= { tnSysIpAclEntry 1 }

    tnSysIpAclDesc OBJECT-TYPE
        SYNTAX         SnmpAdminString (SIZE(0..255))
        MAX-ACCESS     read-create
        STATUS         current
        DESCRIPTION    "Short description about the purpose of this rule."
        DEFVAL         { "" }
        ::= { tnSysIpAclEntry 2 }

    tnSysIpAclAccessID OBJECT-TYPE
        SYNTAX         SnmpAdminString (SIZE(1..30))
        MAX-ACCESS     read-create
        STATUS         current
        DESCRIPTION    "The access ID of the ACL to be created.  It could be one
                        of the following strings: SSH, MAINTSSH, ALTCLI, SNMP,
                        DHCP, OA, GNMIGRPC, RADIUS, NTP, OSPF, ICMP, TRACERT,
                        MCLAG, SYSLOGU, SFTPC or IP."
        ::= { tnSysIpAclEntry 3 }

    tnSysIpAclInterface OBJECT-TYPE
        SYNTAX         Unsigned32 (0..64)
        MAX-ACCESS     read-create
        STATUS         current
        DESCRIPTION    "Access identifier for the interface Index.  It could be
                        one of the following cases:
                        - 41: All
                        - 42: LAN=LAN1+LAN2
                        - 43: All ETHIF
                        - Ifindex of LAN1
                        - ifindex of LAN2
                        - ifindex of CIT
                        - tnEthIfIndex of EthIF, 1...30 for TPS-24; 1...14 for TPS-12."
        ::= { tnSysIpAclEntry 4 }

    tnSysIpAclAction OBJECT-TYPE
        SYNTAX         INTEGER {
                         accept(1),
                         drop(2),
                         reject(3),
                         log(4)
                       }
        MAX-ACCESS     read-create
        STATUS         current
        DESCRIPTION    "Action to be taken on packets matching the specified ACL
                        pattern.  Valid values are:
                        accept - allow the packet if it matches all the pattern
                                 descriptors
                        drop   - matching packets are discarded
                        reject - matching packets are discarded; an ICMP error
                                 message is sent back
                        log    - log the packet if it matches all the pattern
                                 descriptors."
        ::= { tnSysIpAclEntry 5 }

    tnSysIpAclSrcPort OBJECT-TYPE
        SYNTAX         SnmpAdminString (SIZE(1..15))
        MAX-ACCESS     read-create
        STATUS         current
        DESCRIPTION    "TCP/UDP source port.  It can be a range[0-65535:0-65535]."
        ::= { tnSysIpAclEntry 6 }

    tnSysIpAclDestPort OBJECT-TYPE
        SYNTAX         SnmpAdminString (SIZE(1..15))
        MAX-ACCESS     read-create
        STATUS         current
        DESCRIPTION    "TCP/UDP destination port.  It can be a range[0-65535:0-65535]."
        ::= { tnSysIpAclEntry 7 }

    tnSysIpAclIcmpType OBJECT-TYPE
        SYNTAX         Integer32 (0..255)
        MAX-ACCESS     read-create
        STATUS         current
        DESCRIPTION    "ICMP Type identifier.  It is applicable only when
                        IPPROTOCOL is ICMP.  If specified, the pattern will
                        match only packets with this exact ICMP type.  Some
                        of the most commonly used ICMP types are:
                        0       Echo Reply [RFC792]
                        3       Destination Unreachable[RFC792]
                        5       Redirect[RFC792]
                        9       Router Advertisement[RFC1256]
                        42-255  Reserved."
        ::= { tnSysIpAclEntry 8 }

    tnSysIpAclIcmpCode OBJECT-TYPE
        SYNTAX         Integer32 (0..255)
        MAX-ACCESS     read-create
        STATUS         current
        DESCRIPTION    "ICMP code field.  It is applicable only when IP protocol
                        is ICMP and is used along with certain ICMP types to
                        further specify the message type.  It must also specify
                        the ICMP type when setting this parameter.  If specified,
                        the pattern will only match packets with this exact ICMP
                        code value.  For example, there are a few ICMPCODEs
                        associated with the ICMPTYPE Redirect [RFC792]:
                        0  Redirect Datagram for the Network (or subnet)
                        1  Redirect Datagram for the Host
                        2  Redirect Datagram for the Type of Service and Network
                        3  Redirect Datagram for the Type of Service and Host."
        ::= { tnSysIpAclEntry 9 }

    tnSysIpAclIpProtocol OBJECT-TYPE
        SYNTAX         OCTET STRING (SIZE(1..15))
        MAX-ACCESS     read-create
        STATUS         current
        DESCRIPTION    "IP Protocol.  It can be specified by explicit protocol
                        number (Integer, 0 to 255) or by keyword.  Some common
                        protocol types are listed below:
                        ICMP             - IP protocol is ICMP (1)
                        IPIP             - IP protocol is IPIP (4)
                        TCP              - IP protocol is TCP (6)
                        UDP              - IP protocol is UDP (17)
                        RSVP             - IP protocol is RSVP (46)
                        GRE              - IP protocol is GRE (47)
                        OSPF             - IP protocol is OSPF (89)
                        <other protocol> - Specify IP protocol number: 0 to 255."
        ::= { tnSysIpAclEntry 10 }

    tnSysIpAclSrcAddr OBJECT-TYPE
        SYNTAX         IpAddress
        MAX-ACCESS     read-create
        STATUS         current
        DESCRIPTION    "Source IP address.  It can be specified explicitly to
                        match only packets that originate from a particular
                        address or can be used along with the SrcPrefix
                        parameter to specify a range of supported originating
                        IP addresses."
        ::= { tnSysIpAclEntry 11 }

    tnSysIpAclSrcPrefix OBJECT-TYPE
        SYNTAX         Integer32 (0..32)
        MAX-ACCESS     read-create
        STATUS         current
        DESCRIPTION    "Source IP mask prefix.  If the SrcAddr is specified and
                        the SrcPrefix is unspecified (0), the originating IP
                        address of the packet must match the SrcAddr exactly.
                        Otherwise, the pattern will allow packets whose
                        originating IP is within the range implied by the source
                        IP and subnet mask.  This parameter is not valid unless
                        the SrcAddr is also specified."
        DEFVAL         { 0 }
        ::= { tnSysIpAclEntry 12 }

    tnSysIpAclDestAddr OBJECT-TYPE
        SYNTAX         IpAddress
        MAX-ACCESS     read-create
        STATUS         current
        DESCRIPTION    "Destination IP address.  It can be specified explicitly
                        to match only packets that originate from a particular
                        address or can be used along with the DestPrefix parameter
                        to specify a range of supported destination IP addresses."
        ::= { tnSysIpAclEntry 13 }

    tnSysIpAclDestPrefix OBJECT-TYPE
        SYNTAX         Integer32 (0..32)
        MAX-ACCESS     read-create
        STATUS         current
        DESCRIPTION    "Destination IP Mask Prefix.  If the DestAddr is specified
                        and the DestPrefix is unspecified (0), The originating IP
                        address of the packet must match the DestAddr exactly.
                        Otherwise, the pattern will allow packets whose originating
                        IP is within the range implied by the source IP and subnet
                        mask.  This parameter is not valid unless the DestAddr is
                        also specified."
        DEFVAL         { 0 }
        ::= { tnSysIpAclEntry 14 }

    tnSysIpAclIpFragment OBJECT-TYPE
        SYNTAX         TruthValue
        MAX-ACCESS     read-create
        STATUS         current
        DESCRIPTION    "IP Fragmentation.  True means that the filtering is done
                        on all fragments, not just on the initial one (assuming
                        the following ones are ok).  Valid values are:
                        true  - pattern is an IP
                        false - pattern is not an IP fragment."
        DEFVAL         { false }
        ::= { tnSysIpAclEntry 15 }

    tnSysIpAclTcpEstablish OBJECT-TYPE
        SYNTAX         INTEGER {
                         true(1),
                         false(2),
                         local(3)
                       }
        MAX-ACCESS     read-create
        STATUS         current
        DESCRIPTION    "TCP established flag.  It matches a packet depending on
                        whether the TCP flags in the IP header correspond to the
                        established state.  Valid values are:
                        true  - TCP flags correspond to established state
                        false - TCP flags do not correspond to established
                        local - TCP flags correspond to established state
                                only for destination to local NE."
        ::= { tnSysIpAclEntry 16 }

    tnSysIpAclStatCount OBJECT-TYPE
        SYNTAX         Counter32
        MAX-ACCESS     read-only
        STATUS         current
        DESCRIPTION    "Packet match counter.  It is incremented whenever a packet
                        matches the specified ACL pattern in the filter.  This
                        counter will be incremented regardless of the provisioned
                        action on that pattern."
        ::= { tnSysIpAclEntry 17 }

     tnSysIpAclAdminState OBJECT-TYPE
        SYNTAX      INTEGER {
                      active(1),
                      deactive(2),
                      startToAdd(3),
                      startToModify(4)
                    }
        MAX-ACCESS     read-create
        STATUS         current
        DESCRIPTION    "The admin status of IPACL.  All the IPACL rules will be
                        generated automatically when NE DB is generated for the
                        first time.  For example, we may have the 512 rules that
                        are generated by default including the default IPACL rules.
                        All default IPACL rules have AdminState 'active(1)', while
                        others have AdminState 'deactivate(2)'.  Only items with
                        'active(1)' will be sent to Linux IPTable for further
                        processing.  The item with AdminState 'deactivate(2)' will
                        be removed from Linux IPTable.  For example, we have the
                        following default rules:
                        IPACL index     IPACL AdminState
                           1               active
                           2               active
                           3               active

                        If a new IPACL rule is activated after IPACL index 3, then
                        we have:
                        IPACL index, IPACL Adminstate
                           1               active
                           2               active
                           3               active
                           4               active

                        If a new IPACL rule is activated after IPACL index 2, then
                        we have:
                        IPACL index, IPACL Adminstate
                           1               active
                           2               active
                           3               active    <- newly added
                           4               active    <- change IPACL index 3 to 4
                           5               active    <- change IPACL index 4 to 5

                        If index 2 is deactivated, then we have:
                        IPACL index, IPACL Adminstate
                           1               active
                           2               active    <- change IPACL index 3 to 2
                           3               active    <- change IPACL index 4 to 3
                           4               active    <- change IPACL index 5 to 4
                        Only the rules with 'AdminState(1)' can be retrieved."
        ::= { tnSysIpAclEntry 18 }

--------------------------------------------------------------------------------
-- IP Access Control List (ACL) Ipv6 Scalar
--------------------------------------------------------------------------------
    tnSysIpv6AclAttributeTotal OBJECT-TYPE
        SYNTAX         Integer32
        MAX-ACCESS     read-only
        STATUS         current
        DESCRIPTION    "This parameter indicates the total IPACL rules can be
                        supported in tnSysIpv6AclTable."
        ::= { tnSysAccessControlList 24 }

--------------------------------------------------------------------------------
-- IP Access Control List (ACL) Ipv6
--------------------------------------------------------------------------------
    tnSysIpv6AclTable OBJECT-TYPE
        SYNTAX         SEQUENCE OF TnSysIpv6AclEntry
        MAX-ACCESS     not-accessible
        STATUS         current
        DESCRIPTION    "Table of IP ACL rule.  An ACL rule is a set of packet
                        field descriptors that can be tested against a packet.
                        For a rule to match, each of its field descriptors must
                        fit the data in the packet."
        ::= { tnSysAccessControlList 25 }

    tnSysIpv6AclEntry OBJECT-TYPE
        SYNTAX         TnSysIpv6AclEntry
        MAX-ACCESS     not-accessible
        STATUS         current
        DESCRIPTION    "."
        INDEX { tnSysIpv6AclIndex }
        ::= { tnSysIpv6AclTable 1 }

    TnSysIpv6AclEntry ::= SEQUENCE {
        tnSysIpv6AclIndex                   Integer32,
        tnSysIpv6AclDesc                    SnmpAdminString,
        tnSysIpv6AclAccessID                SnmpAdminString,
        tnSysIpv6AclInterface               Unsigned32,
        tnSysIpv6AclAction                  INTEGER,
        tnSysIpv6AclSrcPort                 SnmpAdminString,
        tnSysIpv6AclDestPort                SnmpAdminString,
        tnSysIpv6AclIcmpType                Integer32,
        tnSysIpv6AclIcmpCode                Integer32,
        tnSysIpv6AclIpProtocol              OCTET STRING,
        tnSysIpv6AclSrcAddr                 InetAddressIPv6,
        tnSysIpv6AclSrcPrefixLen            InetAddressPrefixLength,
        tnSysIpv6AclDestAddr                InetAddressIPv6,
        tnSysIpv6AclDestPrefixLen           InetAddressPrefixLength,
        tnSysIpv6AclTcpEstablish            INTEGER,
        tnSysIpv6AclStatCount               Counter32,
        tnSysIpv6AclAdminState              INTEGER
    }

    tnSysIpv6AclIndex OBJECT-TYPE
        SYNTAX         Integer32
        MAX-ACCESS     not-accessible
        STATUS         current
        DESCRIPTION    "The values of 1 to 512 represent the index of IPACL.
                        Default is the number of existing rules + 1, or a number
                        between 1 and the number of existing rules (in this case
                        existing rules after indes will be shifted to index + 1).
                        For modify: an index of an existing rule.
                        For delete: a delete will shift existing rules after
                            index to index - 1.
                        The maximum number of ACL rules is 512.
                        The valid index range is from 1 to 512.
                        If index is not provided by CLI/NMS when a new rule is
                            added, index 65535 shall be used, NE SW will add a
                            new rule using the index with the number of existing
                            rules + 1."
        ::= { tnSysIpv6AclEntry 1 }

    tnSysIpv6AclDesc OBJECT-TYPE
        SYNTAX         SnmpAdminString (SIZE(0..255))
        MAX-ACCESS     read-create
        STATUS         current
        DESCRIPTION    "Short description about the purpose of this rule."
        DEFVAL         { "" }
        ::= { tnSysIpv6AclEntry 2 }

    tnSysIpv6AclAccessID OBJECT-TYPE
        SYNTAX         SnmpAdminString (SIZE(1..30))
        MAX-ACCESS     read-create
        STATUS         current
        DESCRIPTION    "The access ID of the ACL to be created, it could be one
                        of the following strings:  SSH, MAINTSSH, ALTCLI, SNMP, OA,
                        NMIGRPC, RADIUS, NTP, ICMPV6, TRACERT, MCLAG, SYSLOGU, SFTPC or IP."
        ::= { tnSysIpv6AclEntry 3 }

    tnSysIpv6AclInterface OBJECT-TYPE
        SYNTAX         Unsigned32 (1..64)
        MAX-ACCESS     read-create
        STATUS         current
        DESCRIPTION    "Access identifier for the interface Index.  It could be
                        one of the following cases:
                        - 41: All
                        - 42: LAN=LAN1+LAN2
                        - 43: All ETHIF
                        - Ifindex of LAN1
                        - ifindex of LAN2
                        - ifindex of CIT
                        - tnEthIfIndex of EthIF, 1...30 for TPS-24, 1...14 for TPS-12."
        ::= { tnSysIpv6AclEntry 4 }

    tnSysIpv6AclAction OBJECT-TYPE
        SYNTAX         INTEGER {
                         accept(1),
                         drop(2),
                         reject(3),
                         log(4)
                       }
        MAX-ACCESS     read-create
        STATUS         current
        DESCRIPTION    "Action to be taken on packets matching the specified ACL
                        pattern.  Valid values are:
                        accept  - allow the packet if it matches all the pattern
                                  descriptors
                        drop    - matching packets are discarded
                        reject  - matching packets are discarded; an ICMP error
                                  message is sent back
                        log     - log the packet if it matches all the pattern
                                  descriptors."
        ::= { tnSysIpv6AclEntry 5 }

    tnSysIpv6AclSrcPort OBJECT-TYPE
        SYNTAX         SnmpAdminString (SIZE(1..15))
        MAX-ACCESS     read-create
        STATUS         current
        DESCRIPTION    "TCP/UDP source port.  It can be a range[0-65535:0-65535]"
        ::= { tnSysIpv6AclEntry 6 }

    tnSysIpv6AclDestPort OBJECT-TYPE
        SYNTAX         SnmpAdminString (SIZE(1..15))
        MAX-ACCESS     read-create
        STATUS         current
        DESCRIPTION    "TCP/UDP destination port.  It can be a range[0-65535:0-65535]."
        ::= { tnSysIpv6AclEntry 7 }

    tnSysIpv6AclIcmpType OBJECT-TYPE
        SYNTAX         Integer32 (0..255)
        MAX-ACCESS     read-create
        STATUS         current
        DESCRIPTION    "ICMP Type identifier.  It is applicable only when
                        IPPROTOCOL is ICMP.  If specified, the pattern will
                        match only packets with this exact ICMP type.  Some
                        of the most commonly used ICMP types are:
                        0       Echo Reply [RFC792]
                        3       Destination Unreachable[RFC792]
                        5       Redirect[RFC792]
                        9       Router Advertisement[RFC1256]
                        42-255  Reserved."
        ::= { tnSysIpv6AclEntry 8 }

    tnSysIpv6AclIcmpCode OBJECT-TYPE
        SYNTAX         Integer32 (0..255)
        MAX-ACCESS     read-create
        STATUS         current
        DESCRIPTION    "ICMP code field.  It is applicable only when IP protocol
                        is ICMP and is used along with certain ICMP types to
                        further specify the message type.  It must also specify
                        the ICMP type when setting this parameter.  If specified,
                        the pattern will only match packets with this exact ICMP
                        code value.  For example, there are a few ICMPCODEs
                        associated with the ICMPTYPE Redirect [RFC792]:
                        0  Redirect Datagram for the Network (or subnet)
                        1  Redirect Datagram for the Host
                        2  Redirect Datagram for the Type of Service and Network
                        3  Redirect Datagram for the Type of Service and Host."
        ::= { tnSysIpv6AclEntry 9 }

    tnSysIpv6AclIpProtocol OBJECT-TYPE
        SYNTAX         OCTET STRING(SIZE(1..15))
        MAX-ACCESS     read-create
        STATUS         current
        DESCRIPTION    "IP Protocol.  It can be specified by explicit protocol
                        number (Integer, 0 to 255) or by keyword.  Some common
                        protocol types are listed below:
                        ICMP             - IP protocol is ICMP (1)
                        IPIP             - IP protocol is IPIP (4)
                        TCP              - IP protocol is TCP (6)
                        UDP              - IP protocol is UDP (17)
                        RSVP             - IP protocol is RSVP (46)
                        GRE              - IP protocol is GRE (47)
                        OSPF             - IP protocol is OSPF (89)
                        <other protocol> - Specify IP protocol number: 0 to 255."
        ::= { tnSysIpv6AclEntry 10 }

    tnSysIpv6AclSrcAddr OBJECT-TYPE
        SYNTAX         InetAddressIPv6
        MAX-ACCESS     read-create
        STATUS         current
        DESCRIPTION    "Source IPV6 address.  It can be specified explicitly to
                        match only packets that originate from a particular
                        address or can be used along with the SrcPrefixLen
                        parameter to specify a range of supported originating
                        IPV6 addresses."
        ::= { tnSysIpv6AclEntry 11 }

    tnSysIpv6AclSrcPrefixLen OBJECT-TYPE
        SYNTAX         InetAddressPrefixLength
        MAX-ACCESS     read-create
        STATUS         current
        DESCRIPTION    "Denotes the length of source IPV6 address prefix.  A
                        value of n corresponds to an IP address maskthat has
                        n contiguous1-bits from the most significant bit (MSB),
                        with all other bits set to 0."
        ::= { tnSysIpv6AclEntry 12 }

    tnSysIpv6AclDestAddr OBJECT-TYPE
        SYNTAX         InetAddressIPv6
        MAX-ACCESS     read-create
        STATUS         current
        DESCRIPTION    "Destination IPV6 address.  It can be specified explicitly
                        to match only packets that originate from a particular
                        address or can be used along with the DestPrefixLen
                        parameter to specify a range of supported destination
                        IPV6 addresses."
        ::= { tnSysIpv6AclEntry 13 }

    tnSysIpv6AclDestPrefixLen OBJECT-TYPE
        SYNTAX         InetAddressPrefixLength
        MAX-ACCESS     read-create
        STATUS         current
        DESCRIPTION    "Denotes the length of destination IPV6 address prefix.
                        A value of n corresponds to an IP address maskthat has
                        n contiguous1-bits from the most significant bit (MSB),
                        with all other bits set to 0."
        ::= { tnSysIpv6AclEntry 14 }

    tnSysIpv6AclTcpEstablish OBJECT-TYPE
        SYNTAX         INTEGER {
                         true(1),
                         false(2),
                         local(3)
                       }
        MAX-ACCESS     read-create
        STATUS         current
        DESCRIPTION    "TCP established flag.  It matches a packet depending on
                        whether the TCP flags in the IP header correspond to the
                        established state.  Valid values are:
                        true  - TCP flags correspond to established state
                        false - TCP flags do not correspond to established
                        local - TCP flags correspond to established state only
                                for destination to local NE."
        ::= { tnSysIpv6AclEntry 15 }

    tnSysIpv6AclStatCount OBJECT-TYPE
        SYNTAX         Counter32
        MAX-ACCESS     read-only
        STATUS         current
        DESCRIPTION    "Packet match counter.  It is incremented whenever a
                        packet matches the specified ACL pattern in the filter.
                        This counter will be incremented regardless of the
                        provisioned action on that pattern."
        ::= { tnSysIpv6AclEntry 16 }

     tnSysIpv6AclAdminState OBJECT-TYPE
        SYNTAX      INTEGER {
                      active(1),
                      deactive(2),
                      startToAdd(3),
                      startToModify(4)
                    }
        MAX-ACCESS     read-create
        STATUS         current
        DESCRIPTION    "The admin status of IPACL.  All the IPACL rules will be
                        generated automatically when NE DB is generated for the
                        first time.  For example, we may have the 512 rules that
                        are generated by default including the default IPACL rules.
                        All default IPACL rules have AdminState 'active(1)', while
                        others have AdminState 'deactivate(2)'.  Only items with
                        'active(1)' will be sent to Linux IPTable for further
                        processing, the item with AdminState 'deactivate(2)' will
                        be removed from Linux IPTable.  For example, we have the
                        following default rules:
                        IPACL index, IPACL AdminState
                           1               active
                           2               active
                           3               active
                        If a new IPACL rule is activated after IPACL index 3, then
                        we have:
                        IPACL index, IPACL Adminstate
                           1               active
                           2               active
                           3               active
                           4               active
                        If a new IPACL rule is activated after IPACL index 2, then
                        we have:
                        IPACL index, IPACL Adminstate
                           1               active
                           2               active
                           3               active    <- newly added
                           4               active    <- change IPACL index 3 to 4
                           5               active    <- change IPACL index 4 to 5
                        If index 2 is deactivated, then we have:
                        IPACL index, IPACL Adminstate
                           1               active
                           2               active    <- change IPACL index 3 to 2
                           3               active    <- change IPACL index 4 to 3
                           4               active    <- change IPACL index 5 to 4
                        Only the rules with AdminState(1) can be retrieved."
        ::= { tnSysIpv6AclEntry 17 }

--------------------------------------------------------------------------------
-- NTP Servers ID Stats Table
--------------------------------------------------------------------------------
    tnSysNtpServerIdStatsTable OBJECT-TYPE
        SYNTAX         SEQUENCE OF TnSysNtpServerIdStatsEntry
        MAX-ACCESS     not-accessible
        STATUS         current
        DESCRIPTION    "."
        ::= { tnSysNtpServerIdStats 1 }

    tnSysNtpServerIdStatsEntry OBJECT-TYPE
        SYNTAX         TnSysNtpServerIdStatsEntry
        MAX-ACCESS     not-accessible
        STATUS         current
        DESCRIPTION    "."
        INDEX { tnSysNtpServerIdStatsIndex }
        ::= { tnSysNtpServerIdStatsTable 1 }

    TnSysNtpServerIdStatsEntry ::= SEQUENCE {
        tnSysNtpServerIdStatsIndex       Unsigned32,
        tnSysNtpServerIdStatsSelect      SnmpAdminString,
        tnSysNtpServerIdStatsIp          SnmpAdminString,
        tnSysNtpServerIdStatsRefId       SnmpAdminString,
        tnSysNtpServerIdStatsStrtm       SnmpAdminString,
        tnSysNtpServerIdStatsClockType   SnmpAdminString,
        tnSysNtpServerIdStatsPoll        SnmpAdminString,
        tnSysNtpServerIdStatsReach       SnmpAdminString,
        tnSysNtpServerIdStatsDelay       SnmpAdminString,
        tnSysNtpServerIdStatsOffset      SnmpAdminString,
        tnSysNtpServerIdStatsJitter      SnmpAdminString,
        tnSysNtpServerIdStatsKeyIndex    Unsigned32
    }

    tnSysNtpServerIdStatsIndex OBJECT-TYPE
        SYNTAX         Unsigned32 (1..8)
        MAX-ACCESS     not-accessible
        STATUS         current
        DESCRIPTION    "For the 1830 PSS-32.  The maximum number of
                        supported NTP servers is 8."
        ::= { tnSysNtpServerIdStatsEntry 1 }

    tnSysNtpServerIdStatsSelect OBJECT-TYPE
        SYNTAX         SnmpAdminString (SIZE(0..2))
        MAX-ACCESS     read-only
        STATUS         current
        DESCRIPTION    "Character to be displayed is one of the
                        following:
                        '*' - selected reference
                        '+' - member of the alternate references
                        ' ' - disqualified."
        ::= { tnSysNtpServerIdStatsEntry 2 }

    tnSysNtpServerIdStatsIp OBJECT-TYPE
        SYNTAX         SnmpAdminString (SIZE(0..48))
        MAX-ACCESS     read-only
        STATUS         current
        DESCRIPTION    "NTP server IP address."
        ::= { tnSysNtpServerIdStatsEntry 3 }

    tnSysNtpServerIdStatsRefId OBJECT-TYPE
        SYNTAX         SnmpAdminString (SIZE(0..48))
        MAX-ACCESS     read-only
        STATUS         current
        DESCRIPTION    "NTP reference ID."
        ::= { tnSysNtpServerIdStatsEntry 4 }

    tnSysNtpServerIdStatsStrtm OBJECT-TYPE
        SYNTAX         SnmpAdminString (SIZE(0..3))
        MAX-ACCESS     read-only
        STATUS         current
        DESCRIPTION    "Level of reference, from 1 - 16."
        ::= { tnSysNtpServerIdStatsEntry 5 }

    tnSysNtpServerIdStatsClockType OBJECT-TYPE
        SYNTAX         SnmpAdminString (SIZE(0..2))
        MAX-ACCESS     read-only
        STATUS         current
        DESCRIPTION    "Clock type:
                        'u' - unicast
                        'b' - broadcast
                        'l' - local."
        ::= { tnSysNtpServerIdStatsEntry 6 }

    tnSysNtpServerIdStatsPoll OBJECT-TYPE
        SYNTAX         SnmpAdminString (SIZE(0..6))
        MAX-ACCESS     read-only
        STATUS         current
        DESCRIPTION    "Polling interval in log base 2 seconds."
        ::= { tnSysNtpServerIdStatsEntry 7 }

    tnSysNtpServerIdStatsReach OBJECT-TYPE
        SYNTAX         SnmpAdminString (SIZE(0..4))
        MAX-ACCESS     read-only
        STATUS         current
        DESCRIPTION    "8 bit octal number representing success of last
                        8 attempts."
        ::= { tnSysNtpServerIdStatsEntry 8 }

    tnSysNtpServerIdStatsDelay OBJECT-TYPE
        SYNTAX         SnmpAdminString (SIZE(0..12))
        MAX-ACCESS     read-only
        STATUS         current
        DESCRIPTION    "Round trip delay to the reference server."
        ::= { tnSysNtpServerIdStatsEntry 9 }

    tnSysNtpServerIdStatsOffset OBJECT-TYPE
        SYNTAX         SnmpAdminString (SIZE(0..12))
        MAX-ACCESS     read-only
        STATUS         current
        DESCRIPTION    "."
        ::= { tnSysNtpServerIdStatsEntry 10 }

    tnSysNtpServerIdStatsJitter OBJECT-TYPE
        SYNTAX         SnmpAdminString (SIZE(0..12))
        MAX-ACCESS     read-only
        STATUS         current
        DESCRIPTION    "."
        ::= { tnSysNtpServerIdStatsEntry 11 }

    tnSysNtpServerIdStatsKeyIndex OBJECT-TYPE
        SYNTAX         Unsigned32
        MAX-ACCESS     read-only
        STATUS         current
        DESCRIPTION    "."
        ::= { tnSysNtpServerIdStatsEntry 12 }

--------------------------------------------------------------------------------
-- Ftp Server Scalars
--------------------------------------------------------------------------------
    tnSysFtpServerEnabled OBJECT-TYPE
        SYNTAX         TruthValue
        MAX-ACCESS     read-write
        STATUS         current
        DESCRIPTION    "true  - FTP server function is enabled.
                        false - FTP server function is disabled."
        DEFVAL         { false }
        ::= { tnSysFtpServer 1 }

    tnSysFtpServerUserId OBJECT-TYPE
        SYNTAX         SnmpAdminString (SIZE(0..128))
        MAX-ACCESS     read-only
        STATUS         current
        DESCRIPTION    "The FTP server user ID."
        DEFVAL         { "UserSWNE" }
        ::= { tnSysFtpServer 2 }

    tnSysFtpServerPassword OBJECT-TYPE
        SYNTAX         SnmpAdminString (SIZE(0..128))
        MAX-ACCESS     read-write
        STATUS         current
        DESCRIPTION    "The FTP server password.  When read, this
                        attribute will return '********'."
        DEFVAL         { "********" }
        ::= { tnSysFtpServer 3 }

--------------------------------------------------------------------------------
-- NTP Server Authentication Scalar
--------------------------------------------------------------------------------
    tnSysNtpServerAuthenticationAttributeTotal OBJECT-TYPE
        SYNTAX         Integer32
        MAX-ACCESS     read-only
        STATUS         current
        DESCRIPTION    "."
        ::= { tnSysNtpServerAuthentication 1 }

--------------------------------------------------------------------------------
-- NTP Server Authentication
--------------------------------------------------------------------------------
    tnSysNtpServerAuthenticationTable OBJECT-TYPE
        SYNTAX         SEQUENCE OF TnSysNtpServerAuthenticationEntry
        MAX-ACCESS     not-accessible
        STATUS         current
        DESCRIPTION    "."
        ::= { tnSysNtpServerAuthentication 2 }

    tnSysNtpServerAuthenticationEntry OBJECT-TYPE
        SYNTAX         TnSysNtpServerAuthenticationEntry
        MAX-ACCESS     not-accessible
        STATUS         current
        DESCRIPTION    "."
        INDEX { tnSysNtpServerAuthenticationKeyIndex }
        ::= { tnSysNtpServerAuthenticationTable 1 }

    TnSysNtpServerAuthenticationEntry ::= SEQUENCE {
        tnSysNtpServerAuthenticationKeyIndex      Unsigned32,
        tnSysNtpServerAuthenticationRowStatus     RowStatus,
        tnSysNtpServerAuthenticationKeyType       INTEGER,
        tnSysNtpServerAuthenticationKey           OCTET STRING
    }

    tnSysNtpServerAuthenticationKeyIndex OBJECT-TYPE
        SYNTAX         Unsigned32 (0..65535)
        MAX-ACCESS     not-accessible
        STATUS         current
        DESCRIPTION    "NTP server authentication key index."
        ::= { tnSysNtpServerAuthenticationEntry 1 }

    tnSysNtpServerAuthenticationRowStatus OBJECT-TYPE
        SYNTAX         RowStatus
        MAX-ACCESS     read-create
        STATUS         current
        DESCRIPTION    "Status of this NTP server.  Supported values:
                        1 - active
                        4 - createAndGo
                        6 - destroy."
        ::= { tnSysNtpServerAuthenticationEntry 2 }

    tnSysNtpServerAuthenticationKeyType OBJECT-TYPE
        SYNTAX         INTEGER {
                         sha1(1),
                         md5(2)
                       }
        MAX-ACCESS     read-create
        STATUS         current
        DESCRIPTION    "NTP server authentication key type."
        ::= { tnSysNtpServerAuthenticationEntry 3 }

    tnSysNtpServerAuthenticationKey OBJECT-TYPE
        SYNTAX         OCTET STRING (SIZE(0..500))
        MAX-ACCESS     read-create
        STATUS         current
        DESCRIPTION    "NTP server authentication key."
        ::= { tnSysNtpServerAuthenticationEntry 4 }

------------------------------------------------------------------------------
-- NE Discovery Scalar
------------------------------------------------------------------------------
    tnNeDiscoveryAttributeTotal OBJECT-TYPE
        SYNTAX         Integer32
        MAX-ACCESS     read-only
        STATUS         current
        DESCRIPTION    "."
        ::= { tnNeDiscovery 1 }

-------------------------------------------------------------------------------
-- NE Discovery Table
-------------------------------------------------------------------------------
    tnNeDiscoveryTable OBJECT-TYPE
        SYNTAX         SEQUENCE OF TnNeDiscoveryEntry
        MAX-ACCESS     not-accessible
        STATUS         current
        DESCRIPTION    "."
        ::= { tnNeDiscovery 2 }

    tnNeDiscoveryEntry OBJECT-TYPE
        SYNTAX         TnNeDiscoveryEntry
        MAX-ACCESS     not-accessible
        STATUS         current
        DESCRIPTION    "."
        INDEX { tnNeDiscoveryIndex }
        ::= { tnNeDiscoveryTable 1 }

    TnNeDiscoveryEntry ::= SEQUENCE {
        tnNeDiscoveryIndex                  SnmpAdminString,
        tnNeDiscoveryFilename               SnmpAdminString,
        tnNeDiscoveryControl                INTEGER,
        tnNeDiscoveryStatus                 INTEGER,
        tnNeDiscoveryErrorCode              INTEGER,
        tnNeDiscoveryServerIp               IpAddress,
        tnNeDiscoveryServerProtocol         AluWdmNewTransferProtocol,
        tnNeDiscoveryServerUserId           SnmpAdminString,
        tnNeDiscoveryServerPassword         SnmpAdminString,
        tnNeDiscoveryServerTimeOut          Integer32,
        tnNeDiscoveryRowStatus              RowStatus,
        tnNeDiscoveryServerInetAddressType  InetAddressType,
        tnNeDiscoveryServerInetAddress      InetAddress,
        tnNeDiscoveryDeltaFilename          SnmpAdminString,
        tnNeDiscoveryDeltaFileFlag          INTEGER,
        tnNeDiscoveryDeltaSyncStatus        SnmpAdminString,
        tnNeDiscoveryPort                   Unsigned32
    }

    tnNeDiscoveryIndex OBJECT-TYPE
        SYNTAX         SnmpAdminString (SIZE(1..28))
        MAX-ACCESS     not-accessible
        STATUS         current
        DESCRIPTION    "Unique name given by the NMS."
        ::= { tnNeDiscoveryEntry 1 }

    tnNeDiscoveryFilename OBJECT-TYPE
        SYNTAX         SnmpAdminString
        MAX-ACCESS     read-create
        STATUS         current
        DESCRIPTION    "."
        DEFVAL         { "" }
        ::= { tnNeDiscoveryEntry 2 }

    tnNeDiscoveryControl OBJECT-TYPE
        SYNTAX         INTEGER {
                         noCmd(1),
                         start(2),
                         abort(3)
                       }
        MAX-ACCESS     read-create
        STATUS         current
        DESCRIPTION    "Controls the discovery, i.e., starts or aborts it."
        DEFVAL         { noCmd }
        ::= { tnNeDiscoveryEntry 3 }

    tnNeDiscoveryStatus OBJECT-TYPE
        SYNTAX         INTEGER {
                         idle(1),
                         inProgress(2),
                         completedSuccessfully(3),
                         failed(4),
                         aborted(5)
                       }
        MAX-ACCESS     read-only
        STATUS         current
        DESCRIPTION    "The discovery status."
        ::= { tnNeDiscoveryEntry 4 }

    tnNeDiscoveryErrorCode OBJECT-TYPE
        SYNTAX         INTEGER {
                         noError(1),
                         unknown(2),
                         timeout(3),
                         serverError(4),
                         networkError(5),
                         fileSystemError(6),
                         systemNotReady(7)
                       }
        MAX-ACCESS     read-only
        STATUS         current
        DESCRIPTION    "The discovery error code."
        ::= { tnNeDiscoveryEntry 5 }

    tnNeDiscoveryServerIp OBJECT-TYPE
        SYNTAX         IpAddress
        MAX-ACCESS     read-create
        STATUS         current
        DESCRIPTION    "The discovery server IP address."
        DEFVAL         { '00000000'H }
        ::= { tnNeDiscoveryEntry 6 }

    tnNeDiscoveryServerProtocol OBJECT-TYPE
        SYNTAX         AluWdmNewTransferProtocol
        MAX-ACCESS     read-create
        STATUS         current
        DESCRIPTION    "The discovery server protocol."
        ::= { tnNeDiscoveryEntry 7 }

    tnNeDiscoveryServerUserId OBJECT-TYPE
        SYNTAX         SnmpAdminString (SIZE(1..128))
        MAX-ACCESS     read-create
        STATUS         current
        DESCRIPTION    "The user ID used to access the server."
        ::= { tnNeDiscoveryEntry 8 }

    tnNeDiscoveryServerPassword OBJECT-TYPE
        SYNTAX         SnmpAdminString (SIZE(1..128))
        MAX-ACCESS     read-create
        STATUS         current
        DESCRIPTION    "The password used to access the server.  When
                        read, this attribute will return an empty
                        string if the password has not been set and
                        '********' if it has been set."
        ::= { tnNeDiscoveryEntry 9 }

    tnNeDiscoveryServerTimeOut OBJECT-TYPE
        SYNTAX         Integer32
        MAX-ACCESS     read-create
        STATUS         current
        DESCRIPTION    "Timeout from NMS for the discovery request."
        ::= { tnNeDiscoveryEntry 10 }

    tnNeDiscoveryRowStatus OBJECT-TYPE
        SYNTAX         RowStatus
        MAX-ACCESS     read-create
        STATUS         current
        DESCRIPTION    "The row status of this discovery."
        ::= { tnNeDiscoveryEntry 11 }

    tnNeDiscoveryServerInetAddressType OBJECT-TYPE
        SYNTAX         InetAddressType
        MAX-ACCESS     read-create
        STATUS         current
        DESCRIPTION    "The value specifies the type of Internet address
                        stored in tnNeDiscoveryServerInetAddress."
        DEFVAL         { unknown }
        ::= { tnNeDiscoveryEntry 12 }

    tnNeDiscoveryServerInetAddress OBJECT-TYPE
        SYNTAX         InetAddress
        MAX-ACCESS     read-create
        STATUS         current
        DESCRIPTION    "Indicates the IPv6 address of the log server."
        DEFVAL         { ''H }
        ::= { tnNeDiscoveryEntry 13 }

    tnNeDiscoveryDeltaFilename OBJECT-TYPE
        SYNTAX         SnmpAdminString
        MAX-ACCESS     read-create
        STATUS         deprecated
        DESCRIPTION    "."
        DEFVAL         { "" }
        ::= { tnNeDiscoveryEntry 14 }

    tnNeDiscoveryDeltaFileFlag OBJECT-TYPE
        SYNTAX         INTEGER {
                         eqptSyncEnable(1),
                         eqptSyncDisable(2),
                         tpSyncEnable(3),
                         tpSyncDisable(4),
                         sncSyncEnable(5),
                         sncSyncDisable(6),
                         tlSyncEnable(7),
                         tlSyncDisable(8),
                         pgSyncEnable(9),
                         pgSyncDisable(10),
                         syncTransfer(11),
                         syncClear(12),
                         syncDisable(13),
                         eqptSyncTransfer(14),
                         tpSyncTransfer(15),
                         sncSyncTransfer(16),
                         tlSyncTransfer(17),
                         pgSyncTransfer(18),
                         syncTrapEnable(19),
                         syncTrapDisable(20),
                         syncTrapTransfer(21)
                       }
        MAX-ACCESS     read-create
        STATUS         current
        DESCRIPTION    "Delta File Flag."
        ::= { tnNeDiscoveryEntry 15 }

    tnNeDiscoveryDeltaSyncStatus OBJECT-TYPE
        SYNTAX         SnmpAdminString (SIZE(0..255))
        MAX-ACCESS     read-only
        STATUS         current
        DESCRIPTION    "Active sync status."
        DEFVAL         { "" }
        ::= { tnNeDiscoveryEntry 16 }

    tnNeDiscoveryPort OBJECT-TYPE
        SYNTAX         Unsigned32 (1..65535)
        MAX-ACCESS     read-create
        STATUS         current
        DESCRIPTION    "."
        DEFVAL         { 21 }
        ::= { tnNeDiscoveryEntry 17 }

--------------------------------------------------------------------------------
-- OTDR (Optical Time Domain Reflectometer) Scan System Profile Scalar
--------------------------------------------------------------------------------
    tnSysOtdrScanSystemProfileAttributeTotal OBJECT-TYPE
        SYNTAX         Integer32
        MAX-ACCESS     read-only
        STATUS         current
        DESCRIPTION    "."
        ::= { tnSysOtdrScanSystemProfile 1 }

--------------------------------------------------------------------------------
-- OTDR (Optical Time Domain Reflectometer) Scan System Profile Table
--------------------------------------------------------------------------------
    tnSysOtdrScanSystemProfileTable OBJECT-TYPE
        SYNTAX         SEQUENCE OF TnSysOtdrScanSystemProfileEntry
        MAX-ACCESS     not-accessible
        STATUS         current
        DESCRIPTION    "."
        ::= { tnSysOtdrScanSystemProfile 2 }

    tnSysOtdrScanSystemProfileEntry OBJECT-TYPE
        SYNTAX         TnSysOtdrScanSystemProfileEntry
        MAX-ACCESS     not-accessible
        STATUS         current
        DESCRIPTION    "."
        INDEX { tnSysOtdrScanSystemProfileId }
        ::= { tnSysOtdrScanSystemProfileTable 1 }

    TnSysOtdrScanSystemProfileEntry ::= SEQUENCE {
        tnSysOtdrScanSystemProfileId                      Integer32,
        tnSysOtdrScanSystemProfileDescription             SnmpAdminString,
        tnSysOtdrScanSystemProfileWaveLength              Unsigned32,
        tnSysOtdrScanSystemProfilePulseLength             Unsigned32,
        tnSysOtdrScanSystemProfileRange                   Unsigned32,
        tnSysOtdrScanSystemProfileResolution              Unsigned32,
        tnSysOtdrScanSystemProfileAvgTime                 Unsigned32,
        tnSysOtdrScanSystemProfileEventThreshold          Unsigned32,
        tnSysOtdrScanSystemProfileIOR                     Unsigned32
    }

    tnSysOtdrScanSystemProfileId OBJECT-TYPE
        SYNTAX         Integer32 (1..9)
        MAX-ACCESS     not-accessible
        STATUS         current
        DESCRIPTION    "Unique identifier for the profile.  Range is
                        from 1 to 9."
        ::= { tnSysOtdrScanSystemProfileEntry 1 }

    tnSysOtdrScanSystemProfileDescription OBJECT-TYPE
        SYNTAX         SnmpAdminString (SIZE(0..80))
        MAX-ACCESS     read-create
        STATUS         current
        DESCRIPTION    "Describes the scan profile."
        ::= { tnSysOtdrScanSystemProfileEntry 2 }

    tnSysOtdrScanSystemProfileWaveLength OBJECT-TYPE
        SYNTAX         Unsigned32
        UNITS          "nanometers"
        MAX-ACCESS     read-only
        STATUS         current
        DESCRIPTION    "The wavelength used for the OTDR scan.  The
                        wavelength is 1610 nm, and is not configurable."
        DEFVAL         { 1610 }
        ::= { tnSysOtdrScanSystemProfileEntry 3 }

    tnSysOtdrScanSystemProfilePulseLength OBJECT-TYPE
        SYNTAX         Unsigned32
        UNITS          "nanoseconds"
        MAX-ACCESS     read-create
        STATUS         current
        DESCRIPTION    "Length of the pulse.

                        Current values: 5, 10, 30, 100, 300, 1000, 3000,
                        10000, and 20000."
        DEFVAL         { 300 }
        ::= { tnSysOtdrScanSystemProfileEntry 4 }

    tnSysOtdrScanSystemProfileRange OBJECT-TYPE
        SYNTAX         Unsigned32
        UNITS          "meters"
        MAX-ACCESS     read-create
        STATUS         current
        DESCRIPTION    "The range of the span that is being probed in
                        meters.

                        Current values: 500, 1000, 2000, 5000,
                            10000, 20000, 40000, 80000, 160000 and 260000."
        DEFVAL         { 160000 }
        ::= { tnSysOtdrScanSystemProfileEntry 5 }

    tnSysOtdrScanSystemProfileResolution OBJECT-TYPE
        SYNTAX         Unsigned32
        UNITS          "millimeters"
        MAX-ACCESS     read-create
        STATUS         current
        DESCRIPTION    "Distance resolution of the OTDR scan.

                        Current values: 40, 80, 160, 320, 640, 1200,
                            2500, 5000, 10000, 20000, 40000, 80000, and
                            160000."
        DEFVAL         { 2500 }
        ::= { tnSysOtdrScanSystemProfileEntry 6 }

    tnSysOtdrScanSystemProfileAvgTime OBJECT-TYPE
        SYNTAX         Unsigned32 (5..300)
        UNITS          "seconds"
        MAX-ACCESS     read-create
        STATUS         current
        DESCRIPTION    "Signal averaging time for a scan range.

                        Current range: 5 to 300."
        DEFVAL         { 180 }
        ::= { tnSysOtdrScanSystemProfileEntry 7 }

    tnSysOtdrScanSystemProfileEventThreshold OBJECT-TYPE
        SYNTAX         Unsigned32
        UNITS          "mB"
        MAX-ACCESS     read-create
        STATUS         current
        DESCRIPTION    "Sys Otdr Scan Event Threshold.
                        Current range: 5 to 100."
        DEFVAL        { 50 }
        ::= { tnSysOtdrScanSystemProfileEntry 8 }

    tnSysOtdrScanSystemProfileIOR OBJECT-TYPE
        SYNTAX         Unsigned32
        MAX-ACCESS     read-create
        STATUS         current
        DESCRIPTION    "Sys Otdr Scan IOR.
                        Current range: 1400 to 1600."
        DEFVAL         { 1465 }
        ::= { tnSysOtdrScanSystemProfileEntry 9 }

--------------------------------------------------------------------------------
--  OTDR Scan Transfer Scalars
--------------------------------------------------------------------------------
    tnSysOtdrScanTransferRemoteHostIp OBJECT-TYPE
        SYNTAX         IpAddress
        MAX-ACCESS     read-write
        STATUS         current
        DESCRIPTION    "OTDR scan transfer remote host IP address."
        DEFVAL         { '00000000'H }
        ::= { tnSysOtdrScanTransfer 1 }

    tnSysOtdrScanTransferCommand OBJECT-TYPE
        SYNTAX         INTEGER {
                         noCmd(1),
                         transferToRfs(2)
                       }
        MAX-ACCESS     read-write
        STATUS         current
        DESCRIPTION    "OTDR scan transfer command."
        DEFVAL         { noCmd }
        ::= { tnSysOtdrScanTransfer 2 }

    tnSysOtdrScanTransferRemotePath OBJECT-TYPE
        SYNTAX         SnmpAdminString (SIZE(0..255))
        MAX-ACCESS     read-write
        STATUS         current
        DESCRIPTION    "OTDR scan transfer remote path."
        DEFVAL         { "" }
        ::= { tnSysOtdrScanTransfer 3 }

    tnSysOtdrScanTransferStatus OBJECT-TYPE
        SYNTAX         AluWdmTransferStatus
        MAX-ACCESS     read-only
        STATUS         current
        DESCRIPTION    "This attribute indicates the status of the
                        previously executed tnSysOtdrScanTransferCommand
                        operation."
        DEFVAL         { none }
        ::= { tnSysOtdrScanTransfer 4 }

    tnSysOtdrScanTransferFilename OBJECT-TYPE
        SYNTAX         SnmpAdminString (SIZE(0..255))
        MAX-ACCESS     read-write
        STATUS         current
        DESCRIPTION    "This attribute indicates the filename for the
                        OTDR file transfer performed on the node.  If
                        it specifies empty string then bulk transfer
                        the files from NE to RFs.  And if it specifies
                        file name then it is single file transfer.
                        File information can be from the
                        tnOtdrScanStatusSuccessNotif trap."
        DEFVAL         { "" }
        ::= { tnSysOtdrScanTransfer 5 }

    tnSysOtdrScanTransferProtocol OBJECT-TYPE
        SYNTAX         AluWdmTransferProtocol
        MAX-ACCESS     read-write
        STATUS         current
        DESCRIPTION    "This attributes indicates the OTDR scan transfer
                        protocol.  Currently, only sftp/ftp is supported."
        DEFVAL         { ftp }
        ::= { tnSysOtdrScanTransfer 6 }

    tnSysOtdrScanTransferUserId OBJECT-TYPE
        SYNTAX         SnmpAdminString (SIZE(0..32))
        MAX-ACCESS     read-write
        STATUS         current
        DESCRIPTION    "The userId is used to access the RFS."
        DEFVAL         { "" }
        ::= { tnSysOtdrScanTransfer 7 }

    tnSysOtdrScanTransferPassword OBJECT-TYPE
        SYNTAX         SnmpAdminString (SIZE(0..32))
        MAX-ACCESS     read-write
        STATUS         current
        DESCRIPTION    "The password is used to access the RFS.

                        When read, this attribute will return an empty
                        string if the password has not been set and
                        '********' if it has been set."
        DEFVAL         { "" }
        ::= { tnSysOtdrScanTransfer 8 }

    tnSysOtdrScanTransferInetAddressType OBJECT-TYPE
        SYNTAX         InetAddressType
        MAX-ACCESS     read-write
        STATUS         current
        DESCRIPTION    "The value specifies the type of Internet address
                        stored in OTDR SCAN"
        DEFVAL         { unknown }
        ::= { tnSysOtdrScanTransfer 9 }

    tnSysOtdrScanTransferInetAddress OBJECT-TYPE
        SYNTAX         InetAddress
        MAX-ACCESS     read-write
        STATUS         current
        DESCRIPTION    "Indicates the IPv6 address of the OTDR SCAN"
        DEFVAL         { ''H }
        ::= { tnSysOtdrScanTransfer 10 }

    tnSysOtdrScanTransferPort OBJECT-TYPE
        SYNTAX         Unsigned32 (1..65535)
        MAX-ACCESS     read-write
        STATUS         current
        DESCRIPTION    "This attribute indicates the otdr port."
        DEFVAL         { 21 }
        ::= { tnSysOtdrScanTransfer 11 }

---------------------------------------------------------------
-- Cluster Table
---------------------------------------------------------------
    tnClusterTable OBJECT-TYPE
        SYNTAX         SEQUENCE OF TnClusterEntry
        MAX-ACCESS     not-accessible
        STATUS         current
        DESCRIPTION    "."
        ::= { tnClusterObjs 1 }

    tnClusterEntry OBJECT-TYPE
        SYNTAX         TnClusterEntry
        MAX-ACCESS     not-accessible
        STATUS         current
        DESCRIPTION    "."
        INDEX { tnClusterFarEndNode }
        ::= { tnClusterTable 1 }

    TnClusterEntry ::= SEQUENCE {
        tnClusterRowStatus              RowStatus,
        tnClusterFarEndNode             OCTET STRING,
        tnClusterIpAddress              IpAddress,
        tnClusterlinkStatus             INTEGER,
        tnClusterInetAddressType        InetAddressType,
        tnClusterInetAddress            InetAddress
    }

    tnClusterRowStatus OBJECT-TYPE
        SYNTAX         RowStatus
        MAX-ACCESS     read-create
        STATUS         current
        DESCRIPTION    "."
        ::= { tnClusterEntry 1 }

    tnClusterFarEndNode OBJECT-TYPE
        SYNTAX         OCTET STRING
        MAX-ACCESS     not-accessible
        STATUS         current
        DESCRIPTION    "."
        ::= { tnClusterEntry 2 }

    tnClusterIpAddress OBJECT-TYPE
        SYNTAX         IpAddress
        MAX-ACCESS     read-create
        STATUS         current
        DESCRIPTION    "."
        DEFVAL         { '00000000'H }
        ::= { tnClusterEntry 3 }

    tnClusterlinkStatus OBJECT-TYPE
        SYNTAX         INTEGER {
                          up(1),
                          down(2),
                          unknown(3)
                       }
        MAX-ACCESS     read-create
        STATUS         current
        DESCRIPTION    "Cluster link status."
        DEFVAL         { unknown }
        ::= { tnClusterEntry 4 }

    tnClusterInetAddressType OBJECT-TYPE
        SYNTAX         InetAddressType
        MAX-ACCESS     read-create
        STATUS         current
        DESCRIPTION    "The value specifies the type of Internet address stored
                        in Cluster."
        DEFVAL         { unknown }
        ::= { tnClusterEntry 5 }

    tnClusterInetAddress OBJECT-TYPE
        SYNTAX         InetAddress
        MAX-ACCESS     read-create
        STATUS         current
        DESCRIPTION    "Indicates the IPv6 address of the Cluster."
        DEFVAL         { ''H }
        ::= { tnClusterEntry 6 }

--------------------------------------------------------------------------------
--  PM FETCH BULK Transfer Scalars
--------------------------------------------------------------------------------
    tnSysPmFetchBulkStart OBJECT-TYPE
        SYNTAX         TnCommand
        MAX-ACCESS     read-write
        STATUS         current
        DESCRIPTION    "Intiates the PM Fetch bulk operation."
        DEFVAL         { noCmd }
        ::= { tnSysPmFetchBulk 1 }

    tnSysPmFetchBulkStatus OBJECT-TYPE
        SYNTAX         INTEGER {
                         idle(1),
                         inProgress(2),
                         completedSuccessfully(3),
                         failed(4),
                         aborted(5)
                       }
        MAX-ACCESS     read-only
        STATUS         current
        DESCRIPTION    "Indicates the status of the PM Fetch Bulk."
        DEFVAL         { idle }
        ::= { tnSysPmFetchBulk 2 }

    tnSysPmFetchBulkRemoteHostIp OBJECT-TYPE
        SYNTAX         IpAddress
        MAX-ACCESS     read-write
        STATUS         current
        DESCRIPTION    "PM Fetch Bulk remote host IP address."
        DEFVAL         { '00000000'H }
        ::= { tnSysPmFetchBulk 3 }

    tnSysPmFetchBulkUserId OBJECT-TYPE
        SYNTAX         SnmpAdminString (SIZE(0..32))
        MAX-ACCESS     read-write
        STATUS         current
        DESCRIPTION    "Indicates the username of the user who intiates PM
                        fetch Bulk operation."
        DEFVAL         { "" }
        ::= { tnSysPmFetchBulk 4 }

    tnSysPmFetchBulkPassword OBJECT-TYPE
        SYNTAX         SnmpAdminString (SIZE(0..32))
        MAX-ACCESS     read-write
        STATUS         current
        DESCRIPTION    "Indicates the password of the user who intiates PM
                        fetch Bulk operation."
        DEFVAL         { "" }
        ::= { tnSysPmFetchBulk 5 }

    tnSysPmFetchBulkRemotePath OBJECT-TYPE
        SYNTAX         SnmpAdminString (SIZE(0..255))
        MAX-ACCESS     read-write
        STATUS         current
        DESCRIPTION    "PM fetch Bulk remote path."
        DEFVAL         { "" }
        ::= { tnSysPmFetchBulk 6 }

    tnSysPmFetchBulkStatsInterval OBJECT-TYPE
        SYNTAX         Unsigned32
        MAX-ACCESS     read-write
        STATUS         current
        DESCRIPTION    "."
        DEFVAL         { 0 }
        ::= { tnSysPmFetchBulk 7 }

    tnSysPmFetchBulkBinnedStatsBin OBJECT-TYPE
        SYNTAX         Unsigned32
        MAX-ACCESS     read-write
        STATUS         current
        DESCRIPTION    "."
        DEFVAL         { 0 }
        ::= { tnSysPmFetchBulk 8 }

    tnSysPmFetchBulkShelfNum OBJECT-TYPE
        SYNTAX         Integer32
        MAX-ACCESS     read-write
        STATUS         current
        DESCRIPTION    "."
        DEFVAL         { 1 }
        ::= { tnSysPmFetchBulk 9 }

--------------------------------------------------------------------------------
-- DEBUG Transfer Scalars
--------------------------------------------------------------------------------
    tnSysDebugTransferRemoteHostIp OBJECT-TYPE
        SYNTAX         IpAddress
        MAX-ACCESS     read-write
        STATUS         current
        DESCRIPTION    "Debug dump transfer remote host IP address."
        DEFVAL         { '00000000'H }
        ::= { tnSysDebugTransfer 1 }

    tnSysDebugTransferCommand OBJECT-TYPE
        SYNTAX         INTEGER
                       {
                          noCmd(1),
                          transferToRfs(2)
                       }
        MAX-ACCESS     read-write
        STATUS         current
        DESCRIPTION    "Debug dump transfer command."
        DEFVAL         { noCmd }
        ::= { tnSysDebugTransfer 2 }

    tnSysDebugTransferRemotePath OBJECT-TYPE
        SYNTAX         SnmpAdminString (SIZE(0..255))
        MAX-ACCESS     read-write
        STATUS         current
        DESCRIPTION    "Debug dump transfer remote path."
        DEFVAL         { "" }
        ::= { tnSysDebugTransfer 3 }

    tnSysDebugTransferStatus OBJECT-TYPE
        SYNTAX         AluWdmTransferStatus
        MAX-ACCESS     read-only
        STATUS         current
        DESCRIPTION    "This attribute indicates the status of the
                        previously executed tnSysDebugTransferCommand
                        operation."
        DEFVAL         { none }
        ::= { tnSysDebugTransfer 4 }

    tnSysDebugTransferProtocol OBJECT-TYPE
        SYNTAX         AluWdmNewTransferProtocol
        MAX-ACCESS     read-write
        STATUS         current
        DESCRIPTION    "This attributes indicates the Debug dump transfer
                        protocol. Currently, only sftp/ftp is supported."
        DEFVAL         { ftp }
        ::= { tnSysDebugTransfer 5 }

    tnSysDebugTransferUserId OBJECT-TYPE
        SYNTAX         SnmpAdminString (SIZE(0..32))
        MAX-ACCESS     read-write
        STATUS         current
        DESCRIPTION    "The userId is used to access the RFS."
        DEFVAL         { "" }
        ::= { tnSysDebugTransfer 6 }

    tnSysDebugTransferPassword OBJECT-TYPE
        SYNTAX         SnmpAdminString (SIZE(0..32))
        MAX-ACCESS     read-write
        STATUS         current
        DESCRIPTION    "The password is used to access the RFS.
                        When read, this attribute will return an empty
                        string if the password has not been set and
                        '********' if it has been set."
        DEFVAL         { "" }
        ::= { tnSysDebugTransfer 7 }

    tnSysDebugTransferFilename OBJECT-TYPE
        SYNTAX         SnmpAdminString
        MAX-ACCESS     read-only
        STATUS         current
        DESCRIPTION    "This attribute indicates the filename for the
                        Debug Dump file transfer performed on the node."
        DEFVAL         { "" }
        ::= { tnSysDebugTransfer 8 }

    tnSysDebugTransferRecentSuccessFile OBJECT-TYPE
        SYNTAX         SnmpAdminString
        MAX-ACCESS     read-only
        STATUS         current
        DESCRIPTION    "This attribute indicates the filename for the recent
                        successful Debug Dump file transfered on the node."
        DEFVAL         { "" }
        ::= { tnSysDebugTransfer 9 }

    tnSysDebugTransferTimestamp OBJECT-TYPE
        SYNTAX         Unsigned32
        MAX-ACCESS     read-only
        STATUS         current
        DESCRIPTION    "The date and time when the last file was
                        completed."
        DEFVAL         { 0 }
        ::= { tnSysDebugTransfer 10 }

    tnSysDebugTransferShelfNum OBJECT-TYPE
        SYNTAX         Integer32 (1..31)
        MAX-ACCESS     read-write
        STATUS         current
        DESCRIPTION    "ShelfNum where the transfer has to be initiated."
        DEFVAL         { 1 }
        ::= { tnSysDebugTransfer 11 }

    tnSysDebugTransferPercentCompleted OBJECT-TYPE
        SYNTAX         Unsigned32
        MAX-ACCESS     read-only
        STATUS         current
        DESCRIPTION    "The percent completion of the previously
                        executed operation."
        DEFVAL         { 0 }
        ::= { tnSysDebugTransfer 12 }

    tnSysDebugTransferRemoteInetAddressType OBJECT-TYPE
        SYNTAX         InetAddressType
        MAX-ACCESS     read-write
        STATUS         current
        DESCRIPTION    "The value specifies the type of Internet address
                        stored in tnSysDebugTransferRemoteInetAddress."
        DEFVAL         { unknown }
        ::= { tnSysDebugTransfer 15 }

    tnSysDebugTransferRemoteInetAddress OBJECT-TYPE
        SYNTAX         InetAddress
        MAX-ACCESS     read-write
        STATUS         current
        DESCRIPTION    "Indicates the IPv6 address of the remote server."
        DEFVAL         { ''H }
        ::= { tnSysDebugTransfer 14 }

    tnSysDebugTransferScratchDir OBJECT-TYPE
        SYNTAX         SnmpAdminString (SIZE(0..512))
        MAX-ACCESS     read-only
        STATUS         current
        DESCRIPTION    "This contains the file's size in KB, their access
                        date and the filename as 3 attributes per output line
                        format similar to output from ls -ogth."
        ::= { tnSysDebugTransfer 16 }

    tnSysDebugTransferIncludeInDumps OBJECT-TYPE
        SYNTAX         INTEGER {
                          expert(1),
                          basic(2),
                          occ(3)
                       }
        MAX-ACCESS     read-write
        STATUS         current
        DESCRIPTION    "expert - value for include-in-dumps shall have core
                                 files included.
                        basic  - value for include-in-dumps shall have core
                                 files omitted.
                        occ    - occ log transfer support for PSI2T."
        ::= { tnSysDebugTransfer 17 }

    tnSysDebugTransferPort OBJECT-TYPE
        SYNTAX         Unsigned32 (1..65535)
        MAX-ACCESS     read-write
        STATUS         current
        DESCRIPTION    "This attributes indicates the debugdump port."
        DEFVAL         { 21 }
        ::= { tnSysDebugTransfer 18 }

--------------------------------------------------------------------------------
-- License Inventory
--------------------------------------------------------------------------------
    tnSysLicenseInvPathIp OBJECT-TYPE
        SYNTAX         IpAddress
        MAX-ACCESS     read-write
        STATUS         current
        DESCRIPTION    "."
        DEFVAL         { '00000000'H }
        ::= { tnSysLicenseInv 1 }

    tnSysLicenseInvFile OBJECT-TYPE
        SYNTAX         SnmpAdminString (SIZE(0..128))
        MAX-ACCESS     read-write
        STATUS         current
        DESCRIPTION    "."
        DEFVAL         { "./LicenseInv-file" }
        ::= { tnSysLicenseInv 2 }

    tnSysLicenseInvProtocol OBJECT-TYPE
        SYNTAX         AluWdmTransferProtocol
        MAX-ACCESS     read-write
        STATUS         current
        DESCRIPTION    "This attributes indicates the server protocol."
        DEFVAL         { ftp }
        ::= { tnSysLicenseInv 3 }

    tnSysLicenseInvUserId OBJECT-TYPE
        SYNTAX         SnmpAdminString
        MAX-ACCESS     read-write
        STATUS         current
        DESCRIPTION    "The userId used to access the License Inventory server."
        DEFVAL         { "" }
        ::= { tnSysLicenseInv 4 }

    tnSysLicenseInvPassword OBJECT-TYPE
        SYNTAX         SnmpAdminString
        MAX-ACCESS     read-write
        STATUS         current
        DESCRIPTION    "The password used to access the License Inventory server.

                        When read, this attribute will return an empty
                        string if the password has not been set and
                        '********' if it has been set."
        DEFVAL         { "" }
        ::= { tnSysLicenseInv 5 }

    tnSysLicenseInvFileUploadOper OBJECT-TYPE
        SYNTAX         TruthValue
        MAX-ACCESS     read-write
        STATUS         current
        DESCRIPTION    "To display the status of License Inventory."
        DEFVAL         { false }
        ::= { tnSysLicenseInv 6 }

    tnSysLicenseInvPathInetAddressType OBJECT-TYPE
        SYNTAX         InetAddressType
        MAX-ACCESS     read-write
        STATUS         current
        DESCRIPTION    "The value specifies the type of Internet address
                        stored in tnSysLicenseInvPathInetAddress."
        DEFVAL         { unknown }
        ::= { tnSysLicenseInv 7 }

    tnSysLicenseInvPathInetAddress OBJECT-TYPE
        SYNTAX         InetAddress
        MAX-ACCESS     read-write
        STATUS         current
        DESCRIPTION    "Indicates the IPv6 address of the License Inv path."
        DEFVAL         { ''H }
        ::= { tnSysLicenseInv 8 }

    tnSysLicenseInvLastOperPercentCompleted OBJECT-TYPE
        SYNTAX         Unsigned32
        MAX-ACCESS     read-only
        STATUS         current
        DESCRIPTION    "The percent completion of the Last
                        executed operation."
        DEFVAL         { 0 }
        ::= { tnSysLicenseInv 9 }

    tnSysLicenseInvLastUploadFileName OBJECT-TYPE
        SYNTAX         SnmpAdminString
        MAX-ACCESS     read-only
        STATUS         current
        DESCRIPTION    "This attribute indicates the Last Upload filename for the
                        License Inventory."
        DEFVAL         { "" }
        ::= { tnSysLicenseInv 10 }

    tnSysLicenseInvFileLastUploadStatus OBJECT-TYPE
        SYNTAX         INTEGER {
                         success(1),
                         failure(2),
                         none(3)
                       }
        MAX-ACCESS     read-only
        STATUS         current
        DESCRIPTION    "To display the status of License Inventory."
        DEFVAL         { none }
        ::= { tnSysLicenseInv 11 }

    tnSysLicenseInvFileLastUploadTimeStamp OBJECT-TYPE
        SYNTAX         Unsigned32
        MAX-ACCESS     read-only
        STATUS         current
        DESCRIPTION    "The date and time when the License Inventory
                        last upload was completed."
        DEFVAL         { 0 }
        ::= { tnSysLicenseInv 12 }

--    obsolete
--    tnSysDataDumpInfo OBJECT-TYPE ::= { tnSysDataDump 1 }

--------------------------------------------------------------------------------
-- Linux Scalars
--------------------------------------------------------------------------------
    tnSysLinuxRootUserId OBJECT-TYPE
        SYNTAX         SnmpAdminString (SIZE(0..50))
        MAX-ACCESS     read-only
        STATUS         current
        DESCRIPTION    "The Linux root user ID."
        DEFVAL         { "root" }
        ::= { tnSysLinux 1 }

    tnSysLinuxRootUserPassword OBJECT-TYPE
        SYNTAX         SnmpAdminString (SIZE(0..255))
        MAX-ACCESS     read-write
        STATUS         current
        DESCRIPTION    "The Linux root user password."
        DEFVAL         { "" }
        ::= { tnSysLinux 2 }

    tnSysLinuxApplUserId OBJECT-TYPE
        SYNTAX         SnmpAdminString (SIZE(0..50))
        MAX-ACCESS     read-only
        STATUS         current
        DESCRIPTION    "The Linux application user ID."
        DEFVAL         { "appl" }
        ::= { tnSysLinux 3 }

    tnSysLinuxApplUserPassword OBJECT-TYPE
        SYNTAX         SnmpAdminString (SIZE(0..255))
        MAX-ACCESS     read-write
        STATUS         current
        DESCRIPTION    "The Linux application user password."
        DEFVAL         { "" }
        ::= { tnSysLinux 4 }

    tnSysLinuxRootPasswordStatus OBJECT-TYPE
        SYNTAX         TruthValue
        MAX-ACCESS     read-only
        STATUS         current
        DESCRIPTION    "Password status for maint1
                        If password is changed, the value is true.
                        If password is not set (default), the value is false."
        DEFVAL         { false }
        ::= { tnSysLinux 5 }

    tnSysLinuxApplPasswordStatus OBJECT-TYPE
        SYNTAX         TruthValue
        MAX-ACCESS     read-only
        STATUS         current
        DESCRIPTION    "Password status for maint2
                        If password is changed, the value is true.
                        If password is not set (default), the value is false."
        DEFVAL         { false }
        ::= { tnSysLinux 6 }

    tnSysLinuxRootUserStatus OBJECT-TYPE
        SYNTAX         TruthValue
        MAX-ACCESS     read-write
        STATUS         current
        DESCRIPTION    "Remote access enable for Maint1 User."
        DEFVAL         { true }
        ::= { tnSysLinux 7 }

    tnSysLinuxApplUserStatus OBJECT-TYPE
        SYNTAX         TruthValue
        MAX-ACCESS     read-write
        STATUS         current
        DESCRIPTION    "Remote access enable for Maint2 User."
        DEFVAL         { true }
        ::= { tnSysLinux 8 }

    tnSysLinuxLoginInactivityTimeOut OBJECT-TYPE
        SYNTAX         Unsigned32
        UNITS          "minutes"
        MAX-ACCESS     read-write
        STATUS         current
        DESCRIPTION    "Inactivity timeout for Maint1 and Maint2 users.

                        Current configurable range: 0 to 999."
        DEFVAL         { 15 }
        ::= { tnSysLinux 9 }

    tnSysLinuxSmsUserId OBJECT-TYPE
        SYNTAX         SnmpAdminString (SIZE(0..50))
        MAX-ACCESS     read-only
        STATUS         current
        DESCRIPTION    "The System user ID."
        ::= { tnSysLinux 10 }

    tnSysLinuxSmsUserPassword OBJECT-TYPE
        SYNTAX         SnmpAdminString (SIZE(0..255))
        MAX-ACCESS     read-write
        STATUS         current
        DESCRIPTION    "The System user password."
        DEFVAL         { "" }
        ::= { tnSysLinux 11 }

    tnSysLinuxSmsPasswordStatus OBJECT-TYPE
        SYNTAX         TruthValue
        MAX-ACCESS     read-only
        STATUS         current
        DESCRIPTION    "."
        DEFVAL         { false }
        ::= { tnSysLinux 12 }

    tnSysLinuxSmsUserStatus OBJECT-TYPE
        SYNTAX         TruthValue
        MAX-ACCESS     read-write
        STATUS         current
        DESCRIPTION    "."
        DEFVAL         { true }
        ::= { tnSysLinux 13 }

    tnSysLinuxRootUserLocalStatus OBJECT-TYPE
        SYNTAX         TruthValue
        MAX-ACCESS     read-write
        STATUS         current
        DESCRIPTION    "."
        DEFVAL         { true }
        ::= { tnSysLinux 14 }

    tnSysLinuxSecurityCommit OBJECT-TYPE
        SYNTAX         TruthValue
        MAX-ACCESS     read-write
        STATUS         current
        DESCRIPTION    "."
        DEFVAL         { true }
        ::= { tnSysLinux 15 }

    tnSysLinuxRootUserPort OBJECT-TYPE
        SYNTAX         INTEGER {
                         port5122(1),
                         port22(2)
                       }
        MAX-ACCESS     read-write
        STATUS         current
        DESCRIPTION    "."
        DEFVAL         { port5122 }
        ::= { tnSysLinux 16 }

--------------------------------------------------------------------------------
-- IPV6 Scalars
--------------------------------------------------------------------------------
    tnSysIpAclIpv6RxAction OBJECT-TYPE
        SYNTAX         INTEGER {
                         pass(1),
                         block(2),
                         dropAndlog(3)
                       }
        MAX-ACCESS     read-write
        STATUS         current
        DESCRIPTION    "Default action to be taken on received (incoming)
                        packets where ACL IPV6 is enabled but no pattern
                        matches or no action is explicitly defined."
        DEFVAL         { pass }
        ::= { tnSysIpAclIpv6SysDefault 1 }

    tnSysIpAclIpv6TxAction OBJECT-TYPE
        SYNTAX         INTEGER {
                         pass(1),
                         block(2)
                       }
        MAX-ACCESS     read-write
        STATUS         current
        DESCRIPTION    "Default action to be taken on transmitted (outgoing)
                        packets where ACL IPV6 is enabled but no pattern matches
                        or no action is explicitly defined."
        DEFVAL         { pass }
        ::= { tnSysIpAclIpv6SysDefault 2 }

    tnSysIpAclIpv6SnmpCfgEnable OBJECT-TYPE
        SYNTAX         TruthValue
        MAX-ACCESS     read-write
        STATUS         current
        DESCRIPTION    "Indicates whether or not ACL IPV6 configuration is
                        supported via SNMP."
        DEFVAL         { false }
        ::= { tnSysIpAclIpv6SysDefault 3 }

    tnSysIpAclIpv6CfgRestoreToDefault OBJECT-TYPE
        SYNTAX         TruthValue
        MAX-ACCESS     read-write
        STATUS         current
        DESCRIPTION    "If setting to true, it will restore acl_ipv6 config to
                        system default."
        DEFVAL         { false }
        ::= { tnSysIpAclIpv6SysDefault 4 }

    tnSysIpAclIPv6ClearCounter OBJECT-TYPE
        SYNTAX         TruthValue
        MAX-ACCESS     read-write
        STATUS         current
        DESCRIPTION    "Clear IPv6ACL counter to zero."
        DEFVAL         { false }
        ::= { tnSysIpAclIpv6SysDefault 5 }

--------------------------------------------------------------------------------
-- FILE BASED SYSTEM INITIALIZATION Scalars
--------------------------------------------------------------------------------
    tnSysFileInitializationRoot OBJECT-TYPE
        SYNTAX         SnmpAdminString (SIZE(0..255))
        MAX-ACCESS     read-write
        STATUS         current
        DESCRIPTION    "The path to the directory containing releases, relative
                        to the TFTP server root directory.  A forward slash
                        will be prepended if it does not start with one."
        ::= { tnSysFileInitialization 1 }

    tnSysFileInitializationUserId OBJECT-TYPE
        SYNTAX         SnmpAdminString (SIZE(0..32))
        MAX-ACCESS     read-write
        STATUS         current
        DESCRIPTION    "The userId is used to access the RFS."
        DEFVAL         { "" }
        ::= { tnSysFileInitialization 2 }

    tnSysFileInitializationPassword OBJECT-TYPE
        SYNTAX         SnmpAdminString (SIZE(0..32))
        MAX-ACCESS     read-write
        STATUS         current
        DESCRIPTION    "The password is used to access the RFS.  When read,
                        this attribute will return an empty string if the
                        password has not been set and '********' if it has
                        been set."
        DEFVAL         { "" }
        ::= { tnSysFileInitialization 3 }

    tnSysFileInitializationFilename OBJECT-TYPE
        SYNTAX         SnmpAdminString
        MAX-ACCESS     read-write
        STATUS         current
        DESCRIPTION    "This attribute indicates the filename for the file
                        initialization."
        DEFVAL         { "" }
        ::= { tnSysFileInitialization 4 }

    tnSysFileInitializationInetAddressType OBJECT-TYPE
        SYNTAX         InetAddressType
        MAX-ACCESS     read-write
        STATUS         current
        DESCRIPTION    "The value specifies the type of Internet address
                        stored in tnSysFileInitializationInetAddress."
        DEFVAL         { unknown }
        ::= { tnSysFileInitialization 5 }

    tnSysFileInitializationInetAddress OBJECT-TYPE
        SYNTAX         InetAddress
        MAX-ACCESS     read-write
        STATUS         current
        DESCRIPTION    "Indicates the IPv6 address."
        DEFVAL         { ''H }
        ::= { tnSysFileInitialization 6 }

--------------------------------------------------------------------------------
-- OTDRM (Optical Time Domain Reflectometer) Scan System Profile Scalar
--------------------------------------------------------------------------------
    tnSysOtdrScanSystemProfileMAttributeTotal OBJECT-TYPE
        SYNTAX         Integer32
        MAX-ACCESS     read-only
        STATUS         current
        DESCRIPTION    "."
        ::= { tnSysOtdrScanSystemProfileM 1 }

--------------------------------------------------------------------------------
-- OTDRM (Optical Time Domain Reflectometer) Scan System Profile Table
--------------------------------------------------------------------------------
    tnSysOtdrScanSystemProfileMTable OBJECT-TYPE
        SYNTAX         SEQUENCE OF TnSysOtdrScanSystemProfileMEntry
        MAX-ACCESS     not-accessible
        STATUS         current
        DESCRIPTION    "."
        ::= { tnSysOtdrScanSystemProfileM 2 }

    tnSysOtdrScanSystemProfileMEntry OBJECT-TYPE
        SYNTAX         TnSysOtdrScanSystemProfileMEntry
        MAX-ACCESS     not-accessible
        STATUS         current
        DESCRIPTION    "."
        INDEX { tnSysOtdrScanSystemProfileMId }
        ::= { tnSysOtdrScanSystemProfileMTable 1 }

    TnSysOtdrScanSystemProfileMEntry ::= SEQUENCE {
        tnSysOtdrScanSystemProfileMId                      Integer32,
        tnSysOtdrScanSystemProfileMDescription             SnmpAdminString,
        tnSysOtdrScanSystemProfileMWaveLength              Unsigned32,
        tnSysOtdrScanSystemProfileMPulseLength             Unsigned32,
        tnSysOtdrScanSystemProfileMRange                   Unsigned32,
        tnSysOtdrScanSystemProfileMResolution              Unsigned32,
        tnSysOtdrScanSystemProfileMAvgTime                 Unsigned32,
        tnSysOtdrScanSystemProfileMEventThreshold          Unsigned32,
        tnSysOtdrScanSystemProfileMIOR                     Unsigned32
    }

    tnSysOtdrScanSystemProfileMId OBJECT-TYPE
        SYNTAX         Integer32 (1..7)
        MAX-ACCESS     not-accessible
        STATUS         current
        DESCRIPTION    "Unique identifier for the profile.  Range is from
                        1 to 7."
        ::= { tnSysOtdrScanSystemProfileMEntry 1 }

    tnSysOtdrScanSystemProfileMDescription OBJECT-TYPE
        SYNTAX         SnmpAdminString (SIZE(0..80))
        MAX-ACCESS     read-create
        STATUS         current
        DESCRIPTION    "Describes the scan profile."
        ::= { tnSysOtdrScanSystemProfileMEntry 2 }

    tnSysOtdrScanSystemProfileMWaveLength OBJECT-TYPE
        SYNTAX         Unsigned32
        UNITS          "nanometers"
        MAX-ACCESS     read-only
        STATUS         current
        DESCRIPTION    "The wavelength used for the OTDR scan.  The
                        wavelength is 1610 nm, and is not configurable."
        DEFVAL         { 1610 }
        ::= { tnSysOtdrScanSystemProfileMEntry 3 }

    tnSysOtdrScanSystemProfileMPulseLength OBJECT-TYPE
        SYNTAX         Unsigned32
        UNITS          "nanoseconds"
        MAX-ACCESS     read-create
        STATUS         current
        DESCRIPTION    "Length of the pulse.

                        Current values: 5, 10, 30, 100, 300, 1000, 3000,
                        10000, and 20000."
        DEFVAL         { 300 }
        ::= { tnSysOtdrScanSystemProfileMEntry 4 }

    tnSysOtdrScanSystemProfileMRange OBJECT-TYPE
        SYNTAX         Unsigned32
        UNITS          "meters"
        MAX-ACCESS     read-create
        STATUS         current
        DESCRIPTION    "The range of the span that is being probed in
                        meters.

                        Current values: 500, 1000, 2000, 5000,
                            10000, 20000, 40000, 80000, 160000 and 260000."
        DEFVAL         { 160000 }
        ::= { tnSysOtdrScanSystemProfileMEntry 5 }

    tnSysOtdrScanSystemProfileMResolution OBJECT-TYPE
        SYNTAX         Unsigned32
        UNITS          "millimeters"
        MAX-ACCESS     read-create
        STATUS         current
        DESCRIPTION    "Distance resolution of the OTDR scan.

                        Current values: 40, 80, 160, 320, 640, 1200,
                            2500, 5000, 10000, 20000, 40000, 80000, and
                            160000."
        DEFVAL         { 2500 }
        ::= { tnSysOtdrScanSystemProfileMEntry 6 }

    tnSysOtdrScanSystemProfileMAvgTime OBJECT-TYPE
        SYNTAX         Unsigned32 (5..300)
        UNITS          "seconds"
        MAX-ACCESS     read-create
        STATUS         current
        DESCRIPTION    "Signal averaging time for a scan range.

                        Current range: 5 to 300."
        DEFVAL         { 180 }
        ::= { tnSysOtdrScanSystemProfileMEntry 7 }

    tnSysOtdrScanSystemProfileMEventThreshold OBJECT-TYPE
        SYNTAX         Unsigned32
        UNITS          "mB"
        MAX-ACCESS     read-create
        STATUS         current
        DESCRIPTION    "Sys Otdr Scan Event Threshold.
                        Current range: 5 to 100."
        DEFVAL         { 50 }
        ::= { tnSysOtdrScanSystemProfileMEntry 8 }

    tnSysOtdrScanSystemProfileMIOR OBJECT-TYPE
        SYNTAX         Unsigned32
        MAX-ACCESS     read-only
        STATUS         current
        DESCRIPTION    "Sys Otdr Scan IOR.
                        Current range: 1400 to 1600."
        DEFVAL         { 1465 }
        ::= { tnSysOtdrScanSystemProfileMEntry 9 }

--------------------------------------------------------------------------------
-- BLUETOOTH PAN Scalars
--------------------------------------------------------------------------------
    tnSysBtInterfaceDescription OBJECT-TYPE
        SYNTAX         SnmpAdminString (SIZE(0..255))
        MAX-ACCESS     read-write
        STATUS         current
        DESCRIPTION    "BT Description."
        DEFVAL         { "" }
        ::= { tnSysBtInterface 1 }

    tnSysBtInterfaceIpAddr OBJECT-TYPE
        SYNTAX         IpAddress
        MAX-ACCESS     read-write
        STATUS         current
        DESCRIPTION    "Set the IP address of the BT."
        DEFVAL         { 'AC100201'H }
        ::= { tnSysBtInterface 2 }

    tnSysBtInterfaceIpSubMask OBJECT-TYPE
        SYNTAX         IpAddress
        MAX-ACCESS     read-write
        STATUS         current
        DESCRIPTION    "Subnet mask for BtIpSubMask."
        DEFVAL         { 'FFFFFF00'H }  -- 255.255.255.0
        ::= { tnSysBtInterface 3 }

    tnSysBtInterfaceAdminState OBJECT-TYPE
        SYNTAX         TropicAdminStateType
        MAX-ACCESS     read-write
        STATUS         current
        DESCRIPTION    "Administratively enable or disable the BT feature on
                        the USB port.  When enabled, the USB port will come up
                        once a bluetooth dongle is plugged in."
        DEFVAL         { up }
        ::= { tnSysBtInterface 4 }

    tnSysBtInterfaceLinkIntegrityStatus OBJECT-TYPE
        SYNTAX         TropicOperationalStateType
        MAX-ACCESS     read-only
        STATUS         current
        DESCRIPTION    "BT link Integrity Status."
        DEFVAL         { down }
        ::= { tnSysBtInterface 5 }

    tnSysBtInterfaceDHCPServer OBJECT-TYPE
        SYNTAX         INTEGER {
                          enabled(1),
                          disabled(2)
                       }
        MAX-ACCESS     read-write
        STATUS         current
        DESCRIPTION    "Dynamic Host Configuration Protocol on the BT port."
        DEFVAL         { enabled }
        ::= { tnSysBtInterface 6 }

    tnSysBtInterfaceDHCPRange OBJECT-TYPE
        SYNTAX         Unsigned32 (1..10)
        MAX-ACCESS     read-write
        STATUS         current
        DESCRIPTION    "This is the range of the IP pool for the DHCP server.
                        The port can dole out from 1 to up to 10 IP addresses,
                        beginning with the BT port's IP address. This parameter
                        is valid only when dhcp is enabled. For the BT port,
                        the default value is 1, and thus the assigned IP address
                        will be the next address after the BT port's address.
                        For example, if the BT port is 172.16.2.1 (default value),
                        then the assigned IP address for the attached device,
                        i.e., smartphone, will be 172.16.2.2.

                        Current configurable range: 1 to 10"
        DEFVAL         { 1 }
        ::= { tnSysBtInterface 7 }

    tnSysBtInterfaceNodeSerialNum OBJECT-TYPE
        SYNTAX         SnmpAdminString (SIZE(0..16))
        MAX-ACCESS     read-only
        STATUS         current
        DESCRIPTION    "BT serial number."
        DEFVAL         { "" }
        ::= { tnSysBtInterface 8 }

    tnSysBtInterfaceMacAddress OBJECT-TYPE
        SYNTAX         MacAddress
        MAX-ACCESS     read-only
        STATUS         current
        DESCRIPTION    "The value of tnSysBtInterfaceMacAddress specifies the mac
                        address that is assigned to tnSysBtInterfaceMacAddress."
        ::= { tnSysBtInterface 9 }

--------------------------------------------------------------------------------
-- OTDR Scan Results Transfer Scalars
--------------------------------------------------------------------------------
    tnSysOtdrScanResultsTransferRemoteHostIp OBJECT-TYPE
        SYNTAX         IpAddress
        MAX-ACCESS     read-write
        STATUS         current
        DESCRIPTION    "OTDR scan results transfer remote host IP address."
        DEFVAL         { '00000000'H }
        ::= { tnSysOtdrScanResultsTransfer 1 }

    tnSysOtdrScanResultsTransferProtocol OBJECT-TYPE
        SYNTAX         AluWdmNewTransferProtocol
        MAX-ACCESS     read-write
        STATUS         current
        DESCRIPTION    "This attributes indicates the OTDR scan results transfer
                        protocol. Currently, only sftp/ftp is supported."
        DEFVAL         { ftp }
        ::= { tnSysOtdrScanResultsTransfer 2 }

    tnSysOtdrScanResultsTransferUserId OBJECT-TYPE
        SYNTAX         SnmpAdminString (SIZE(0..32))
        MAX-ACCESS     read-write
        STATUS         current
        DESCRIPTION    "The userId is used to access the RFS."
        DEFVAL         { "" }
        ::= { tnSysOtdrScanResultsTransfer 3 }

    tnSysOtdrScanResultsTransferPassword OBJECT-TYPE
        SYNTAX         SnmpAdminString (SIZE(0..32))
        MAX-ACCESS     read-write
        STATUS         current
        DESCRIPTION    "The password is used to access the RFS.
                        When read, this attribute will return an empty
                        string if the password has not been set and
                        '********' if it has been set."
        DEFVAL         { "" }
        ::= { tnSysOtdrScanResultsTransfer 4 }

    tnSysOtdrScanResultsTransferRemotePath OBJECT-TYPE
        SYNTAX         SnmpAdminString (SIZE(0..255))
        MAX-ACCESS     read-write
        STATUS         current
        DESCRIPTION    "OTDR scan results transfer remote path."
        DEFVAL         { "" }
        ::= { tnSysOtdrScanResultsTransfer 5 }

    tnSysOtdrScanResultsTransferCommand OBJECT-TYPE
        SYNTAX         INTEGER {
                         noCmd(1),
                         transferToRfs(2)
                       }
        MAX-ACCESS     read-write
        STATUS         current
        DESCRIPTION    "OTDR scan results transfer command."
        DEFVAL         { noCmd }
        ::= { tnSysOtdrScanResultsTransfer 6 }

    tnSysOtdrScanResultsTransferFilename OBJECT-TYPE
        SYNTAX         SnmpAdminString (SIZE(0..255))
        MAX-ACCESS     read-write
        STATUS         current
        DESCRIPTION    "This attribute indicates the filename for the
                        OTDR file results transfer performed on the node."
        DEFVAL         { "" }
        ::= { tnSysOtdrScanResultsTransfer 7 }

    tnSysOtdrScanResultsTransferRecentSuccessFile OBJECT-TYPE
        SYNTAX         SnmpAdminString
        MAX-ACCESS     read-only
        STATUS         current
        DESCRIPTION    "This attribute indicates the filename for the recent
                        successful OTDR scan results file transfered on the node."
        DEFVAL         { "" }
        ::= { tnSysOtdrScanResultsTransfer 8 }

    tnSysOtdrScanResultsTransferStatus OBJECT-TYPE
        SYNTAX         AluWdmTransferStatus
        MAX-ACCESS     read-only
        STATUS         current
        DESCRIPTION    "This attribute indicates the status of the
                        previously executed tnSysOtdrScanResultsTransferStatus
                        operation."
        DEFVAL         { none }
        ::= { tnSysOtdrScanResultsTransfer 9 }

    tnSysOtdrScanResultsLastTransferTimestamp OBJECT-TYPE
        SYNTAX         Unsigned32
        MAX-ACCESS     read-only
        STATUS         current
        DESCRIPTION    "The date and time when the last file transfer was
                        completed."
        DEFVAL         { 0 }
        ::= { tnSysOtdrScanResultsTransfer 10 }

    tnSysOtdrScanResultsTransferRemoteInetAddressType OBJECT-TYPE
        SYNTAX         InetAddressType
        MAX-ACCESS     read-write
        STATUS         current
        DESCRIPTION    "The value specifies the type of Internet address stored
                        in tnSysOtdrScanResultsTransferRemoteInetAddress."
        DEFVAL         { unknown }
        ::= { tnSysOtdrScanResultsTransfer 11 }

    tnSysOtdrScanResultsTransferRemoteInetAddress OBJECT-TYPE
        SYNTAX         InetAddress
        MAX-ACCESS     read-write
        STATUS         current
        DESCRIPTION    "Indicates the IPv6 address of the remote server."
        DEFVAL         { ''H }
        ::= { tnSysOtdrScanResultsTransfer 12 }

    tnSysOtdrScanResultsTransferPort OBJECT-TYPE
        SYNTAX         Unsigned32 (1..65535)
        MAX-ACCESS     read-write
        STATUS         current
        DESCRIPTION    "This attributes indicates the otdr port."
        DEFVAL         { 21 }
        ::= { tnSysOtdrScanResultsTransfer 13 }

    tnSysOtdrScanResultsTransferRemoveFileFromNE OBJECT-TYPE
        SYNTAX         SnmpAdminString
        MAX-ACCESS     read-write
        STATUS         current
        DESCRIPTION    "Remove the selected .sor file from the NE."
        DEFVAL         { "" }
        ::= { tnSysOtdrScanResultsTransfer 14 }

--------------------------------------------------------------------------------
-- License Manager Scalars
--------------------------------------------------------------------------------
    tnSysLicenseMgrKeepAliveTimer OBJECT-TYPE
        SYNTAX         Unsigned32 (3600..86400)
        MAX-ACCESS     read-write
        STATUS         current
        DESCRIPTION    "the interval (in seconds) for the NE to send a
                        keep-alive message to the license man-ager.  The
                        message will also automatically refresh the
                        entitlements on the NE."
        DEFVAL         { 3600 }
        ::= { tnSysLicenseMgr 1 }

    tnSysLicenseMgrPrimaryServerIp OBJECT-TYPE
        SYNTAX         IpAddress
        MAX-ACCESS     read-write
        STATUS         current
        DESCRIPTION    "Indicates the IPv4 address of the CLM server 1."
        DEFVAL         { '00000000'H }
        ::= { tnSysLicenseMgr 2 }

    tnSysLicenseMgrPrimaryServerInetAddressType OBJECT-TYPE
        SYNTAX         InetAddressType
        MAX-ACCESS     read-write
        STATUS         current
        DESCRIPTION    "The value specifies the type of Internet address stored
                        in tnSysLicenseMgrPrimaryServerInetAddress."
        DEFVAL         { unknown }
        ::= { tnSysLicenseMgr 3 }

    tnSysLicenseMgrPrimaryServerInetAddress OBJECT-TYPE
        SYNTAX         InetAddress
        MAX-ACCESS     read-write
        STATUS         current
        DESCRIPTION    "Indicates the IPv6 address of the CLM server 1."
        DEFVAL         { ''H }
        ::= { tnSysLicenseMgr 4 }

    tnSysLicenseMgrSecondaryServerIp OBJECT-TYPE
        SYNTAX         IpAddress
        MAX-ACCESS     read-write
        STATUS         current
        DESCRIPTION    "Indicates the IPv4 address of the CLM server 2."
        DEFVAL         { '00000000'H }
        ::= { tnSysLicenseMgr 5 }

    tnSysLicenseMgrSecondaryServerInetAddressType OBJECT-TYPE
        SYNTAX         InetAddressType
        MAX-ACCESS     read-write
        STATUS         current
        DESCRIPTION    "The value specifies the type of Internet address stored
                        in tnSysLicenseMgrSecondaryServerInetAddress."
        DEFVAL         { unknown }
        ::= { tnSysLicenseMgr 6 }

    tnSysLicenseMgrSecondaryServerInetAddress OBJECT-TYPE
        SYNTAX         InetAddress
        MAX-ACCESS     read-write
        STATUS         current
        DESCRIPTION    "Indicates the IPv6 address of the CLM server 2."
        DEFVAL         { ''H }
        ::= { tnSysLicenseMgr 7 }

    tnSysLicenseMgrPrimaryServerStatus OBJECT-TYPE
        SYNTAX         INTEGER {
--                          obsolete
--                          unknown(1)
                          active(2),
--                          obsolete
--                          standBy(3),
                          notConnected(4)
                       }
        MAX-ACCESS     read-write
        STATUS         current
        DESCRIPTION    "Indicates the status of CLM Primary server."
        DEFVAL         { notConnected }
        ::= { tnSysLicenseMgr 8 }

    tnSysLicenseMgrSecondaryServerStatus OBJECT-TYPE
        SYNTAX         INTEGER {
--                          obsolete
--                          unknown(1)
                          active(2),
--                          obsolete
--                          standBy(3),
                          notConnected(4)
                       }
        MAX-ACCESS     read-write
        STATUS         current
        DESCRIPTION    "Indicates the status of CLM Secondary server."
        DEFVAL         { notConnected }
        ::= { tnSysLicenseMgr 9 }

    tnSysLicenseMgrExpiration OBJECT-TYPE
        SYNTAX         SnmpAdminString (SIZE(0..64))
        MAX-ACCESS     read-only
        STATUS         current
        DESCRIPTION    "License Expiration date and time."
        DEFVAL         { "" }
        ::= { tnSysLicenseMgr 10 }

    tnSysLicenseMgrTimeOut OBJECT-TYPE
        SYNTAX         Unsigned32 (1..1000)
        MAX-ACCESS     read-write
        STATUS         current
        DESCRIPTION    "Timeout for the NE to wait for the response from CLM
                        server. The failure is declared after the timeout is
                        elapsed."
        DEFVAL         { 5 }
        ::= { tnSysLicenseMgr 11 }

    tnSysLicenseMgrRetries OBJECT-TYPE
        SYNTAX         Unsigned32 (0..100)
        MAX-ACCESS     read-write
        STATUS         current
        DESCRIPTION    "Specifies the number of attempts that the NE will try
                        to contact the specified CLM server that has failed
                        to respond during the previous request. If there is no
                        response from the CLM server after the specified tries
                        then the NE will try to contact the second CLM server
                        if one is provisioned."
        DEFVAL         { 3 }
        ::= { tnSysLicenseMgr 12 }

    tnSysLicenseMgrLastRefresh OBJECT-TYPE
        SYNTAX         SnmpAdminString
        MAX-ACCESS     read-only
        STATUS         current
        DESCRIPTION    "License Last Refresh date and time."
        DEFVAL         { "" }
        ::= { tnSysLicenseMgr 13 }

    tnSysLicenseMgrCertStatus OBJECT-TYPE
        SYNTAX         INTEGER {
                         unknown(1),
                         success(2),
                         failure(3)
                       }
        MAX-ACCESS     read-only
        STATUS         current
        DESCRIPTION    "Indicates the CLM Certificate Status."
        DEFVAL         { unknown }
        ::= { tnSysLicenseMgr 14 }

    tnSysLicenseMgrNextRefreshTime OBJECT-TYPE
        SYNTAX         Integer32
        MAX-ACCESS     read-only
        STATUS         current
        DESCRIPTION    "Time remaining for next refresh in seconds."
        ::= { tnSysLicenseMgr 15 }

---------------------------------------------------------------
-- License Entity Table
---------------------------------------------------------------
    tnLicenseEntityTable OBJECT-TYPE
        SYNTAX         SEQUENCE OF TnLicenseEntityEntry
        MAX-ACCESS     not-accessible
        STATUS         current
        DESCRIPTION    "."
        ::= { tnLicenseObjs 1 }

    tnLicenseEntityEntry OBJECT-TYPE
        SYNTAX         TnLicenseEntityEntry
        MAX-ACCESS     not-accessible
        STATUS         current
        DESCRIPTION    "."
        INDEX { tnLicenseEntity }
        ::= { tnLicenseEntityTable 1 }

    TnLicenseEntityEntry ::=
        SEQUENCE {
            tnLicenseEntity                   Unsigned32,
            tnLicenseEntityRefreshSet         TnCommand,
            tnLicenseEntityNumberInUse        Unsigned32,
            tnLicenseEntityNumberExceedAvail  Unsigned32,
            tnLicenseEntityEntitlementNeeded  Unsigned32
        }

    tnLicenseEntity OBJECT-TYPE
        SYNTAX         Unsigned32
        MAX-ACCESS     not-accessible
        STATUS         current
        DESCRIPTION    "."
        ::= { tnLicenseEntityEntry 1 }

    tnLicenseEntityRefreshSet OBJECT-TYPE
        SYNTAX         TnCommand
        MAX-ACCESS     read-create
        STATUS         current
        DESCRIPTION    "."
        DEFVAL         { noCmd }
        ::= { tnLicenseEntityEntry 2 }

    tnLicenseEntityNumberInUse OBJECT-TYPE
        SYNTAX         Unsigned32
        MAX-ACCESS     read-only
        STATUS         current
        DESCRIPTION    "Number in Use."
        ::= { tnLicenseEntityEntry 3 }

    tnLicenseEntityNumberExceedAvail OBJECT-TYPE
        SYNTAX         Unsigned32
        MAX-ACCESS     read-only
        STATUS         current
        DESCRIPTION    "Number Exceeding available."
        ::= { tnLicenseEntityEntry 4 }

    tnLicenseEntityEntitlementNeeded OBJECT-TYPE
        SYNTAX         Unsigned32
        MAX-ACCESS     read-only
        STATUS         current
        DESCRIPTION    "Entitlement needed by NE."
        ::= { tnLicenseEntityEntry 5 }

---------------------------------------------------------------
-- License Entitlement Table
---------------------------------------------------------------
    tnLicenseEntitlementTable OBJECT-TYPE
        SYNTAX         SEQUENCE OF TnLicenseEntitlementEntry
        MAX-ACCESS     not-accessible
        STATUS         current
        DESCRIPTION    "."
        ::= { tnLicenseObjs 2 }

    tnLicenseEntitlementEntry OBJECT-TYPE
        SYNTAX         TnLicenseEntitlementEntry
        MAX-ACCESS     not-accessible
        STATUS         current
        DESCRIPTION    "."
        INDEX { tnLicenseEntitlementCategoryID,
                tnLicenseEntitlementEntries }
        ::= { tnLicenseEntitlementTable 1 }

    TnLicenseEntitlementEntry ::=
        SEQUENCE {
            tnLicenseEntitlementCategoryID     Unsigned32,
            tnLicenseEntitlementEntries        Unsigned32,
            tnLicenseEntitlementDetails        SnmpAdminString
        }

    tnLicenseEntitlementCategoryID OBJECT-TYPE
        SYNTAX         Unsigned32
        MAX-ACCESS     not-accessible
        STATUS         current
        DESCRIPTION    "."
        ::= { tnLicenseEntitlementEntry 1 }

    tnLicenseEntitlementEntries OBJECT-TYPE
        SYNTAX         Unsigned32
        MAX-ACCESS     not-accessible
        STATUS         current
        DESCRIPTION    "."
        ::= { tnLicenseEntitlementEntry 2 }

    tnLicenseEntitlementDetails OBJECT-TYPE
        SYNTAX         SnmpAdminString (SIZE(0..2047))
        MAX-ACCESS     read-only
        STATUS         current
        DESCRIPTION    "The format will be
                        cardName_LineRate_RequestedCount_MissingCount."
        ::= { tnLicenseEntitlementEntry 3 }

---------------------------------------------------------------
-- Key Store Table
---------------------------------------------------------------
    tnSysKeyStoreServiceTable OBJECT-TYPE
        SYNTAX         SEQUENCE OF TnSysKeyStoreServiceEntry
        MAX-ACCESS     not-accessible
        STATUS         current
        DESCRIPTION    "KeyStore Service Management."
        ::= { tnSysKeyStore 1 }

    tnSysKeyStoreServiceEntry OBJECT-TYPE
        SYNTAX         TnSysKeyStoreServiceEntry
        MAX-ACCESS     not-accessible
        STATUS         current
        DESCRIPTION    "."
        INDEX { tnSysKeyStoreNameIndex,
                tnSysKeyStoreTypeIndex }
        ::= { tnSysKeyStoreServiceTable 1 }

    TnSysKeyStoreServiceEntry ::=
        SEQUENCE {
           tnSysKeyStoreNameIndex                      INTEGER,
           tnSysKeyStoreTypeIndex                      INTEGER,
           tnSysKeyStoreTransServerCommand             INTEGER,
           tnSysKeyStoreTransServerProtocol            INTEGER,
           tnSysKeyStoreTransServerHost                SnmpAdminString,
           tnSysKeyStoreTransServerPort                Unsigned32,
           tnSysKeyStoreTransServerLocation            SnmpAdminString,
           tnSysKeyStoreTransServerUserId              SnmpAdminString,
           tnSysKeyStoreTransServerPassword            SnmpAdminString,
           tnSysKeyStoreTransServerInetAddressType     InetAddressType,
           tnSysKeyStoreTransServerInetAddress         InetAddress,
           tnSysKeyStoreServiceStatus                  INTEGER,
           tnSysKeyStoreServerLastTransferTime         SnmpAdminString,
           tnSysKeyStoreTransServerURI                 SnmpAdminString
        }

    tnSysKeyStoreNameIndex OBJECT-TYPE
        SYNTAX         INTEGER {
                         invalid(1),
                         ztp(2),
                         internecomm(3),
                         system(4)
                       }
        MAX-ACCESS     not-accessible
        STATUS         current
        DESCRIPTION    "KeyStore name."
        ::= { tnSysKeyStoreServiceEntry 1 }

    tnSysKeyStoreTypeIndex OBJECT-TYPE
        SYNTAX         INTEGER {
                         invalid(1),
                         trustAnchor(2),
                         privateKey(3)
                       }
        MAX-ACCESS     not-accessible
        STATUS         current
        DESCRIPTION    "KeyStore type."
        ::= { tnSysKeyStoreServiceEntry 2 }

    tnSysKeyStoreTransServerCommand OBJECT-TYPE
        SYNTAX         INTEGER {
                         noCmd(1),
                         upload(2),
                         download(3),
                         install(4),
                         restoreToDefault(5),
                         downloadThenInstall(6),
                         clear(7)
                       }
        MAX-ACCESS     read-create
        STATUS         current
        DESCRIPTION    "noCmd               - No operation
                        upload              - Upload file to remote server
                        download            - Only download, not install.
                        install             - Install the former downloaded
                        restoreToDefault    - Clear former intalled and install
                                            - to default
                        downloadThenInstall - Download then auto-install
                        clear               - Removes all items installed."
        ::= { tnSysKeyStoreServiceEntry 3 }

    tnSysKeyStoreTransServerProtocol OBJECT-TYPE
        SYNTAX         INTEGER {
                         invalid(1),
                         https(2),
                         sftp(3)
                       }
        MAX-ACCESS     read-create
        STATUS         current
        DESCRIPTION    "KeyStore transfer server protocol:
                          invalid - Not configed yet
                          https   - Use https protocol
                          sftp    - Use sftp protocol."
        ::= { tnSysKeyStoreServiceEntry 4 }

    tnSysKeyStoreTransServerHost OBJECT-TYPE
        SYNTAX         SnmpAdminString (SIZE(0..255))
        MAX-ACCESS     read-create
        STATUS         current
        DESCRIPTION    "Domain or ip address of URI. https used only."
        ::= { tnSysKeyStoreServiceEntry 5 }

    tnSysKeyStoreTransServerPort OBJECT-TYPE
        SYNTAX         Unsigned32
        MAX-ACCESS     read-create
        STATUS         current
        DESCRIPTION    "Port of URI.  https used only."
        ::= { tnSysKeyStoreServiceEntry 6 }

    tnSysKeyStoreTransServerLocation OBJECT-TYPE
        SYNTAX         SnmpAdminString (SIZE(0..255))
        MAX-ACCESS     read-create
        STATUS         current
        DESCRIPTION    "For https: location of URI; for others: path on server."
        ::= { tnSysKeyStoreServiceEntry 7 }

    tnSysKeyStoreTransServerUserId OBJECT-TYPE
        SYNTAX         SnmpAdminString (SIZE(0..32))
        MAX-ACCESS     read-create
        STATUS         current
        DESCRIPTION    "Username for authentication."
        ::= { tnSysKeyStoreServiceEntry 8 }

    tnSysKeyStoreTransServerPassword OBJECT-TYPE
        SYNTAX         SnmpAdminString (SIZE(0..256))
        MAX-ACCESS     read-create
        STATUS         current
        DESCRIPTION    "Password for authentication."
        ::= { tnSysKeyStoreServiceEntry 9 }

    tnSysKeyStoreTransServerInetAddressType OBJECT-TYPE
        SYNTAX         InetAddressType
        MAX-ACCESS     read-create
        STATUS         current
        DESCRIPTION    "."
        ::= { tnSysKeyStoreServiceEntry 10 }

    tnSysKeyStoreTransServerInetAddress OBJECT-TYPE
        SYNTAX         InetAddress
        MAX-ACCESS     read-create
        STATUS         current
        DESCRIPTION    "."
        ::= { tnSysKeyStoreServiceEntry 11 }

    tnSysKeyStoreServiceStatus OBJECT-TYPE
        SYNTAX         INTEGER {
                         none(1),
                         installed(2),
                         downloaded(3),
                         in-progress(4),
                         transferfail(5),
                         formaterror(6)
                       }
        MAX-ACCESS     read-only
        STATUS         current
        DESCRIPTION    "Last operation status:
                          none         - No command
                          installed    - Installed successfully
                          downloaded   - Downloaded successfully
                          in-progress  - Processing and need to wait
                          transferfail - File transfer fail
                          formaterror  - File format error."
        ::= { tnSysKeyStoreServiceEntry 12 }

    tnSysKeyStoreServerLastTransferTime OBJECT-TYPE
        SYNTAX         SnmpAdminString (SIZE(0..255))
        MAX-ACCESS     read-only
        STATUS         current
        DESCRIPTION    "The last transfer (download/upload) time."
        ::= { tnSysKeyStoreServiceEntry 13 }

    tnSysKeyStoreTransServerURI OBJECT-TYPE
        SYNTAX         SnmpAdminString (SIZE(0..511))
        MAX-ACCESS     read-create
        STATUS         current
        DESCRIPTION    "URI."
        ::= { tnSysKeyStoreServiceEntry 14 }

---------------------------------------------------------------
-- Key Store Certificates Info Table
---------------------------------------------------------------
    tnSysKeyStoreCertInfoTable OBJECT-TYPE
        SYNTAX         SEQUENCE OF TnSysKeyStoreCertInfoEntry
        MAX-ACCESS     not-accessible
        STATUS         current
        DESCRIPTION    "KeyStore Certificate Information."
        ::= { tnSysKeyStore 2 }

    tnSysKeyStoreCertInfoEntry OBJECT-TYPE
        SYNTAX         TnSysKeyStoreCertInfoEntry
        MAX-ACCESS     not-accessible
        STATUS         current
        DESCRIPTION    "."
        INDEX { tnSysKeyStoreCertRepositoryIndex,
                tnSysKeyStoreCertIndex }
        ::= { tnSysKeyStoreCertInfoTable 1 }

    TnSysKeyStoreCertInfoEntry ::=
        SEQUENCE {
           tnSysKeyStoreCertRepositoryIndex          INTEGER,
           tnSysKeyStoreCertIndex                    Unsigned32,
           tnSysKeyStoreCertVersion                  SnmpAdminString,
           tnSysKeyStoreCertSerialNumber             SnmpAdminString,
           tnSysKeyStoreCertSignatureAlgorithm       SnmpAdminString,
           tnSysKeyStoreCertIssuer                   SnmpAdminString,
           tnSysKeyStoreCertValidity                 SnmpAdminString,
           tnSysKeyStoreCertSubject                  SnmpAdminString,
           tnSysKeyStoreCertSubjectPublicKeyInfo     SnmpAdminString,
           tnSysKeyStoreCertKeyUsage                 SnmpAdminString,
           tnSysKeyStoreCertSubjectAlternativeName   SnmpAdminString,
           tnSysKeyStoreCertExtendedKeyUsage         SnmpAdminString,
           tnSysKeyStoreCertBasicConstraints         SnmpAdminString,
           tnSysKeyStoreCertSHA256Fingerprint        SnmpAdminString
        }

    tnSysKeyStoreCertRepositoryIndex OBJECT-TYPE
        SYNTAX         INTEGER {
                         invalid(1),
                         trustAnchorInstalledOfZtp(2),
                         trustAnchorDownLoadedOfZtp(3),
                         trustAnchorInstalledOfSystem(4),
                         trustAnchorDownLoadedOfSystem(5)
                       }
        MAX-ACCESS     not-accessible
        STATUS         current
        DESCRIPTION    "KeyStore certificate repository."
        ::= { tnSysKeyStoreCertInfoEntry 1 }

    tnSysKeyStoreCertIndex OBJECT-TYPE
        SYNTAX         Unsigned32
        MAX-ACCESS     not-accessible
        STATUS         current
        DESCRIPTION    "."
        ::= { tnSysKeyStoreCertInfoEntry 2 }

    tnSysKeyStoreCertVersion OBJECT-TYPE
        SYNTAX         SnmpAdminString (SIZE(0..31))
        MAX-ACCESS     read-only
        STATUS         current
        DESCRIPTION    "Certificate version."
        ::= { tnSysKeyStoreCertInfoEntry 3 }

    tnSysKeyStoreCertSerialNumber OBJECT-TYPE
        SYNTAX         SnmpAdminString (SIZE(0..63))
        MAX-ACCESS     read-only
        STATUS         current
        DESCRIPTION    "Certificate serial number."
        ::= { tnSysKeyStoreCertInfoEntry 4 }

    tnSysKeyStoreCertSignatureAlgorithm OBJECT-TYPE
        SYNTAX         SnmpAdminString (SIZE(0..63))
        MAX-ACCESS     read-only
        STATUS         current
        DESCRIPTION    "Certificate signature algorithm."
        ::= { tnSysKeyStoreCertInfoEntry 5 }

    tnSysKeyStoreCertIssuer OBJECT-TYPE
        SYNTAX         SnmpAdminString (SIZE(0..511))
        MAX-ACCESS     read-only
        STATUS         current
        DESCRIPTION    "Certificate issuer."
        ::= { tnSysKeyStoreCertInfoEntry 6 }

    tnSysKeyStoreCertValidity OBJECT-TYPE
        SYNTAX         SnmpAdminString (SIZE(0..255))
        MAX-ACCESS     read-only
        STATUS         current
        DESCRIPTION    "Certificate validity."
        ::= { tnSysKeyStoreCertInfoEntry 7 }

    tnSysKeyStoreCertSubject OBJECT-TYPE
        SYNTAX         SnmpAdminString (SIZE(0..511))
        MAX-ACCESS     read-only
        STATUS         current
        DESCRIPTION    "Certificate subject."
        ::= { tnSysKeyStoreCertInfoEntry 8 }

    tnSysKeyStoreCertSubjectPublicKeyInfo OBJECT-TYPE
        SYNTAX         SnmpAdminString (SIZE(0..63))
        MAX-ACCESS     read-only
        STATUS         current
        DESCRIPTION    "Certificate subject publicKey info."
        ::= { tnSysKeyStoreCertInfoEntry 9 }

    tnSysKeyStoreCertKeyUsage OBJECT-TYPE
        SYNTAX         SnmpAdminString (SIZE(0..127))
        MAX-ACCESS     read-only
        STATUS         current
        DESCRIPTION    "Certificate key usage."
        ::= { tnSysKeyStoreCertInfoEntry 10 }

    tnSysKeyStoreCertSubjectAlternativeName OBJECT-TYPE
        SYNTAX         SnmpAdminString (SIZE(0..512))
        MAX-ACCESS     read-only
        STATUS         current
        DESCRIPTION    "Certificate subject alternative name."
        ::= { tnSysKeyStoreCertInfoEntry 11 }

    tnSysKeyStoreCertExtendedKeyUsage OBJECT-TYPE
        SYNTAX         SnmpAdminString (SIZE(0..127))
        MAX-ACCESS     read-only
        STATUS         current
        DESCRIPTION    "Certificate extended key usage."
        ::= { tnSysKeyStoreCertInfoEntry 12 }

    tnSysKeyStoreCertBasicConstraints OBJECT-TYPE
        SYNTAX         SnmpAdminString (SIZE(0..127))
        MAX-ACCESS     read-only
        STATUS         current
        DESCRIPTION    "Certificate basic constraints."
        ::= { tnSysKeyStoreCertInfoEntry 13 }

    tnSysKeyStoreCertSHA256Fingerprint OBJECT-TYPE
        SYNTAX         SnmpAdminString (SIZE(0..127))
        MAX-ACCESS     read-only
        STATUS         current
        DESCRIPTION    "Certificate SHA256 Fingerprint."
        ::= { tnSysKeyStoreCertInfoEntry 14 }

--------------------------------------------------------------------------------
-- BgpPeer Table
--------------------------------------------------------------------------------
    tnSysBgpPeerTable OBJECT-TYPE
        SYNTAX         SEQUENCE OF TnSysBgpPeerEntry
        MAX-ACCESS     not-accessible
        STATUS         current
        DESCRIPTION    "."
        ::= { tnSysBgp 1 }

    tnSysBgpPeerEntry OBJECT-TYPE
        SYNTAX         TnSysBgpPeerEntry
        MAX-ACCESS     not-accessible
        STATUS         current
        DESCRIPTION    "."
        INDEX { tnSysBgpPeerIndex }
        ::= { tnSysBgpPeerTable 1 }

    TnSysBgpPeerEntry ::= SEQUENCE {
        tnSysBgpPeerIndex                    Unsigned32,
        tnSysBgpPeerRowStatus                RowStatus,
        tnSysBgpPeerInetAddressType          InetAddressType,
        tnSysBgpPeerIp                       IpAddress,
        tnSysBgpPeerInetAddress              InetAddress,
        tnSysBgpPeerRemoteASN                Unsigned32,
        tnSysBgpPeerSecurityKey              SnmpAdminString,
        tnSysBgpPeerRouterId                 IpAddress,
        tnSysBgpPeerStatus                   INTEGER,
        tnSysBgpMaxPrefixIpv4Limit           Unsigned32,
        tnSysBgpMaxPrefixIpv4Threshold       Unsigned32,
        tnSysBgpMaxPrefixIpv4Action          NokiaSysBgpMaxPrefixAction,
        tnSysBgpMaxPrefixIpv6Limit           Unsigned32,
        tnSysBgpMaxPrefixIpv6Threshold       Unsigned32,
        tnSysBgpMaxPrefixIpv6Action          NokiaSysBgpMaxPrefixAction,
        tnSysBgpStatsIpv4PrefixInCount       Unsigned32,
        tnSysBgpStatsIpv6PrefixInCount       Unsigned32,
        tnSysBgpStatsIpv4PrefixOutCount      Unsigned32,
        tnSysBgpStatsIpv6PrefixOutCount      Unsigned32,
        tnSysBgpPeerStatsInetAddressType     InetAddressType,
        tnSysBgpPeerStatsIp                  IpAddress,
        tnSysBgpPeerStatsInetAddress         InetAddress
    }

    tnSysBgpPeerIndex OBJECT-TYPE
        SYNTAX         Unsigned32
        MAX-ACCESS     not-accessible
        STATUS         current
        DESCRIPTION    "."
        ::= { tnSysBgpPeerEntry 1 }

    tnSysBgpPeerRowStatus OBJECT-TYPE
        SYNTAX         RowStatus
        MAX-ACCESS     read-create
        STATUS         current
        DESCRIPTION    "."
        ::= { tnSysBgpPeerEntry 2 }

    tnSysBgpPeerInetAddressType OBJECT-TYPE
        SYNTAX         InetAddressType
        MAX-ACCESS     read-create
        STATUS         current
        DESCRIPTION    "The value specifies the type of Internet address stored
                        in tnSysBgpPeerInetAddress."
        DEFVAL         { unknown }
        ::= { tnSysBgpPeerEntry 3 }

    tnSysBgpPeerIp OBJECT-TYPE
        SYNTAX         IpAddress
        MAX-ACCESS     read-create
        STATUS         current
        DESCRIPTION    "IP address."
        DEFVAL         { '00000000'H }
        ::= { tnSysBgpPeerEntry 4 }

    tnSysBgpPeerInetAddress OBJECT-TYPE
        SYNTAX         InetAddress
        MAX-ACCESS     read-create
        STATUS         current
        DESCRIPTION    "Indicates the IPv6 address."
        DEFVAL         { ''H }
        ::= { tnSysBgpPeerEntry 5 }

    tnSysBgpPeerRemoteASN OBJECT-TYPE
        SYNTAX         Unsigned32
        MAX-ACCESS     read-create
        STATUS         current
        DESCRIPTION    "."
        ::= { tnSysBgpPeerEntry 6 }

    tnSysBgpPeerSecurityKey OBJECT-TYPE
        SYNTAX         SnmpAdminString (SIZE(0..80))
        MAX-ACCESS     read-create
        STATUS         current
        DESCRIPTION    "."
        DEFVAL         { "" }
        ::= { tnSysBgpPeerEntry 7 }

    tnSysBgpPeerRouterId OBJECT-TYPE
        SYNTAX         IpAddress
        MAX-ACCESS     read-only
        STATUS         current
        DESCRIPTION    "IP address."
        DEFVAL         { '00000000'H }
        ::= { tnSysBgpPeerEntry 8 }

    tnSysBgpPeerStatus OBJECT-TYPE
        SYNTAX         INTEGER {
                         idle(1),
                         connect(2),
                         active(3),
                         openSent(4),
                         openConfirm(5),
                         established(6)
                       }
        MAX-ACCESS     read-only
        STATUS         current
        DESCRIPTION    "."
        ::= { tnSysBgpPeerEntry 9 }

    tnSysBgpMaxPrefixIpv4Limit OBJECT-TYPE
        SYNTAX         Unsigned32
        MAX-ACCESS     read-create
        STATUS         current
        DESCRIPTION    "."
        ::= { tnSysBgpPeerEntry 10 }

    tnSysBgpMaxPrefixIpv4Threshold OBJECT-TYPE
        SYNTAX         Unsigned32
        MAX-ACCESS     read-create
        STATUS         current
        DESCRIPTION    "."
        ::= { tnSysBgpPeerEntry 11 }

    tnSysBgpMaxPrefixIpv4Action OBJECT-TYPE
        SYNTAX         NokiaSysBgpMaxPrefixAction
        MAX-ACCESS     read-create
        STATUS         current
        DESCRIPTION    "."
        ::= { tnSysBgpPeerEntry 12 }

    tnSysBgpMaxPrefixIpv6Limit OBJECT-TYPE
        SYNTAX         Unsigned32
        MAX-ACCESS     read-create
        STATUS         current
        DESCRIPTION    "."
        ::= { tnSysBgpPeerEntry 13 }

    tnSysBgpMaxPrefixIpv6Threshold OBJECT-TYPE
        SYNTAX         Unsigned32
        MAX-ACCESS     read-create
        STATUS         current
        DESCRIPTION    "."
        ::= { tnSysBgpPeerEntry 14 }

    tnSysBgpMaxPrefixIpv6Action OBJECT-TYPE
        SYNTAX         NokiaSysBgpMaxPrefixAction
        MAX-ACCESS     read-create
        STATUS         current
        DESCRIPTION    "."
        ::= { tnSysBgpPeerEntry 15 }

    tnSysBgpStatsIpv4PrefixInCount OBJECT-TYPE
        SYNTAX         Unsigned32
        MAX-ACCESS     read-only
        STATUS         current
        DESCRIPTION    "."
        ::= { tnSysBgpPeerEntry 16 }

    tnSysBgpStatsIpv6PrefixInCount OBJECT-TYPE
        SYNTAX         Unsigned32
        MAX-ACCESS     read-only
        STATUS         current
        DESCRIPTION    "."
        ::= { tnSysBgpPeerEntry 17 }

    tnSysBgpStatsIpv4PrefixOutCount OBJECT-TYPE
        SYNTAX         Unsigned32
        MAX-ACCESS     read-only
        STATUS         current
        DESCRIPTION    "."
        ::= { tnSysBgpPeerEntry 18 }

    tnSysBgpStatsIpv6PrefixOutCount OBJECT-TYPE
        SYNTAX         Unsigned32
        MAX-ACCESS     read-only
        STATUS         current
        DESCRIPTION    "."
        ::= { tnSysBgpPeerEntry 19 }

    tnSysBgpPeerStatsInetAddressType OBJECT-TYPE
        SYNTAX         InetAddressType
        MAX-ACCESS     read-create
        STATUS         current
        DESCRIPTION    "The value specifies the type of Internet address stored
                        in tnSysBgpPeerStatsInetAddress."
        DEFVAL         { unknown }
        ::= { tnSysBgpPeerEntry 20 }

    tnSysBgpPeerStatsIp OBJECT-TYPE
        SYNTAX         IpAddress
        MAX-ACCESS     read-create
        STATUS         current
        DESCRIPTION    "IP address."
        DEFVAL         { '00000000'H }
        ::= { tnSysBgpPeerEntry 21 }

    tnSysBgpPeerStatsInetAddress OBJECT-TYPE
        SYNTAX         InetAddress
        MAX-ACCESS     read-create
        STATUS         current
        DESCRIPTION    "Indicates the IPv6 address."
        DEFVAL         { ''H }
        ::= { tnSysBgpPeerEntry 22 }

--------------------------------------------------------------------------------
-- Discover Me Table
--------------------------------------------------------------------------------
    tnSysDiscoverMeTraps OBJECT-TYPE
        SYNTAX         TmnxEnabledDisabled
        MAX-ACCESS     read-write
        STATUS         current
        DESCRIPTION    "Enable or disable the sending of 'discover me' traps
                        by the system."
        DEFVAL         { disabled }
        ::= { tnSysDiscoverMe 1 }

--------------------------------------------------------------------------------
-- Syslog Server Table
--------------------------------------------------------------------------------
    tnSyslogServerTable OBJECT-TYPE
        SYNTAX         SEQUENCE OF TnSyslogServerEntry
        MAX-ACCESS     not-accessible
        STATUS         current
        DESCRIPTION    "."
        ::= { tnSyslogServer 1 }

    tnSyslogServerEntry OBJECT-TYPE
        SYNTAX         TnSyslogServerEntry
        MAX-ACCESS     not-accessible
        STATUS         current
        DESCRIPTION    "."
        INDEX { tnSyslogServerIndex  }
        ::= { tnSyslogServerTable 1 }

    TnSyslogServerEntry ::=
        SEQUENCE {
            tnSyslogServerIndex                  Unsigned32,
            tnSyslogServerIpAddress              IpAddress,
            tnSyslogServerPort                   Unsigned32,
            tnSyslogServerFacility               INTEGER,
            tnSyslogServerPriority               INTEGER,
            tnSyslogServerEnabled                TruthValue,
            tnSyslogServerInetAddress            InetAddress,
            tnSyslogServerInetAddressType        InetAddressType,
            tnSyslogServerProtocol               INTEGER,
            tnSyslogServerType                   INTEGER,
            tnSyslogServerDomain                 SnmpAdminString
        }

    tnSyslogServerIndex OBJECT-TYPE
        SYNTAX         Unsigned32
        MAX-ACCESS     not-accessible
        STATUS         current
        DESCRIPTION    "."
        ::= { tnSyslogServerEntry 1 }

    tnSyslogServerIpAddress OBJECT-TYPE
        SYNTAX         IpAddress
        MAX-ACCESS     read-create
        STATUS         current
        DESCRIPTION    "."
        DEFVAL         { '00000000'H }
        ::= { tnSyslogServerEntry 2 }

    tnSyslogServerPort OBJECT-TYPE
        SYNTAX         Unsigned32 (1..65535)
        MAX-ACCESS     read-create
        STATUS         current
        DESCRIPTION    "."
        DEFVAL         { 514 }
        ::= { tnSyslogServerEntry 3 }

    tnSyslogServerFacility OBJECT-TYPE
        SYNTAX         INTEGER {
                         kern(1),
                         user(2),
                         mail(3),
                         daemon(4),
                         auth(5),
                         syslog(6),
                         lpr(7),
                         news(8),
                         uucp(9),
                         cron(10),
                         authPriv(11),
                         ftp(12),
                         local0(13),
                         local1(14),
                         local2(15),
                         local3(16),
                         local4(17),
                         local5(18),
                         local6(19),
                         local7(20),
                         all(21),
                         logAudit(22),
                         logAlert(23)
                       }
        MAX-ACCESS     read-create
        STATUS         current
        DESCRIPTION    "."
        DEFVAL         { local0 }
        ::= { tnSyslogServerEntry 4 }

    tnSyslogServerPriority OBJECT-TYPE
        SYNTAX         INTEGER {
                         emergency(1),
                         alert(2),
                         critical(3),
                         error(4),
                         warning(5),
                         notice(6),
                         info(7),
                         debug(8)
                       }
        MAX-ACCESS     read-create
        STATUS         current
        DESCRIPTION    "."
        DEFVAL         { debug }
        ::= { tnSyslogServerEntry 5 }

    tnSyslogServerEnabled OBJECT-TYPE
        SYNTAX         TruthValue
        MAX-ACCESS     read-create
        STATUS         current
        DESCRIPTION    "."
        DEFVAL         { false }
        ::= { tnSyslogServerEntry 6 }

    tnSyslogServerInetAddress OBJECT-TYPE
        SYNTAX         InetAddress
        MAX-ACCESS     read-create
        STATUS         current
        DESCRIPTION    "Indicates the IPv6 address of the Syslog Server."
        DEFVAL         { ''H }
        ::= { tnSyslogServerEntry 7 }

    tnSyslogServerInetAddressType OBJECT-TYPE
        SYNTAX         InetAddressType
        MAX-ACCESS     read-create
        STATUS         current
        DESCRIPTION    "The value specifies the type of Internet address
                        stored in tnSyslogServerInetAddress."
        DEFVAL         { unknown }
        ::= { tnSyslogServerEntry 8 }

    tnSyslogServerProtocol OBJECT-TYPE
        SYNTAX         INTEGER {
                         udp(1),
                         tcp(2),
                         tls(3)
                       }
        MAX-ACCESS     read-create
        STATUS         current
        DESCRIPTION    "Syslog Transmission Protocol."
        DEFVAL         { udp }
        ::= { tnSyslogServerEntry 9 }

    tnSyslogServerType OBJECT-TYPE
        SYNTAX         INTEGER {
                         ip(1),
                         domain(2)
                       }
        MAX-ACCESS     read-create
        STATUS         current
        DESCRIPTION    "Syslog Server Type."
        ::= { tnSyslogServerEntry 10 }

    tnSyslogServerDomain OBJECT-TYPE
        SYNTAX         SnmpAdminString
        MAX-ACCESS     read-create
        STATUS         current
        DESCRIPTION    "Syslog Server Domain."
        ::= { tnSyslogServerEntry 11 }

--------------------------------------------------------------------------------
-- PCT Verification Scalars
--------------------------------------------------------------------------------
    tnPctVerificationPeriod OBJECT-TYPE
        SYNTAX         Unsigned32
        MAX-ACCESS     read-write
        STATUS         current
        DESCRIPTION    "."
        DEFVAL         { 6 }
        ::= { tnPctObjs 1 }

    tnPctVerificationLossThreshold OBJECT-TYPE
        SYNTAX         Integer32
        UNITS          "mB"
        MAX-ACCESS     read-write
        STATUS         current
        DESCRIPTION    "Verification Port to Port loss Threshold.
                        Current configurable range:100 to 500 mB in steps of 10.
                        -100 indicates that the threshold is not configured."
        ::= { tnPctObjs 2 }

    tnPctVerificationOffset OBJECT-TYPE
        SYNTAX         Unsigned32
        MAX-ACCESS     read-write
        STATUS         current
        DESCRIPTION    "."
        DEFVAL         { 0 }
        ::= { tnPctObjs 3 }

    tnPctVerificationStatus OBJECT-TYPE
        SYNTAX         INTEGER {
                         running(1),
                         notRunning(2),
                         disabled(3),
                         singlePath(4)
                       }
        MAX-ACCESS     read-only
        STATUS         current
        DESCRIPTION    "."
        ::= { tnPctObjs 4 }

---------------------------------------------------------------
-- NIAP HostKey Table
---------------------------------------------------------------
    tnHostKeyTable OBJECT-TYPE
        SYNTAX         SEQUENCE OF TnHostKeyEntry
        MAX-ACCESS     not-accessible
        STATUS         current
        DESCRIPTION    "."
        ::= { tnKeyObjs 1 }

    tnHostKeyEntry OBJECT-TYPE
        SYNTAX         TnHostKeyEntry
        MAX-ACCESS     not-accessible
        STATUS         current
        DESCRIPTION    "."
        INDEX { tnHostKeyModuleID,
                tnHostKeyIndex }
        ::= { tnHostKeyTable 1 }

    TnHostKeyEntry ::= SEQUENCE {
        tnHostKeyModuleID     Integer32,
        tnHostKeyIndex        Integer32,
        tnHostKeyString1      SnmpAdminString,
        tnHostKeyString2      SnmpAdminString
    }

    tnHostKeyModuleID OBJECT-TYPE
        SYNTAX         Integer32
        MAX-ACCESS     not-accessible
        STATUS         current
        DESCRIPTION    "Host key string module ID."
        ::= { tnHostKeyEntry 1 }

    tnHostKeyIndex OBJECT-TYPE
        SYNTAX         Integer32
        MAX-ACCESS     not-accessible
        STATUS         current
        DESCRIPTION    "Host key string key index."
        ::= { tnHostKeyEntry 2 }

    tnHostKeyString1 OBJECT-TYPE
        SYNTAX         SnmpAdminString (SIZE(0..2048))
        MAX-ACCESS     read-create
        STATUS         current
        DESCRIPTION    "Host key string 1."
        ::= { tnHostKeyEntry 3 }

    tnHostKeyString2 OBJECT-TYPE
        SYNTAX         SnmpAdminString (SIZE(0..2048))
        MAX-ACCESS     read-create
        STATUS         current
        DESCRIPTION    "Host key string 2."
        ::= { tnHostKeyEntry 4 }

---------------------------------------------------------------
-- NIAP Ssh Priv Key Table
---------------------------------------------------------------
    tnSshPrivKeyTable OBJECT-TYPE
        SYNTAX         SEQUENCE OF TnSshPrivKeyEntry
        MAX-ACCESS     not-accessible
        STATUS         current
        DESCRIPTION    "."
        ::= { tnKeyObjs 2 }

    tnSshPrivKeyEntry OBJECT-TYPE
        SYNTAX         TnSshPrivKeyEntry
        MAX-ACCESS     not-accessible
        STATUS         current
        DESCRIPTION    "."
        INDEX { tnSshPrivKeyModuleID }
        ::= { tnSshPrivKeyTable 1 }

    TnSshPrivKeyEntry ::= SEQUENCE {
        tnSshPrivKeyModuleID     Integer32,
        tnSshPrivKeyString1      SnmpAdminString,
        tnSshPrivKeyString2      SnmpAdminString,
        tnSshPrivKeyPassword     SnmpAdminString
    }

    tnSshPrivKeyModuleID OBJECT-TYPE
        SYNTAX         Integer32
        MAX-ACCESS     not-accessible
        STATUS         current
        DESCRIPTION    "Ssh Private key string module ID."
        ::= { tnSshPrivKeyEntry 1 }

    tnSshPrivKeyString1 OBJECT-TYPE
        SYNTAX         SnmpAdminString (SIZE(0..2048))
        MAX-ACCESS     read-create
        STATUS         current
        DESCRIPTION    "Ssh Private key string 1."
        ::= { tnSshPrivKeyEntry 2 }

    tnSshPrivKeyString2 OBJECT-TYPE
        SYNTAX         SnmpAdminString (SIZE(0..2048))
        MAX-ACCESS     read-create
        STATUS         current
        DESCRIPTION    "Ssh Private key string 2."
        ::= { tnSshPrivKeyEntry 3 }

    tnSshPrivKeyPassword OBJECT-TYPE
        SYNTAX         SnmpAdminString (SIZE(0..128))
        MAX-ACCESS     read-create
        STATUS         current
        DESCRIPTION    "Ssh Private key password."
        ::= { tnSshPrivKeyEntry 4 }

---------------------------------------------------------------
-- NIAP SysNESshKey Table
---------------------------------------------------------------
    tnSysNESshKeyTable OBJECT-TYPE
        SYNTAX         SEQUENCE OF TnSysNESshKeyEntry
        MAX-ACCESS     not-accessible
        STATUS         current
        DESCRIPTION    "."
        ::= { tnKeyObjs 3 }

    tnSysNESshKeyEntry OBJECT-TYPE
        SYNTAX         TnSysNESshKeyEntry
        MAX-ACCESS     not-accessible
        STATUS         current
        DESCRIPTION    "."
        INDEX { tnSysNESshKeyUserName,
                tnSysNESshKeyIndex }
        ::= { tnSysNESshKeyTable 1 }

    TnSysNESshKeyEntry ::= SEQUENCE {
        tnSysNESshKeyUserName     SnmpAdminString,
        tnSysNESshKeyIndex        Integer32,
        tnSysNESshKeyRowStatus    RowStatus,
        tnSysNESshKeyString1      SnmpAdminString,
        tnSysNESshKeyString2      SnmpAdminString
    }

    tnSysNESshKeyUserName OBJECT-TYPE
        SYNTAX         SnmpAdminString (SIZE(1..64))
        MAX-ACCESS     not-accessible
        STATUS         current
        DESCRIPTION    "."
        ::= { tnSysNESshKeyEntry 1 }

    tnSysNESshKeyIndex OBJECT-TYPE
        SYNTAX         Integer32
        MAX-ACCESS     not-accessible
        STATUS         current
        DESCRIPTION    "."
        ::= { tnSysNESshKeyEntry 2 }

    tnSysNESshKeyRowStatus OBJECT-TYPE
        SYNTAX         RowStatus
        MAX-ACCESS     read-create
        STATUS         current
        DESCRIPTION    "The row status."
        ::= { tnSysNESshKeyEntry 3 }


    tnSysNESshKeyString1 OBJECT-TYPE
        SYNTAX         SnmpAdminString (SIZE(0..2048))
        MAX-ACCESS     read-create
        STATUS         current
        DESCRIPTION    "The SSH key string 1.
                        Provisions the user public keys used for SSH user
                        authentication.  The number of keys configurable per
                        user is defined by available key indices."
        ::= { tnSysNESshKeyEntry 4 }

    tnSysNESshKeyString2 OBJECT-TYPE
        SYNTAX         SnmpAdminString (SIZE(0..2048))
        MAX-ACCESS     read-create
        STATUS         current
        DESCRIPTION    "The SSH key string 2.
                        Provisions the user public keys used for SSH user
                        authentication. The number of keys configurable per
                        user is defined by available key indices."
        ::= { tnSysNESshKeyEntry 5 }

---------------------------------------------------------------
-- NIAP NE Ssh Key Table
---------------------------------------------------------------
    tnNESshKeyTable OBJECT-TYPE
        SYNTAX         SEQUENCE OF TnNESshKeyEntry
        MAX-ACCESS     not-accessible
        STATUS         current
        DESCRIPTION    "."
        ::= { tnKeyObjs 4 }

    tnNESshKeyEntry OBJECT-TYPE
        SYNTAX         TnNESshKeyEntry
        MAX-ACCESS     not-accessible
        STATUS         current
        DESCRIPTION    "."
        INDEX { tnNESshKeyUserName,
                tnNESshKeyIndex }
        ::= { tnNESshKeyTable 1 }

    TnNESshKeyEntry ::= SEQUENCE {
        tnNESshKeyUserName     SnmpAdminString,
        tnNESshKeyIndex        Integer32,
        tnNESshKeyRowStatus    RowStatus,
        tnNESshKeyString1      SnmpAdminString,
        tnNESshKeyString2      SnmpAdminString
    }

    tnNESshKeyUserName OBJECT-TYPE
        SYNTAX         SnmpAdminString (SIZE(1..64))
        MAX-ACCESS     not-accessible
        STATUS         current
        DESCRIPTION    "."
        ::= { tnNESshKeyEntry 1 }

    tnNESshKeyIndex OBJECT-TYPE
        SYNTAX         Integer32
        MAX-ACCESS     not-accessible
        STATUS         current
        DESCRIPTION    "."
        ::= { tnNESshKeyEntry 2 }

    tnNESshKeyRowStatus OBJECT-TYPE
        SYNTAX         RowStatus
        MAX-ACCESS     read-create
        STATUS         current
        DESCRIPTION    "The row status."
        ::= { tnNESshKeyEntry 3 }


    tnNESshKeyString1 OBJECT-TYPE
        SYNTAX         SnmpAdminString (SIZE(0..2048))
        MAX-ACCESS     read-create
        STATUS         current
        DESCRIPTION    "The SSH key string 1.
                        Provisions the user public keys used for SSH user
                        authentication.  The number of keys configurable per
                        user is defined by available key indices."
        ::= { tnNESshKeyEntry 4 }

    tnNESshKeyString2 OBJECT-TYPE
        SYNTAX         SnmpAdminString (SIZE(0..2048))
        MAX-ACCESS     read-create
        STATUS         current
        DESCRIPTION    "The SSH key string 2.
                        Provisions the user public keys used for SSH user
                        authentication.  The number of keys configurable per
                        user is defined by available key indices."
        ::= { tnNESshKeyEntry 5 }

--------------------------------------------------------------------------------
--  Transfer Sys Log
--------------------------------------------------------------------------------
    tnTransferSysLogCommand OBJECT-TYPE
        SYNTAX         INTEGER {
                         noCmd(1),
                         transferToRfs(2)
                       }
        MAX-ACCESS     read-write
        STATUS         current
        DESCRIPTION    "This attribute indicates the transfer log Command."
        DEFVAL         { noCmd }
        ::= { tnTransferSysLog 1 }

    tnTransferSysLogRemoteHostIp OBJECT-TYPE
        SYNTAX         IpAddress
        MAX-ACCESS     read-write
        STATUS         current
        DESCRIPTION    "This attribute indicates the transfer log Remote Host Ip."
        DEFVAL         { '00000000'H }
        ::= { tnTransferSysLog 2 }

    tnTransferSysLogRemoteHostInetAddressType OBJECT-TYPE
        SYNTAX         InetAddressType
        MAX-ACCESS     read-write
        STATUS         current
        DESCRIPTION    "The value specifies the type of Internet address
                        stored in tnTransferSysLogRemoteHostInetAddress."
        DEFVAL         { unknown }
        ::= { tnTransferSysLog 3 }

    tnTransferSysLogRemoteHostInetAddress OBJECT-TYPE
        SYNTAX         InetAddress
        MAX-ACCESS     read-write
        STATUS         current
        DESCRIPTION    "Indicates the IPv6 address of the log server."
        DEFVAL         { ''H }
        ::= { tnTransferSysLog 4 }

    tnTransferSysLogPort OBJECT-TYPE
        SYNTAX         Unsigned32 (1..65535)
        MAX-ACCESS     read-write
        STATUS         current
        DESCRIPTION    "This attributes indicates the transfer Syslog port."
        DEFVAL         { 22 }
        ::= { tnTransferSysLog 5 }

    tnTransferSysLogProtocol OBJECT-TYPE
        SYNTAX         AluWdmNewTransferProtocol
        MAX-ACCESS     read-write
        STATUS         current
        DESCRIPTION    "This attributes indicates the transfer Syslog protocol."
        DEFVAL         { sftp }
        ::= { tnTransferSysLog 6 }

    tnTransferSysLogUserId OBJECT-TYPE
        SYNTAX         SnmpAdminString (SIZE(0..32))
        MAX-ACCESS     read-write
        STATUS         current
        DESCRIPTION    "The userId used to access the RFS."
        DEFVAL         { "" }
        ::= { tnTransferSysLog 7 }

    tnTransferSysLogPassword OBJECT-TYPE
        SYNTAX         SnmpAdminString (SIZE(0..255))
        MAX-ACCESS     read-write
        STATUS         current
        DESCRIPTION    "The password used to access the RFS.

                        When read, this attribute will return an empty string
                        if the password has not been set and '********' if it
                        has been set."
        DEFVAL         { "" }
        ::= { tnTransferSysLog 8 }

    tnTransferSysLogRemotePath OBJECT-TYPE
        SYNTAX         SnmpAdminString (SIZE(0..255))
        MAX-ACCESS     read-write
        STATUS         current
        DESCRIPTION    "This attribute indicates the transfer Log Remote Path."
        DEFVAL         { "" }
        ::= { tnTransferSysLog 9 }

    tnTransferSysLogPeriod OBJECT-TYPE
        SYNTAX         Unsigned32
        MAX-ACCESS     read-write
        STATUS         current
        DESCRIPTION    "This attribute indicates the transfer Log Period."
        ::= { tnTransferSysLog 10 }

    tnTransferSysLogLastFileTransfer OBJECT-TYPE
        SYNTAX         INTEGER {
                         none(1),
                         completed(2),
                         inProgress(3),
                         failed(4),
                         failTimeOut(5)
                       }
        MAX-ACCESS     read-only
        STATUS         current
        DESCRIPTION    "This attribute indicates the recent file transfer."
        ::= { tnTransferSysLog 11 }

    tnTransferSysLogEnable OBJECT-TYPE
        SYNTAX         TruthValue
        MAX-ACCESS     read-write
        STATUS         current
        DESCRIPTION    "This attribute indicates whether the transfer Log is enabled/disabled."
        DEFVAL         { false }
        ::= { tnTransferSysLog 12 }

--------------------------------------------------------------------------------
-- HEALTHCARE Check Scalars
--------------------------------------------------------------------------------
    tnSysHealthCareCheckCommand OBJECT-TYPE
        SYNTAX         INTEGER {
                         noCmd(1),
                         check(2),
                         abort(3)
                       }
        MAX-ACCESS     read-write
        STATUS         current
        DESCRIPTION    "Healthcare check command."
        DEFVAL         { noCmd }
        ::= { tnSysHealthCare 1 }

    tnSysHealthCareCheckShelfNum OBJECT-TYPE
        SYNTAX         Integer32
        MAX-ACCESS     read-write
        STATUS         current
        DESCRIPTION    "ShelfNum where the healthcare check has to be initiated."
        DEFVAL         { 0 }
        ::= { tnSysHealthCare 2 }

    tnSysHealthCareCheckSlotNum OBJECT-TYPE
        SYNTAX         Integer32
        MAX-ACCESS     read-write
        STATUS         current
        DESCRIPTION    "SlotNum where the healthcare check has to be initiated."
        DEFVAL         { 0 }
        ::= { tnSysHealthCare 3 }

    tnSysHealthCareCheckPercentCompleted OBJECT-TYPE
        SYNTAX         Unsigned32
        MAX-ACCESS     read-only
        STATUS         current
        DESCRIPTION    "The percent complete of the previously executed
                        tnSysHealthCareCheckCommand operation."
        DEFVAL         { 0 }
        ::= { tnSysHealthCare 4 }

    tnSysHealthCareCheckStatus OBJECT-TYPE
        SYNTAX         INTEGER {
                         completed(1),
                         inProgress(2),
                         failed(3),
                         none(4)
                       }
        MAX-ACCESS     read-only
        STATUS         current
        DESCRIPTION    "Indicates the status of the previously executed
                        tnSysHealthCareCheckCommand operation."
        DEFVAL         { none }
        ::= { tnSysHealthCare 5 }

    tnSysHealthCareCheckResult OBJECT-TYPE
        SYNTAX         INTEGER {
                         ok(1),
                         warning(2),
                         critical(3),
                         none(4)
                       }
        MAX-ACCESS     read-only
        STATUS         current
        DESCRIPTION    "Indicates the result of the previously executed
                        tnSysHealthCareCheckCommand operation."
        DEFVAL         { none }
        ::= { tnSysHealthCare 6 }

    tnSysHealthCareCheckScratchDir OBJECT-TYPE
        SYNTAX         SnmpAdminString (SIZE(0..512))
        MAX-ACCESS     read-only
        STATUS         current
        DESCRIPTION    "Contains the file's size in KB, its access date and the
                        filename as 3 attributes per output line format similar
                        to output from ls -ogth."
        ::= { tnSysHealthCare 7 }

    tnSysHealthCareServerIp OBJECT-TYPE
        SYNTAX         IpAddress
        MAX-ACCESS     read-write
        STATUS         current
        DESCRIPTION    "Healthcare remote file server IP address."
        DEFVAL         { '00000000'H }
        ::= { tnSysHealthCare 8 }

    tnSysHealthCareServerProtocol OBJECT-TYPE
        SYNTAX         AluWdmNewTransferProtocol
        MAX-ACCESS     read-write
        STATUS         current
        DESCRIPTION    "Indicates the healthcare server protocol."
        DEFVAL         { ftp }
        ::= { tnSysHealthCare 9 }

    tnSysHealthCareServerInetAddressType OBJECT-TYPE
        SYNTAX         InetAddressType
        MAX-ACCESS     read-write
        STATUS         current
        DESCRIPTION    "Specifies the type of Healthcare address stored in
                        tnSysHealthCareServerInetAddress."
        DEFVAL         { unknown }
        ::= { tnSysHealthCare 10 }

    tnSysHealthCareServerInetAddress OBJECT-TYPE
        SYNTAX         InetAddress
        MAX-ACCESS     read-write
        STATUS         current
        DESCRIPTION    "Healthcare remote file server IPv6 address."
        DEFVAL         { ''H }
        ::= { tnSysHealthCare 11 }

    tnSysHealthCareServerPort OBJECT-TYPE
        SYNTAX         Unsigned32 (1..65535)
        MAX-ACCESS     read-write
        STATUS         current
        DESCRIPTION    "Indicates the Heathcare server port."
        DEFVAL         { 21 }
        ::= { tnSysHealthCare 12 }

    tnSysHealthCareServerUserId OBJECT-TYPE
        SYNTAX         SnmpAdminString (SIZE(0..128))
        MAX-ACCESS     read-write
        STATUS         current
        DESCRIPTION    "The userId used to access the Healthcare server."
        DEFVAL         { "" }
        ::= { tnSysHealthCare 13 }

    tnSysHealthCareServerPassword OBJECT-TYPE
        SYNTAX         SnmpAdminString (SIZE(0..128))
        MAX-ACCESS     read-write
        STATUS         current
        DESCRIPTION    "The password used to access the Healthcare server.
                        When read, this attribute will return an empty string
                        if the password has not been set and '********' if it
                        has been set."
        DEFVAL         { "" }
        ::= { tnSysHealthCare 14 }

    tnSysHealthCareServerLocation OBJECT-TYPE
        SYNTAX         SnmpAdminString (SIZE(0..255))
        MAX-ACCESS     read-write
        STATUS         current
        DESCRIPTION    "For https: location of URI; for others: path on the
                        Healthcare server."
        DEFVAL         { "" }
        ::= { tnSysHealthCare 15 }

    tnSysHealthCareTransferCommand OBJECT-TYPE
        SYNTAX         INTEGER {
                         noCmd(1),
                         transfer(2),
                         abort(3)
                       }
        MAX-ACCESS     read-write
        STATUS         current
        DESCRIPTION    "Healthcare transfer command."
        DEFVAL         { noCmd }
        ::= { tnSysHealthCare 16 }

    tnSysHealthCareTransferPercentCompleted OBJECT-TYPE
        SYNTAX         Unsigned32
        MAX-ACCESS     read-only
        STATUS         current
        DESCRIPTION    "The percent completion of the previously executed
                        transfer operation."
        DEFVAL         { 0 }
        ::= { tnSysHealthCare 17 }

    tnSysHealthCareTransferStatus OBJECT-TYPE
        SYNTAX         AluWdmTransferStatus
        MAX-ACCESS     read-only
        STATUS         current
        DESCRIPTION    "Indicates the status of the previously executed
                        tnSysHealthCareTransferCommand operation."
        DEFVAL         { none }
        ::= { tnSysHealthCare 18 }

    tnSysHealthCareTransferLastFile OBJECT-TYPE
        SYNTAX         SnmpAdminString
        MAX-ACCESS     read-only
        STATUS         current
        DESCRIPTION    "Indicates the filename for the last Healthcare check
                        result file transfer."
        DEFVAL         { "" }
        ::= { tnSysHealthCare 19 }

    tnSysHealthCareLastOperation OBJECT-TYPE
        SYNTAX         INTEGER {
                         none(1),
                         check(2),
                         transfer(3)
                       }
        MAX-ACCESS     read-only
        STATUS         current
        DESCRIPTION    "Healthcare last operation."
        DEFVAL         { none }
        ::= { tnSysHealthCare 20 }

    tnSysHealthCareSetCriteriaTcId OBJECT-TYPE
        SYNTAX         SnmpAdminString (SIZE(0..255))
        MAX-ACCESS     read-write
        STATUS         current
        DESCRIPTION    "Sets Criteria TcId in string format."
        DEFVAL         { "" }
        ::= { tnSysHealthCare 21 }

    tnSysHealthCareSetCriteria OBJECT-TYPE
        SYNTAX         SnmpAdminString (SIZE(0..2048))
        MAX-ACCESS     read-write
        STATUS         current
        DESCRIPTION    "Sets one test case criteria in JSONL format."
        DEFVAL         { "" }
        ::= { tnSysHealthCare 22 }

    tnSysHealthCareDeleteCriteriaTcId OBJECT-TYPE
        SYNTAX         SnmpAdminString (SIZE(0..255))
        MAX-ACCESS     read-write
        STATUS         current
        DESCRIPTION    "Deletes Criteria TcId in string format."
        DEFVAL         { "" }
        ::= { tnSysHealthCare 23 }

    tnSysHealthCareDeleteCriteria OBJECT-TYPE
        SYNTAX         SnmpAdminString (SIZE(0..2048))
        MAX-ACCESS     read-write
        STATUS         current
        DESCRIPTION    "Deletes one test case criteria in JSONL format."
        DEFVAL         { "" }
        ::= { tnSysHealthCare 24 }

    tnSysHealthCareApplyCriteriaCommand OBJECT-TYPE
        SYNTAX         INTEGER {
                         none(1),
                         apply(2),
                         resetToDefault(3)
                       }
        MAX-ACCESS     read-write
        STATUS         current
        DESCRIPTION    "Command to apply the preset or default criteria of all
                        test cases."
        DEFVAL         { none }
        ::= { tnSysHealthCare 25 }

--------------------------------------------------------------------------------
-- TRAP THROTTLING Check Scalars
--------------------------------------------------------------------------------
    tnSysTrapThrottlingStatus OBJECT-TYPE
        SYNTAX         AluWdmDisabledEnabled
        MAX-ACCESS     read-write
        STATUS         current
        DESCRIPTION    "Disables or enables the trap throttling related parameters
                        on the network element."
        DEFVAL         { disabled }
        ::= { tnSysTrapThrottling 1 }

    tnSysTrapThrottlingThreshold1 OBJECT-TYPE
        SYNTAX         Unsigned32
        MAX-ACCESS     read-write
        STATUS         current
        DESCRIPTION    "Configures the maximum number of category1 traps that can
                        be processed as part of the trap-throttling functionality
                        (if enabled) on the network element.

                        Current Range: 1 to 150."
        DEFVAL         { 20 }
        ::= { tnSysTrapThrottling 2 }

    tnSysTrapThrottlingThreshold2 OBJECT-TYPE
        SYNTAX         Unsigned32
        MAX-ACCESS     read-write
        STATUS         current
        DESCRIPTION    "Configures the maximum number of category2 traps that can
                        be processed as part of the trap-throttling functionality
                        (if enabled) on the network element.

                        Current Range: 1 to 150."
        DEFVAL         { 20 }
        ::= { tnSysTrapThrottling 3 }

    tnSysTrapThrottlingThreshold3 OBJECT-TYPE
        SYNTAX         Unsigned32
        MAX-ACCESS     read-write
        STATUS         current
        DESCRIPTION    "Configures the maximum number of category3 traps that can
                        be processed as part of the trap-throttling functionality
                        (if enabled) on the network element.

                        Current Range: 1 to 150."
        DEFVAL         { 20 }
        ::= { tnSysTrapThrottling 4 }

    tnSysTrapThrottlingTimeOverThreshold OBJECT-TYPE
        SYNTAX         Unsigned32
        UNITS          "seconds"
        MAX-ACCESS     read-write
        STATUS         current
        DESCRIPTION    "Configures the number of consecutive seconds for which
                        traps are above the threshold (sum of the set threshold1,
                        threshold2, and threshold3 values), after which the network
                        element enters the trap throttling state.

                        Current Range: 1 to 600."
        DEFVAL         { 5 }
        ::= { tnSysTrapThrottling 5 }

    tnSysTrapThrottlingTimeUnderThreshold OBJECT-TYPE
        SYNTAX         Unsigned32
        UNITS          "seconds"
        MAX-ACCESS     read-write
        STATUS         current
        DESCRIPTION    "Configures the number of consecutive seconds for which
                        traps are below the threshold (sum of the set threshold1,
                        threshold2, and threshold3 values), after which the trap
                        throttling state is exited on the network element.

                        Current Range: 1 to 600."
        DEFVAL         { 20 }
        ::= { tnSysTrapThrottling 6 }

    tnSysTrapThrottlingState OBJECT-TYPE
        SYNTAX         TruthValue
        MAX-ACCESS     read-only
        STATUS         current
        DESCRIPTION    "Indicates if the network element is in trap throttling state."
        DEFVAL         { false }
        ::= { tnSysTrapThrottling 7 }

---------------------------------------------------------------
-- Ssh Ciphers Table
---------------------------------------------------------------
    tnSshCiphersTable OBJECT-TYPE
        SYNTAX         SEQUENCE OF TnSshCiphersEntry
        MAX-ACCESS     not-accessible
        STATUS         current
        DESCRIPTION    "."
        ::= { tnKeyObjs 5 }

    tnSshCiphersEntry OBJECT-TYPE
        SYNTAX         TnSshCiphersEntry
        MAX-ACCESS     not-accessible
        STATUS         current
        DESCRIPTION    "."
        INDEX { tnSshCiphersAlgType,
                tnSshCiphersProfileName }
        ::= { tnSshCiphersTable 1 }

    TnSshCiphersEntry ::= SEQUENCE {
        tnSshCiphersAlgType          Unsigned32,
        tnSshCiphersProfileName      OCTET STRING,
        tnSshCiphersEnabled          TruthValue
    }

    tnSshCiphersAlgType OBJECT-TYPE
        SYNTAX         Unsigned32
        MAX-ACCESS     not-accessible
        STATUS         current
        DESCRIPTION    "This attribute indicates the SSH Ciphers Algorithm type
                        Supported values:
                        aes128-ctr              - 1
                        aes256-ctr              - 2
                        aes128-gcm@openssh.com  - 3
                        aes256-gcm@openssh.com  - 4."
        ::= { tnSshCiphersEntry 1 }

    tnSshCiphersProfileName OBJECT-TYPE
        SYNTAX         OCTET STRING
        MAX-ACCESS     not-accessible
        STATUS         current
        DESCRIPTION    "This attribute indicates the SSH Ciphers ProfileName."
        ::= { tnSshCiphersEntry 2 }

    tnSshCiphersEnabled OBJECT-TYPE
        SYNTAX         TruthValue
        MAX-ACCESS     read-create
        STATUS         current
        DESCRIPTION    "This attribute indicates whether the SSH Ciphers algorithm
                        setting is enabled/disabled."
        ::= { tnSshCiphersEntry 3 }

---------------------------------------------------------------
-- Ssh HostKey Table
---------------------------------------------------------------
    tnSshHostKeyTable OBJECT-TYPE
        SYNTAX         SEQUENCE OF TnSshHostKeyEntry
        MAX-ACCESS     not-accessible
        STATUS         current
        DESCRIPTION    "."
        ::= { tnKeyObjs 6 }

    tnSshHostKeyEntry OBJECT-TYPE
        SYNTAX         TnSshHostKeyEntry
        MAX-ACCESS     not-accessible
        STATUS         current
        DESCRIPTION    "."
        INDEX { tnSshHostKeyAlgType,
                tnSshHostKeyProfileName }
        ::= { tnSshHostKeyTable 1 }

    TnSshHostKeyEntry ::= SEQUENCE {
        tnSshHostKeyAlgType          Unsigned32,
        tnSshHostKeyProfileName      OCTET STRING,
        tnSshHostKeyEnabled          TruthValue
    }

    tnSshHostKeyAlgType OBJECT-TYPE
        SYNTAX         Unsigned32
        MAX-ACCESS     not-accessible
        STATUS         current
        DESCRIPTION    "This attribute indicates the SSH HostKey Algorithm type
                        Supported values:
                        ssh-rsa              - 1
                        rsa-sha2-256         - 2
                        rsa-sha2-512         - 3
                        ecdsa-sha2-nistp256  - 4
                        ecdsa-sha2-nistp384  - 5
                        ecdsa-sha2-nistp521  - 6
                        ssh-ed25519          - 7."
        ::= { tnSshHostKeyEntry 1 }

    tnSshHostKeyProfileName OBJECT-TYPE
        SYNTAX         OCTET STRING
        MAX-ACCESS     not-accessible
        STATUS         current
        DESCRIPTION    "This attribute indicates the SSH HostKey Profilename."
        ::= { tnSshHostKeyEntry 2 }

    tnSshHostKeyEnabled OBJECT-TYPE
        SYNTAX         TruthValue
        MAX-ACCESS     read-create
        STATUS         current
        DESCRIPTION    "This attribute indicates whether the SSH HostKey algorithm
                        setting is enabled/disabled."
        ::= { tnSshHostKeyEntry 3 }

---------------------------------------------------------------
-- Ssh Macs Table
---------------------------------------------------------------
    tnSshMacsTable OBJECT-TYPE
        SYNTAX         SEQUENCE OF TnSshMacsEntry
        MAX-ACCESS     not-accessible
        STATUS         current
        DESCRIPTION    "."
        ::= { tnKeyObjs 7 }

    tnSshMacsEntry OBJECT-TYPE
        SYNTAX         TnSshMacsEntry
        MAX-ACCESS     not-accessible
        STATUS         current
        DESCRIPTION    "."
        INDEX { tnSshMacsAlgType,
                tnSshMacsProfileName }
        ::= { tnSshMacsTable 1 }

    TnSshMacsEntry ::= SEQUENCE {
        tnSshMacsAlgType          Unsigned32,
        tnSshMacsProfileName      OCTET STRING,
        tnSshMacsEnabled          TruthValue
    }

    tnSshMacsAlgType OBJECT-TYPE
        SYNTAX         Unsigned32
        MAX-ACCESS     not-accessible
        STATUS         current
        DESCRIPTION    "This attribute indicates the SSH Macs Algorithm type
                        Supported values:
                        hmac-sha1      - 1
                        hmac-sha2-256  - 2
                        hmac-sha2-512  - 3."
        ::= { tnSshMacsEntry 1 }

    tnSshMacsProfileName OBJECT-TYPE
        SYNTAX         OCTET STRING
        MAX-ACCESS     not-accessible
        STATUS         current
        DESCRIPTION    "This attribute indicates the SSH Macs Profilename."
        ::= { tnSshMacsEntry 2 }

    tnSshMacsEnabled OBJECT-TYPE
        SYNTAX         TruthValue
        MAX-ACCESS     read-create
        STATUS         current
        DESCRIPTION    "This attribute indicates whether the SSH Macs algorithm
                        setting is enabled/disabled."
        ::= { tnSshMacsEntry 3 }

---------------------------------------------------------------
-- Ssh Kex Table
---------------------------------------------------------------
    tnSshKexTable OBJECT-TYPE
        SYNTAX         SEQUENCE OF TnSshKexEntry
        MAX-ACCESS     not-accessible
        STATUS         current
        DESCRIPTION    "."
        ::= { tnKeyObjs 8 }

    tnSshKexEntry OBJECT-TYPE
        SYNTAX         TnSshKexEntry
        MAX-ACCESS     not-accessible
        STATUS         current
        DESCRIPTION    "."
        INDEX { tnSshKexAlgType,
                tnSshKexProfileName }
        ::= { tnSshKexTable 1 }

    TnSshKexEntry ::= SEQUENCE {
        tnSshKexAlgType          Unsigned32,
        tnSshKexProfileName      OCTET STRING,
        tnSshKexEnabled          TruthValue
    }

    tnSshKexAlgType OBJECT-TYPE
        SYNTAX         Unsigned32
        MAX-ACCESS     not-accessible
        STATUS         current
        DESCRIPTION    "This attribute indicates the SSH Kex Algorithm type
                        Supported values:
                        diffie-hellman-group14-sha1    - 1
                        diffie-hellman-group14-sha256  - 2
                        diffie-hellman-group16-sha512  - 3
                        diffie-hellman-group18-sha512  - 4
                        ecdh-sha2-nistp256             - 5
                        ecdh-sha2-nistp384             - 6
                        ecdh-sha2-nistp521             - 7
                        curve25519-sha256              - 8
                        curve25519_sha256_libssh       - 9."
        ::= { tnSshKexEntry 1 }

    tnSshKexProfileName OBJECT-TYPE
        SYNTAX         OCTET STRING
        MAX-ACCESS     not-accessible
        STATUS         current
        DESCRIPTION    "This attribute indicates the SSH Kex Profile name."
        ::= { tnSshKexEntry 2 }

    tnSshKexEnabled OBJECT-TYPE
        SYNTAX         TruthValue
        MAX-ACCESS     read-create
        STATUS         current
        DESCRIPTION    "This attribute indicates whether the SSH Kex algorithm
                        setting is enabled/disabled."
        ::= { tnSshKexEntry 3 }

---------------------------------------------------------------
-- Ssh PubKey Table
---------------------------------------------------------------
    tnSshPubKeyTable OBJECT-TYPE
        SYNTAX         SEQUENCE OF TnSshPubKeyEntry
        MAX-ACCESS     not-accessible
        STATUS         current
        DESCRIPTION    "."
        ::= { tnKeyObjs 9 }

    tnSshPubKeyEntry OBJECT-TYPE
        SYNTAX         TnSshPubKeyEntry
        MAX-ACCESS     not-accessible
        STATUS         current
        DESCRIPTION    "."
        INDEX { tnSshPubKeyAlgType,
                tnSshPubKeyProfileName }
        ::= { tnSshPubKeyTable 1 }

    TnSshPubKeyEntry ::= SEQUENCE {
        tnSshPubKeyAlgType          Unsigned32,
        tnSshPubKeyProfileName      OCTET STRING,
        tnSshPubKeyEnabled          TruthValue
    }

    tnSshPubKeyAlgType OBJECT-TYPE
        SYNTAX         Unsigned32
        MAX-ACCESS     not-accessible
        STATUS         current
        DESCRIPTION    "This attribute indicates the SSH PubKey Algorithm type
                        Supported values:
                        ssh-rsa              - 1
                        rsa-sha2-256         - 2
                        rsa-sha2-512         - 3
                        ecdsa-sha2-nistp256  - 4
                        ecdsa-sha2-nistp384  - 5
                        ecdsa-sha2-nistp521  - 6."
        ::= { tnSshPubKeyEntry 1 }

    tnSshPubKeyProfileName OBJECT-TYPE
        SYNTAX         OCTET STRING
        MAX-ACCESS     not-accessible
        STATUS         current
        DESCRIPTION    "This attribute indicates the SSH PubKey Profile name."
        ::= { tnSshPubKeyEntry 2 }

    tnSshPubKeyEnabled OBJECT-TYPE
        SYNTAX         TruthValue
        MAX-ACCESS     read-create
        STATUS         current
        DESCRIPTION    "This attribute indicates whether the SSH PubKey algorithm
                        setting is enabled/disabled."
        ::= { tnSshPubKeyEntry 3 }

---------------------------------------------------------------
-- TLS Profile Table
---------------------------------------------------------------
    tnTlsProfileTable OBJECT-TYPE
        SYNTAX         SEQUENCE OF TnTlsProfileEntry
        MAX-ACCESS     not-accessible
        STATUS         current
        DESCRIPTION    "."
        ::= { tnKeyObjs 10 }

    tnTlsProfileEntry OBJECT-TYPE
        SYNTAX         TnTlsProfileEntry
        MAX-ACCESS     not-accessible
        STATUS         current
        DESCRIPTION    "."
        INDEX { tnTlsProfileName }
        ::= { tnTlsProfileTable 1 }

    TnTlsProfileEntry ::= SEQUENCE {
        tnTlsProfileName             OCTET STRING,
        tnTlsProfileMinVersion       Integer32,
        tnTlsProfileMaxVersion       Integer32,
        tnTlsProfileMutualAuth       AluWdmEnabledDisabled,
        tnTlsProfileDescription      SnmpAdminString
    }

    tnTlsProfileName OBJECT-TYPE
        SYNTAX         OCTET STRING
        MAX-ACCESS     not-accessible
        STATUS         current
        DESCRIPTION    "This attribute indicates the TLS ProfileName
                        and specifies an TLS profile which will be
                        applied to TLS clients and servers or applications
                        which uses this profile or have this profile
                        assigned respectively."
        ::= { tnTlsProfileEntry 1 }

    tnTlsProfileMinVersion OBJECT-TYPE
        SYNTAX         Integer32
        MAX-ACCESS     read-create
        STATUS         current
        DESCRIPTION    "Configures the minimum TLS version supported
                        by the TLS clients and servers. The version
                        specified must be lower or equal to the maximum
                        supported version."
        ::= { tnTlsProfileEntry 2 }

    tnTlsProfileMaxVersion OBJECT-TYPE
        SYNTAX         Integer32
        MAX-ACCESS     read-create
        STATUS         current
        DESCRIPTION    "Configures the maximum TLS version supported
                        by the TLS clients and servers. The version
                        specified must be higher or equal to the minimum
                        supported version."
        ::= { tnTlsProfileEntry 3 }

    tnTlsProfileMutualAuth OBJECT-TYPE
        SYNTAX         AluWdmEnabledDisabled
        MAX-ACCESS     read-create
        STATUS         current
        DESCRIPTION    "Enables or Disables the mutual authentication
                        If mutual authentication is enabled, a client
                        certificate will be requested by an TLS server.
                        A client of server implementation verifies the
                        received certificates and its revocation status.
                        If the verification fail, then a TLS connection
                        will be cancelled."
        ::= { tnTlsProfileEntry 4 }

    tnTlsProfileDescription OBJECT-TYPE
        SYNTAX         SnmpAdminString (SIZE(0..64))
        MAX-ACCESS     read-create
        STATUS         current
        DESCRIPTION    "."
        ::= { tnTlsProfileEntry 5 }

---------------------------------------------------------------
-- San List Table
---------------------------------------------------------------
    tnSanListTable OBJECT-TYPE
        SYNTAX         SEQUENCE OF TnSanListEntry
        MAX-ACCESS     not-accessible
        STATUS         current
        DESCRIPTION    "."
        ::= { tnKeyObjs 11 }

    tnSanListEntry OBJECT-TYPE
        SYNTAX         TnSanListEntry
        MAX-ACCESS     not-accessible
        STATUS         current
        DESCRIPTION    "."
        INDEX { tnSanListName,
                tnSanListType,
                tnSanListIndex }
        ::= { tnSanListTable 1 }

    TnSanListEntry ::= SEQUENCE {
        tnSanListName                OCTET STRING,
        tnSanListType                INTEGER,
        tnSanListIndex               OCTET STRING,
        tnSanListRowStatus           RowStatus
    }

    tnSanListName OBJECT-TYPE
        SYNTAX         OCTET STRING
        MAX-ACCESS     not-accessible
        STATUS         current
        DESCRIPTION    "."
        ::= { tnSanListEntry 1 }

    tnSanListType OBJECT-TYPE
        SYNTAX         INTEGER {
                         ipv4(1),
                         ipv6(2),
                         domain(3)
                       }
        MAX-ACCESS     not-accessible
        STATUS         current
        DESCRIPTION    "."
        ::= { tnSanListEntry 2 }

    tnSanListIndex OBJECT-TYPE
        SYNTAX         OCTET STRING
        MAX-ACCESS     not-accessible
        STATUS         current
        DESCRIPTION    "."
        ::= { tnSanListEntry 3 }

    tnSanListRowStatus OBJECT-TYPE
        SYNTAX         RowStatus
        MAX-ACCESS     read-create
        STATUS         current
        DESCRIPTION    "The row status."
        ::= { tnSanListEntry 4 }

---------------------------------------------------------------
-- Csr San List Table
---------------------------------------------------------------
    tnCsrSanListTable OBJECT-TYPE
        SYNTAX         SEQUENCE OF TnCsrSanListEntry
        MAX-ACCESS     not-accessible
        STATUS         current
        DESCRIPTION    "."
        ::= { tnKeyObjs 12 }

    tnCsrSanListEntry OBJECT-TYPE
        SYNTAX         TnCsrSanListEntry
        MAX-ACCESS     not-accessible
        STATUS         current
        DESCRIPTION    "."
        INDEX { tnCsrSanListType,
                tnCsrSanListIndex }
        ::= { tnCsrSanListTable 1 }

    TnCsrSanListEntry ::= SEQUENCE {
        tnCsrSanListType                INTEGER,
        tnCsrSanListIndex               OCTET STRING,
        tnCsrSanListRowStatus           RowStatus
    }

    tnCsrSanListType OBJECT-TYPE
        SYNTAX         INTEGER {
                         ipv4(1),
                         ipv6(2),
                         domain(3)
                       }
        MAX-ACCESS     not-accessible
        STATUS         current
        DESCRIPTION    "."
        ::= { tnCsrSanListEntry 1 }

    tnCsrSanListIndex OBJECT-TYPE
        SYNTAX         OCTET STRING
        MAX-ACCESS     not-accessible
        STATUS         current
        DESCRIPTION    "."
        ::= { tnCsrSanListEntry 2 }

    tnCsrSanListRowStatus OBJECT-TYPE
        SYNTAX         RowStatus
        MAX-ACCESS     read-create
        STATUS         current
        DESCRIPTION    "The row status."
        ::= { tnCsrSanListEntry 3 }

---------------------------------------------------------------
-- San List Auth Table
---------------------------------------------------------------
    tnSanListAuthTable OBJECT-TYPE
        SYNTAX         SEQUENCE OF TnSanListAuthEntry
        MAX-ACCESS     not-accessible
        STATUS         current
        DESCRIPTION    "."
        ::= { tnKeyObjs 13 }

    tnSanListAuthEntry OBJECT-TYPE
        SYNTAX         TnSanListAuthEntry
        MAX-ACCESS     not-accessible
        STATUS         current
        DESCRIPTION    "."
        INDEX { tnSanListName }
        ::= { tnSanListAuthTable 1 }

    TnSanListAuthEntry ::= SEQUENCE {
        tnSanListAuthentication       AluWdmEnabledDisabled,
        tnSanListProfileDescription   SnmpAdminString
    }

    tnSanListAuthentication OBJECT-TYPE
        SYNTAX         AluWdmEnabledDisabled
        MAX-ACCESS     read-create
        STATUS         current
        DESCRIPTION    "."
        ::= { tnSanListAuthEntry 1 }

    tnSanListProfileDescription OBJECT-TYPE
        SYNTAX         SnmpAdminString (SIZE(0..64))
        MAX-ACCESS     read-create
        STATUS         current
        DESCRIPTION    "."
        ::= { tnSanListAuthEntry 2 }

---------------------------------------------------------------
-- Sys NMS IP List Table
---------------------------------------------------------------
    tnSysNmsIpListTable OBJECT-TYPE
        SYNTAX         SEQUENCE OF TnSysNmsIpListEntry
        MAX-ACCESS     not-accessible
        STATUS         current
        DESCRIPTION    "."
        ::= { tnSysNmsObjs 1 }

    tnSysNmsIpListEntry OBJECT-TYPE
        SYNTAX         TnSysNmsIpListEntry
        MAX-ACCESS     not-accessible
        STATUS         current
        DESCRIPTION    "."
        INDEX { tnSysNmsIpListIndex }
        ::= { tnSysNmsIpListTable 1 }

    TnSysNmsIpListEntry ::= SEQUENCE {
        tnSysNmsIpListIndex               OCTET STRING,
        tnSysNmsIpListRowStatus           RowStatus,
        tnSysNmsIpListIpAddress           IpAddress,
        tnSysNmsIpListInetAddress         InetAddress,
        tnSysNmsIpListInetAddressType     InetAddressType
    }

    tnSysNmsIpListIndex OBJECT-TYPE
        SYNTAX         OCTET STRING
        MAX-ACCESS     not-accessible
        STATUS         current
        DESCRIPTION    "."
        ::= { tnSysNmsIpListEntry 1 }

    tnSysNmsIpListRowStatus OBJECT-TYPE
        SYNTAX         RowStatus
        MAX-ACCESS     read-create
        STATUS         current
        DESCRIPTION    "The row status."
        ::= { tnSysNmsIpListEntry 2 }

    tnSysNmsIpListIpAddress OBJECT-TYPE
        SYNTAX         IpAddress
        MAX-ACCESS     read-create
        STATUS         current
        DESCRIPTION    "."
        DEFVAL         { '00000000'H }
        ::= { tnSysNmsIpListEntry 3 }

    tnSysNmsIpListInetAddress OBJECT-TYPE
        SYNTAX         InetAddress
        MAX-ACCESS     read-create
        STATUS         current
        DESCRIPTION    "Indicates the IPv6 address of the Syslog Server."
        DEFVAL         { ''H }
        ::= { tnSysNmsIpListEntry 4 }

    tnSysNmsIpListInetAddressType OBJECT-TYPE
        SYNTAX         InetAddressType
        MAX-ACCESS     read-create
        STATUS         current
        DESCRIPTION    "The value specifies the type of Internet address
                        stored in tnSysNmsIpListInetAddress."
        DEFVAL         { unknown }
        ::= { tnSysNmsIpListEntry 5 }

---------------------------------------------------------------
-- Ocsp Profile Table
---------------------------------------------------------------
    tnOcspProfileTable OBJECT-TYPE
        SYNTAX         SEQUENCE OF TnOcspProfileEntry
        MAX-ACCESS     not-accessible
        STATUS         current
        DESCRIPTION    "."
        ::= { tnKeyObjs 14 }

    tnOcspProfileEntry OBJECT-TYPE
        SYNTAX         TnOcspProfileEntry
        MAX-ACCESS     not-accessible
        STATUS         current
        DESCRIPTION    "."
        INDEX { tnOcspProfileName }
        ::= { tnOcspProfileTable 1 }

    TnOcspProfileEntry ::= SEQUENCE {
        tnOcspProfileName            OCTET STRING,
        tnOcspProfileRowStatus       RowStatus,
        tnOcspProfileRetry           Unsigned32,
        tnOcspProfileServerUrl       SnmpAdminString,
        tnOcspProfileStatus          AluWdmEnabledDisabled,
        tnOcspProfileTimeout         Unsigned32
    }

    tnOcspProfileName OBJECT-TYPE
        SYNTAX         OCTET STRING
        MAX-ACCESS     not-accessible
        STATUS         current
        DESCRIPTION    "."
        ::= { tnOcspProfileEntry 1 }

    tnOcspProfileRowStatus OBJECT-TYPE
        SYNTAX         RowStatus
        MAX-ACCESS     read-create
        STATUS         current
        DESCRIPTION    "The row status."
        ::= { tnOcspProfileEntry 2 }

    tnOcspProfileRetry OBJECT-TYPE
        SYNTAX         Unsigned32 (1..10)
        MAX-ACCESS     read-create
        STATUS         current
        DESCRIPTION    "Number of entries if an OCSP responder does not respond."
        DEFVAL         { 1 }
        ::= { tnOcspProfileEntry 3 }

    tnOcspProfileServerUrl OBJECT-TYPE
        SYNTAX         SnmpAdminString (SIZE(0..255))
        MAX-ACCESS     read-create
        STATUS         current
        DESCRIPTION    "URL of the OCSP responder."
        DEFVAL         { "" }
        ::= { tnOcspProfileEntry 4 }

    tnOcspProfileStatus OBJECT-TYPE
        SYNTAX         AluWdmEnabledDisabled
        MAX-ACCESS     read-create
        STATUS         current
        DESCRIPTION    "Enables or disables the X.509v3 certificate revocation
                        using the specified OCSP responder.

                        If the service is disabled, then the revocation check
                        will be not done."
        ::= { tnOcspProfileEntry 5 }

    tnOcspProfileTimeout OBJECT-TYPE
        SYNTAX           Unsigned32 (1..3600)
        MAX-ACCESS       read-create
        STATUS           current
        DESCRIPTION      "Timeout for OCSP responses."
        DEFVAL           { 10 }
        ::= { tnOcspProfileEntry 6 }

--------------------------------------------------------------------------------
-- Sys Dns Server Table
--------------------------------------------------------------------------------
    tnSysDnsServerTable OBJECT-TYPE
        SYNTAX         SEQUENCE OF TnSysDnsServerEntry
        MAX-ACCESS     not-accessible
        STATUS         current
        DESCRIPTION    "."
        ::= { tnSysDnsServer 1 }

    tnSysDnsServerEntry OBJECT-TYPE
        SYNTAX         TnSysDnsServerEntry
        MAX-ACCESS     not-accessible
        STATUS         current
        DESCRIPTION    "."
        INDEX { tnSysDnsServerIndex  }
        ::= { tnSysDnsServerTable 1 }

    TnSysDnsServerEntry ::=
        SEQUENCE {
            tnSysDnsServerIndex               Unsigned32,
            tnSysDnsServerIpAddress           IpAddress,
            tnSysDnsServerInetAddress         InetAddress,
            tnSysDnsServerInetAddressType     InetAddressType
        }

    tnSysDnsServerIndex OBJECT-TYPE
        SYNTAX         Unsigned32
        MAX-ACCESS     not-accessible
        STATUS         current
        DESCRIPTION    "."
        ::= { tnSysDnsServerEntry 1 }

    tnSysDnsServerIpAddress OBJECT-TYPE
        SYNTAX         IpAddress
        MAX-ACCESS     read-create
        STATUS         current
        DESCRIPTION    "."
        DEFVAL         { '00000000'H }
        ::= { tnSysDnsServerEntry 2 }

    tnSysDnsServerInetAddress OBJECT-TYPE
        SYNTAX         InetAddress
        MAX-ACCESS     read-create
        STATUS         current
        DESCRIPTION    "Indicates the IPv6 address of the Syslog Server."
        DEFVAL         { ''H }
        ::= { tnSysDnsServerEntry 3 }

    tnSysDnsServerInetAddressType OBJECT-TYPE
        SYNTAX         InetAddressType
        MAX-ACCESS     read-create
        STATUS         current
        DESCRIPTION    "The value specifies the type of Internet address
                        stored in tnSysDnsServerInetAddress."
        DEFVAL         { unknown }
        ::= { tnSysDnsServerEntry 4 }

--------------------------------------------------------------------------------
-- Transfer PM Discovery Table
--------------------------------------------------------------------------------
    tnTransferPMDiscoveryTable OBJECT-TYPE
        SYNTAX         SEQUENCE OF TnTransferPMDiscoveryEntry
        MAX-ACCESS     not-accessible
        STATUS         current
        DESCRIPTION    "."
        ::= { tnTransferPMDiscovery 1 }

    tnTransferPMDiscoveryEntry OBJECT-TYPE
        SYNTAX         TnTransferPMDiscoveryEntry
        MAX-ACCESS     not-accessible
        STATUS         current
        DESCRIPTION    "."
        INDEX { tnTransferPMDiscoveryIndex }
        ::= { tnTransferPMDiscoveryTable 1 }

    TnTransferPMDiscoveryEntry ::=
        SEQUENCE {
            tnTransferPMDiscoveryIndex                              SnmpAdminString,
            tnTransferPMDiscoveryRowStatus                          RowStatus,
            tnTransferPMDiscoveryFilename                           SnmpAdminString,
            tnTransferPMDiscoveryControl                            INTEGER,
            tnTransferPMDiscoveryStatus                             INTEGER,
            tnTransferPMDiscoveryErrorCode                          INTEGER,
            tnTransferPMDiscoveryServerProtocol                     AluWdmNewTransferProtocol,
            tnTransferPMDiscoveryServerIp                           IpAddress,
            tnTransferPMDiscoveryServerUserId                       SnmpAdminString,
            tnTransferPMDiscoveryServerPassword                     SnmpAdminString,
            tnTransferPMDiscoveryServerInetAddressType              InetAddressType,
            tnTransferPMDiscoveryServerInetAddress                  InetAddress,
            tnTransferPMDiscoveryPort                               Unsigned32,
            tnTransferPMDiscoveryPrevious15minBinFilesTransfer      Unsigned32,
            tnTransferPMDiscoveryPrevious1dayBinFilesTransfer       Unsigned32,
            tnTransferPMDiscoveryTransferTimeOffset                 Unsigned32,
            tnTransferPMDiscovery15minBinFileTransferCount          Unsigned32,
            tnTransferPMDiscovery1dayBinFileTransferCount           Unsigned32,
            tnTransferPMDiscovery15minBinFileTransferFailureCount   Unsigned32,
            tnTransferPMDiscovery1dayBinFileTransferFailureCount    Unsigned32
        }

    tnTransferPMDiscoveryIndex OBJECT-TYPE
        SYNTAX         SnmpAdminString
        MAX-ACCESS     not-accessible
        STATUS         current
        DESCRIPTION    "Unique identifier associated with this tnTransferPMDiscoveryEntry."
        ::= { tnTransferPMDiscoveryEntry 1 }

    tnTransferPMDiscoveryRowStatus OBJECT-TYPE
        SYNTAX         RowStatus
        MAX-ACCESS     read-create
        STATUS         current
        DESCRIPTION    "Currently all entries have a row status of active.
                        Sets are permitted with values of createAndGo and
                        destroy, exclusively."
        ::= { tnTransferPMDiscoveryEntry 2 }

    tnTransferPMDiscoveryFilename OBJECT-TYPE
        SYNTAX         SnmpAdminString (SIZE(0..255))
        MAX-ACCESS     read-create
        STATUS         current
        DESCRIPTION    "This attribute indicates remote destination file path."
        DEFVAL         { "" }
        ::= { tnTransferPMDiscoveryEntry 3 }

    tnTransferPMDiscoveryControl OBJECT-TYPE
        SYNTAX         INTEGER {
                         noCmd(1),
                         start(2),
                         abort(3)
                       }
        MAX-ACCESS     read-create
        STATUS         current
        DESCRIPTION    "Controls the Discovery, i.e., starts after the next
                        bin rolled over trap is generated or aborts."
        DEFVAL         { noCmd }
        ::= { tnTransferPMDiscoveryEntry 4 }

    tnTransferPMDiscoveryStatus OBJECT-TYPE
        SYNTAX         INTEGER {
                         idle(1),
                         inProgress(2),
                         completedSuccessfully(3),
                         failed(4),
                         aborted(5)
                       }
        MAX-ACCESS     read-only
        STATUS         current
        DESCRIPTION    "This attribute indicates the status of the most recent
                        file transfer."
        DEFVAL         { idle }
        ::= { tnTransferPMDiscoveryEntry 5 }

    tnTransferPMDiscoveryErrorCode OBJECT-TYPE
        SYNTAX         INTEGER {
                         noError(1),
                         unknown(2),
                         timeout(3),
                         serverError(4),
                         networkError(5),
                         fileSystemError(6),
                         statsBinsRolled(7)
                       }
        MAX-ACCESS     read-only
        STATUS         current
        DESCRIPTION    "This attribute indicates the error code of the most
                        recent file transfer."
        DEFVAL         { noError }
        ::= { tnTransferPMDiscoveryEntry 6 }

    tnTransferPMDiscoveryServerProtocol OBJECT-TYPE
        SYNTAX         AluWdmNewTransferProtocol
        MAX-ACCESS     read-create
        STATUS         current
        DESCRIPTION    "This attributes indicates the server protocol."
        DEFVAL         { ftp }
        ::= { tnTransferPMDiscoveryEntry 7 }

    tnTransferPMDiscoveryServerIp OBJECT-TYPE
        SYNTAX         IpAddress
        MAX-ACCESS     read-create
        STATUS         current
        DESCRIPTION    "This attributes indicates the server IPv4 address."
        DEFVAL         { '00000000'H }
        ::= { tnTransferPMDiscoveryEntry 8 }

    tnTransferPMDiscoveryServerUserId OBJECT-TYPE
        SYNTAX         SnmpAdminString (SIZE(0..128))
        MAX-ACCESS     read-create
        STATUS         current
        DESCRIPTION    "This attribute indicates the userId used to access
                        the server."
        DEFVAL         { "" }
        ::= { tnTransferPMDiscoveryEntry 9 }

    tnTransferPMDiscoveryServerPassword OBJECT-TYPE
        SYNTAX         SnmpAdminString (SIZE(0..128))
        MAX-ACCESS     read-create
        STATUS         current
        DESCRIPTION    "This attribute indicates the password used to access
                        the server.

                        When read, this attribute will return an empty string
                        if the password has not been set and '********' if it
                        has been set."
        DEFVAL         { "" }
        ::= { tnTransferPMDiscoveryEntry 10 }

    tnTransferPMDiscoveryServerInetAddressType OBJECT-TYPE
        SYNTAX         InetAddressType
        MAX-ACCESS     read-create
        STATUS         current
        DESCRIPTION    "The value specifies the type of Internet address stored
                        in tnTransferPMDiscoveryServerInetAddress."
        DEFVAL         { unknown }
        ::= { tnTransferPMDiscoveryEntry 11 }

    tnTransferPMDiscoveryServerInetAddress OBJECT-TYPE
        SYNTAX         InetAddress
        MAX-ACCESS     read-create
        STATUS         current
        DESCRIPTION    "This attribute indicates the IPv6 address of the server."
        DEFVAL         { ''H }
        ::= { tnTransferPMDiscoveryEntry 12 }

    tnTransferPMDiscoveryPort OBJECT-TYPE
        SYNTAX         Unsigned32 (1..65535)
        MAX-ACCESS     read-create
        STATUS         current
        DESCRIPTION    "This attributes indicates the server port."
        DEFVAL         { 21 }
        ::= { tnTransferPMDiscoveryEntry 13 }

    tnTransferPMDiscoveryPrevious15minBinFilesTransfer OBJECT-TYPE
        SYNTAX         Unsigned32
        MAX-ACCESS     read-create
        STATUS         current
        DESCRIPTION    "This attribute indicates the number of previous 15
                        min bin files that needs to be transferred in the
                        range of 0 to 8."
        DEFVAL         { 0 }
        ::= { tnTransferPMDiscoveryEntry 14 }

    tnTransferPMDiscoveryPrevious1dayBinFilesTransfer OBJECT-TYPE
        SYNTAX         Unsigned32
        MAX-ACCESS     read-create
        STATUS         current
        DESCRIPTION    "This attribute indicates the number of previous 1 day
                        bin files that needs to be transferred in the range
                        of 0 to 7."
        DEFVAL         { 0 }
        ::= { tnTransferPMDiscoveryEntry 15 }

    tnTransferPMDiscoveryTransferTimeOffset OBJECT-TYPE
        SYNTAX         Unsigned32
        MAX-ACCESS     read-create
        STATUS         current
        DESCRIPTION    "This attribute indicates the file transfer time offset
                        in the range 0 to 600 seconds."
        DEFVAL         { 0 }
        ::= { tnTransferPMDiscoveryEntry 16 }

    tnTransferPMDiscovery15minBinFileTransferCount OBJECT-TYPE
        SYNTAX         Unsigned32 (0..8)
        MAX-ACCESS     read-only
        STATUS         current
        DESCRIPTION    "This attribute indicates the recent number of 15 min
                        bin files transferred."
        DEFVAL         { 0 }
        ::= { tnTransferPMDiscoveryEntry 17 }

    tnTransferPMDiscovery1dayBinFileTransferCount OBJECT-TYPE
        SYNTAX         Unsigned32 (0..8)
        MAX-ACCESS     read-only
        STATUS         current
        DESCRIPTION    "This attribute indicates the recent number of 1 day
                        bin files transferred."
        DEFVAL         { 0 }
        ::= { tnTransferPMDiscoveryEntry 18 }

    tnTransferPMDiscovery15minBinFileTransferFailureCount OBJECT-TYPE
        SYNTAX         Unsigned32 (0..8)
        MAX-ACCESS     read-only
        STATUS         current
        DESCRIPTION    "This attribute indicates the number of 15 min bin
                        files transferred failure count."
        DEFVAL         { 0 }
        ::= { tnTransferPMDiscoveryEntry 19 }

    tnTransferPMDiscovery1dayBinFileTransferFailureCount OBJECT-TYPE
        SYNTAX         Unsigned32 (0..8)
        MAX-ACCESS     read-only
        STATUS         current
        DESCRIPTION    "This attribute indicates the number of 1 day bin files
                        transferred failure count."
        DEFVAL         { 0 }
        ::= { tnTransferPMDiscoveryEntry 20 }

---------------------------------------------------------------
-- SSH Profile Table
---------------------------------------------------------------
    tnSshProfileTable OBJECT-TYPE
        SYNTAX         SEQUENCE OF TnSshProfileEntry
        MAX-ACCESS     not-accessible
        STATUS         current
        DESCRIPTION    "."
        ::= { tnKeyObjs 15 }

    tnSshProfileEntry OBJECT-TYPE
        SYNTAX         TnSshProfileEntry
        MAX-ACCESS     not-accessible
        STATUS         current
        DESCRIPTION    "."
        INDEX { tnSshProfileName }
        ::= { tnSshProfileTable 1 }

    TnSshProfileEntry ::= SEQUENCE {
        tnSshProfileName            OCTET STRING,
        tnSshProfileDescription     SnmpAdminString
    }

    tnSshProfileName OBJECT-TYPE
        SYNTAX         OCTET STRING
        MAX-ACCESS     not-accessible
        STATUS         current
        DESCRIPTION    "."
        ::= { tnSshProfileEntry 1 }

    tnSshProfileDescription OBJECT-TYPE
        SYNTAX         SnmpAdminString (SIZE(0..64))
        MAX-ACCESS     read-create
        STATUS         current
        DESCRIPTION    "."
        ::= { tnSshProfileEntry 2 }

--------------------------------------------------------------------------------
-- Conformance Group Definitions
--------------------------------------------------------------------------------
    tnSystemBasicsGroup OBJECT-GROUP
        OBJECTS {
            tnSysDescr,
            tnSysTelnetPort,
            tnSysHttpPort,
            tnSysDateAndTime,
            tnSysReset,
            tnSysMIBVersion,
            tnSysRingID,
            tnSysNetworkElementID,
            tnSysAINSDebounceTime,
            tnSysSonetSdhMode,
            tnSysAlarmReportingControl,
            tnSysWavelengthTrackerWaveKeySpace,
            tnSysSecureMode,
--            obsolete
--            tnSysMinPasswordLength,
--            tnSysMaxPasswordLength,
            tnSysExtendedTemperatureRange,
            tnSysTemperatureInCelsius,
            tnSysName,
            tnSysEquipmentControllerCapacity,
            tnSysFirstLevelControllerCapacity,
            tnSysMatrix0CompactCapacity,
            tnSysUniversalMatrixFirstLevelControllerCapacity,
            tnSysTimeOffsetTimeZone,
--            obsolete
--            tnSysOperationPercentCompleted,
--            tnSysLastOperationTimeStamp,
            tnSysFipsSquelchMode,
            tnSysOtdrListOfFileNames,
            tnSysOtdrFileCounts,
            tnSysAltitude,
            tnSysThermalShutdownAutotimer,
            tnSysDisplayShelfLabel,
            tnSysPMFineGranularityControl,
            tnSysFmRead,
            tnSysPMStreamingServerControl,
            tnSysSlotMigrationControl,
            tnSysFlexGridClusterOcsAddDropEnabled,
            tnSysFilterCheckTime,
            tnSysCNLinkPhysicalIfIndex,
            tnSysUserlabel,
            tnSysOpenAgentControl,
            tnSysUnkeyedDanglingOchAddDropEnabled,
            tnSysNetWorkTraceV3SecurityUser,
            tnSysScotV3SecurityUser,
            tnSysTL1Enable,
            tnSysLMEnabled,
            tnSysAlienChannelLicensingEnabled,
            tnSysDebug,
            tnSysClusterV3SecurityUser,
--            obsolete
--            tnSysNFMTPublicKey,
            tnSysSyncMode,
            tnSysPMMode,
            tnSysShelfLatitude,
            tnSysShelfLongitude,
            tnSysAlmProfName,
            tnSysBgpAsn,
            tnSysBgpLocalRouterId,
            tnSysNodeIdLabel,
            tnSysNodeNumber,
            tnSysNodeCLLI,
            tnSysNodeTemplate,
--            obsolete
--            tnSysNodeLatitude,
--            tnSysNodeLongitude,
            tnSysCustomerApplicationMode,
            tnSysMDCli,
            tnSysMultiShelfMode,
            tnSysMultiShelfConfigList,
            tnSysMultiShelfUnknownList,
            tnSysMultiShelfMissingList,
            tnSysPrompt,
            tnSysPromptType,
            tnSysShelfAltitude,
            tnSysTacacsSourceIpMode,
            tnSysRadiusSourceIpMode,
            tnSysFtpSourceIpMode,
            tnSysSftpSourceIpMode,
            tnSysHttpSourceIpMode,
            tnSysHttpsSourceIpMode,
            tnSysSnmpSourceIpMode,
            tnSysSyslogSourceIpMode,
            tnSysSshSourceIpMode,
            tnSysAutoTurnUpActiveTemplate,
            tnSysAuthenticationOrder,
            tnSysAuthRejectOption,
            tnSysAutoTurnUpActiveTemplateForce,
            tnSysNtpSourceIpMode,
            tnSysFeatureAutoTurnUp,
            tnSysDelayResetNE,
            tnSysDelayReboot,
            tnSysNmsUserName,
            tnSysVersionPatchId,
            tnSysVersionPatchDescr,
            tnSysCustomerLifeCycleState,
            tnSysUSBInstall,
            tnSysNmsIpVerifyState,
            tnSysOcspSourceIpMode,
            tnSysDnsSourceIpMode,
            tnSysOtcWaitTimeAfterPowerChange,
            tnSysDHCPClassName,
            tnSysDHCPMatchString,
            tnSysKeyLicense,
            tnSysHwIfMode,
            tnSysIpAclNextIndex,
            tnSysIpv6AclNextIndex,
            tnSysDHCPClass,
            tnSysProtocolIpMode,
            tnSysMultiShelfAvailableList,
            tnSysPerformanceMemoryTotal,
            tnSysPerformanceMemoryUsed,
            tnSysPerformanceMemoryUsedPercentage,
            tnSysPerformanceTime,
            tnSysPerformanceCPUStatsPercentages,
            tnSysPower,
            tnSysKeyStoreCertExpiration,
            tnSysNumOspfV2AreaIndependentLsas,
            tnSysNumOspfV3AreaIndependentLsas,
            tnSysBgpAdminDistance
        }
        STATUS         current
        DESCRIPTION    "A collection of objects providing basic system
                        extensions."
        ::= { tnSystemGroups 1 }

    tnSystemControlNetworkGroup OBJECT-GROUP
        OBJECTS {
            tnSysIpAddress,
            tnSysSubnetMask,
            tnSysConfiguredIpAddress,
            tnSysConfiguredSubnetMask,
            tnSysConfiguredSnmpSource,
            tnSysConfiguredOcsIpAddress,
            tnSysConfiguredOcs2IpAddress,
            tnSysConfiguredOcs3IpAddress,
            tnSysOcs1LinkStatus,
            tnSysOcs2LinkStatus,
            tnSysOcs3LinkStatus,
            tnSysConfiguredRadiusSource,
            tnSysConfiguredLoopbackIp1,
            tnSysConfiguredLoopbackIp1SubnetMask,
            tnSysConfiguredSnmpSource1,
            tnSysConfiguredRadiusSource1,
            tnSysLoopbackIpAddress1,
            tnSysLoopbackIp1SubnetMask,
            tnSysConfiguredInetAddressType,
            tnSysConfiguredInetAddress,
            tnSysConfiguredPrefixLength,
            tnSysOcsIp1Password,
            tnSysOcsIp2Password,
            tnSysOcsIp3Password,
            tnSysConfiguredSnmpSourceIPv6,
            tnSysConfiguredRadiusSourceIPv6
        }
        STATUS         current
        DESCRIPTION    "A collection of objects providing basic system
                        extensions."
        ::= { tnSystemGroups 2 }

    tnSystemRedundancyGroup OBJECT-GROUP
        OBJECTS {
            tnSysRedundancyDbSynchState,
            tnSysRedundancyDbResynch,
            tnSysRedundancyDbAudit,
            tnSysRedundancyDbClear,
            tnSysRedundancyActiveCCSlot,
            tnSysRedundancyDbInvalid,
            tnSysRedundancyMateCCReadyToProtect
        }
        STATUS         current
        DESCRIPTION    "A collection of objects providing basic system
                        extensions."
        ::= { tnSystemGroups 3 }

    tnSystemDiscoveryGroup OBJECT-GROUP
        OBJECTS {
--            obsolete
--            tnSysDiscoveryTFTPServer,
            tnSysDiscoveryFilename,
            tnSysDiscoveryMask,
            tnSysDiscoveryControl,
            tnSysDiscoveryStatus,
            tnSysDiscoveryErrorCode,
--            obsolete
--            tnSysDiscoveryNMSMask,
            tnSysDiscoveryBinnedStatsInterval,
            tnSysDiscoveryBinnedStatsBin,
            tnSysDiscoveryServerProtocol,
            tnSysDiscoveryServerIp,
            tnSysDiscoveryServerUserId,
            tnSysDiscoveryServerPassword,
            tnSysDiscoveryServerInetAddressType,
            tnSysDiscoveryServerInetAddress,
            tnSysDiscoveryPort,
            tnSysDiscoveryPrevious15minBinFilesTransfer,
            tnSysDiscoveryPrevious1dayBinFilesTransfer,
            tnSysDiscoveryTransferTimeOffset,
            tnSysDiscoveryTransferTraps
        }
        STATUS         current
        DESCRIPTION    "A collection of objects providing System Discovery."
        ::= { tnSystemGroups 4 }

    tnSystemLoggingGroup OBJECT-GROUP
        OBJECTS {
            tnSysLoggingCLI,
            tnSysLoggingSNMP
        }
        STATUS         current
        DESCRIPTION    "."
        ::= { tnSystemGroups 5 }

    tnSystemBackupAndRestoreGroup OBJECT-GROUP
        OBJECTS {
            tnSysBackupAndRestoreCommand,
            tnSysBackupAndRestoreRemoteHostIp,
            tnSysBackupAndRestoreRemotePath,
            tnSysBackupAndRestoreStatus,
            tnSysBackupAndRestoreLastBackupFilename,
            tnSysBackupAndRestoreLastCommand,
            tnSysBackupAndRestorePercentCompleted,
            tnSysBackupAndRestoreLastBackupFileTimeStamp,
            tnSysBackupAndRestoreProtocol,
            tnSysBackupAndRestoreUserId,
            tnSysBackupAndRestorePassword,
            tnSysBackupAndRestoreLastBackupFileCrc,
--            obsolete
--            tnSysBackupAndRestoreRemotePort
            tnSysBackupAndRestoreRemoteHostInetAddressType,
            tnSysBackupAndRestoreRemoteHostInetAddress,
            tnSysBackupAndRestoreLocalInfo,
--            obsolete
--            tnSysBackupAndRestoreType,
            tnSysBackupAndRestoreLocalDelete,
            tnSysBackupAndRestorePort,
            tnSysBackupAndRestoreFallBackTimeStamp
        }
        STATUS         current
        DESCRIPTION    "."
        ::= { tnSystemGroups 6 }

    tnSysNtpGroup OBJECT-GROUP
        OBJECTS {
            tnSysNtpEnable,
--            obsolete
--            tnSysNtpTimeOffsetHours,
--            tnSysNtpTimeOffsetMinutes,
--            tnSysNtpTimeOffsetTimeZone,
--            tnSysNtpDrift,
--            tnSysNtpTimeOffset,
--            tnSysNtpScale,
            tnSysNtpSynched,
            tnSysNtpServerCurrentIpAddress,
--            obsolete
--            tnSysNtpDaylightSavingsTimeConfigured,
            tnSysNtpDriftString,
            tnSysNtpTimeOffsetString,
            tnSysNtpClockMode,
            tnSysNtpServerCurrentInetAddressType,
            tnSysNtpServerCurrentInetAddress
        }
        STATUS         current
        DESCRIPTION    "."
        ::= { tnSystemGroups 7 }

    tnSysNtpServerGroup OBJECT-GROUP
        OBJECTS {
            tnSysNtpServerIpAddress,
            tnSysNtpServerRowStatus,
            tnSysNtpServerKeyIndex,
            tnSysNtpServerInetAddress,
            tnSysNtpServerInetAddressType
        }
        STATUS         current
        DESCRIPTION    "."
        ::= { tnSystemGroups 8 }

    tnSnmpTargetAddressGroup OBJECT-GROUP
        OBJECTS {
            tnSnmpTargetAddrNmsStationGroupId,
            tnSnmpTargetAddrTrapGroupId,
            tnSnmpTargetAddrDisableTrap
        }
        STATUS         current
        DESCRIPTION    "."
        ::= { tnSystemGroups 9 }

    tnSyslogGroup OBJECT-GROUP
        OBJECTS {
            tnSyslogIpAddress,
            tnSyslogPort,
            tnSyslogFacility,
            tnSyslogPriority,
            tnSyslogEnabled,
            tnSyslogInetAddress,
            tnSyslogInetAddressType,
            tnSyslogProtocol
        }
        STATUS         current
        DESCRIPTION    "."
        ::= { tnSystemGroups 10 }

    tnSysTimingGroup OBJECT-GROUP
        OBJECTS {
            tnSysTimingPrimaryReference,
            tnSysTimingSecondaryReference,
            tnSysTimingLastSwitchTime,
            tnSysTimingControl,
            tnSysTimingPrimaryReferenceStatus,
            tnSysTimingSecondaryReferenceStatus,
            tnSysTimingPrimaryReferenceQuality,
            tnSysTimingSecondaryReferenceQuality,
            tnSysTimingPrimaryReferenceTimingMode,
            tnSysTimingSecondaryReferenceTimingMode,
            tnSysTimingActiveReference,
            tnSysTimingClockingMode,
            tnSysTimingSwitchingMode,
            tnSysTimingFreeRunSuppressAlarms,
            tnSysTimingDs1FramingMode,
            tnSysTimingDs1LineCoding,
            tnSysTimingDs1SsmProcessing,
            tnSysTimingBitsAClockQuality,
            tnSysTimingBitsBClockQuality,
            tnSysTimingActiveLineTimingCable,
            tnSysTimingBitSourceType,
            tnSysTimingBitsAModuleType,
            tnSysTimingBitsBModuleType
        }
        STATUS         current
        DESCRIPTION    "."
        ::= { tnSystemGroups 11 }

    tnSysFeaturesGroup OBJECT-GROUP
        OBJECTS {
--            obsolete
--            tnSysFeatureWavelengthTracker,
--            tnSysFeatureNetworkElementFaultCorrelation,
            tnSysFeatureAutoTopology,
            tnSysFeaturePauseFlowControl,
            tnSysFeatureIpUtilitiesRestricted,
            tnSysFeatureFastServiceSetup
        }
        STATUS         current
        DESCRIPTION    "."
        ::= { tnSystemGroups 12 }

    tnSysFaultCorrelationGroup OBJECT-GROUP
        OBJECTS {
            tnSysFaultCorrelationTransientSuppression
        }
        STATUS         current
        DESCRIPTION    "."
        ::= { tnSystemGroups 13 }

    tnSysErrorHandlingGroup OBJECT-GROUP
        OBJECTS {
            tnSysSetRequestErrorMessage
        }
        STATUS         current
        DESCRIPTION    "."
        ::= { tnSystemGroups 14 }

    tnSysSecurityGroup OBJECT-GROUP
        OBJECTS {
            tnSysSecurityMode,
            tnSysSshKeyType,
            tnSysSshKeyModulus,
            tnSysSshPublicKey,
            tnSysSshKeyCommand,
            tnSysSshKeyGenerationStatus,
            tnSysSshEcdsaKeyModulus,
            tnSysSslKeyType,
            tnSysSslKeyModulus,
            tnSysSslPublicKey,
            tnSysSslKeyCommand,
            tnSysSslKeyGenerationStatus,
            tnSysSslCertTransferCommand,
--            obsolete
--            tnSysSslCertTransferStatus,
            tnSysSslCertTransferProtocol,
            tnSysSslCertTransferRemoteIp,
            tnSysSslCertTransferRemotePath,
            tnSysSslCertTransferRemoteUserId,
            tnSysSslCertTransferRemotePassword,
            tnSysSslCsrCommand,
            tnSysSslCsrCountry,
            tnSysSslCsrState,
            tnSysSslCsrLocality,
            tnSysSslCsrOrganization,
            tnSysSslCsrOrganizationUnit,
            tnSysSslCsrCommonName,
            tnSysSslCsrEmailAddress,
            tnSysSslCertCommand,
            tnSysSslCertSignatureAlgorithm,
            tnSysSslCertValidity,
            tnSysSslCsrUploadStatus,
            tnSysSslCertDownloadStatus,
            tnSysSslCertInstallStatus,
            tnSysSslCsrGenerationStatus,
            tnSshPublicKey,
            tnSysSslCertTransferInetAddressType,
            tnSysSslCertTransferInetAddress,
            tnSysSslCertTransferPort,
            tnSysSslCertVerification,
            tnSshPublicKey1,
            tnSshEcdsaPublicKey,
            tnSshEcdsaPublicKey1,
            tnSshEd25519PublicKey,
            tnSshEd25519PublicKey1,
            tnSysSslCertExpiration
        }
        STATUS         current
        DESCRIPTION    "."
        ::= { tnSystemGroups 15 }

    tnSysTransferLogGroup OBJECT-GROUP
        OBJECTS {
            tnSysTransferLogCommand,
            tnSysTransferLogRemoteHostIp,
            tnSysTransferLogRemotePath,
            tnSysTransferLogType,
            tnSysTransferLogStatus,
            tnSysTransferLogLastLogFilename,
            tnSysTransferLogLastCommand,
            tnSysTransferLogLastFileTimeStamp,
            tnSysTransferLogProtocol,
            tnSysTransferLogUserId,
            tnSysTransferLogPassword,
            tnSysTransferLogWindowStart,
            tnSysTransferLogWindowStop,
            tnSysTransferLogRemoteHostInetAddressType,
            tnSysTransferLogRemoteHostInetAddress,
            tnSysTransferLogPort
        }
        STATUS         current
        DESCRIPTION    "."
        ::= { tnSystemGroups 16 }

    tnSysIpAclSysDefaultGroup OBJECT-GROUP
        OBJECTS {
            tnSysIpAclRxAction,
            tnSysIpAclTxAction,
            tnSysIpAclSnmpCfgEnable,
            tnSysIpAclCfgRestoreToDefault,
            tnSysIpAclClearCounter
        }
        STATUS         current
        DESCRIPTION    "."
        ::= { tnSystemGroups 17 }

    tnSysIpAclPatternScalarsGroup OBJECT-GROUP
        OBJECTS {
            tnSysIpAclPatternAttributeTotal
        }
        STATUS         current
        DESCRIPTION    "."
        ::= { tnSystemGroups 18 }

    tnSysIpAclPatternGroup OBJECT-GROUP
        OBJECTS {
            tnSysIpAclPatternAction,
            tnSysIpAclPatternICMPERROR,
            tnSysIpAclPatternSrcAddr,
            tnSysIpAclPatternSrcPrefix,
            tnSysIpAclPatternDestAddr,
            tnSysIpAclPatternDestPrefix,
            tnSysIpAclPatternDestPort,
            tnSysIpAclPatternIpProtocol,
            tnSysIpAclPatternIpFragment,
            tnSysIpAclPatternIcmpType,
            tnSysIpAclPatternIcmpCode,
            tnSysIpAclPatternTcpEstablish,
            tnSysIpAclPatternRowStatus,
            tnSysIpAclPatternSrcPort,
            tnSysIpAclPatternSystemDefault,
            tnSysIpAclPatternSrcPortRangeEnd,
            tnSysIpAclPatternDestPortRangeEnd
        }
        STATUS         current
        DESCRIPTION    "."
        ::= { tnSystemGroups 19 }

    tnSysIpAclFilterScalarsGroup OBJECT-GROUP
        OBJECTS {
            tnSysIpAclFilterAttributeTotal
        }
        STATUS         current
        DESCRIPTION    "."
        ::= { tnSystemGroups 20 }

    tnSysIpAclFilterGroup OBJECT-GROUP
        OBJECTS {
            tnSysIpAclFilterPatternID,
            tnSysIpAclFilterStatCount,
            tnSysIpAclFilterRowStatus,
            tnSysIpAclFilterSystemDefault
        }
        STATUS         current
        DESCRIPTION    "."
        ::= { tnSystemGroups 21 }

    tnSysIpAclInterfaceScalarsGroup OBJECT-GROUP
        OBJECTS {
            tnSysIpAclInterfaceAttributeTotal
        }
        STATUS         current
        DESCRIPTION    "."
        ::= { tnSystemGroups 22 }

    tnSysIpAclInterfaceGroup OBJECT-GROUP
        OBJECTS {
            tnSysIpAclInterfaceFilterID,
            tnSysIpAclInterfaceFilterEnable,
            tnSysIpAclInterfaceFilterRowStatus,
            tnSysIpAclInterfaceSystemDefault,
            tnSysIpAclInterfaceFilterLog
        }
        STATUS         current
        DESCRIPTION    "."
        ::= { tnSystemGroups 23 }

    tnSysNtpServerIdStatsGroup OBJECT-GROUP
        OBJECTS {
            tnSysNtpServerIdStatsSelect,
            tnSysNtpServerIdStatsIp,
            tnSysNtpServerIdStatsRefId,
            tnSysNtpServerIdStatsStrtm,
            tnSysNtpServerIdStatsClockType,
            tnSysNtpServerIdStatsPoll,
            tnSysNtpServerIdStatsReach,
            tnSysNtpServerIdStatsDelay,
            tnSysNtpServerIdStatsOffset,
            tnSysNtpServerIdStatsJitter,
            tnSysNtpServerIdStatsKeyIndex
        }
        STATUS         current
        DESCRIPTION    "."
        ::= { tnSystemGroups 24 }

    tnSysFtpServerGroup OBJECT-GROUP
        OBJECTS {
            tnSysFtpServerEnabled,
            tnSysFtpServerUserId,
            tnSysFtpServerPassword
        }
        STATUS         current
        DESCRIPTION    "."
        ::= { tnSystemGroups 25 }

    tnSysNtpServerAuthenticationScalarsGroup OBJECT-GROUP
        OBJECTS {
            tnSysNtpServerAuthenticationAttributeTotal
        }
        STATUS         current
        DESCRIPTION    "."
        ::= { tnSystemGroups 26 }

    tnSysNtpServerAuthenticationGroup OBJECT-GROUP
        OBJECTS {
            tnSysNtpServerAuthenticationRowStatus,
            tnSysNtpServerAuthenticationKeyType,
            tnSysNtpServerAuthenticationKey
        }
        STATUS         current
        DESCRIPTION    "."
        ::= { tnSystemGroups 27 }

    tnSysIpAclNetIfFilterScalarsGroup OBJECT-GROUP
        OBJECTS {
            tnSysIpAclNetIfFilterAttributeTotal
        }
        STATUS         current
        DESCRIPTION    "."
        ::= { tnSystemGroups 28 }

    tnSysIpAclNetIfFilterGroup OBJECT-GROUP
        OBJECTS {
            tnSysIpAclNetIfFilterRowStatus,
            tnSysIpAclNetIfFilterID,
            tnSysIpAclNetIfFilterEnable,
            tnSysIpAclNetIfFilterSystemDefault
        }
        STATUS         current
        DESCRIPTION    "."
        ::= { tnSystemGroups 29 }

    tnNeDiscoveryScalarsGroup OBJECT-GROUP
        OBJECTS {
            tnNeDiscoveryAttributeTotal
        }
        STATUS         current
        DESCRIPTION    "."
        ::= { tnSystemGroups 30 }

    tnNeDiscoveryGroup OBJECT-GROUP
        OBJECTS {
            tnNeDiscoveryFilename,
            tnNeDiscoveryControl,
            tnNeDiscoveryStatus,
            tnNeDiscoveryErrorCode,
            tnNeDiscoveryServerIp,
            tnNeDiscoveryServerProtocol,
            tnNeDiscoveryServerUserId,
            tnNeDiscoveryServerPassword,
            tnNeDiscoveryServerTimeOut,
            tnNeDiscoveryRowStatus,
            tnNeDiscoveryServerInetAddressType,
            tnNeDiscoveryServerInetAddress,
            tnNeDiscoveryDeltaFilename,
            tnNeDiscoveryDeltaFileFlag,
            tnNeDiscoveryDeltaSyncStatus,
            tnNeDiscoveryPort
        }
        STATUS         current
        DESCRIPTION    "."
        ::= { tnSystemGroups 31 }

    tnSysOtdrScanSystemProfileScalarsGroup OBJECT-GROUP
        OBJECTS {
            tnSysOtdrScanSystemProfileAttributeTotal
        }
        STATUS         current
        DESCRIPTION    "."
        ::= { tnSystemGroups 32 }

    tnSysOtdrScanSystemProfileGroup OBJECT-GROUP
        OBJECTS {
            tnSysOtdrScanSystemProfileDescription,
            tnSysOtdrScanSystemProfileWaveLength,
            tnSysOtdrScanSystemProfilePulseLength,
            tnSysOtdrScanSystemProfileRange,
            tnSysOtdrScanSystemProfileResolution,
            tnSysOtdrScanSystemProfileAvgTime,
            tnSysOtdrScanSystemProfileEventThreshold,
            tnSysOtdrScanSystemProfileIOR
        }
        STATUS         current
        DESCRIPTION    "."
        ::= { tnSystemGroups 33 }

    tnSysOtdrScanTransferGroup OBJECT-GROUP
        OBJECTS {
            tnSysOtdrScanTransferRemoteHostIp,
            tnSysOtdrScanTransferCommand,
            tnSysOtdrScanTransferRemotePath,
            tnSysOtdrScanTransferStatus,
            tnSysOtdrScanTransferFilename,
            tnSysOtdrScanTransferProtocol,
            tnSysOtdrScanTransferUserId,
            tnSysOtdrScanTransferPassword,
            tnSysOtdrScanTransferInetAddressType,
            tnSysOtdrScanTransferInetAddress,
            tnSysOtdrScanTransferPort
        }
        STATUS         current
        DESCRIPTION    "."
        ::= { tnSystemGroups 34 }

    tnClusterGroup OBJECT-GROUP
        OBJECTS {
            tnClusterRowStatus,
            tnClusterIpAddress,
            tnClusterlinkStatus,
            tnClusterInetAddressType,
            tnClusterInetAddress
        }
        STATUS         current
        DESCRIPTION    "."
        ::= { tnSystemGroups 35 }

    tnSysPmFetchBulkGroup OBJECT-GROUP
        OBJECTS {
            tnSysPmFetchBulkStart,
            tnSysPmFetchBulkStatus,
            tnSysPmFetchBulkRemoteHostIp,
            tnSysPmFetchBulkUserId,
            tnSysPmFetchBulkPassword,
            tnSysPmFetchBulkRemotePath,
            tnSysPmFetchBulkStatsInterval,
            tnSysPmFetchBulkBinnedStatsBin,
            tnSysPmFetchBulkShelfNum
        }
        STATUS         current
        DESCRIPTION    "."
        ::= { tnSystemGroups 36 }

    tnSysDebugTransferGroup OBJECT-GROUP
        OBJECTS {
            tnSysDebugTransferRemoteHostIp,
            tnSysDebugTransferCommand,
            tnSysDebugTransferRemotePath,
            tnSysDebugTransferStatus,
            tnSysDebugTransferProtocol,
            tnSysDebugTransferUserId,
            tnSysDebugTransferPassword,
            tnSysDebugTransferFilename,
            tnSysDebugTransferRecentSuccessFile,
            tnSysDebugTransferTimestamp,
            tnSysDebugTransferShelfNum,
            tnSysDebugTransferPercentCompleted,
            tnSysDebugTransferRemoteInetAddressType,
            tnSysDebugTransferRemoteInetAddress,
            tnSysDebugTransferScratchDir,
            tnSysDebugTransferIncludeInDumps,
            tnSysDebugTransferPort
        }
        STATUS         current
        DESCRIPTION    "."
        ::= { tnSystemGroups 37 }

    tnSysLicenseInvGroup OBJECT-GROUP
        OBJECTS {
            tnSysLicenseInvPathIp,
            tnSysLicenseInvFile,
            tnSysLicenseInvProtocol,
            tnSysLicenseInvUserId,
            tnSysLicenseInvPassword,
            tnSysLicenseInvFileUploadOper,
            tnSysLicenseInvPathInetAddressType,
            tnSysLicenseInvPathInetAddress,
            tnSysLicenseInvLastOperPercentCompleted,
            tnSysLicenseInvLastUploadFileName,
            tnSysLicenseInvFileLastUploadStatus,
            tnSysLicenseInvFileLastUploadTimeStamp
        }
        STATUS         current
        DESCRIPTION    "."
        ::= { tnSystemGroups 38 }

--    obsolete
--    tnSysDataDumpInfoGroup OBJECT-GROUP ::= { tnSystemGroups 39 }

    tnSysLinuxGroup OBJECT-GROUP
        OBJECTS {
            tnSysLinuxRootUserId,
            tnSysLinuxRootUserPassword,
            tnSysLinuxApplUserId,
            tnSysLinuxApplUserPassword,
            tnSysLinuxRootPasswordStatus,
            tnSysLinuxApplPasswordStatus,
            tnSysLinuxRootUserStatus,
            tnSysLinuxApplUserStatus,
            tnSysLinuxLoginInactivityTimeOut,
            tnSysLinuxSmsUserId,
            tnSysLinuxSmsUserPassword,
            tnSysLinuxSmsPasswordStatus,
            tnSysLinuxSmsUserStatus,
            tnSysLinuxRootUserLocalStatus,
            tnSysLinuxSecurityCommit,
            tnSysLinuxRootUserPort
        }
        STATUS         current
        DESCRIPTION    "."
        ::= { tnSystemGroups 40 }

    tnSysIpAclIpv6SysDefaultGroup OBJECT-GROUP
        OBJECTS {
            tnSysIpAclIpv6RxAction,
            tnSysIpAclIpv6TxAction,
            tnSysIpAclIpv6SnmpCfgEnable,
            tnSysIpAclIpv6CfgRestoreToDefault,
            tnSysIpAclIPv6ClearCounter
        }
        STATUS         current
        DESCRIPTION    "."
        ::= { tnSystemGroups 41 }

    tnSysFileInitializationGroup OBJECT-GROUP
        OBJECTS {
            tnSysFileInitializationRoot,
            tnSysFileInitializationUserId,
            tnSysFileInitializationPassword,
            tnSysFileInitializationFilename,
            tnSysFileInitializationInetAddressType,
            tnSysFileInitializationInetAddress
        }
        STATUS         current
        DESCRIPTION    "."
        ::= { tnSystemGroups 42 }

    tnSysOtdrScanSystemProfileMScalarsGroup OBJECT-GROUP
        OBJECTS {
            tnSysOtdrScanSystemProfileMAttributeTotal
        }
        STATUS         current
        DESCRIPTION    "."
        ::= { tnSystemGroups 43 }

    tnSysOtdrScanSystemProfileMGroup OBJECT-GROUP
        OBJECTS {
            tnSysOtdrScanSystemProfileMDescription,
            tnSysOtdrScanSystemProfileMWaveLength,
            tnSysOtdrScanSystemProfileMPulseLength,
            tnSysOtdrScanSystemProfileMRange,
            tnSysOtdrScanSystemProfileMResolution,
            tnSysOtdrScanSystemProfileMAvgTime,
            tnSysOtdrScanSystemProfileMEventThreshold,
            tnSysOtdrScanSystemProfileMIOR
        }
        STATUS         current
        DESCRIPTION    "."
        ::= { tnSystemGroups 44 }

    tnSysSecurityScalarsGroup OBJECT-GROUP
        OBJECTS {
            tnSshKeyAttributeTotal
        }
        STATUS         current
        DESCRIPTION    "."
        ::= { tnSystemGroups 45 }

    tnSysIpAclIpv6PatternScalarsGroup OBJECT-GROUP
        OBJECTS {
            tnSysIpAclIpv6PatternAttributeTotal
        }
        STATUS         current
        DESCRIPTION    "."
        ::= { tnSystemGroups 46 }

    tnSysIpAclIpv6PatternGroup OBJECT-GROUP
        OBJECTS {
            tnSysIpAclIpv6PatternAction,
            tnSysIpAclIpv6PatternICMPV6ERROR,
            tnSysIpAclIpv6PatternSrcAddr,
            tnSysIpAclIpv6PatternSrcPrefixLen,
            tnSysIpAclIpv6PatternDestAddr,
            tnSysIpAclIpv6PatternDestPrefixLen,
            tnSysIpAclIpv6PatternIpProtocol,
            tnSysIpAclIpv6PatternIcmpType,
            tnSysIpAclIpv6PatternIcmpCode,
            tnSysIpAclIpv6PatternSrcPort,
            tnSysIpAclIpv6PatternDestPort,
            tnSysIpAclIpv6PatternIpFragment,
            tnSysIpAclIpv6PatternTcpEstablish,
            tnSysIpAclIpv6PatternSystemDefault,
            tnSysIpAclIpv6PatternRowStatus,
            tnSysIpAclIpv6PatternSrcPortRangeEnd,
            tnSysIpAclIpv6PatternDestPortRangeEnd
        }
        STATUS         current
        DESCRIPTION    "."
        ::= { tnSystemGroups 47 }

    tnSysIpAclIpv6FilterScalarsGroup OBJECT-GROUP
        OBJECTS {
            tnSysIpAclIpv6FilterAttributeTotal
        }
        STATUS         current
        DESCRIPTION    "."
        ::= { tnSystemGroups 48 }

    tnSysIpAclIpv6FilterGroup OBJECT-GROUP
        OBJECTS {
            tnSysIpAclIpv6FilterPatternID,
            tnSysIpAclIpv6FilterStatCount,
            tnSysIpAclIpv6FilterRowStatus,
            tnSysIpAclIpv6FilterSystemDefault
        }
        STATUS         current
        DESCRIPTION    "."
        ::= { tnSystemGroups 49 }

    tnSysIpAclIpv6InterfaceScalarsGroup OBJECT-GROUP
        OBJECTS {
            tnSysIpAclIpv6InterfaceAttributeTotal
        }
        STATUS         current
        DESCRIPTION    "."
        ::= { tnSystemGroups 50 }

    tnSysIpAclIpv6InterfaceGroup OBJECT-GROUP
        OBJECTS {
            tnSysIpAclIpv6InterfaceFilterID,
            tnSysIpAclIpv6InterfaceFilterEnable,
            tnSysIpAclIpv6InterfaceFilterRowStatus,
            tnSysIpAclIpv6InterfaceSystemDefault,
            tnSysIpAclIpv6InterfaceFilterLog
        }
        STATUS         current
        DESCRIPTION    "."
        ::= { tnSystemGroups 51 }

    tnSysIpv6AclNetIfFilterScalarsGroup OBJECT-GROUP
        OBJECTS {
            tnSysIpv6AclNetIfFilterAttributeTotal
        }
        STATUS         current
        DESCRIPTION    "."
        ::= { tnSystemGroups 52 }

    tnSysIpv6AclNetIfFilterGroup OBJECT-GROUP
        OBJECTS {
            tnSysIpv6AclNetIfFilterRowStatus,
            tnSysIpv6AclNetIfFilterID,
            tnSysIpv6AclNetIfFilterEnable,
            tnSysIpv6AclNetIfFilterSystemDefault
        }
        STATUS         current
        DESCRIPTION    "."
        ::= { tnSystemGroups 53 }

    tnSysIpAclEthIfFilterScalarsGroup OBJECT-GROUP
        OBJECTS {
            tnSysIpAclEthIfFilterAttributeTotal
        }
        STATUS         current
        DESCRIPTION    "."
        ::= { tnSystemGroups 54 }

    tnSysIpAclEthIfFilterGroup OBJECT-GROUP
        OBJECTS {
            tnSysIpAclEthIfFilterRowStatus,
            tnSysIpAclEthIfFilterID,
            tnSysIpAclEthIfFilterEnable,
            tnSysIpAclEthIfFilterSystemDefault
        }
        STATUS         current
        DESCRIPTION    "."
        ::= { tnSystemGroups 55 }

    tnSysIpv6AclEthIfFilterScalarsGroup OBJECT-GROUP
        OBJECTS {
            tnSysIpv6AclEthIfFilterAttributeTotal
        }
        STATUS         current
        DESCRIPTION    "."
        ::= { tnSystemGroups 56 }


    tnSysIpv6AclEthIfFilterGroup OBJECT-GROUP
        OBJECTS {
            tnSysIpv6AclEthIfFilterRowStatus,
            tnSysIpv6AclEthIfFilterID,
            tnSysIpv6AclEthIfFilterEnable,
            tnSysIpv6AclEthIfFilterSystemDefault
        }
        STATUS         current
        DESCRIPTION    "."
        ::= { tnSystemGroups 57 }

    tnSysBtInterfaceGroup OBJECT-GROUP
        OBJECTS {
            tnSysBtInterfaceDescription,
            tnSysBtInterfaceIpAddr,
            tnSysBtInterfaceIpSubMask,
            tnSysBtInterfaceAdminState,
            tnSysBtInterfaceLinkIntegrityStatus,
            tnSysBtInterfaceDHCPServer,
            tnSysBtInterfaceDHCPRange,
            tnSysBtInterfaceNodeSerialNum,
            tnSysBtInterfaceMacAddress
        }
        STATUS         current
        DESCRIPTION    "."
        ::= { tnSystemGroups 58 }

    tnSysOtdrScanResultsTransferGroup OBJECT-GROUP
        OBJECTS {
            tnSysOtdrScanResultsTransferRemoteHostIp,
            tnSysOtdrScanResultsTransferProtocol,
            tnSysOtdrScanResultsTransferUserId,
            tnSysOtdrScanResultsTransferPassword,
            tnSysOtdrScanResultsTransferRemotePath,
            tnSysOtdrScanResultsTransferCommand,
            tnSysOtdrScanResultsTransferFilename,
            tnSysOtdrScanResultsTransferRecentSuccessFile,
            tnSysOtdrScanResultsTransferStatus,
            tnSysOtdrScanResultsLastTransferTimestamp,
            tnSysOtdrScanResultsTransferRemoteInetAddressType,
            tnSysOtdrScanResultsTransferRemoteInetAddress,
            tnSysOtdrScanResultsTransferPort,
            tnSysOtdrScanResultsTransferRemoveFileFromNE
        }
        STATUS         current
        DESCRIPTION    "."
        ::= { tnSystemGroups 59 }

    tnSysLicenseMgrGroup OBJECT-GROUP
        OBJECTS {
            tnSysLicenseMgrKeepAliveTimer,
            tnSysLicenseMgrPrimaryServerIp,
            tnSysLicenseMgrPrimaryServerInetAddressType,
            tnSysLicenseMgrPrimaryServerInetAddress,
            tnSysLicenseMgrSecondaryServerIp,
            tnSysLicenseMgrSecondaryServerInetAddressType,
            tnSysLicenseMgrSecondaryServerInetAddress,
            tnSysLicenseMgrPrimaryServerStatus,
            tnSysLicenseMgrSecondaryServerStatus,
            tnSysLicenseMgrExpiration,
            tnSysLicenseMgrTimeOut,
            tnSysLicenseMgrRetries,
            tnSysLicenseMgrLastRefresh,
            tnSysLicenseMgrCertStatus,
            tnSysLicenseMgrNextRefreshTime
        }
        STATUS         current
        DESCRIPTION    "."
        ::= { tnSystemGroups 60 }

    tnLicenseEntityGroup OBJECT-GROUP
        OBJECTS {
            tnLicenseEntityRefreshSet,
            tnLicenseEntityNumberInUse,
            tnLicenseEntityNumberExceedAvail,
            tnLicenseEntityEntitlementNeeded
        }
        STATUS         current
        DESCRIPTION    "."
        ::= { tnSystemGroups 61 }

    tnSysKeyStoreServiceGroup OBJECT-GROUP
        OBJECTS {
            tnSysKeyStoreTransServerCommand,
            tnSysKeyStoreTransServerProtocol,
            tnSysKeyStoreTransServerHost,
            tnSysKeyStoreTransServerPort,
            tnSysKeyStoreTransServerLocation,
            tnSysKeyStoreTransServerUserId,
            tnSysKeyStoreTransServerPassword,
            tnSysKeyStoreTransServerInetAddressType,
            tnSysKeyStoreTransServerInetAddress,
            tnSysKeyStoreServiceStatus,
            tnSysKeyStoreServerLastTransferTime,
            tnSysKeyStoreTransServerURI
        }
        STATUS         current
        DESCRIPTION    "."
        ::= { tnSystemGroups 62 }

    tnSysKeyStoreCertInfoGroup OBJECT-GROUP
        OBJECTS {
            tnSysKeyStoreCertVersion,
            tnSysKeyStoreCertSerialNumber,
            tnSysKeyStoreCertSignatureAlgorithm,
            tnSysKeyStoreCertIssuer,
            tnSysKeyStoreCertValidity,
            tnSysKeyStoreCertSubject,
            tnSysKeyStoreCertSubjectPublicKeyInfo,
            tnSysKeyStoreCertKeyUsage,
            tnSysKeyStoreCertSubjectAlternativeName,
            tnSysKeyStoreCertExtendedKeyUsage,
            tnSysKeyStoreCertBasicConstraints,
            tnSysKeyStoreCertSHA256Fingerprint
        }
        STATUS         current
        DESCRIPTION    "."
        ::= { tnSystemGroups 63 }

    tnSysBgpPeerGroup OBJECT-GROUP
        OBJECTS {
            tnSysBgpPeerRowStatus,
            tnSysBgpPeerInetAddressType,
            tnSysBgpPeerIp,
            tnSysBgpPeerInetAddress,
            tnSysBgpPeerRemoteASN,
            tnSysBgpPeerSecurityKey,
            tnSysBgpPeerRouterId,
            tnSysBgpPeerStatus,
            tnSysBgpMaxPrefixIpv4Limit,
            tnSysBgpMaxPrefixIpv4Threshold,
            tnSysBgpMaxPrefixIpv4Action,
            tnSysBgpMaxPrefixIpv6Limit,
            tnSysBgpMaxPrefixIpv6Threshold,
            tnSysBgpMaxPrefixIpv6Action,
            tnSysBgpStatsIpv4PrefixInCount,
            tnSysBgpStatsIpv6PrefixInCount,
            tnSysBgpStatsIpv4PrefixOutCount,
            tnSysBgpStatsIpv6PrefixOutCount,
            tnSysBgpPeerStatsInetAddressType,
            tnSysBgpPeerStatsIp,
            tnSysBgpPeerStatsInetAddress
        }
        STATUS         current
        DESCRIPTION    "."
        ::= { tnSystemGroups 64 }

    tnSysDiscoverMeGroup OBJECT-GROUP
        OBJECTS {
            tnSysDiscoverMeTraps
        }
        STATUS         current
        DESCRIPTION    "Discover Me related system objects."
        ::= { tnSystemGroups 65 }

    tnSyslogServerGroup OBJECT-GROUP
        OBJECTS {
            tnSyslogServerIpAddress,
            tnSyslogServerPort,
            tnSyslogServerFacility,
            tnSyslogServerPriority,
            tnSyslogServerEnabled,
            tnSyslogServerInetAddress,
            tnSyslogServerInetAddressType,
            tnSyslogServerProtocol,
            tnSyslogServerType,
            tnSyslogServerDomain
        }
        STATUS         current
        DESCRIPTION    "."
        ::= { tnSystemGroups 66 }

    tnLicenseEntitlementGroup OBJECT-GROUP
        OBJECTS {
            tnLicenseEntitlementDetails
        }
        STATUS         current
        DESCRIPTION    "."
        ::= { tnSystemGroups 67 }

    tnPctObjsGroup OBJECT-GROUP
        OBJECTS {
            tnPctVerificationPeriod,
            tnPctVerificationLossThreshold,
            tnPctVerificationOffset,
            tnPctVerificationStatus
        }
        STATUS         current
        DESCRIPTION    "."
        ::= { tnSystemGroups 68 }

    tnHostKeyGroup OBJECT-GROUP
        OBJECTS {
            tnHostKeyString1,
            tnHostKeyString2
        }
        STATUS         current
        DESCRIPTION    "."
        ::= { tnSystemGroups 69 }

    tnSshPrivKeyGroup OBJECT-GROUP
        OBJECTS {
            tnSshPrivKeyString1,
            tnSshPrivKeyString2,
            tnSshPrivKeyPassword
        }
        STATUS         current
        DESCRIPTION    "."
        ::= { tnSystemGroups 70 }

    tnSysNESshKeyGroup OBJECT-GROUP
        OBJECTS {
            tnSysNESshKeyRowStatus,
            tnSysNESshKeyString1,
            tnSysNESshKeyString2
        }
        STATUS         current
        DESCRIPTION    "."
        ::= { tnSystemGroups 71 }

    tnNESshKeyGroup OBJECT-GROUP
        OBJECTS {
            tnNESshKeyRowStatus,
            tnNESshKeyString1,
            tnNESshKeyString2
        }
        STATUS         current
        DESCRIPTION    "."
        ::= { tnSystemGroups 72 }

    tnTransferSysLogGroup OBJECT-GROUP
        OBJECTS {
            tnTransferSysLogCommand,
            tnTransferSysLogRemoteHostIp,
            tnTransferSysLogRemoteHostInetAddressType,
            tnTransferSysLogRemoteHostInetAddress,
            tnTransferSysLogPort,
            tnTransferSysLogProtocol,
            tnTransferSysLogUserId,
            tnTransferSysLogPassword,
            tnTransferSysLogRemotePath,
            tnTransferSysLogPeriod,
            tnTransferSysLogLastFileTransfer,
            tnTransferSysLogEnable
        }
        STATUS         current
        DESCRIPTION    "."
        ::= { tnSystemGroups 73 }

    tnSysHealthCareGroup OBJECT-GROUP
        OBJECTS {
            tnSysHealthCareCheckCommand,
            tnSysHealthCareCheckShelfNum,
            tnSysHealthCareCheckSlotNum,
            tnSysHealthCareCheckPercentCompleted,
            tnSysHealthCareCheckStatus,
            tnSysHealthCareCheckResult,
            tnSysHealthCareCheckScratchDir,
            tnSysHealthCareServerIp,
            tnSysHealthCareServerProtocol,
            tnSysHealthCareServerInetAddressType,
            tnSysHealthCareServerInetAddress,
            tnSysHealthCareServerPort,
            tnSysHealthCareServerUserId,
            tnSysHealthCareServerPassword,
            tnSysHealthCareServerLocation,
            tnSysHealthCareTransferCommand,
            tnSysHealthCareTransferPercentCompleted,
            tnSysHealthCareTransferStatus,
            tnSysHealthCareTransferLastFile,
            tnSysHealthCareLastOperation,
            tnSysHealthCareSetCriteriaTcId,
            tnSysHealthCareSetCriteria,
            tnSysHealthCareDeleteCriteriaTcId,
            tnSysHealthCareDeleteCriteria,
            tnSysHealthCareApplyCriteriaCommand
        }
        STATUS         current
        DESCRIPTION    "."
        ::= { tnSystemGroups 74 }

    tnSshCiphersGroup OBJECT-GROUP
        OBJECTS {
            tnSshCiphersEnabled
        }
        STATUS         current
        DESCRIPTION    "."
        ::= { tnSystemGroups 75 }

    tnSshHostKeyGroup OBJECT-GROUP
        OBJECTS {
            tnSshHostKeyEnabled
        }
        STATUS         current
        DESCRIPTION    "."
        ::= { tnSystemGroups 76 }

    tnSshMacsGroup OBJECT-GROUP
        OBJECTS {
            tnSshMacsEnabled
        }
        STATUS         current
        DESCRIPTION    "."
        ::= { tnSystemGroups 77 }

    tnSshKexGroup OBJECT-GROUP
        OBJECTS {
            tnSshKexEnabled
        }
        STATUS         current
        DESCRIPTION    "."
        ::= { tnSystemGroups 78 }

    tnSshPubKeyGroup OBJECT-GROUP
        OBJECTS {
            tnSshPubKeyEnabled
        }
        STATUS         current
        DESCRIPTION    "."
        ::= { tnSystemGroups 79 }

    tnTlsProfileGroup OBJECT-GROUP
        OBJECTS {
            tnTlsProfileMinVersion,
            tnTlsProfileMaxVersion,
            tnTlsProfileMutualAuth,
            tnTlsProfileDescription
        }
        STATUS         current
        DESCRIPTION    "."
        ::= { tnSystemGroups 80 }

    tnSysTrapThrottlingGroup OBJECT-GROUP
        OBJECTS {
            tnSysTrapThrottlingStatus,
            tnSysTrapThrottlingThreshold1,
            tnSysTrapThrottlingThreshold2,
            tnSysTrapThrottlingThreshold3,
            tnSysTrapThrottlingTimeOverThreshold,
            tnSysTrapThrottlingTimeUnderThreshold,
            tnSysTrapThrottlingState
        }
        STATUS         current
        DESCRIPTION    "."
        ::= { tnSystemGroups 81 }

    tnSanListGroup OBJECT-GROUP
        OBJECTS {
            tnSanListRowStatus
        }
        STATUS         current
        DESCRIPTION    "."
        ::= { tnSystemGroups 82 }

    tnCsrSanListGroup OBJECT-GROUP
        OBJECTS {
            tnCsrSanListRowStatus
        }
        STATUS         current
        DESCRIPTION    "."
        ::= { tnSystemGroups 83 }

    tnSanListAuthGroup OBJECT-GROUP
        OBJECTS {
            tnSanListAuthentication,
            tnSanListProfileDescription
        }
        STATUS         current
        DESCRIPTION    "."
        ::= { tnSystemGroups 84 }

    tnSysNmsIpListGroup OBJECT-GROUP
        OBJECTS {
            tnSysNmsIpListRowStatus,
            tnSysNmsIpListIpAddress,
            tnSysNmsIpListInetAddress,
            tnSysNmsIpListInetAddressType
        }
        STATUS         current
        DESCRIPTION    "."
        ::= { tnSystemGroups 85 }

    tnOcspProfileGroup OBJECT-GROUP
        OBJECTS {
            tnOcspProfileRowStatus,
            tnOcspProfileRetry,
            tnOcspProfileServerUrl,
            tnOcspProfileStatus,
            tnOcspProfileTimeout
        }
        STATUS         current
        DESCRIPTION    "."
        ::= { tnSystemGroups 86 }

    tnSysDnsServerGroup OBJECT-GROUP
        OBJECTS {
            tnSysDnsServerIpAddress,
            tnSysDnsServerInetAddress,
            tnSysDnsServerInetAddressType
        }
        STATUS         current
        DESCRIPTION    "."
        ::= { tnSystemGroups 87 }

    tnTransferPMDiscoveryGroup OBJECT-GROUP
        OBJECTS {
            tnTransferPMDiscoveryRowStatus,
            tnTransferPMDiscoveryFilename,
            tnTransferPMDiscoveryControl,
            tnTransferPMDiscoveryStatus,
            tnTransferPMDiscoveryErrorCode,
            tnTransferPMDiscoveryServerProtocol,
            tnTransferPMDiscoveryServerIp,
            tnTransferPMDiscoveryServerUserId,
            tnTransferPMDiscoveryServerPassword,
            tnTransferPMDiscoveryServerInetAddressType,
            tnTransferPMDiscoveryServerInetAddress,
            tnTransferPMDiscoveryPort,
            tnTransferPMDiscoveryPrevious15minBinFilesTransfer,
            tnTransferPMDiscoveryPrevious1dayBinFilesTransfer,
            tnTransferPMDiscoveryTransferTimeOffset,
            tnTransferPMDiscovery15minBinFileTransferCount,
            tnTransferPMDiscovery1dayBinFileTransferCount,
            tnTransferPMDiscovery15minBinFileTransferFailureCount,
            tnTransferPMDiscovery1dayBinFileTransferFailureCount
        }
        STATUS         current
        DESCRIPTION    "."
        ::= { tnSystemGroups 88 }

    tnSysIpAclScalarsGroup OBJECT-GROUP
        OBJECTS {
            tnSysIpAclAttributeTotal
        }
        STATUS         current
        DESCRIPTION    "."
        ::= { tnSystemGroups 89 }

    tnSysIpAclGroup OBJECT-GROUP
        OBJECTS {
            tnSysIpAclDesc,
            tnSysIpAclAccessID,
            tnSysIpAclInterface,
            tnSysIpAclAction,
            tnSysIpAclSrcPort,
            tnSysIpAclDestPort,
            tnSysIpAclIcmpType,
            tnSysIpAclIcmpCode,
            tnSysIpAclIpProtocol,
            tnSysIpAclSrcAddr,
            tnSysIpAclSrcPrefix,
            tnSysIpAclDestAddr,
            tnSysIpAclDestPrefix,
            tnSysIpAclIpFragment,
            tnSysIpAclTcpEstablish,
            tnSysIpAclStatCount,
            tnSysIpAclAdminState
        }
        STATUS         current
        DESCRIPTION    "."
        ::= { tnSystemGroups 90 }

    tnSysIpv6AclGroup OBJECT-GROUP
        OBJECTS {
            tnSysIpv6AclDesc,
            tnSysIpv6AclAccessID,
            tnSysIpv6AclInterface,
            tnSysIpv6AclAction,
            tnSysIpv6AclSrcPort,
            tnSysIpv6AclDestPort,
            tnSysIpv6AclIcmpType,
            tnSysIpv6AclIcmpCode,
            tnSysIpv6AclIpProtocol,
            tnSysIpv6AclSrcAddr,
            tnSysIpv6AclSrcPrefixLen,
            tnSysIpv6AclDestAddr,
            tnSysIpv6AclDestPrefixLen,
            tnSysIpv6AclTcpEstablish,
            tnSysIpv6AclStatCount,
            tnSysIpv6AclAdminState
        }
        STATUS         current
        DESCRIPTION    "."
        ::= { tnSystemGroups 91 }

    tnSysIpv6AclScalarsGroup OBJECT-GROUP
        OBJECTS {
            tnSysIpv6AclAttributeTotal
        }
        STATUS         current
        DESCRIPTION    "."
        ::= { tnSystemGroups 92 }

    tnSshProfileGroup OBJECT-GROUP
        OBJECTS {
            tnSshProfileDescription
        }
        STATUS         current
        DESCRIPTION    "."
        ::= { tnSystemGroups 93 }

--------------------------------------------------------------------------------
-- Compliance Statements (mandatory)
--------------------------------------------------------------------------------
    tnSystemCompliance MODULE-COMPLIANCE
        STATUS         current
        DESCRIPTION    "The compliance statement for System Extensions."
        MODULE
        MANDATORY-GROUPS  {
            tnSystemBasicsGroup,
            tnSystemControlNetworkGroup,
            tnSystemRedundancyGroup,
            tnSystemDiscoveryGroup,
            tnSystemLoggingGroup,
            tnSystemBackupAndRestoreGroup,
            tnSysNtpGroup,
            tnSysNtpServerGroup,
            tnSnmpTargetAddressGroup,
            tnSyslogGroup,
            tnSysTimingGroup,
            tnSysFeaturesGroup,
            tnSysFaultCorrelationGroup,
            tnSysErrorHandlingGroup,
            tnSysSecurityGroup,
            tnSysTransferLogGroup,
            tnSysIpAclSysDefaultGroup,
            tnSysIpAclPatternScalarsGroup,
            tnSysIpAclPatternGroup,
            tnSysIpAclFilterScalarsGroup,
            tnSysIpAclFilterGroup,
            tnSysIpAclInterfaceScalarsGroup,
            tnSysIpAclInterfaceGroup,
            tnSysNtpServerIdStatsGroup,
            tnSysFtpServerGroup,
            tnSysNtpServerAuthenticationScalarsGroup,
            tnSysNtpServerAuthenticationGroup,
            tnSysIpAclNetIfFilterScalarsGroup,
            tnSysIpAclNetIfFilterGroup,
            tnNeDiscoveryScalarsGroup,
            tnNeDiscoveryGroup,
            tnSysOtdrScanSystemProfileScalarsGroup,
            tnSysOtdrScanSystemProfileGroup,
            tnSysOtdrScanTransferGroup,
            tnClusterGroup,
            tnSysPmFetchBulkGroup,
            tnSysDebugTransferGroup,
            tnSysLicenseInvGroup,
--            obsolete
--            tnSysDataDumpInfoGroup,
            tnSysLinuxGroup,
            tnSysIpAclIpv6SysDefaultGroup,
            tnSysFileInitializationGroup,
            tnSysOtdrScanSystemProfileMScalarsGroup,
            tnSysOtdrScanSystemProfileMGroup,
            tnSysSecurityScalarsGroup,
            tnSysIpAclIpv6PatternScalarsGroup,
            tnSysIpAclIpv6PatternGroup,
            tnSysIpAclIpv6FilterScalarsGroup,
            tnSysIpAclIpv6FilterGroup,
            tnSysIpAclIpv6InterfaceScalarsGroup,
            tnSysIpAclIpv6InterfaceGroup,
            tnSysIpv6AclNetIfFilterScalarsGroup,
            tnSysIpv6AclNetIfFilterGroup,
            tnSysIpAclEthIfFilterScalarsGroup,
            tnSysIpAclEthIfFilterGroup,
            tnSysIpv6AclEthIfFilterScalarsGroup,
            tnSysIpv6AclEthIfFilterGroup,
            tnSysBtInterfaceGroup,
            tnSysOtdrScanResultsTransferGroup,
            tnSysLicenseMgrGroup,
            tnLicenseEntityGroup,
            tnSysKeyStoreServiceGroup,
            tnSysKeyStoreCertInfoGroup,
            tnSysBgpPeerGroup,
            tnSysDiscoverMeGroup,
            tnSyslogServerGroup,
            tnLicenseEntitlementGroup,
            tnPctObjsGroup,
            tnHostKeyGroup,
            tnSshPrivKeyGroup,
            tnSysNESshKeyGroup,
            tnNESshKeyGroup,
            tnTransferSysLogGroup,
            tnSysHealthCareGroup,
            tnSshCiphersGroup,
            tnSshHostKeyGroup,
            tnSshMacsGroup,
            tnSshKexGroup,
            tnSshPubKeyGroup,
            tnTlsProfileGroup,
            tnSysTrapThrottlingGroup,
            tnSanListGroup,
            tnCsrSanListGroup,
            tnSanListAuthGroup,
            tnSysNmsIpListGroup,
            tnOcspProfileGroup,
            tnSysDnsServerGroup,
            tnTransferPMDiscoveryGroup,
            tnSysIpAclScalarsGroup,
            tnSysIpAclGroup,
            tnSysIpv6AclScalarsGroup,
            tnSysIpv6AclGroup,
            tnSshProfileGroup
        }
        ::= { tnSystemCompliances 1 }

END -- DEFINITION OF TROPIC-SYSTEM-MIB
