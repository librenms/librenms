TROPIC-DHP-MIB DEFINITIONS ::= BEGIN

-- (c) Copyright 2023 Nokia Networks.  All rights reserved.
-- This software is the confidential and proprietary property of
-- Nokia and may only be used in accordance with the terms of the
-- license agreement provided with this software.

IMPORTS
      MODULE-IDENTITY, OBJECT-TYPE,
      Unsigned32, Integer32                   FROM SNMPv2-SMI
      MODULE-COMPLIANCE, OBJECT-GROUP         FROM SNMPv2-CONF
      TEXTUAL-CONVENTION,
      RowStatus                               FROM SNMPv2-TC
      tnDhpMIBModules, tnDhpObjs,
      tnDhpMIB                                FROM TROPIC-GLOBAL-REG
      InterfaceIndex                          FROM IF-MIB
      TmnxEncapVal                            FROM TN-TC-MIB;

  tnDhpMibModule MODULE-IDENTITY
      LAST-UPDATED    "202302240000Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION     "Dual Home Port Protectin MIB."

      REVISION        "202302240000Z"
      DESCRIPTION     "Added the following to tnDhpGrpTable:
                       tnDhpGrpTimeToRevert."

      REVISION        "202212090000Z"
      DESCRIPTION     "Initial version"

      ::= { tnDhpMIBModules 1 }

--------------------------------------------------------------------------------
-- Top level components of this MIB
--------------------------------------------------------------------------------
    tnDhpConf           OBJECT IDENTIFIER ::= { tnDhpMIB  2 }
    tnDhpGroups         OBJECT IDENTIFIER ::= { tnDhpConf 1 }
    tnDhpCompliances    OBJECT IDENTIFIER ::= { tnDhpConf 2 }

--------------------------------------------------------------------------------
-- Port protection Scalar
--------------------------------------------------------------------------------
    tnDhpAttributeTotal OBJECT-TYPE
        SYNTAX         Integer32
        MAX-ACCESS     read-only
        STATUS         current
        DESCRIPTION    "Total number of attributes in this MIB file."
        ::= { tnDhpObjs 1 }

--------------------------------------------------------------------------------
-- TEXTUAL CONVENTIONS (i.e. types used in this MIB file
--------------------------------------------------------------------------------
    TnDhpOpState ::= TEXTUAL-CONVENTION
        STATUS         current
        DESCRIPTION    "The sync status of port protection.
                        insync - interface is fully functional.
                        outofsync - it is not operational."
        SYNTAX         INTEGER {
                         insync(1),    -- InSync
                         outofsync(2)  -- OutofSync
                       }

    TnDhpGrpPortRole ::= TEXTUAL-CONVENTION
        STATUS         current
        DESCRIPTION    "The protection role of the port in the port protection group.
                        Working - working role
                        Protection - protection role."
        SYNTAX         INTEGER {
                         working(1),    -- working
                         protection(2)  -- protection
                       }

    TnDhpGrpSwReq ::= TEXTUAL-CONVENTION
        STATUS         current
        DESCRIPTION    "The port protection switch request commands
                        0 - Clear.
                        1 - Forced Switch to Working (FS-W).
                        2 - Forced Switch to Protection (FS-P).
                        3 - Manual Switch to Working (MS-W).
                        4 - Manual Switch to Protection (MS-P)."
        SYNTAX         INTEGER {
                         clear(0),
                         fs-w(1),
                         fs-p(2),
                         ms-w(3),
                         ms-p(4)
                       }

    TnDhpGrpSwState ::= TEXTUAL-CONVENTION
        STATUS         current
        DESCRIPTION    "The port protection switch state:
                        1  - Forced Switch to Working (FS-W).
                        2  - Forced Switch to Protection (FS-P).
                        3  - Signal Failure on Protection (SF-P).
                        4  - Signal Failure on Working (SF-W).
                        5  - Manual Switch to Working (MS-W).
                        6  - Manual Switch to Protection (MS-P).
                        7  - Wait to Restore (revertive only) (WTR).
                        8  - Do not Revert (non-revertive only) (DNR).
                        9  - No Request (NR-W).
                        10 - No Request (NR-P)."
        SYNTAX         INTEGER {
                         fs-w(1),
                         fs-p(2),
                         sf-p(3),
                         sf-w(4),
                         ms-w(5),
                         ms-p(6),
                         wtr(7),
                         dnr(8),
                         nr-w(9),
                         nr-p(10)
                       }

--------------------------------------------------------------------------------
-- Port Protection Mate Channel Table
--------------------------------------------------------------------------------
    tnDhpMaChanGrpTable OBJECT-TYPE
        SYNTAX         SEQUENCE OF TnDhpMaChanGrpEntry
        MAX-ACCESS     not-accessible
        STATUS         current
        DESCRIPTION    "The Mate Channel group Table."
        ::= { tnDhpObjs 2 }

    tnDhpMaChanGrpEntry OBJECT-TYPE
        SYNTAX         TnDhpMaChanGrpEntry
        MAX-ACCESS     not-accessible
        STATUS         current
        DESCRIPTION    "The mate channel group table."
        INDEX          { tnDhpMaChanGrpId }
        ::= { tnDhpMaChanGrpTable 1 }

    TnDhpMaChanGrpEntry ::= SEQUENCE {
        tnDhpMaChanGrpId          Unsigned32,
        tnDhpMaChanGrpLocalId     Unsigned32,
        tnDhpMaChanGrpRemoteId    Unsigned32,
        tnDhpMaChanGrpState       TnDhpOpState,
        tnDhpMaChanGrpRowstatus   RowStatus
    }

    tnDhpMaChanGrpId OBJECT-TYPE
        SYNTAX         Unsigned32
        MAX-ACCESS     not-accessible
        STATUS         current
        DESCRIPTION    "The port protection mate group.  Fixed to 1."
        ::= { tnDhpMaChanGrpEntry 1 }

    tnDhpMaChanGrpLocalId OBJECT-TYPE
        SYNTAX         Unsigned32
        MAX-ACCESS     read-create
        STATUS         current
        DESCRIPTION    "The port protection local id."
        ::= { tnDhpMaChanGrpEntry 2 }

    tnDhpMaChanGrpRemoteId OBJECT-TYPE
        SYNTAX         Unsigned32
        MAX-ACCESS     read-create
        STATUS         current
        DESCRIPTION    "The port protection remote id."
        ::= { tnDhpMaChanGrpEntry 3 }

    tnDhpMaChanGrpState OBJECT-TYPE
        SYNTAX         TnDhpOpState
        MAX-ACCESS     read-only
        STATUS         current
        DESCRIPTION    "Sync Status of the port protection mate group."
        ::= { tnDhpMaChanGrpEntry 4 }

    tnDhpMaChanGrpRowstatus OBJECT-TYPE
        SYNTAX         RowStatus
        MAX-ACCESS     read-create
        STATUS         current
        DESCRIPTION    "This variable is used to create, modify, and/or delete
                        a row in this table."
        ::= { tnDhpMaChanGrpEntry 5 }

--------------------------------------------------------------------------------
-- Port Protection Mate Channel Table
--------------------------------------------------------------------------------
    tnDhpMaChanTable OBJECT-TYPE
        SYNTAX         SEQUENCE OF TnDhpMaChanEntry
        MAX-ACCESS     not-accessible
        STATUS         current
        DESCRIPTION    "The Mate Channel Table."
        ::= { tnDhpObjs 3 }

    tnDhpMaChanEntry OBJECT-TYPE
        SYNTAX         TnDhpMaChanEntry
        MAX-ACCESS     not-accessible
        STATUS         current
        DESCRIPTION    "The mate channel table."
        INDEX          { tnDhpMaChanGrpId,
                         tnDhpMaChanId }
        ::= { tnDhpMaChanTable 1 }

    TnDhpMaChanEntry ::= SEQUENCE {
        tnDhpMaChanId             Unsigned32,
        tnDhpMaChanPortId         InterfaceIndex,
        tnDhpMaChanName           SnmpAdminString,
        tnDhpMaChanVlantag        TmnxEncapVal,
        tnDhpMaChanState          TnDhpOpState,
        tnDhpMaChanRowstatus      RowStatus
    }

    tnDhpMaChanId OBJECT-TYPE
        SYNTAX         Unsigned32
        MAX-ACCESS     not-accessible
        STATUS         current
        DESCRIPTION    "Index of the channel in this mate group, currently two
                        channel is supported."
        ::= { tnDhpMaChanEntry 1 }

    tnDhpMaChanPortId OBJECT-TYPE
        SYNTAX         InterfaceIndex
        MAX-ACCESS     read-create
        STATUS         current
        DESCRIPTION    "Index of the port in this mate group."
        ::= { tnDhpMaChanEntry 2 }

    tnDhpMaChanName OBJECT-TYPE
        SYNTAX         SnmpAdminString (SIZE(1..32))
        MAX-ACCESS     read-create
        STATUS         current
        DESCRIPTION    "The description for this mate channel."
        ::= { tnDhpMaChanEntry 3 }

    tnDhpMaChanVlantag OBJECT-TYPE
        SYNTAX         TmnxEncapVal
        MAX-ACCESS     read-create
        STATUS         current
        DESCRIPTION    "The vlan tag of the port, the port shall be QinQ encap
                        and vlan tag shall be S+C tags."
        ::= { tnDhpMaChanEntry 4 }

    tnDhpMaChanState OBJECT-TYPE
        SYNTAX         TnDhpOpState
        MAX-ACCESS     read-only
        STATUS         current
        DESCRIPTION    "Operational State of the port protection channel."
        ::= { tnDhpMaChanEntry 5 }

    tnDhpMaChanRowstatus OBJECT-TYPE
        SYNTAX         RowStatus
        MAX-ACCESS     read-create
        STATUS         current
        DESCRIPTION    "This variable is used to create, modify, and/or delete
                        a row in this table."
        ::= { tnDhpMaChanEntry 6 }

--------------------------------------------------------------------------------
-- Port Protection Group Table
--------------------------------------------------------------------------------
    tnDhpGrpTable OBJECT-TYPE
        SYNTAX         SEQUENCE OF TnDhpGrpEntry
        MAX-ACCESS     not-accessible
        STATUS         current
        DESCRIPTION    "The port protection group Table."
        ::= { tnDhpObjs 5 }

    tnDhpGrpEntry OBJECT-TYPE
        SYNTAX         TnDhpGrpEntry
        MAX-ACCESS     not-accessible
        STATUS         current
        DESCRIPTION    "The port protection group table."
        INDEX          { tnDhpGrpID }
        ::= { tnDhpGrpTable 1 }

    TnDhpGrpEntry ::= SEQUENCE {
        tnDhpGrpID                Unsigned32,
        tnDhpGrpLPort             InterfaceIndex,
        tnDhpGrpLPortRole         TnDhpGrpPortRole,
        tnDhpGrpDesc              SnmpAdminString,
        tnDhpGrpRevert            TnDhpGrpRevertMode,
        tnDhpGrpWTR               Unsigned32,
        tnDhpGrpHoldoff           Unsigned32,
        tnDhpGrpSwReq             TnDhpGrpSwReq,
        tnDhpGrpSwState           TnDhpGrpSwState,
        tnDhpGrpStatus            INTEGER,
        tnDhpGrpLastStateChanged  TimeStamp,
        tnDhpGrpRowstatus         RowStatus,
        tnDhpGrpTimeToRevert      Unsigned32
    }

    tnDhpGrpID OBJECT-TYPE
        SYNTAX         Unsigned32
        MAX-ACCESS     not-accessible
        STATUS         current
        DESCRIPTION    "The port protection group ID.  The range is 1-48."
        ::= { tnDhpGrpEntry 1 }

    tnDhpGrpLPort OBJECT-TYPE
        SYNTAX         InterfaceIndex
        MAX-ACCESS     read-create
        STATUS         current
        DESCRIPTION    "The local port in this port protection group."
        ::= { tnDhpGrpEntry 2 }

    tnDhpGrpLPortRole OBJECT-TYPE
        SYNTAX         TnDhpGrpPortRole
        MAX-ACCESS     read-create
        STATUS         current
        DESCRIPTION    "The port role in this port protection group.  It can't
                        be changed after the port is added."
        ::= { tnDhpGrpEntry 3 }

    tnDhpGrpDesc OBJECT-TYPE
        SYNTAX         SnmpAdminString (SIZE(1..32))
        MAX-ACCESS     read-create
        STATUS         current
        DESCRIPTION    "The description for this local port protection group."
        ::= { tnDhpGrpEntry 4 }

    tnDhpGrpRevert OBJECT-TYPE
        SYNTAX         INTEGER {
                         revertive(1),
                         nonrevertive(2)
                       }
        MAX-ACCESS     read-create
        STATUS         current
        DESCRIPTION    "Revertive or non-revertive mode.  Default is non-revertive."
        ::= { tnDhpGrpEntry 5 }

    tnDhpGrpWTR OBJECT-TYPE
        SYNTAX         Unsigned32
        MAX-ACCESS     read-create
        STATUS         current
        DESCRIPTION    "Wait to restore timer.  Minutes: 1-15 minutes.  Default is 5 minutes."
        ::= { tnDhpGrpEntry 6 }

    tnDhpGrpHoldoff OBJECT-TYPE
        SYNTAX         Unsigned32
        MAX-ACCESS     read-create
        STATUS         current
        DESCRIPTION    "Hold off timer.  Timer: 0 - 10 s in steps of 10 ms.  Default is 0."
        ::= { tnDhpGrpEntry 7 }

    tnDhpGrpSwReq OBJECT-TYPE
        SYNTAX         TnDhpGrpSwReq
        MAX-ACCESS     read-only
        STATUS         current
        DESCRIPTION    "Switching request manual command which is executed."
        ::= { tnDhpGrpEntry 8 }

    tnDhpGrpSwState OBJECT-TYPE
        SYNTAX         TnDhpGrpSwState
        MAX-ACCESS     read-only
        STATUS         current
        DESCRIPTION    "Switching request state."
        ::= { tnDhpGrpEntry 9 }

    tnDhpGrpStatus OBJECT-TYPE
        SYNTAX         INTEGER {
                         active(1),
                         standby(2)
                       }
        MAX-ACCESS     read-only
        STATUS         current
        DESCRIPTION    "The port protection Grp status."
        ::= { tnDhpGrpEntry 10 }

    tnDhpGrpLastStateChanged OBJECT-TYPE
        SYNTAX         TimeStamp
        MAX-ACCESS     read-only
        STATUS         current
        DESCRIPTION    "The TnDhpGrpLastStateChanged variable contains the
                        value of the sysUpTime the last time the operational
                        status of the port proteection group changed state."
        ::= { tnDhpGrpEntry 11 }

    tnDhpGrpRowstatus OBJECT-TYPE
        SYNTAX         RowStatus
        MAX-ACCESS     read-create
        STATUS         current
        DESCRIPTION    "This variable is used to create, modify, and/or
                        delete a row in this table."
        ::= { tnDhpGrpEntry 12 }

    tnDhpGrpTimeToRevert OBJECT-TYPE
        SYNTAX         Unsigned32
        MAX-ACCESS     read-create
        STATUS         current
        DESCRIPTION    "The remaining time (seconds) for WTR timer to expire."
        ::= { tnDhpGrpEntry 13 }

--------------------------------------------------------------------------------
-- Port Protection Switching Command Table
--------------------------------------------------------------------------------
    tnDhpSwCmdTable OBJECT-TYPE
        SYNTAX         SEQUENCE OF TnDhpSwCmdEntry
        MAX-ACCESS     not-accessible
        STATUS         current
        DESCRIPTION    "The port protection switching command table."
        ::= { tnDhpObjs 6 }

    tnDhpSwCmdEntry OBJECT-TYPE
        SYNTAX         TnDhpSwCmdEntry
        MAX-ACCESS     not-accessible
        STATUS         current
        DESCRIPTION    "The port protection switching command table."
        INDEX          { tnDhpSwCmdId }
        ::= { tnDhpSwCmdTable 1 }

    TnDhpSwCmdEntry ::= SEQUENCE {
        tnDhpSwCmdId         Unsigned32,
        tnDhpSwCmdEntity     Unsigned32,
        tnDhpSwCmd           TnDhpGrpSwReq,
        tnDhpSwCmdRowstatus  RowStatus
    }

    tnDhpSwCmdId OBJECT-TYPE
        SYNTAX         Unsigned32
        MAX-ACCESS     not-accessible
        STATUS         current
        DESCRIPTION    "The dual home port switch command.  Only one instance is
                        supported for this table."
        ::= { tnDhpSwCmdEntry 1 }

    tnDhpSwCmdEntity OBJECT-TYPE
        SYNTAX         Unsigned32
        MAX-ACCESS     read-create
        STATUS         current
        DESCRIPTION    "The dual home port switch entity.  It could be all group
                        id if '0' is used, or it could be one of the group id from
                        1-48."
        ::= { tnDhpSwCmdEntry 2 }

    tnDhpSwCmd OBJECT-TYPE
        SYNTAX         TnDhpGrpSwReq
        MAX-ACCESS     read-create
        STATUS         current
        DESCRIPTION    "The switching command."
        ::= { tnDhpSwCmdEntry 3 }

    tnDhpSwCmdRowstatus OBJECT-TYPE
        SYNTAX         RowStatus
        MAX-ACCESS     read-create
        STATUS         current
        DESCRIPTION    "This variable is used to create, modify, and/or delete
                        a row in this table."
        ::= { tnDhpSwCmdEntry 4 }

--------------------------------------------------------------------------
-- Conformance Group Definitions
---------------------------------------------------------------------------
    tnDhpObjsGroup OBJECT-GROUP
        OBJECTS {
            tnDhpAttributeTotal
        }
        STATUS         current
        DESCRIPTION    "."
        ::= { tnDhpGroups 1 }

    tnDhpMaChanGrpGroup OBJECT-GROUP
        OBJECTS {
            tnDhpMaChanGrpLocalId,
            tnDhpMaChanGrpRemoteId,
            tnDhpMaChanGrpState,
            tnDhpMaChanGrpRowstatus
        }
        STATUS         current
        DESCRIPTION    "The port proection mate channel group."
        ::= { tnDhpGroups 2 }

    tnDhpMaChanGroup OBJECT-GROUP
        OBJECTS {
            tnDhpMaChanPortId,
            tnDhpMaChanName,
            tnDhpMaChanVlantag,
            tnDhpMaChanState,
            tnDhpMaChanRowstatus
        }
        STATUS         current
        DESCRIPTION    "The port protection mate channel."
        ::= { tnDhpGroups 3 }

    tnDhpGrpGroup OBJECT-GROUP
        OBJECTS {
            tnDhpGrpID,
            tnDhpGrpLPort,
            tnDhpGrpLPortRole,
            tnDhpGrpDesc,
            tnDhpGrpRevert,
            tnDhpGrpWTR,
            tnDhpGrpHoldoff,
            tnDhpGrpSwReq,
            tnDhpGrpSwState,
            tnDhpGrpStatus,
            tnDhpGrpLastStateChanged,
            tnDhpGrpRowstatus,
            tnDhpGrpTimeToRevert
        }
        STATUS         current
        DESCRIPTION    "The port protection group table."
        ::= { tnDhpGroups 4 }

    tnDhpSwCmdGroup OBJECT-GROUP
        OBJECTS {
            tnDhpSwCmdEntity,
            tnDhpSwCmd,
            tnDhpSwCmdRowstatus
        }
        STATUS         current
        DESCRIPTION    "The port protection switching command table."
        ::= { tnDhpGroups 5 }
---------------------------------------------------------------------------
-- Compliance Statements (mandatory)
---------------------------------------------------------------------------
    tnDhpCompliance MODULE-COMPLIANCE
        STATUS         current
        DESCRIPTION    "The compliance statement for SNMPv2 entities which
                        implement Port Protection."
        MODULE
        MANDATORY-GROUPS {
            tnDhpObjsGroup,
            tnDhpMaChanGrpGroup,
            tnDhpMaChanGroup,
            tnDhpGrpGroup,
            tnDhpSwCmdGroup
        }
        ::= { tnDhpCompliances 1 }

END -- DEFINITION OF TROPIC-DHP-MIB
