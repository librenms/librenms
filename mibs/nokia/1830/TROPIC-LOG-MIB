TROPIC-LOG-MIB DEFINITIONS ::= BEGIN

-- (c) Copyright 2023 Nokia Networks.  All rights reserved.
-- This software is the confidential and proprietary property of
-- Nokia and may only be used in accordance with the terms of the
-- license agreement provided with this software.

IMPORTS
      SnmpAdminString                         FROM SNMP-FRAMEWORK-MIB
      OBJECT-TYPE,MODULE-IDENTITY,
      IpAddress,
      Unsigned32, Integer32,OBJECT-IDENTITY   FROM SNMPv2-SMI
      TEXTUAL-CONVENTION,
      TruthValue, RowStatus                   FROM SNMPv2-TC
      OBJECT-GROUP,MODULE-COMPLIANCE          FROM SNMPv2-CONF
      dot1agCfmMdIndex,
      dot1agCfmMaIndex,
      dot1agCfmMepIdentifier                  FROM IEEE8021-CFM-MIB
      tnEthRingIndex                          FROM TN-ETH-RING-MIB
      tnOamSaaCtlTestIndex                    FROM TN-OAM-TEST-MIB
      tnRmdCfmMepNumber                       FROM TN-RMD-CFM-MIB
      tnRmdIfIndex,
      tnRmdIfMauIndex,
      TnRmdNimDirection                       FROM TN-RMD-IF-MIB
      tnRmdSystemId                           FROM TN-RMD-SYSTEM-MIB
      tnRmdTsopIwfChannelNumber               FROM TN-RMD-TSOP-MIB
      tnSapPortId,
      tnSapEncapValue                         FROM TN-SAP-MIB
      tnSvcId                                 FROM TN-SERV-MIB
      tnSysSwitchId                           FROM TROPIC-SYSTEM-MIB
      TnTrapCategory,
      TnEntityType,
      TnCondition,
      AluWdmAsapType                          FROM TROPIC-TC
      tnSystemModules, tnLogMIB               FROM TROPIC-GLOBAL-REG
      vRtrMplsLspIndex                        FROM TN-MPLS-MIB
      vRtrID, vRtrIfIndex                     FROM TN-VRTR-MIB
      sdpBindId                               FROM TN-SDP-MIB
      vRtrMplsTpLspPathIndex                  FROM TN-MPLS-TP-MIB;

  tnLogMIBModule MODULE-IDENTITY
      LAST-UPDATED    "202203251200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION "."

      REVISION    "202203251200Z"
      DESCRIPTION "Updated DESCRIPTION of the following:
                   tnAsapTypeIndex."

      REVISION    "202104161200Z"
      DESCRIPTION "1) Added the following to tnCriticalAlarmLogBufferTable:
                      tnCriticalAlarmLogSlotProgrammedGenericType.
                   2) Added the following to tnMajorAlarmLogBufferTable:
                      tnMajorAlarmLogSlotProgrammedGenericType.
                   3) Added the following to tnMinorAlarmLogBufferTable:
                      tnMinorAlarmLogSlotProgrammedGenericType.
                   4) Added the following to tnStateChangeLogBufferTable:
                      tnStateChangeLogSlotProgrammedGenericType.
                   5) Added the following to tnGeneralEventLogBufferTable:
                      tnGeneralEventLogSlotProgrammedGenericType.
                   6) Added the following to tnLogBufferTable:
                      tnLogSlotProgrammedGenericType.
                   7) Added the following to tnActiveAlarmTable:
                      tnActiveAlarmSlotProgrammedGenericType.
                   8) Added the following to tnNotAlarmedLogBufferTable:
                      tnNotAlarmedLogSlotProgrammedGenericType.
                   9) Added the following to tnWarningAlarmLogBufferTable:
                      tnWarningAlarmLogSlotProgrammedGenericType."

      REVISION    "202001171200Z"
      DESCRIPTION "Added the following table:
                   tnActiveAlarmInfoTable."

      REVISION    "201903011200Z"
      DESCRIPTION "Updated description of the following:
                   tnLagAlarmCategoryObjectId."

      REVISION    "201811261200Z"
      DESCRIPTION "Marked the following as obsolete:
                   tnAsapMgmtDetailTable."

      REVISION    "201807201200Z"
      DESCRIPTION "Added the following table:
                   tnPerPacketSwitchObjectAlarmCategoryConfigTable."

      REVISION    "201803091200Z"
      DESCRIPTION "Added the following table:
                   tnPerWanifObjectAlarmCategoryConfigTable."

      REVISION    "201802231200Z"
      DESCRIPTION "Updated the contact info."

      REVISION    "201707071200Z"
      DESCRIPTION "Fixed MIB compile issues."

      REVISION    "201705241200Z"
      DESCRIPTION "1) Added the following to tnCriticalAlarmLogBufferTable:
                      tnCriticalAlarmLogObjectIDIpV6.
                   2) Added the following to tnMajorAlarmLogBufferTable:
                      tnMajorAlarmLogObjectIDIpV6.
                   3) Added the following to tnMinorAlarmLogBufferTable:
                      tnMinorAlarmLogObjectIDIpV6.
                   4) Added the following to tnStateChangeLogBufferTable:
                      tnStateChangeLogObjectIDIpV6.
                   5) Added the following to tnUserActionLogBufferTable:
                      tnUserActionLogObjectIDIpV6.
                   6) Added the following to tnGeneralEventLogBufferTable:
                      tnGeneralEventLogObjectIDIpV6.
                   7) Added the following to tnLogBufferTable:
                      tnLogObjectIDIpV6.
                   8) Added the following to tnPersistentLogBufferTable:
                      tnPersistentLogObjectIDIpV6.
                   9) Added the following to tnNotAlarmedLogBufferTable:
                      tnNotAlarmedLogObjectIDIpV6.
                   10) Added the following to tnSecurityLogBufferTable:
                       tnSecurityLogObjectIDIpV6.
                   11) Added the following to tnWarningAlarmLogBufferTable:
                       tnWarningAlarmLogObjectIDIpV6."

      REVISION    "201704261200Z"
      DESCRIPTION "Added the following table:
                   tnAsapMgmtDetailsTable."

      REVISION    "201611161200Z"
      DESCRIPTION "Updated the contact info."

      REVISION    "201609301200Z"
      DESCRIPTION "Added the default value to tnAsapType."

      REVISION    "201510261200Z"
      DESCRIPTION "Added the following table:
                   tnPerMplsLspPathObjectAlarmCategoryConfigTable."

      REVISION    "201508131200Z"
      DESCRIPTION "Added the following table:
                   tnPerMplsIfObjectAlarmCategoryConfigTable."

      REVISION    "201508051200Z"
      DESCRIPTION "Added the following tables:
                   tnPerMplsLspObjectAlarmCategoryConfigTable
                   tnPerSdpBindObjectAlarmCategoryConfigTable."

      REVISION    "201505251200Z"
      DESCRIPTION "Added the following MIB to tnAsapMgmtTable:
                   tnAsapRowStatus."

      REVISION    "201505151200Z"
      DESCRIPTION "Added the following ASAP Tables:
                   tnAsapMgmtTable
                   tnAsapMgmtDetailTable."

      REVISION    "201502131200Z"
      DESCRIPTION "Added the following PowerMgr log:
                   tnPowerMgmtMultiNodeIngressMonitorExchangeStartLog
                   tnPowerMgmtMultiNodeIngressMonitorExchangeEndLog
                   tnPowerMgmtMultiNodeEgressAutoAdjustTriggeredLog."

      REVISION    "201402281200Z"
      DESCRIPTION "1) Added the following to tnCriticalAlarmLogBufferTable:
                      tnCriticalAlarmLogEntityType
                      tnCriticalAlarmLogCondition.
                   2) Added the following to tnMajorAlarmLogBufferTable:
                      tnMajorAlarmLogEntityType
                      tnMajorAlarmLogCondition.
                   3) Added the following to tnMinorAlarmLogBufferTable:
                      tnMinorAlarmLogEntityType
                      tnMinorAlarmLogCondition.
                   4) Added the following to tnNotAlarmedLogBufferTable:
                      tnNotAlarmedLogEntityType
                      tnNotAlarmedLogCondition.
                   5) Added the following to tnWarningAlarmLogBufferTable:
                      tnWarningAlarmLogEntityType
                      tnWarningAlarmLogCondition."

      REVISION    "201402271200Z"
      DESCRIPTION "1) Added tnPowerMgmtExpressThruPathLossTooHighLog.
                   2) Added the following to tnLogBufferTable:
                      tnLogEntityType
                      tnLogCondition."

      REVISION    "201310141200Z"
      DESCRIPTION "Added the following table:
                   tnPerRmdNimObjectAlarmCategoryConfigTable."

      REVISION    "201309251200Z"
      DESCRIPTION "1) Restored the following table:
                      tnPerTcmObjectAlarmCategoryConfigTable.
                   2) Added the following table:
                      tnPerOthObjectAlarmCategoryConfigTable.
                   3) Marked the following table as deprecated:
                      tnPerOtnObjectAlarmCategoryConfigTable."

      REVISION    "201309161200Z"
      DESCRIPTION "Added the following table:
                   tnPerRmdCesChannelObjectAlarmCategoryConfigTable."

      REVISION    "201308021200Z"
      DESCRIPTION "Added the following tables:
                   tnPerSrSvcObjectAlarmCategoryConfigTable
                   tnPerSrSapObjectAlarmCategoryConfigTable
                   tnPerSrErpObjectAlarmCategoryConfigTable
                   tnPerSrMepObjectAlarmCategoryConfigTable
                   tnPerSrOamTestObjectAlarmCategoryConfigTable
                   tnPerRmdObjectAlarmCategoryConfigTable
                   tnPerRmdMepObjectAlarmCategoryConfigTable
                   tnPerRmdIfObjectAlarmCategoryConfigTable
                   tnPerRmdIfMauObjectAlarmCategoryConfigTable."

      REVISION    "201304191200Z"
      DESCRIPTION "Added the following to tnSecurityLogUserPrivilege:
                   crypto(6)."

      REVISION    "201304161200Z"
      DESCRIPTION "Marked the following as obsolete:
                   tnPerLogicObjectAlarmCategoryConfigTable."

      REVISION    "201301071200Z"
      DESCRIPTION "Updated DESCRIPTION of the following:
                   tnOtnAlarmCategoryObjectId
                   tnOtnAlarmCategoryTribObjectId."

      REVISION    "201212051200Z"
      DESCRIPTION "Added the following line to DESCRIPTION of
                   tnSyncAlarmCategoryObjectId:
                   shelf/slot/100/direction which means syncOut objectId."

      REVISION    "201211061200Z"
      DESCRIPTION "Added the following table:
                   tnPerOtnObjectAlarmCategoryConfigTable."

      REVISION    "201205251200Z"
      DESCRIPTION "Marked the following as obsolete:
                   tnPerTcmObjectAlarmCategoryConfigAttributeTotal
                   tnPerTcmObjectAlarmCategoryConfigTable."

      REVISION    "201205091200Z"
      DESCRIPTION "Added the following table:
                   tnPerLagObjectAlarmCategoryConfigTable."

      REVISION    "201204091200Z"
      DESCRIPTION "Added the following table:
                   tnPerPtpObjectAlarmCategoryConfigTable."

      REVISION    "201105021200Z"
      DESCRIPTION "1) Added tnPerTcmObjectAlarmCategoryConfigTable.
                   2) Added the following scalar MIB nodes to improve performance:
                      tnPerVtsObjectAlarmCategoryConfigAttributeTotal
                      tnPerCcmObjectAlarmCategoryConfigAttributeTotal
                      tnPerTcmObjectAlarmCategoryConfigAttributeTotal."

      REVISION    "201104081200Z"
      DESCRIPTION "Added tnPerCcmObjectAlarmCategoryConfigTable."

      REVISION    "201102251200Z"
      DESCRIPTION "1) Defined AluWdmAlarmCategoryDirection.
                   2) Added tnPerVtsObjectAlarmCategoryConfigTable."

      REVISION    "201101211200Z"
      DESCRIPTION "Added tnPerSyncObjectAlarmCategoryConfigTable."

      REVISION    "201012061200Z"
      DESCRIPTION "Added tnPerLogicObjectAlarmCategoryConfigTable."

      REVISION    "201010041200Z"
      DESCRIPTION "Added the following:
                   tnAlarmEventCategoryChangeEventidLog
                   tnProgrammedPortTypeChangeLog
                   tnPtchgOkLog
                   tnPtchgUnknownPortTypeLog
                   tnPtchgNoSlotCorrLog
                   tnPtchgNotAllowedLog
                   tnPtchgNoPortCorrLog."

      REVISION    "201008091200Z"
      DESCRIPTION "Added tnPowerMgmtTiltAdjustRequestClearedLog."

      REVISION    "201007291200Z"
      DESCRIPTION "Added:
                   tnPowerMgmtTiltAdjustStartedLog
                   tnPowerMgmtTiltAdjustCompleteLog
                   tnPowerMgmtTiltAdjustRequestLog."

      REVISION    "201006161200Z"
      DESCRIPTION "Added tnPowerMgmtVectoredAddDropFailureLog."

      REVISION    "201004161200Z"
      DESCRIPTION "1) Added warningAlarms(12) to MIB descriptions.
                   2) Added the following MIB attributes:
                      tnWarningAlarmLogTotal
                      tnActiveWarningAlarmTotal.
                   3) Added tnWarningAlarmLogBufferTable with the following
                      MIB attributes:
                      tnWarningAlarmLogSerialNumber
                      tnWarningAlarmLogType
                      tnWarningAlarmLogTime
                      tnWarningAlarmLogObjectIDType
                      tnWarningAlarmLogObjectID
                      tnWarningAlarmLogDescr
                      tnWarningAlarmLogData
                      tnWarningAlarmLogServiceAffecting
                      tnWarningAlarmLogSlotProgrammedType."

      REVISION    "200907171200Z"
      DESCRIPTION "Added attributes for security logs."

      ::= { tnSystemModules 3 }

  tnLogConf                   OBJECT IDENTIFIER ::= { tnLogMIB  1 }
  tnLogGroups                 OBJECT IDENTIFIER ::= { tnLogConf 1 }
  tnLogCompliances            OBJECT IDENTIFIER ::= { tnLogConf 2 }
  tnLogObjs                   OBJECT IDENTIFIER ::= { tnLogMIB  2 }
  tnLogs                      OBJECT IDENTIFIER ::= { tnLogObjs 1 }
  tnLogBasics                 OBJECT IDENTIFIER ::= { tnLogObjs 2 }
  tnLogQueues                 OBJECT IDENTIFIER ::= { tnLogObjs 3 }
  tnLogAlarmCategoryConfig    OBJECT IDENTIFIER ::= { tnLogObjs 4 }
  tnAsapManagement            OBJECT IDENTIFIER ::= { tnLogObjs 5 }

--------------------------------------------------------------------------------
-- Type Definitions
--------------------------------------------------------------------------------
    AluWdmAlarmCategoryDirection ::= TEXTUAL-CONVENTION
        STATUS         current
        DESCRIPTION    "The direction to which the new category will be
                        applied."
        SYNTAX         INTEGER {
                         none(1),
                         tx(2),
                         rx(3)
                       }

-------------------------------------------------------------------
-- Object Definitions
-------------------------------------------------------------------

-------------------------------------------------------------------
-- System Logs
-------------------------------------------------------------------
    tnSystemLogs OBJECT IDENTIFIER ::= { tnLogs 1 }

    tnUserActionLog OBJECT-IDENTITY
        STATUS         current
        DESCRIPTION    "An event generated by a user action from the CLI,
                        Web or NMS."
        ::= { tnSystemLogs 1 }

    tnApplicationProcessStartFailureLog OBJECT-IDENTITY
        STATUS         current
        DESCRIPTION    "."
        ::= { tnSystemLogs 2 }

    tnDiscardedEventsLog OBJECT-IDENTITY
        STATUS         current
        DESCRIPTION    "."
        ::= { tnSystemLogs 3 }

    tnExceededSystemLimitLog OBJECT-IDENTITY
        STATUS         current
        DESCRIPTION    "."
        ::= { tnSystemLogs 4 }

    tnInvalidDatabaseRecordLog OBJECT-IDENTITY
        STATUS         current
        DESCRIPTION    "."
        ::= { tnSystemLogs 5 }

    tnAlarmEventCategoryChangeEventidLog OBJECT-IDENTITY
        STATUS         current
        DESCRIPTION    "."
        ::= { tnSystemLogs 6 }

    tnProgrammedPortTypeChangeLog OBJECT-IDENTITY
        STATUS         current
        DESCRIPTION    "."
        ::= { tnSystemLogs 7 }

    tnPtchgOkLog OBJECT-IDENTITY
        STATUS         current
        DESCRIPTION    "."
        ::= { tnSystemLogs 8 }

    tnPtchgUnknownPortTypeLog OBJECT-IDENTITY
        STATUS         current
        DESCRIPTION    "."
        ::= { tnSystemLogs 9 }

    tnPtchgNoSlotCorrLog OBJECT-IDENTITY
        STATUS         current
        DESCRIPTION    "."
        ::= { tnSystemLogs 10 }

    tnPtchgNotAllowedLog OBJECT-IDENTITY
        STATUS         current
        DESCRIPTION    "."
        ::= { tnSystemLogs 11 }

    tnPtchgNoPortCorrLog OBJECT-IDENTITY
        STATUS         current
        DESCRIPTION    "."
        ::= { tnSystemLogs 12 }

-------------------------------------------------------------------
-- Database Logs
-------------------------------------------------------------------
    tnDatabaseLogs OBJECT IDENTIFIER ::= { tnLogs 2 }

    tnDatabaseConvertLog OBJECT-IDENTITY
        STATUS         current
        DESCRIPTION    "."
        ::= { tnDatabaseLogs 1 }

    tnDatabaseRestoreLog OBJECT-IDENTITY
        STATUS         current
        DESCRIPTION    "."
        ::= { tnDatabaseLogs 2 }

--    obsolete
--    tnDatabaseCannotConvertRecordTypeLog OBJECT-IDENTITY ::= { tnDatabaseLogs 3 }
--    tnDatabaseBadFileHeaderLog OBJECT-IDENTITY ::= { tnDatabaseLogs 4 }
--    tnDatabaseReadErrorLog OBJECT-IDENTITY ::= { tnDatabaseLogs 5 }

    tnDatabaseClearPersistentRepositoryLog OBJECT-IDENTITY
        STATUS         current
        DESCRIPTION    "."
        ::= { tnDatabaseLogs 6 }

    tnDatabaseBackupFailedLog OBJECT-IDENTITY
        STATUS         current
        DESCRIPTION    "."
        ::= { tnDatabaseLogs 7 }

    tnDatabaseRestoreFailedLog OBJECT-IDENTITY
        STATUS         current
        DESCRIPTION    "."
        ::= { tnDatabaseLogs 8 }

--    obsolete
--    tnDatabaseDiskFailureLog OBJECT-IDENTITY ::= { tnDatabaseLogs 9 }

-------------------------------------------------------------------
-- Diagnostics Logs
-------------------------------------------------------------------
    tnDiagnosticsLogs OBJECT IDENTIFIER ::= { tnLogs 3 }

-------------------------------------------------------------------
-- Equipment Logs
-------------------------------------------------------------------
    tnEquipmentLogs OBJECT IDENTIFIER ::= { tnLogs 4 }

    tnSlotMonitorCardPulledLog OBJECT-IDENTITY
        STATUS         current
        DESCRIPTION    "."
        ::= { tnEquipmentLogs 1 }

    tnSlotMonitorCardInsertedLog OBJECT-IDENTITY
        STATUS         current
        DESCRIPTION    "."
        ::= { tnEquipmentLogs 2 }

    tnI2CReadErrorLog OBJECT-IDENTITY
        STATUS         current
        DESCRIPTION    "."
        ::= { tnEquipmentLogs 3 }

    tnI2CWriteErrorLog OBJECT-IDENTITY
        STATUS         current
        DESCRIPTION    "."
        ::= { tnEquipmentLogs 4 }

    tnSandiskATAReadErrorLog OBJECT-IDENTITY
        STATUS         current
        DESCRIPTION    "."
        ::= { tnEquipmentLogs 5 }

    tnSandiskATAWriteErrorLog OBJECT-IDENTITY
        STATUS         current
        DESCRIPTION    "."
        ::= { tnEquipmentLogs 6 }

    tnAutoTopologyConfigFailedLog OBJECT-IDENTITY
        STATUS         current
        DESCRIPTION    "."
        ::= { tnEquipmentLogs 7 }

    tnAutoTopologyConfigFailedROADMCardMissingLog OBJECT-IDENTITY
        STATUS         current
        DESCRIPTION    "."
        ::= { tnEquipmentLogs 8 }

    tnAutoTopologyConfigFailedMateCADCardMissingLog OBJECT-IDENTITY
        STATUS         current
        DESCRIPTION    "."
        ::= { tnEquipmentLogs 9 }

    tnAutoTopologyConfigFailedPortAlreadyConnectedLog OBJECT-IDENTITY
        STATUS         current
        DESCRIPTION    "."
        ::= { tnEquipmentLogs 10 }

    tnAutoTopologyConfigFailedFarEndPortAlreadyConnectedLog OBJECT-IDENTITY
        STATUS         current
        DESCRIPTION    "."
        ::= { tnEquipmentLogs 11 }

-------------------------------------------------------------------
-- Software Downloading Logs
-------------------------------------------------------------------
    tnSoftwareDownloadingLogs OBJECT IDENTIFIER ::= { tnLogs 5 }

    tnSwdlResultLog OBJECT-IDENTITY
        STATUS         current
        DESCRIPTION    "."
        ::= { tnSoftwareDownloadingLogs 1 }

    tnSwdlTransferStartedLog OBJECT-IDENTITY
        STATUS         current
        DESCRIPTION    "."
        ::= { tnSoftwareDownloadingLogs 2 }

    tnSwdlTransferCompleteLog OBJECT-IDENTITY
        STATUS         current
        DESCRIPTION    "."
        ::= { tnSoftwareDownloadingLogs 3 }

    tnSwdlSwitchBankLog OBJECT-IDENTITY
        STATUS         current
        DESCRIPTION    "."
        ::= { tnSoftwareDownloadingLogs 4 }

    tnSwdlSwitchActivityLog OBJECT-IDENTITY
        STATUS         current
        DESCRIPTION    "."
        ::= { tnSoftwareDownloadingLogs 5 }

    tnSwdlDatabaseBackupLog OBJECT-IDENTITY
        STATUS         current
        DESCRIPTION    "."
        ::= { tnSoftwareDownloadingLogs 6 }

    tnSwdlDatabaseRestoreLog OBJECT-IDENTITY
        STATUS         current
        DESCRIPTION    "."
        ::= { tnSoftwareDownloadingLogs 7 }

    tnSwdlResetCardLog OBJECT-IDENTITY
        STATUS         current
        DESCRIPTION    "."
        ::= { tnSoftwareDownloadingLogs 8 }

    tnSwdlDatabaseClearLog OBJECT-IDENTITY
        STATUS         current
        DESCRIPTION    "."
        ::= { tnSoftwareDownloadingLogs 9 }

-------------------------------------------------------------------
-- L1 APS Logs
-------------------------------------------------------------------
    tnL1APSLogs OBJECT IDENTIFIER ::= { tnLogs 6 }

    tnProtectionSwitchToWorkingChannelLog OBJECT-IDENTITY
        STATUS         current
        DESCRIPTION    "."
        ::= { tnL1APSLogs 1 }

    tnProtectionSwitchToProtectionChannelLog OBJECT-IDENTITY
        STATUS         current
        DESCRIPTION    "."
        ::= { tnL1APSLogs 2 }

    tnProtectionSwitchFailedLog OBJECT-IDENTITY
        STATUS         current
        DESCRIPTION    "."
        ::= { tnL1APSLogs 3 }

-------------------------------------------------------------------
-- OSPF Logs
-------------------------------------------------------------------
    tnOspfLogs OBJECT IDENTIFIER ::= { tnLogs 7 }

    tnOspfLsdbOverflowLog OBJECT-IDENTITY
        STATUS         current
        DESCRIPTION    "."
        ::= { tnOspfLogs 1 }

-------------------------------------------------------------------
-- OCH Cross Connect Logs
-------------------------------------------------------------------
    tnOchXcLogs OBJECT IDENTIFIER ::= { tnLogs 8 }

    tnExceededSystemLimitForConnectionsLog OBJECT-IDENTITY
        STATUS         current
        DESCRIPTION    "."
        ::= { tnOchXcLogs 1 }

    tnChangedWaveKeysOfConnectionLog OBJECT-IDENTITY
        STATUS         current
        DESCRIPTION    "."
        ::= { tnOchXcLogs 2 }

-------------------------------------------------------------------
-- Power Management Logs
-------------------------------------------------------------------
    tnPowerMgmtLogs OBJECT IDENTIFIER ::= { tnLogs 9 }

    tnPowerMgmtAdjustStartedLog OBJECT-IDENTITY
        STATUS         current
        DESCRIPTION    "."
        ::= { tnPowerMgmtLogs 1 }

    tnPowerMgmtAdjustCompletedLog OBJECT-IDENTITY
        STATUS         current
        DESCRIPTION    "."
        ::= { tnPowerMgmtLogs 2 }

    tnPowerControlReinitializedLog OBJECT-IDENTITY
        STATUS         current
        DESCRIPTION    "."
        ::= { tnPowerMgmtLogs 3 }

    tnPowerMgmtAutoAdjustRequestedLog OBJECT-IDENTITY
        STATUS         current
        DESCRIPTION    "."
        ::= { tnPowerMgmtLogs 4 }

    tnPowerMgmtCommissioningRequiredLog OBJECT-IDENTITY
        STATUS         current
        DESCRIPTION    "."
        ::= { tnPowerMgmtLogs 5 }

    tnPowerMgmtVectoredAddDropFailureLog OBJECT-IDENTITY
        STATUS         current
        DESCRIPTION    "."
        ::= { tnPowerMgmtLogs 6 }

    tnPowerMgmtTiltAdjustStartedLog OBJECT-IDENTITY
        STATUS         current
        DESCRIPTION    "."
        ::= { tnPowerMgmtLogs 7 }

    tnPowerMgmtTiltAdjustCompleteLog OBJECT-IDENTITY
        STATUS         current
        DESCRIPTION    "."
        ::= { tnPowerMgmtLogs 8 }

    tnPowerMgmtTiltAdjustRequestLog OBJECT-IDENTITY
        STATUS         current
        DESCRIPTION    "."
        ::= { tnPowerMgmtLogs 9 }

    tnPowerMgmtTiltAdjustRequestClearedLog OBJECT-IDENTITY
        STATUS         current
        DESCRIPTION    "."
        ::= { tnPowerMgmtLogs 10 }

    tnPowerMgmtExpressThruPathLossTooHighLog OBJECT-IDENTITY
        STATUS         current
        DESCRIPTION    "."
        ::= { tnPowerMgmtLogs 11 }

    tnPowerMgmtMultiNodeIngressMonitorExchangeStartLog OBJECT-IDENTITY
        STATUS         current
        DESCRIPTION    "."
        ::= { tnPowerMgmtLogs 12 }

    tnPowerMgmtMultiNodeIngressMonitorExchangeEndLog OBJECT-IDENTITY
        STATUS         current
        DESCRIPTION    "."
        ::= { tnPowerMgmtLogs 13 }

    tnPowerMgmtMultiNodeEgressAutoAdjustTriggeredLog OBJECT-IDENTITY
        STATUS         current
        DESCRIPTION    "."
        ::= { tnPowerMgmtLogs 14 }

-------------------------------------------------------------------
-- Log Basics
-------------------------------------------------------------------
    tnCriticalAlarmLogTotal OBJECT-TYPE
        SYNTAX         Unsigned32
        MAX-ACCESS     read-only
        STATUS         current
        DESCRIPTION    "."
        ::= { tnLogBasics 1 }

    tnMajorAlarmLogTotal OBJECT-TYPE
        SYNTAX         Unsigned32
        MAX-ACCESS     read-only
        STATUS         current
        DESCRIPTION    "."
        ::= { tnLogBasics 2 }

    tnMinorAlarmLogTotal OBJECT-TYPE
        SYNTAX         Unsigned32
        MAX-ACCESS     read-only
        STATUS         current
        DESCRIPTION    "."
        ::= { tnLogBasics 3 }

    tnStateChangeLogTotal OBJECT-TYPE
        SYNTAX         Unsigned32
        MAX-ACCESS     read-only
        STATUS         current
        DESCRIPTION    "."
        ::= { tnLogBasics 4 }

    tnUserActionLogTotal OBJECT-TYPE
        SYNTAX         Unsigned32
        MAX-ACCESS     read-only
        STATUS         current
        DESCRIPTION    "."
        ::= { tnLogBasics 5 }

    tnGeneralEventLogTotal OBJECT-TYPE
        SYNTAX         Unsigned32
        MAX-ACCESS     read-only
        STATUS         current
        DESCRIPTION    "."
        ::= { tnLogBasics 6 }

    tnLogTotal OBJECT-TYPE
        SYNTAX         Unsigned32
        MAX-ACCESS     read-only
        STATUS         current
        DESCRIPTION    "."
        ::= { tnLogBasics 7 }

    tnActiveAlarmTotal OBJECT-TYPE
        SYNTAX         Unsigned32
        MAX-ACCESS     read-only
        STATUS         current
        DESCRIPTION    "."
        ::= { tnLogBasics 8 }

    tnPersistentLogTotal OBJECT-TYPE
        SYNTAX         Unsigned32
        MAX-ACCESS     read-only
        STATUS         current
        DESCRIPTION    "."
        ::= { tnLogBasics 9 }

    tnActiveCriticalAlarmTotal OBJECT-TYPE
        SYNTAX         Unsigned32
        MAX-ACCESS     read-only
        STATUS         current
        DESCRIPTION    "."
        ::= { tnLogBasics 10 }

    tnActiveMajorAlarmTotal OBJECT-TYPE
        SYNTAX         Unsigned32
        MAX-ACCESS     read-only
        STATUS         current
        DESCRIPTION    "."
        ::= { tnLogBasics 11 }

    tnActiveMinorAlarmTotal OBJECT-TYPE
        SYNTAX         Unsigned32
        MAX-ACCESS     read-only
        STATUS         current
        DESCRIPTION    "."
        ::= { tnLogBasics 12 }

    tnActiveOrMaskedAlarmTotal OBJECT-TYPE
        SYNTAX         Unsigned32
        MAX-ACCESS     read-only
        STATUS         current
        DESCRIPTION    "."
        ::= { tnLogBasics 13 }

    tnNotAlarmedLogTotal OBJECT-TYPE
        SYNTAX         Unsigned32
        MAX-ACCESS     read-only
        STATUS         current
        DESCRIPTION    "."
        ::= { tnLogBasics 14 }

    tnSecurityLogTotal OBJECT-TYPE
        SYNTAX         Unsigned32
        MAX-ACCESS     read-only
        STATUS         current
        DESCRIPTION    "."
        ::= { tnLogBasics 15 }

    tnWarningAlarmLogTotal OBJECT-TYPE
        SYNTAX         Unsigned32
        MAX-ACCESS     read-only
        STATUS         current
        DESCRIPTION    "."
        ::= { tnLogBasics 16 }

    tnActiveWarningAlarmTotal OBJECT-TYPE
        SYNTAX         Unsigned32
        MAX-ACCESS     read-only
        STATUS         current
        DESCRIPTION    "."
        ::= { tnLogBasics 17 }

-------------------------------------------------------------------
-- Critical Alarm Log Buffer Table
-------------------------------------------------------------------
    tnCriticalAlarmLogBufferTable OBJECT-TYPE
        SYNTAX         SEQUENCE OF TnCriticalAlarmLogBufferEntry
        MAX-ACCESS     not-accessible
        STATUS         current
        DESCRIPTION    "The critical alarm log history table."
        ::= { tnLogQueues 1 }

    tnCriticalAlarmLogBufferEntry OBJECT-TYPE
        SYNTAX         TnCriticalAlarmLogBufferEntry
        MAX-ACCESS     not-accessible
        STATUS         current
        DESCRIPTION    "."
        INDEX { tnCriticalAlarmLogSerialNumber }
        ::= { tnCriticalAlarmLogBufferTable 1 }

    TnCriticalAlarmLogBufferEntry ::=
        SEQUENCE {
            tnCriticalAlarmLogSerialNumber                Unsigned32,
            tnCriticalAlarmLogType                        OBJECT IDENTIFIER,
            tnCriticalAlarmLogTime                        Unsigned32,
            tnCriticalAlarmLogObjectIDType                Unsigned32,
            tnCriticalAlarmLogObjectID                    Unsigned32,
            tnCriticalAlarmLogDescr                       SnmpAdminString,
            tnCriticalAlarmLogData                        SnmpAdminString,
            tnCriticalAlarmLogServiceAffecting            TruthValue,
            tnCriticalAlarmLogSlotProgrammedType          OBJECT IDENTIFIER,
            tnCriticalAlarmLogEntityType                  TnEntityType,
            tnCriticalAlarmLogCondition                   TnCondition,
            tnCriticalAlarmLogObjectIDIpV6                InetAddress,
            tnCriticalAlarmLogSlotProgrammedGenericType   SnmpAdminString
        }

    tnCriticalAlarmLogSerialNumber OBJECT-TYPE
        SYNTAX         Unsigned32 (1..2147483647)
        MAX-ACCESS     not-accessible
        STATUS         current
        DESCRIPTION    "The independently incremented number associated
                        with the sequential ordering of incoming critical
                        alarms."
        ::= { tnCriticalAlarmLogBufferEntry 1 }

    tnCriticalAlarmLogType OBJECT-TYPE
        SYNTAX         OBJECT IDENTIFIER
        MAX-ACCESS     read-only
        STATUS         current
        DESCRIPTION    "The OID of the critical alarm event ID."
        ::= { tnCriticalAlarmLogBufferEntry 2 }

    tnCriticalAlarmLogTime OBJECT-TYPE
        SYNTAX         Unsigned32
        MAX-ACCESS     read-only
        STATUS         current
        DESCRIPTION    "The time at which the critical alarm occurred,
                        measured in total time ticks (seconds) from the
                        year 1970."
        ::= { tnCriticalAlarmLogBufferEntry 3 }

    tnCriticalAlarmLogObjectIDType OBJECT-TYPE
        SYNTAX         Unsigned32
        MAX-ACCESS     read-only
        STATUS         current
        DESCRIPTION    "The type of Object ID associated with the critical
                        alarm."
        ::= { tnCriticalAlarmLogBufferEntry 4 }

    tnCriticalAlarmLogObjectID OBJECT-TYPE
        SYNTAX         Unsigned32
        MAX-ACCESS     read-only
        STATUS         current
        DESCRIPTION    "The physical interface or service associated with
                        the critical alarm."
        ::= { tnCriticalAlarmLogBufferEntry 5 }

    tnCriticalAlarmLogDescr OBJECT-TYPE
        SYNTAX         SnmpAdminString (SIZE(0..255))
        MAX-ACCESS     read-only
        STATUS         current
        DESCRIPTION    "A detailed description of the critical alarm."
        ::= { tnCriticalAlarmLogBufferEntry 6 }

    tnCriticalAlarmLogData OBJECT-TYPE
        SYNTAX         SnmpAdminString (SIZE(0..255))
        MAX-ACCESS     read-only
        STATUS         current
        DESCRIPTION    "Any application specific data relevant to the
                        critical alarm.  This could be the value of a
                        changed attribute or any other formatted
                        information related to a notification."
        ::= { tnCriticalAlarmLogBufferEntry 7 }

    tnCriticalAlarmLogServiceAffecting OBJECT-TYPE
        SYNTAX         TruthValue
        MAX-ACCESS     read-only
        STATUS         current
        DESCRIPTION    "An indication as to whether or not this critical
                        alarm is service affecting."
        ::= { tnCriticalAlarmLogBufferEntry 8 }

    tnCriticalAlarmLogSlotProgrammedType OBJECT-TYPE
        SYNTAX         OBJECT IDENTIFIER
        MAX-ACCESS     read-only
        STATUS         current
        DESCRIPTION    "Type of card provisioned in the given slot.  If
                        tnCriticalAlarmLogObjectID does not include a
                        slot, a value of 0.0 will be returned."
        ::= { tnCriticalAlarmLogBufferEntry 9 }

    tnCriticalAlarmLogEntityType OBJECT-TYPE
        SYNTAX         TnEntityType
        MAX-ACCESS     read-only
        STATUS         current
        DESCRIPTION    "The entity type."
        ::= { tnCriticalAlarmLogBufferEntry 10 }

    tnCriticalAlarmLogCondition OBJECT-TYPE
        SYNTAX         TnCondition
        MAX-ACCESS     read-only
        STATUS         current
        DESCRIPTION    "The condition."
        ::= { tnCriticalAlarmLogBufferEntry 11 }

    tnCriticalAlarmLogObjectIDIpV6 OBJECT-TYPE
        SYNTAX         InetAddress
        MAX-ACCESS     read-only
        STATUS         current
        DESCRIPTION    "Denotes a generic Internet address."
        ::= { tnCriticalAlarmLogBufferEntry 12 }

    tnCriticalAlarmLogSlotProgrammedGenericType OBJECT-TYPE
        SYNTAX         SnmpAdminString (SIZE(0..255))
        MAX-ACCESS     read-only
        STATUS         current
        DESCRIPTION    "."
        ::= { tnCriticalAlarmLogBufferEntry 13 }

-------------------------------------------------------------------
-- Major Alarm Log Buffer Table
-------------------------------------------------------------------
    tnMajorAlarmLogBufferTable OBJECT-TYPE
        SYNTAX         SEQUENCE OF TnMajorAlarmLogBufferEntry
        MAX-ACCESS     not-accessible
        STATUS         current
        DESCRIPTION    "The major alarm log history table."
        ::= { tnLogQueues 2 }

    tnMajorAlarmLogBufferEntry OBJECT-TYPE
        SYNTAX         TnMajorAlarmLogBufferEntry
        MAX-ACCESS     not-accessible
        STATUS         current
        DESCRIPTION    "."
        INDEX { tnMajorAlarmLogSerialNumber }
        ::= { tnMajorAlarmLogBufferTable 1 }

    TnMajorAlarmLogBufferEntry ::=
        SEQUENCE {
            tnMajorAlarmLogSerialNumber               Unsigned32,
            tnMajorAlarmLogType                       OBJECT IDENTIFIER,
            tnMajorAlarmLogTime                       Unsigned32,
            tnMajorAlarmLogObjectIDType               Unsigned32,
            tnMajorAlarmLogObjectID                   Unsigned32,
            tnMajorAlarmLogDescr                      SnmpAdminString,
            tnMajorAlarmLogData                       SnmpAdminString,
            tnMajorAlarmLogServiceAffecting           TruthValue,
            tnMajorAlarmLogSlotProgrammedType         OBJECT IDENTIFIER,
            tnMajorAlarmLogEntityType                 TnEntityType,
            tnMajorAlarmLogCondition                  TnCondition,
            tnMajorAlarmLogObjectIDIpV6               InetAddress,
            tnMajorAlarmLogSlotProgrammedGenericType  SnmpAdminString
       }

    tnMajorAlarmLogSerialNumber OBJECT-TYPE
        SYNTAX         Unsigned32 (1..2147483647)
        MAX-ACCESS     not-accessible
        STATUS         current
        DESCRIPTION    "The independently incremented number associated
                        with the sequential ordering of incoming major
                        alarms."
        ::= { tnMajorAlarmLogBufferEntry 1 }

    tnMajorAlarmLogType OBJECT-TYPE
        SYNTAX         OBJECT IDENTIFIER
        MAX-ACCESS     read-only
        STATUS         current
        DESCRIPTION    "The OID of the major alarm event ID."
        ::= { tnMajorAlarmLogBufferEntry 2 }

    tnMajorAlarmLogTime OBJECT-TYPE
        SYNTAX         Unsigned32
        MAX-ACCESS     read-only
        STATUS         current
        DESCRIPTION    "The time at which the major alarm occurred,
                        measured in total time ticks (seconds) from
                        the year 1970."
        ::= { tnMajorAlarmLogBufferEntry 3 }

    tnMajorAlarmLogObjectIDType OBJECT-TYPE
        SYNTAX         Unsigned32
        MAX-ACCESS     read-only
        STATUS         current
        DESCRIPTION    "The type of Object ID associated with the major
                        alarm."
        ::= { tnMajorAlarmLogBufferEntry 4 }

    tnMajorAlarmLogObjectID OBJECT-TYPE
        SYNTAX         Unsigned32
        MAX-ACCESS     read-only
        STATUS         current
        DESCRIPTION    "The physical interface or service associated with
                        the major alarm."
        ::= { tnMajorAlarmLogBufferEntry 5 }

    tnMajorAlarmLogDescr OBJECT-TYPE
        SYNTAX         SnmpAdminString (SIZE(0..255))
        MAX-ACCESS     read-only
        STATUS         current
        DESCRIPTION    "A detailed description of the major alarm."
        ::= { tnMajorAlarmLogBufferEntry 6 }

    tnMajorAlarmLogData OBJECT-TYPE
        SYNTAX         SnmpAdminString (SIZE(0..255))
        MAX-ACCESS     read-only
        STATUS         current
        DESCRIPTION    "Any application specific data relevant to the
                        major alarm.  This could be the value of a changed
                        attribute or any other formatted information
                        related to a notification."
        ::= { tnMajorAlarmLogBufferEntry 7 }

    tnMajorAlarmLogServiceAffecting OBJECT-TYPE
        SYNTAX         TruthValue
        MAX-ACCESS     read-only
        STATUS         current
        DESCRIPTION    "An indication as to whether or not this major
                        alarm is service affecting."
        ::= { tnMajorAlarmLogBufferEntry 8 }

    tnMajorAlarmLogSlotProgrammedType OBJECT-TYPE
        SYNTAX         OBJECT IDENTIFIER
        MAX-ACCESS     read-only
        STATUS         current
        DESCRIPTION    "Type of card provisioned in the given slot.  If
                        tnMajorAlarmLogObjectID does not include a slot,
                        a value of 0.0 will be returned."
        ::= { tnMajorAlarmLogBufferEntry 9 }

    tnMajorAlarmLogEntityType OBJECT-TYPE
        SYNTAX         TnEntityType
        MAX-ACCESS     read-only
        STATUS         current
        DESCRIPTION    "The entity type."
        ::= { tnMajorAlarmLogBufferEntry 10 }

    tnMajorAlarmLogCondition OBJECT-TYPE
        SYNTAX         TnCondition
        MAX-ACCESS     read-only
        STATUS         current
        DESCRIPTION    "The condition."
        ::= { tnMajorAlarmLogBufferEntry 11 }

    tnMajorAlarmLogObjectIDIpV6 OBJECT-TYPE
        SYNTAX         InetAddress
        MAX-ACCESS     read-only
        STATUS         current
        DESCRIPTION    "Denotes a generic Internet address."
        ::= { tnMajorAlarmLogBufferEntry 12 }

    tnMajorAlarmLogSlotProgrammedGenericType OBJECT-TYPE
        SYNTAX         SnmpAdminString (SIZE(0..255))
        MAX-ACCESS     read-only
        STATUS         current
        DESCRIPTION    "."
        ::= { tnMajorAlarmLogBufferEntry 13 }

-------------------------------------------------------------------
-- Minor Alarm Log Buffer Table
-------------------------------------------------------------------
    tnMinorAlarmLogBufferTable OBJECT-TYPE
        SYNTAX         SEQUENCE OF TnMinorAlarmLogBufferEntry
        MAX-ACCESS     not-accessible
        STATUS         current
        DESCRIPTION    "The minor alarm log history table."
        ::= { tnLogQueues 3 }

    tnMinorAlarmLogBufferEntry OBJECT-TYPE
        SYNTAX         TnMinorAlarmLogBufferEntry
        MAX-ACCESS     not-accessible
        STATUS         current
        DESCRIPTION    "."
        INDEX { tnMinorAlarmLogSerialNumber }
        ::= { tnMinorAlarmLogBufferTable 1 }

    TnMinorAlarmLogBufferEntry ::=
        SEQUENCE {
            tnMinorAlarmLogSerialNumber                Unsigned32,
            tnMinorAlarmLogType                        OBJECT IDENTIFIER,
            tnMinorAlarmLogTime                        Unsigned32,
            tnMinorAlarmLogObjectIDType                Unsigned32,
            tnMinorAlarmLogObjectID                    Unsigned32,
            tnMinorAlarmLogDescr                       SnmpAdminString,
            tnMinorAlarmLogData                        SnmpAdminString,
            tnMinorAlarmLogServiceAffecting            TruthValue,
            tnMinorAlarmLogSlotProgrammedType          OBJECT IDENTIFIER,
            tnMinorAlarmLogEntityType                  TnEntityType,
            tnMinorAlarmLogCondition                   TnCondition,
            tnMinorAlarmLogObjectIDIpV6                InetAddress,
            tnMinorAlarmLogSlotProgrammedGenericType   SnmpAdminString
       }

    tnMinorAlarmLogSerialNumber OBJECT-TYPE
        SYNTAX         Unsigned32 (1..2147483647)
        MAX-ACCESS     not-accessible
        STATUS         current
        DESCRIPTION    "The independently incremented number associated
                        with the sequential ordering of incoming minor
                        alarms."
        ::= { tnMinorAlarmLogBufferEntry 1 }

    tnMinorAlarmLogType OBJECT-TYPE
        SYNTAX         OBJECT IDENTIFIER
        MAX-ACCESS     read-only
        STATUS         current
        DESCRIPTION    "The OID of the minor alarm event ID."
        ::= { tnMinorAlarmLogBufferEntry 2 }

    tnMinorAlarmLogTime OBJECT-TYPE
        SYNTAX         Unsigned32
        MAX-ACCESS     read-only
        STATUS         current
        DESCRIPTION    "The time at which the minor alarm occurred,
                        measured in total time ticks (seconds) from the
                        year 1970."
        ::= { tnMinorAlarmLogBufferEntry 3 }

    tnMinorAlarmLogObjectIDType OBJECT-TYPE
        SYNTAX         Unsigned32
        MAX-ACCESS     read-only
        STATUS         current
        DESCRIPTION    "The type of Object ID associated with the minor
                        alarm."
        ::= { tnMinorAlarmLogBufferEntry 4 }

    tnMinorAlarmLogObjectID OBJECT-TYPE
        SYNTAX         Unsigned32
        MAX-ACCESS     read-only
        STATUS         current
        DESCRIPTION    "The physical interface or service associated with
                        the minor alarm."
        ::= { tnMinorAlarmLogBufferEntry 5 }

    tnMinorAlarmLogDescr OBJECT-TYPE
        SYNTAX         SnmpAdminString (SIZE(0..255))
        MAX-ACCESS     read-only
        STATUS         current
        DESCRIPTION    "A detailed description of the minor alarm."
        ::= { tnMinorAlarmLogBufferEntry 6 }

    tnMinorAlarmLogData OBJECT-TYPE
        SYNTAX         SnmpAdminString (SIZE(0..255))
        MAX-ACCESS     read-only
        STATUS         current
        DESCRIPTION    "Any application specific data relevant to the
                        minor alarm.  This could be the value of a changed
                        attribute or any other formatted information
                        related to a notification."
        ::= { tnMinorAlarmLogBufferEntry 7 }

    tnMinorAlarmLogServiceAffecting OBJECT-TYPE
        SYNTAX         TruthValue
        MAX-ACCESS     read-only
        STATUS         current
        DESCRIPTION    "An indication as to whether or not this minor
                        alarm is service affecting."
        ::= { tnMinorAlarmLogBufferEntry 8 }

    tnMinorAlarmLogSlotProgrammedType OBJECT-TYPE
        SYNTAX         OBJECT IDENTIFIER
        MAX-ACCESS     read-only
        STATUS         current
        DESCRIPTION    "Type of card provisioned in the given slot.  If
                        tnMinorAlarmLogObjectID does not include a slot,
                        a value of 0.0 will be returned."
        ::= { tnMinorAlarmLogBufferEntry 9 }

    tnMinorAlarmLogEntityType OBJECT-TYPE
        SYNTAX         TnEntityType
        MAX-ACCESS     read-only
        STATUS         current
        DESCRIPTION    "The entity type."
        ::= { tnMinorAlarmLogBufferEntry 10 }

    tnMinorAlarmLogCondition OBJECT-TYPE
        SYNTAX         TnCondition
        MAX-ACCESS     read-only
        STATUS         current
        DESCRIPTION    "The condition."
        ::= { tnMinorAlarmLogBufferEntry 11 }

    tnMinorAlarmLogObjectIDIpV6 OBJECT-TYPE
        SYNTAX         InetAddress
        MAX-ACCESS     read-only
        STATUS         current
        DESCRIPTION    "Denotes a generic Internet address."
        ::= { tnMinorAlarmLogBufferEntry 12 }

    tnMinorAlarmLogSlotProgrammedGenericType OBJECT-TYPE
        SYNTAX         SnmpAdminString (SIZE(0..255))
        MAX-ACCESS     read-only
        STATUS         current
        DESCRIPTION    "."
        ::= { tnMinorAlarmLogBufferEntry 13 }

-------------------------------------------------------------------
-- State Change Log Buffer Table
-------------------------------------------------------------------
    tnStateChangeLogBufferTable OBJECT-TYPE
        SYNTAX         SEQUENCE OF TnStateChangeLogBufferEntry
        MAX-ACCESS     not-accessible
        STATUS         current
        DESCRIPTION    "The state change log history table."
        ::= { tnLogQueues 4 }

    tnStateChangeLogBufferEntry OBJECT-TYPE
        SYNTAX         TnStateChangeLogBufferEntry
        MAX-ACCESS     not-accessible
        STATUS         current
        DESCRIPTION    "."
        INDEX { tnStateChangeLogSerialNumber }
        ::= { tnStateChangeLogBufferTable 1 }

    TnStateChangeLogBufferEntry ::=
        SEQUENCE {
            tnStateChangeLogSerialNumber                Unsigned32,
            tnStateChangeLogType                        OBJECT IDENTIFIER,
            tnStateChangeLogTime                        Unsigned32,
            tnStateChangeLogObjectIDType                Unsigned32,
            tnStateChangeLogObjectID                    Unsigned32,
            tnStateChangeLogDescr                       SnmpAdminString,
            tnStateChangeLogData                        SnmpAdminString,
            tnStateChangeLogSlotProgrammedType          OBJECT IDENTIFIER,
            tnStateChangeLogObjectIDIpV6                InetAddress,
            tnStateChangeLogSlotProgrammedGenericType   SnmpAdminString
       }

    tnStateChangeLogSerialNumber OBJECT-TYPE
        SYNTAX         Unsigned32 (1..2147483647)
        MAX-ACCESS     not-accessible
        STATUS         current
        DESCRIPTION    "The independently incremented number associated
                        with the sequential ordering of incoming state
                        changes."
        ::= { tnStateChangeLogBufferEntry 1 }

    tnStateChangeLogType OBJECT-TYPE
        SYNTAX         OBJECT IDENTIFIER
        MAX-ACCESS     read-only
        STATUS         current
        DESCRIPTION    "The OID of the state change event ID."
        ::= { tnStateChangeLogBufferEntry 2 }

    tnStateChangeLogTime OBJECT-TYPE
        SYNTAX         Unsigned32
        MAX-ACCESS     read-only
        STATUS         current
        DESCRIPTION    "The time at which the state change occurred,
                        measured in total time ticks (seconds) from the
                        year 1970."
        ::= { tnStateChangeLogBufferEntry 3 }

    tnStateChangeLogObjectIDType OBJECT-TYPE
        SYNTAX         Unsigned32
        MAX-ACCESS     read-only
        STATUS         current
        DESCRIPTION    "The type of Object ID associated with the state
                        change."
        ::= { tnStateChangeLogBufferEntry 4 }

    tnStateChangeLogObjectID OBJECT-TYPE
        SYNTAX         Unsigned32
        MAX-ACCESS     read-only
        STATUS         current
        DESCRIPTION    "The physical interface or service associated with
                        the state change."
        ::= { tnStateChangeLogBufferEntry 5 }

    tnStateChangeLogDescr OBJECT-TYPE
        SYNTAX         SnmpAdminString (SIZE(0..255))
        MAX-ACCESS     read-only
        STATUS         current
        DESCRIPTION    "A detailed description of the state change."
        ::= { tnStateChangeLogBufferEntry 6 }

    tnStateChangeLogData OBJECT-TYPE
        SYNTAX         SnmpAdminString (SIZE(0..255))
        MAX-ACCESS     read-only
        STATUS         current
        DESCRIPTION    "Any application specific data relevant to the
                        state change.  This could be the value of a
                        changed attribute or any other formatted
                        information related to a notification."
        ::= { tnStateChangeLogBufferEntry 7 }

    tnStateChangeLogSlotProgrammedType OBJECT-TYPE
        SYNTAX         OBJECT IDENTIFIER
        MAX-ACCESS     read-only
        STATUS         current
        DESCRIPTION    "Type of card provisioned in the given slot.  If
                        tnStateChangeLogObjectID does not include a slot,
                        a value of 0.0 will be returned."
        ::= { tnStateChangeLogBufferEntry 8 }

    tnStateChangeLogObjectIDIpV6 OBJECT-TYPE
        SYNTAX         InetAddress
        MAX-ACCESS     read-only
        STATUS         current
        DESCRIPTION    "Denotes a generic Internet address."
        ::= { tnStateChangeLogBufferEntry 9 }

    tnStateChangeLogSlotProgrammedGenericType OBJECT-TYPE
        SYNTAX         SnmpAdminString (SIZE(0..255))
        MAX-ACCESS     read-only
        STATUS         current
        DESCRIPTION    "."
        ::= { tnStateChangeLogBufferEntry 10 }

-------------------------------------------------------------------
-- User Action Log Buffer Table
-------------------------------------------------------------------
    tnUserActionLogBufferTable OBJECT-TYPE
        SYNTAX         SEQUENCE OF TnUserActionLogBufferEntry
        MAX-ACCESS     not-accessible
        STATUS         current
        DESCRIPTION    "The user action log history table."
        ::= { tnLogQueues 5 }

    tnUserActionLogBufferEntry OBJECT-TYPE
        SYNTAX         TnUserActionLogBufferEntry
        MAX-ACCESS     not-accessible
        STATUS         current
        DESCRIPTION    "."
        INDEX { tnUserActionLogSerialNumber }
        ::= { tnUserActionLogBufferTable 1 }

    TnUserActionLogBufferEntry ::=
        SEQUENCE {
            tnUserActionLogSerialNumber  Unsigned32,
            tnUserActionLogType          OBJECT IDENTIFIER,
            tnUserActionLogTime          Unsigned32,
            tnUserActionLogObjectIDType  Unsigned32,
            tnUserActionLogObjectID      Unsigned32,
            tnUserActionLogDescr         SnmpAdminString,
            tnUserActionLogChangedObject OBJECT IDENTIFIER,
            tnUserActionLogData          SnmpAdminString,
            tnUserActionLogObjectIDIpV6  InetAddress
       }

    tnUserActionLogSerialNumber OBJECT-TYPE
        SYNTAX         Unsigned32 (1..2147483647)
        MAX-ACCESS     not-accessible
        STATUS         current
        DESCRIPTION    "The independently incremented number associated
                        with the sequential ordering of incoming user
                        actions."
        ::= { tnUserActionLogBufferEntry 1 }

    tnUserActionLogType OBJECT-TYPE
        SYNTAX         OBJECT IDENTIFIER
        MAX-ACCESS     read-only
        STATUS         current
        DESCRIPTION    "The OID of the user action event ID."
        ::= { tnUserActionLogBufferEntry 2 }

    tnUserActionLogTime OBJECT-TYPE
        SYNTAX         Unsigned32
        MAX-ACCESS     read-only
        STATUS         current
        DESCRIPTION    "The time at which the user action occurred,
                        measured in total time ticks (seconds) from the
                        year 1970."
        ::= { tnUserActionLogBufferEntry 3 }

    tnUserActionLogObjectIDType OBJECT-TYPE
        SYNTAX         Unsigned32
        MAX-ACCESS     read-only
        STATUS         current
        DESCRIPTION    "The type of Object ID associated with the user
                        action."
        ::= { tnUserActionLogBufferEntry 4 }

    tnUserActionLogObjectID OBJECT-TYPE
        SYNTAX         Unsigned32
        MAX-ACCESS     read-only
        STATUS         current
        DESCRIPTION    "The physical interface or service associated with
                        the user action."
        ::= { tnUserActionLogBufferEntry 5 }

    tnUserActionLogDescr OBJECT-TYPE
        SYNTAX         SnmpAdminString (SIZE(0..255))
        MAX-ACCESS     read-only
        STATUS         current
        DESCRIPTION    "A detailed description of the user action."
        ::= { tnUserActionLogBufferEntry 6 }

    tnUserActionLogChangedObject OBJECT-TYPE
        SYNTAX         OBJECT IDENTIFIER
        MAX-ACCESS     read-only
        STATUS         current
        DESCRIPTION    "The OID of an attribute changed in a tnChangeNotif
                        log."
        ::= { tnUserActionLogBufferEntry 7 }

    tnUserActionLogData OBJECT-TYPE
        SYNTAX         SnmpAdminString (SIZE(0..255))
        MAX-ACCESS     read-only
        STATUS         current
        DESCRIPTION    "Any application specific data relevant to the user
                        action.  This could be the value of a changed
                        attribute or any other formatted information related
                        to a notification."
        ::= { tnUserActionLogBufferEntry 8 }

    tnUserActionLogObjectIDIpV6 OBJECT-TYPE
        SYNTAX         InetAddress
        MAX-ACCESS     read-only
        STATUS         current
        DESCRIPTION    "Denotes a generic Internet address."
        ::= { tnUserActionLogBufferEntry 9 }

-------------------------------------------------------------------
-- General Event Log Buffer Table
-------------------------------------------------------------------
    tnGeneralEventLogBufferTable OBJECT-TYPE
        SYNTAX         SEQUENCE OF TnGeneralEventLogBufferEntry
        MAX-ACCESS     not-accessible
        STATUS         current
        DESCRIPTION    "The general event log history table."
        ::= { tnLogQueues 6 }

    tnGeneralEventLogBufferEntry OBJECT-TYPE
        SYNTAX         TnGeneralEventLogBufferEntry
        MAX-ACCESS     not-accessible
        STATUS         current
        DESCRIPTION    "."
        INDEX { tnGeneralEventLogSerialNumber }
        ::= { tnGeneralEventLogBufferTable 1 }

    TnGeneralEventLogBufferEntry ::=
        SEQUENCE {
            tnGeneralEventLogSerialNumber                Unsigned32,
            tnGeneralEventLogType                        OBJECT IDENTIFIER,
            tnGeneralEventLogTime                        Unsigned32,
            tnGeneralEventLogObjectIDType                Unsigned32,
            tnGeneralEventLogObjectID                    Unsigned32,
            tnGeneralEventLogDescr                       SnmpAdminString,
            tnGeneralEventLogChangedObject               OBJECT IDENTIFIER,
            tnGeneralEventLogData                        SnmpAdminString,
            tnGeneralEventLogSlotProgrammedType          OBJECT IDENTIFIER,
            tnGeneralEventLogObjectIDIpV6                InetAddress,
            tnGeneralEventLogSlotProgrammedGenericType   SnmpAdminString
       }

    tnGeneralEventLogSerialNumber OBJECT-TYPE
        SYNTAX         Unsigned32 (1..2147483647)
        MAX-ACCESS     not-accessible
        STATUS         current
        DESCRIPTION    "The independently incremented number associated
                        with the sequential ordering of incoming general
                        events."
        ::= { tnGeneralEventLogBufferEntry 1 }

    tnGeneralEventLogType OBJECT-TYPE
        SYNTAX         OBJECT IDENTIFIER
        MAX-ACCESS     read-only
        STATUS         current
        DESCRIPTION    "The OID of the general event event ID."
        ::= { tnGeneralEventLogBufferEntry 2 }

    tnGeneralEventLogTime OBJECT-TYPE
        SYNTAX         Unsigned32
        MAX-ACCESS     read-only
        STATUS         current
        DESCRIPTION    "The time at which the general event occurred,
                        measured in total time ticks (seconds) from the
                        year 1970."
        ::= { tnGeneralEventLogBufferEntry 3 }

    tnGeneralEventLogObjectIDType OBJECT-TYPE
        SYNTAX         Unsigned32
        MAX-ACCESS     read-only
        STATUS         current
        DESCRIPTION    "The type of Object ID associated with the general
                        event."
        ::= { tnGeneralEventLogBufferEntry 4 }

    tnGeneralEventLogObjectID OBJECT-TYPE
        SYNTAX         Unsigned32
        MAX-ACCESS     read-only
        STATUS         current
        DESCRIPTION    "The physical interface or service associated with
                        the general event."
        ::= { tnGeneralEventLogBufferEntry 5 }

    tnGeneralEventLogDescr OBJECT-TYPE
        SYNTAX         SnmpAdminString (SIZE(0..255))
        MAX-ACCESS     read-only
        STATUS         current
        DESCRIPTION    "A detailed description of the general event."
        ::= { tnGeneralEventLogBufferEntry 6 }

    tnGeneralEventLogChangedObject OBJECT-TYPE
        SYNTAX         OBJECT IDENTIFIER
        MAX-ACCESS     read-only
        STATUS         current
        DESCRIPTION    "The OID of a changed attribute."
        ::= { tnGeneralEventLogBufferEntry 7 }

    tnGeneralEventLogData OBJECT-TYPE
        SYNTAX         SnmpAdminString (SIZE(0..255))
        MAX-ACCESS     read-only
        STATUS         current
        DESCRIPTION    "Any application specific data relevant to the
                        general event.  This could be the value of a
                        changed attribute or any other formatted
                        information related to a notification."
        ::= { tnGeneralEventLogBufferEntry 8 }

    tnGeneralEventLogSlotProgrammedType OBJECT-TYPE
        SYNTAX         OBJECT IDENTIFIER
        MAX-ACCESS     read-only
        STATUS         current
        DESCRIPTION    "Type of card provisioned in the given slot.  If
                        tnGeneralEventLogObjectID does not include a slot,
                        a value of 0.0 will be returned."
        ::= { tnGeneralEventLogBufferEntry 9 }

    tnGeneralEventLogObjectIDIpV6 OBJECT-TYPE
        SYNTAX         InetAddress
        MAX-ACCESS     read-only
        STATUS         current
        DESCRIPTION    "Denotes a generic Internet address."
        ::= { tnGeneralEventLogBufferEntry 10 }

    tnGeneralEventLogSlotProgrammedGenericType OBJECT-TYPE
        SYNTAX         SnmpAdminString (SIZE(0..255))
        MAX-ACCESS     read-only
        STATUS         current
        DESCRIPTION    "."
        ::= { tnGeneralEventLogBufferEntry 11 }

-------------------------------------------------------------------
-- Generic Log Buffer Table
-------------------------------------------------------------------
    tnLogBufferTable OBJECT-TYPE
        SYNTAX         SEQUENCE OF TnLogBufferEntry
        MAX-ACCESS     not-accessible
        STATUS         current
        DESCRIPTION    "The generic log history table."
        ::= { tnLogQueues 7 }

    tnLogBufferEntry OBJECT-TYPE
        SYNTAX         TnLogBufferEntry
        MAX-ACCESS     not-accessible
        STATUS         current
        DESCRIPTION    "."
        INDEX { tnLogSerialNumber }
        ::= { tnLogBufferTable 1 }

    TnLogBufferEntry ::=
        SEQUENCE {
            tnLogSerialNumber                Unsigned32,
            tnLogType                        OBJECT IDENTIFIER,
            tnLogTime                        Unsigned32,
            tnLogObjectIDType                Unsigned32,
            tnLogObjectID                    Unsigned32,
            tnLogCategory                    TnTrapCategory,
            tnLogDescr                       SnmpAdminString,
            tnLogChangedObject               OBJECT IDENTIFIER,
            tnLogData                        SnmpAdminString,
            tnLogServiceAffecting            TruthValue,
            tnLogSlotProgrammedType          OBJECT IDENTIFIER,
            tnLogEntityType                  TnEntityType,
            tnLogCondition                   TnCondition,
            tnLogObjectIDIpV6                InetAddress,
            tnLogSlotProgrammedGenericType   SnmpAdminString
       }

    tnLogSerialNumber OBJECT-TYPE
        SYNTAX         Unsigned32 (1..2147483647)
        MAX-ACCESS     not-accessible
        STATUS         current
        DESCRIPTION    "The independently incremented number associated
                        with the sequential ordering of incoming logs."
        ::= { tnLogBufferEntry 1 }

    tnLogType OBJECT-TYPE
        SYNTAX         OBJECT IDENTIFIER
        MAX-ACCESS     read-only
        STATUS         current
        DESCRIPTION    "The OID of the event ID."
        ::= { tnLogBufferEntry 2 }

    tnLogTime OBJECT-TYPE
        SYNTAX         Unsigned32
        MAX-ACCESS     read-only
        STATUS         current
        DESCRIPTION    "The time at which the log occurred, measured in
                        total time ticks (seconds) from the year 1970."
        ::= { tnLogBufferEntry 3 }

    tnLogObjectIDType OBJECT-TYPE
        SYNTAX         Unsigned32
        MAX-ACCESS     read-only
        STATUS         current
        DESCRIPTION    "The type of Object ID associated with the log."
        ::= { tnLogBufferEntry 4 }

    tnLogObjectID OBJECT-TYPE
        SYNTAX         Unsigned32
        MAX-ACCESS     read-only
        STATUS         current
        DESCRIPTION    "The physical interface or service associated with
                        the log."
        ::= { tnLogBufferEntry 5 }

    tnLogCategory OBJECT-TYPE
        SYNTAX         TnTrapCategory
        MAX-ACCESS     read-only
        STATUS         current
        DESCRIPTION    "The log category."
        ::= { tnLogBufferEntry 6 }

    tnLogDescr OBJECT-TYPE
        SYNTAX         SnmpAdminString (SIZE(0..255))
        MAX-ACCESS     read-only
        STATUS         current
        DESCRIPTION    "A detailed description of the log."
        ::= { tnLogBufferEntry 7 }

    tnLogChangedObject OBJECT-TYPE
        SYNTAX         OBJECT IDENTIFIER
        MAX-ACCESS     read-only
        STATUS         current
        DESCRIPTION    "The OID of an attribute changed in a tnChangeNotif
                        log.  This is null for all for non User Action logs."
        ::= { tnLogBufferEntry 8 }

    tnLogData OBJECT-TYPE
        SYNTAX         SnmpAdminString (SIZE(0..255))
        MAX-ACCESS     read-only
        STATUS         current
        DESCRIPTION    "Any application specific data relevant to the log.
                        This could be the value of a changed attribute or
                        any other formatted information related to a
                        notification."
        ::= { tnLogBufferEntry 9 }

    tnLogServiceAffecting OBJECT-TYPE
        SYNTAX         TruthValue
        MAX-ACCESS     read-only
        STATUS         current
        DESCRIPTION    "An indication as to whether or not this log is
                        service affecting."
        ::= { tnLogBufferEntry 10 }

    tnLogSlotProgrammedType OBJECT-TYPE
        SYNTAX         OBJECT IDENTIFIER
        MAX-ACCESS     read-only
        STATUS         current
        DESCRIPTION    "Type of card provisioned in the given slot.  If
                        tnLogObjectID does not include a slot, a value of
                        0.0 will be returned."
        ::= { tnLogBufferEntry 11 }

    tnLogEntityType OBJECT-TYPE
        SYNTAX         TnEntityType
        MAX-ACCESS     read-only
        STATUS         current
        DESCRIPTION    "The entity type."
        ::= { tnLogBufferEntry 12 }

    tnLogCondition OBJECT-TYPE
        SYNTAX         TnCondition
        MAX-ACCESS     read-only
        STATUS         current
        DESCRIPTION    "The condition."
        ::= { tnLogBufferEntry 13 }

    tnLogObjectIDIpV6 OBJECT-TYPE
        SYNTAX         InetAddress
        MAX-ACCESS     read-only
        STATUS         current
        DESCRIPTION    "Denotes a generic Internet address."
        ::= { tnLogBufferEntry 14 }

    tnLogSlotProgrammedGenericType OBJECT-TYPE
        SYNTAX         SnmpAdminString (SIZE(0..255))
        MAX-ACCESS     read-only
        STATUS         current
        DESCRIPTION    "."
        ::= { tnLogBufferEntry 15 }

-------------------------------------------------------------------
-- Active Alarm Table
-------------------------------------------------------------------
    tnActiveAlarmTable OBJECT-TYPE
        SYNTAX         SEQUENCE OF TnActiveAlarmEntry
        MAX-ACCESS     not-accessible
        STATUS         current
        DESCRIPTION    "The active alarm table.  This table includes the
                        following categories:

                        criticalAlarms(1)
                        majorAlarms(2)
                        minorAlarms(3)
                        notAlarmed(7)
                        warningAlarms(12)"
        ::= { tnLogQueues 8 }

    tnActiveAlarmEntry OBJECT-TYPE
        SYNTAX         TnActiveAlarmEntry
        MAX-ACCESS     not-accessible
        STATUS         current
        DESCRIPTION    "."
        INDEX { tnActiveAlarmSerialNumber }
        ::= { tnActiveAlarmTable 1 }

    TnActiveAlarmEntry ::=
        SEQUENCE {
            tnActiveAlarmSerialNumber                Unsigned32,
            tnActiveAlarmType                        OBJECT IDENTIFIER,
            tnActiveAlarmTime                        Unsigned32,
            tnActiveAlarmObjectIDType                Unsigned32,
            tnActiveAlarmObjectID                    Unsigned32,
            tnActiveAlarmCategory                    TnTrapCategory,
            tnActiveAlarmDescr                       SnmpAdminString,
            tnActiveAlarmData                        SnmpAdminString,
            tnActiveAlarmServiceAffecting            TruthValue,
            tnActiveAlarmSlotProgrammedType          OBJECT IDENTIFIER,
            tnActiveAlarmEntityType                  TnEntityType,
            tnActiveAlarmCondition                   TnCondition,
            tnActiveAlarmSlotProgrammedGenericType   SnmpAdminString
       }

    tnActiveAlarmSerialNumber OBJECT-TYPE
        SYNTAX         Unsigned32 (1..2147483647)
        MAX-ACCESS     not-accessible
        STATUS         current
        DESCRIPTION    "The independently incremented number associated
                        with the sequential ordering of active alarms."
        ::= { tnActiveAlarmEntry 1 }

    tnActiveAlarmType OBJECT-TYPE
        SYNTAX         OBJECT IDENTIFIER
        MAX-ACCESS     read-only
        STATUS         current
        DESCRIPTION    "The OID of the notification."
        ::= { tnActiveAlarmEntry 2 }

    tnActiveAlarmTime OBJECT-TYPE
        SYNTAX         Unsigned32
        MAX-ACCESS     read-only
        STATUS         current
        DESCRIPTION    "The time at which the active alarm occurred,
                        measured in total time ticks (seconds) from the
                        year 1970."
        ::= { tnActiveAlarmEntry 3 }

    tnActiveAlarmObjectIDType OBJECT-TYPE
        SYNTAX         Unsigned32
        MAX-ACCESS     read-only
        STATUS         current
        DESCRIPTION    "The type of Object ID associated with the active
                        alarm."
        ::= { tnActiveAlarmEntry 4 }

    tnActiveAlarmObjectID OBJECT-TYPE
        SYNTAX         Unsigned32
        MAX-ACCESS     read-only
        STATUS         current
        DESCRIPTION    "The physical interface or service associated
                        with the active alarm."
        ::= { tnActiveAlarmEntry 5 }

    tnActiveAlarmCategory OBJECT-TYPE
        SYNTAX         TnTrapCategory
        MAX-ACCESS     read-only
        STATUS         current
        DESCRIPTION    "The active alarm's category."
        ::= { tnActiveAlarmEntry 6 }

    tnActiveAlarmDescr OBJECT-TYPE
        SYNTAX         SnmpAdminString (SIZE(0..255))
        MAX-ACCESS     read-only
        STATUS         current
        DESCRIPTION    "A detailed description of the active alarm."
        ::= { tnActiveAlarmEntry 7 }

    tnActiveAlarmData OBJECT-TYPE
        SYNTAX         SnmpAdminString (SIZE(0..255))
        MAX-ACCESS     read-only
        STATUS         current
        DESCRIPTION    "Any application specific data relevant to the
                        active alarm.  This could be the value of a
                        changed attribute or any other formatted
                        information related to a notification."
        ::= { tnActiveAlarmEntry 8 }

    tnActiveAlarmServiceAffecting OBJECT-TYPE
        SYNTAX         TruthValue
        MAX-ACCESS     read-only
        STATUS         current
        DESCRIPTION    "An indication as to whether or not this active
                        alarm is service affecting."
        ::= { tnActiveAlarmEntry 9 }

    tnActiveAlarmSlotProgrammedType OBJECT-TYPE
        SYNTAX         OBJECT IDENTIFIER
        MAX-ACCESS     read-only
        STATUS         current
        DESCRIPTION    "Type of card provisioned in the given slot.  If
                        tnActiveAlarmObjectID does not include a slot, a
                        value of 0.0 will be returned."
        ::= { tnActiveAlarmEntry 10 }

    tnActiveAlarmEntityType OBJECT-TYPE
        SYNTAX         TnEntityType
        MAX-ACCESS     read-only
        STATUS         current
        DESCRIPTION    "The entity type."
        ::= { tnActiveAlarmEntry 11 }

    tnActiveAlarmCondition OBJECT-TYPE
        SYNTAX         TnCondition
        MAX-ACCESS     read-only
        STATUS         current
        DESCRIPTION    "The condition."
        ::= { tnActiveAlarmEntry 12 }

    tnActiveAlarmSlotProgrammedGenericType OBJECT-TYPE
        SYNTAX         SnmpAdminString (SIZE(0..255))
        MAX-ACCESS     read-only
        STATUS         current
        DESCRIPTION    "."
        ::= { tnActiveAlarmEntry 13 }

-------------------------------------------------------------------
-- Persistent Log Buffer Table
-------------------------------------------------------------------
    tnPersistentLogBufferTable OBJECT-TYPE
        SYNTAX         SEQUENCE OF TnPersistentLogBufferEntry
        MAX-ACCESS     not-accessible
        STATUS         current
        DESCRIPTION    "This table keeps record of the last three hundred
                        events over restarts."
        ::= { tnLogQueues 9 }

    tnPersistentLogBufferEntry OBJECT-TYPE
        SYNTAX         TnPersistentLogBufferEntry
        MAX-ACCESS     not-accessible
        STATUS         current
        DESCRIPTION    "."
        INDEX { tnPersistentLogSerialNumber }
        ::= { tnPersistentLogBufferTable 1 }

    TnPersistentLogBufferEntry ::=
        SEQUENCE {
            tnPersistentLogSerialNumber       Unsigned32,
            tnPersistentLogType               OBJECT IDENTIFIER,
            tnPersistentLogTime               Unsigned32,
            tnPersistentLogObjectIDType       Unsigned32,
            tnPersistentLogObjectID           Unsigned32,
            tnPersistentLogCategory           TnTrapCategory,
            tnPersistentLogDescr              SnmpAdminString,
            tnPersistentLogChangedObject      OBJECT IDENTIFIER,
            tnPersistentLogData               SnmpAdminString,
            tnPersistentLogServiceAffecting   TruthValue,
            tnPersistentLogSlotProgrammedType OBJECT IDENTIFIER,
            tnPersistentLogObjectIDIpV6       InetAddress
       }

    tnPersistentLogSerialNumber OBJECT-TYPE
        SYNTAX         Unsigned32 (1..2147483647)
        MAX-ACCESS     not-accessible
        STATUS         current
        DESCRIPTION    "The independently incremented number associated
                        with the sequential ordering of incoming logs."
        ::= { tnPersistentLogBufferEntry 1 }

    tnPersistentLogType OBJECT-TYPE
        SYNTAX         OBJECT IDENTIFIER
        MAX-ACCESS     read-only
        STATUS         current
        DESCRIPTION    "The OID of the event ID."
        ::= { tnPersistentLogBufferEntry 2 }

    tnPersistentLogTime OBJECT-TYPE
        SYNTAX         Unsigned32
        MAX-ACCESS     read-only
        STATUS         current
        DESCRIPTION    "The time at which the log occurred, measured in
                        total time ticks (seconds) from the year 1970."
        ::= { tnPersistentLogBufferEntry 3 }

    tnPersistentLogObjectIDType OBJECT-TYPE
        SYNTAX         Unsigned32
        MAX-ACCESS     read-only
        STATUS         current
        DESCRIPTION    "The type of Object ID associated with the log."
        ::= { tnPersistentLogBufferEntry 4 }

    tnPersistentLogObjectID OBJECT-TYPE
        SYNTAX         Unsigned32
        MAX-ACCESS     read-only
        STATUS         current
        DESCRIPTION    "The physical interface or service associated with
                        the log."
        ::= { tnPersistentLogBufferEntry 5 }

    tnPersistentLogCategory OBJECT-TYPE
        SYNTAX         TnTrapCategory
        MAX-ACCESS     read-only
        STATUS         current
        DESCRIPTION    "The log category."
        ::= { tnPersistentLogBufferEntry 6 }

    tnPersistentLogDescr OBJECT-TYPE
        SYNTAX         SnmpAdminString (SIZE(0..255))
        MAX-ACCESS     read-only
        STATUS         current
        DESCRIPTION    "A detailed description of the log."
        ::= { tnPersistentLogBufferEntry 7 }

    tnPersistentLogChangedObject OBJECT-TYPE
        SYNTAX         OBJECT IDENTIFIER
        MAX-ACCESS     read-only
        STATUS         current
        DESCRIPTION    "The OID of an attribute changed in a tnChangeNotif
                        log.  This is null for all for non User Action logs."
        ::= { tnPersistentLogBufferEntry 8 }

    tnPersistentLogData OBJECT-TYPE
        SYNTAX         SnmpAdminString (SIZE(0..255))
        MAX-ACCESS     read-only
        STATUS         current
        DESCRIPTION    "Any application specific data relevant to the log.
                        This could be the value of a changed attribute or
                        any other formatted information related to a
                        notification."
        ::= { tnPersistentLogBufferEntry 9 }

    tnPersistentLogServiceAffecting OBJECT-TYPE
        SYNTAX         TruthValue
        MAX-ACCESS     read-only
        STATUS         current
        DESCRIPTION    "An indication as to whether or not this log is
                        service affecting."
        ::= { tnPersistentLogBufferEntry 10 }

    tnPersistentLogSlotProgrammedType OBJECT-TYPE
        SYNTAX         OBJECT IDENTIFIER
        MAX-ACCESS     read-only
        STATUS         current
        DESCRIPTION    "Type of card provisioned in the given slot.  If
                        tnPersistentLogObjectID does not include a slot,
                        a value of 0.0 will be returned."
        ::= { tnPersistentLogBufferEntry 11 }

    tnPersistentLogObjectIDIpV6 OBJECT-TYPE
        SYNTAX         InetAddress
        MAX-ACCESS     read-only
        STATUS         current
        DESCRIPTION    "Denotes a generic Internet address."
        ::= { tnPersistentLogBufferEntry 12 }

-------------------------------------------------------------------
-- Active or Masked Alarm Table
-------------------------------------------------------------------
    tnActiveOrMaskedAlarmTable OBJECT-TYPE
        SYNTAX         SEQUENCE OF TnActiveOrMaskedAlarmEntry
        MAX-ACCESS     not-accessible
        STATUS         current
        DESCRIPTION    "The active or masked alarm table.  This table
                        includes locally masked alarms if the network
                        operator access level is service.  This table
                        includes the following categories:

                        criticalAlarms(1)
                        majorAlarms(2)
                        minorAlarms(3)
                        notAlarmed(7)
                        notReported(10)
                        warningAlarms(12)"
        ::= { tnLogQueues 10 }

    tnActiveOrMaskedAlarmEntry OBJECT-TYPE
        SYNTAX         TnActiveOrMaskedAlarmEntry
        MAX-ACCESS     not-accessible
        STATUS         current
        DESCRIPTION    "."
        INDEX { tnActiveOrMaskedAlarmSerialNumber }
        ::= { tnActiveOrMaskedAlarmTable 1 }

    TnActiveOrMaskedAlarmEntry ::=
        SEQUENCE {
            tnActiveOrMaskedAlarmSerialNumber       Unsigned32,
            tnActiveOrMaskedAlarmType               OBJECT IDENTIFIER,
            tnActiveOrMaskedAlarmTime               Unsigned32,
            tnActiveOrMaskedAlarmObjectIDType       Unsigned32,
            tnActiveOrMaskedAlarmObjectID           Unsigned32,
            tnActiveOrMaskedAlarmCategory           TnTrapCategory,
            tnActiveOrMaskedAlarmDescr              SnmpAdminString,
            tnActiveOrMaskedAlarmData               SnmpAdminString,
            tnActiveOrMaskedAlarmServiceAffecting   TruthValue,
            tnActiveOrMaskedAlarmSlotProgrammedType OBJECT IDENTIFIER,
            tnActiveOrMaskedAlarmIsMasked           TruthValue,
            tnActiveOrMaskedAlarmEntityType         TnEntityType,
            tnActiveOrMaskedAlarmCondition          TnCondition
       }

    tnActiveOrMaskedAlarmSerialNumber OBJECT-TYPE
        SYNTAX         Unsigned32 (1..2147483647)
        MAX-ACCESS     not-accessible
        STATUS         current
        DESCRIPTION    "The independently incremented number associated
                        with the sequential ordering of active or masked
                        alarms."
        ::= { tnActiveOrMaskedAlarmEntry 1 }

    tnActiveOrMaskedAlarmType OBJECT-TYPE
        SYNTAX         OBJECT IDENTIFIER
        MAX-ACCESS     read-only
        STATUS         current
        DESCRIPTION    "The OID of the notification."
        ::= { tnActiveOrMaskedAlarmEntry 2 }

    tnActiveOrMaskedAlarmTime OBJECT-TYPE
        SYNTAX         Unsigned32
        MAX-ACCESS     read-only
        STATUS         current
        DESCRIPTION    "The time at which the active or masked alarm
                        occurred, measured in total time ticks (seconds)
                        from the year 1970."
        ::= { tnActiveOrMaskedAlarmEntry 3 }

    tnActiveOrMaskedAlarmObjectIDType OBJECT-TYPE
        SYNTAX         Unsigned32
        MAX-ACCESS     read-only
        STATUS         current
        DESCRIPTION    "The type of Object ID associated with the active
                        or masked alarm."
        ::= { tnActiveOrMaskedAlarmEntry 4 }

    tnActiveOrMaskedAlarmObjectID OBJECT-TYPE
        SYNTAX         Unsigned32
        MAX-ACCESS     read-only
        STATUS         current
        DESCRIPTION    "The physical interface or service associated with
                        the active or masked alarm."
        ::= { tnActiveOrMaskedAlarmEntry 5 }

    tnActiveOrMaskedAlarmCategory OBJECT-TYPE
        SYNTAX         TnTrapCategory
        MAX-ACCESS     read-only
        STATUS         current
        DESCRIPTION    "The active or masked alarm's category."
        ::= { tnActiveOrMaskedAlarmEntry 6 }

    tnActiveOrMaskedAlarmDescr OBJECT-TYPE
        SYNTAX         SnmpAdminString (SIZE(0..255))
        MAX-ACCESS     read-only
        STATUS         current
        DESCRIPTION    "A detailed description of the active or masked
                        alarm."
        ::= { tnActiveOrMaskedAlarmEntry 7 }

    tnActiveOrMaskedAlarmData OBJECT-TYPE
        SYNTAX         SnmpAdminString (SIZE(0..255))
        MAX-ACCESS     read-only
        STATUS         current
        DESCRIPTION    "Any application specific data relevant to the
                        active or masked alarm.  This could be the value
                        of a changed attribute or any other formatted
                        information related to a notification."
        ::= { tnActiveOrMaskedAlarmEntry 8 }

    tnActiveOrMaskedAlarmServiceAffecting OBJECT-TYPE
        SYNTAX         TruthValue
        MAX-ACCESS     read-only
        STATUS         current
        DESCRIPTION    "An indication as to whether or not this active
                        or masked alarm is service affecting."
        ::= { tnActiveOrMaskedAlarmEntry 9 }

    tnActiveOrMaskedAlarmSlotProgrammedType OBJECT-TYPE
        SYNTAX         OBJECT IDENTIFIER
        MAX-ACCESS     read-only
        STATUS         current
        DESCRIPTION    "Type of card provisioned in the given slot.  If
                        tnActiveOrMaskedAlarmObjectID does not include
                        a slot, a value of 0.0 will be returned."
        ::= { tnActiveOrMaskedAlarmEntry 10 }

    tnActiveOrMaskedAlarmIsMasked OBJECT-TYPE
        SYNTAX         TruthValue
        MAX-ACCESS     read-only
        STATUS         current
        DESCRIPTION    "An indication as to whether or not this is a
                        masked alarm."
        ::= { tnActiveOrMaskedAlarmEntry 11 }

    tnActiveOrMaskedAlarmEntityType OBJECT-TYPE
        SYNTAX         TnEntityType
        MAX-ACCESS     read-only
        STATUS         current
        DESCRIPTION    "The entity type."
        ::= { tnActiveOrMaskedAlarmEntry 12 }

    tnActiveOrMaskedAlarmCondition OBJECT-TYPE
        SYNTAX         TnCondition
        MAX-ACCESS     read-only
        STATUS         current
        DESCRIPTION    "The condition."
        ::= { tnActiveOrMaskedAlarmEntry 13 }

-------------------------------------------------------------------
-- Not Alarmed Log Buffer Table
-------------------------------------------------------------------
    tnNotAlarmedLogBufferTable OBJECT-TYPE
        SYNTAX         SEQUENCE OF TnNotAlarmedLogBufferEntry
        MAX-ACCESS     not-accessible
        STATUS         current
        DESCRIPTION    "The warning log history table."
        ::= { tnLogQueues 11 }

    tnNotAlarmedLogBufferEntry OBJECT-TYPE
        SYNTAX         TnNotAlarmedLogBufferEntry
        MAX-ACCESS     not-accessible
        STATUS         current
        DESCRIPTION    "."
        INDEX { tnNotAlarmedLogSerialNumber }
        ::= { tnNotAlarmedLogBufferTable 1 }

    TnNotAlarmedLogBufferEntry ::=
        SEQUENCE {
            tnNotAlarmedLogSerialNumber               Unsigned32,
            tnNotAlarmedLogType                       OBJECT IDENTIFIER,
            tnNotAlarmedLogTime                       Unsigned32,
            tnNotAlarmedLogObjectIDType               Unsigned32,
            tnNotAlarmedLogObjectID                   Unsigned32,
            tnNotAlarmedLogDescr                      SnmpAdminString,
            tnNotAlarmedLogData                       SnmpAdminString,
            tnNotAlarmedLogServiceAffecting           TruthValue,
            tnNotAlarmedLogSlotProgrammedType         OBJECT IDENTIFIER,
            tnNotAlarmedLogEntityType                 TnEntityType,
            tnNotAlarmedLogCondition                  TnCondition,
            tnNotAlarmedLogObjectIDIpV6               InetAddress,
            tnNotAlarmedLogSlotProgrammedGenericType  SnmpAdminString
        }

    tnNotAlarmedLogSerialNumber OBJECT-TYPE
        SYNTAX         Unsigned32 (1..2147483647)
        MAX-ACCESS     not-accessible
        STATUS         current
        DESCRIPTION    "The independently incremented number associated
                        with the sequential ordering of incoming not
                        alarmed events."
        ::= { tnNotAlarmedLogBufferEntry 1 }

    tnNotAlarmedLogType OBJECT-TYPE
        SYNTAX         OBJECT IDENTIFIER
        MAX-ACCESS     read-only
        STATUS         current
        DESCRIPTION    "The OID of the not alarmed event ID."
        ::= { tnNotAlarmedLogBufferEntry 2 }

    tnNotAlarmedLogTime OBJECT-TYPE
        SYNTAX         Unsigned32
        MAX-ACCESS     read-only
        STATUS         current
        DESCRIPTION    "The time at which the not alarmed event occurred,
                        measured in total time ticks (seconds) from the
                        year 1970."
        ::= { tnNotAlarmedLogBufferEntry 3 }

    tnNotAlarmedLogObjectIDType OBJECT-TYPE
        SYNTAX         Unsigned32
        MAX-ACCESS     read-only
        STATUS         current
        DESCRIPTION    "The type of Object ID associated with the not
                        alarmed event."
        ::= { tnNotAlarmedLogBufferEntry 4 }

    tnNotAlarmedLogObjectID OBJECT-TYPE
        SYNTAX         Unsigned32
        MAX-ACCESS     read-only
        STATUS         current
        DESCRIPTION    "The physical interface or service associated with
                        the not alarmed event."
        ::= { tnNotAlarmedLogBufferEntry 5 }

    tnNotAlarmedLogDescr OBJECT-TYPE
        SYNTAX         SnmpAdminString (SIZE(0..255))
        MAX-ACCESS     read-only
        STATUS         current
        DESCRIPTION    "A detailed description of the not alarmed event."
        ::= { tnNotAlarmedLogBufferEntry 6 }

    tnNotAlarmedLogData OBJECT-TYPE
        SYNTAX         SnmpAdminString (SIZE(0..255))
        MAX-ACCESS     read-only
        STATUS         current
        DESCRIPTION    "Any application specific data relevant to the
                        not alarmed event.  This could be the value of
                        a changed attribute or any other formatted
                        information related to a notification."
        ::= { tnNotAlarmedLogBufferEntry 7 }

    tnNotAlarmedLogServiceAffecting OBJECT-TYPE
        SYNTAX         TruthValue
        MAX-ACCESS     read-only
        STATUS         current
        DESCRIPTION    "An indication as to whether or not this not alarmed
                        event is service affecting."
        ::= { tnNotAlarmedLogBufferEntry 8 }

    tnNotAlarmedLogSlotProgrammedType OBJECT-TYPE
        SYNTAX         OBJECT IDENTIFIER
        MAX-ACCESS     read-only
        STATUS         current
        DESCRIPTION    "Type of card provisioned in the given slot.  If
                        tnNotAlarmedLogObjectID does not include a slot,
                        a value of 0.0 will be returned."
        ::= { tnNotAlarmedLogBufferEntry 9 }

    tnNotAlarmedLogEntityType OBJECT-TYPE
        SYNTAX         TnEntityType
        MAX-ACCESS     read-only
        STATUS         current
        DESCRIPTION    "The entity type."
        ::= { tnNotAlarmedLogBufferEntry 10 }

    tnNotAlarmedLogCondition OBJECT-TYPE
        SYNTAX         TnCondition
        MAX-ACCESS     read-only
        STATUS         current
        DESCRIPTION    "The condition."
        ::= { tnNotAlarmedLogBufferEntry 11 }

    tnNotAlarmedLogObjectIDIpV6 OBJECT-TYPE
        SYNTAX         InetAddress
        MAX-ACCESS     read-only
        STATUS         current
        DESCRIPTION    "Denotes a generic Internet address."
        ::= { tnNotAlarmedLogBufferEntry 12 }

    tnNotAlarmedLogSlotProgrammedGenericType OBJECT-TYPE
        SYNTAX         SnmpAdminString (SIZE(0..255))
        MAX-ACCESS     read-only
        STATUS         current
        DESCRIPTION    "."
        ::= { tnNotAlarmedLogBufferEntry 13 }

-------------------------------------------------------------------
-- Security Log Buffer Table
-------------------------------------------------------------------
    tnSecurityLogBufferTable OBJECT-TYPE
        SYNTAX         SEQUENCE OF TnSecurityLogBufferEntry
        MAX-ACCESS     not-accessible
        STATUS         current
        DESCRIPTION    "The security log history table."
        ::= { tnLogQueues 12 }

    tnSecurityLogBufferEntry OBJECT-TYPE
        SYNTAX         TnSecurityLogBufferEntry
        MAX-ACCESS     not-accessible
        STATUS         current
        DESCRIPTION    "."
        INDEX { tnSecurityLogSerialNumber }
        ::= { tnSecurityLogBufferTable 1 }

    TnSecurityLogBufferEntry ::=
        SEQUENCE {
            tnSecurityLogSerialNumber              Unsigned32,
            tnSecurityLogType                      OBJECT IDENTIFIER,
            tnSecurityLogTime                      Unsigned32,
            tnSecurityLogObjectIDType              Unsigned32,
            tnSecurityLogObjectID                  Unsigned32,
            tnSecurityLogDescr                     SnmpAdminString,
            tnSecurityLogData                      SnmpAdminString,
            tnSecurityLogUserID                    SnmpAdminString,
            tnSecurityLogUserSessionNumber         Unsigned32,
            tnSecurityLogHeaderType                SnmpAdminString,
            tnSecurityLogUserPrivilege             INTEGER,
            tnSecurityLogUserDestinationAddress    IpAddress,
            tnSecurityLogResult                    INTEGER,
            tnSecurityLogObjectIDIpV6              InetAddress
       }

    tnSecurityLogSerialNumber OBJECT-TYPE
        SYNTAX         Unsigned32 (1..2147483647)
        MAX-ACCESS     not-accessible
        STATUS         current
        DESCRIPTION    "The independently incremented number associated
                        with the sequential ordering of incoming user
                        actions."
        ::= { tnSecurityLogBufferEntry 1 }

    tnSecurityLogType OBJECT-TYPE
        SYNTAX         OBJECT IDENTIFIER
        MAX-ACCESS     read-only
        STATUS         current
        DESCRIPTION    "The OID of the user action event ID."
        ::= { tnSecurityLogBufferEntry 2 }

    tnSecurityLogTime OBJECT-TYPE
        SYNTAX         Unsigned32
        MAX-ACCESS     read-only
        STATUS         current
        DESCRIPTION    "The time at which the user action occurred,
                        measured in total time ticks (seconds) from the
                        year 1970."
        ::= { tnSecurityLogBufferEntry 3 }

    tnSecurityLogObjectIDType OBJECT-TYPE
        SYNTAX         Unsigned32
        MAX-ACCESS     read-only
        STATUS         current
        DESCRIPTION    "The type of Object ID associated with the security
                        events."
        ::= { tnSecurityLogBufferEntry 4 }

    tnSecurityLogObjectID OBJECT-TYPE
        SYNTAX         Unsigned32
        MAX-ACCESS     read-only
        STATUS         current
        DESCRIPTION    "The physical interface or service associated with
                        the security events."
        ::= { tnSecurityLogBufferEntry 5 }

    tnSecurityLogDescr OBJECT-TYPE
        SYNTAX         SnmpAdminString (SIZE(0..255))
        MAX-ACCESS     read-only
        STATUS         current
        DESCRIPTION    "A detailed description of the security events."
        ::= { tnSecurityLogBufferEntry 6 }

    tnSecurityLogData OBJECT-TYPE
        SYNTAX         SnmpAdminString (SIZE(0..255))
        MAX-ACCESS     read-only
        STATUS         current
        DESCRIPTION    "Any application specific data relevant to the
                        user action.  This could be the value of a changed
                        attribute or any other formatted information
                        related to a notification."
        ::= { tnSecurityLogBufferEntry 7 }

    tnSecurityLogUserID OBJECT-TYPE
        SYNTAX         SnmpAdminString (SIZE(0..13))
        MAX-ACCESS     read-only
        STATUS         current
        DESCRIPTION    "User Identifier.  It specifies the user ID that
                        issued the logged event. In case of invalid login
                        attempt, this parameter shall contain the value
                        'NULL'."
        ::= { tnSecurityLogBufferEntry 8 }


    tnSecurityLogUserSessionNumber OBJECT-TYPE
        SYNTAX         Unsigned32
        MAX-ACCESS     read-only
        STATUS         current
        DESCRIPTION    "Session number.  It specifies the session number
                        where the logged event occurred."
        ::= { tnSecurityLogBufferEntry 9 }

    tnSecurityLogHeaderType OBJECT-TYPE
        SYNTAX         SnmpAdminString (SIZE(0..10))
        MAX-ACCESS     read-only
        STATUS         current
        DESCRIPTION    "Header type.  It specifies the interface to which
                        the logged event is related."
        ::= { tnSecurityLogBufferEntry 10 }

    tnSecurityLogUserPrivilege OBJECT-TYPE
        SYNTAX         INTEGER {
                     service(1),
                     administrator(2),
                     provisioner(3),
                     observer(4),
                     null(5),
                     crypto(6)
                   }
        MAX-ACCESS     read-only
        STATUS         current
        DESCRIPTION    "It specifies the access privileges of the user ID
                        that issued the logged event. In case of invalid
                        login attempt, this parameter shall contain the
                        value 'null'."
        ::= { tnSecurityLogBufferEntry 11 }

    tnSecurityLogUserDestinationAddress OBJECT-TYPE
        SYNTAX         IpAddress
        MAX-ACCESS     read-only
        STATUS         current
        DESCRIPTION    "Destination address is the IP/port address that
                        is being used for access.  There could be a number
                        of IP addresses for the NE, along with the ports
                        used (e.g., 22, 23, 3082, 3083, etc).  If a non
                        IP port is used to connect to the NE, one of the
                        values GCC, OSC, RS232 can be used.  This
                        parameter is required ONLY for login attempts.
                        Event is related."
        ::= { tnSecurityLogBufferEntry 12 }

    tnSecurityLogResult OBJECT-TYPE
        SYNTAX         INTEGER {
                         compld(1),
                         prtl(2),
                         deny(3),
                         other(4)
                       }
        MAX-ACCESS     read-only
        STATUS         current
        DESCRIPTION    "Completion Code for the logged event.  In case of
                        INTRUSION event, this parameter shall contain the
                        value 'other'."
        ::= { tnSecurityLogBufferEntry 13 }

    tnSecurityLogObjectIDIpV6 OBJECT-TYPE
        SYNTAX         InetAddress
        MAX-ACCESS     read-only
        STATUS         current
        DESCRIPTION    "Denotes a generic Internet address."
        ::= { tnSecurityLogBufferEntry 14 }

-------------------------------------------------------------------
-- Warning Alarm Log Buffer Table
-------------------------------------------------------------------
    tnWarningAlarmLogBufferTable OBJECT-TYPE
        SYNTAX         SEQUENCE OF TnWarningAlarmLogBufferEntry
        MAX-ACCESS     not-accessible
        STATUS         current
        DESCRIPTION    "The warning alarm log history table."
        ::= { tnLogQueues 13 }

    tnWarningAlarmLogBufferEntry OBJECT-TYPE
        SYNTAX         TnWarningAlarmLogBufferEntry
        MAX-ACCESS     not-accessible
        STATUS         current
        DESCRIPTION    "."
        INDEX { tnWarningAlarmLogSerialNumber }
        ::= { tnWarningAlarmLogBufferTable 1 }

    TnWarningAlarmLogBufferEntry ::=
        SEQUENCE {
            tnWarningAlarmLogSerialNumber                Unsigned32,
            tnWarningAlarmLogType                        OBJECT IDENTIFIER,
            tnWarningAlarmLogTime                        Unsigned32,
            tnWarningAlarmLogObjectIDType                Unsigned32,
            tnWarningAlarmLogObjectID                    Unsigned32,
            tnWarningAlarmLogDescr                       SnmpAdminString,
            tnWarningAlarmLogData                        SnmpAdminString,
            tnWarningAlarmLogServiceAffecting            TruthValue,
            tnWarningAlarmLogSlotProgrammedType          OBJECT IDENTIFIER,
            tnWarningAlarmLogEntityType                  TnEntityType,
            tnWarningAlarmLogCondition                   TnCondition,
            tnWarningAlarmLogObjectIDIpV6                InetAddress,
            tnWarningAlarmLogSlotProgrammedGenericType   SnmpAdminString
       }

    tnWarningAlarmLogSerialNumber OBJECT-TYPE
        SYNTAX         Unsigned32 (1..2147483647)
        MAX-ACCESS     not-accessible
        STATUS         current
        DESCRIPTION    "The independently incremented number associated with
                        the sequential ordering of incoming warning alarms."
        ::= { tnWarningAlarmLogBufferEntry 1 }

    tnWarningAlarmLogType OBJECT-TYPE
        SYNTAX         OBJECT IDENTIFIER
        MAX-ACCESS     read-only
        STATUS         current
        DESCRIPTION    "The OID of the warning alarm event ID."
        ::= { tnWarningAlarmLogBufferEntry 2 }

    tnWarningAlarmLogTime OBJECT-TYPE
        SYNTAX         Unsigned32
        MAX-ACCESS     read-only
        STATUS         current
        DESCRIPTION    "The time at which the warning alarm occurred,
                        measured in total time ticks (seconds) from the
                        year 1970."
        ::= { tnWarningAlarmLogBufferEntry 3 }

    tnWarningAlarmLogObjectIDType OBJECT-TYPE
        SYNTAX         Unsigned32
        MAX-ACCESS     read-only
        STATUS         current
        DESCRIPTION    "The type of Object ID associated with the warning
                        alarm."
        ::= { tnWarningAlarmLogBufferEntry 4 }

    tnWarningAlarmLogObjectID OBJECT-TYPE
        SYNTAX         Unsigned32
        MAX-ACCESS     read-only
        STATUS         current
        DESCRIPTION    "The physical interface or service associated with
                        the warning alarm."
        ::= { tnWarningAlarmLogBufferEntry 5 }

    tnWarningAlarmLogDescr OBJECT-TYPE
        SYNTAX         SnmpAdminString (SIZE(0..255))
        MAX-ACCESS     read-only
        STATUS         current
        DESCRIPTION    "A detailed description of the warning alarm."
        ::= { tnWarningAlarmLogBufferEntry 6 }

    tnWarningAlarmLogData OBJECT-TYPE
        SYNTAX         SnmpAdminString (SIZE(0..255))
        MAX-ACCESS     read-only
        STATUS         current
        DESCRIPTION    "Any application specific data relevant to the
                        warning alarm.  This could be the value of a
                        changed attribute or any other formatted
                        information related to a notification."
        ::= { tnWarningAlarmLogBufferEntry 7 }

    tnWarningAlarmLogServiceAffecting OBJECT-TYPE
        SYNTAX         TruthValue
        MAX-ACCESS     read-only
        STATUS         current
        DESCRIPTION    "An indication as to whether or not this warning
                        alarm is service affecting."
        ::= { tnWarningAlarmLogBufferEntry 8 }

    tnWarningAlarmLogSlotProgrammedType OBJECT-TYPE
        SYNTAX         OBJECT IDENTIFIER
        MAX-ACCESS     read-only
        STATUS         current
        DESCRIPTION    "Type of card provisioned in the given slot.  If
                        tnWarningAlarmLogObjectID does not include a slot,
                        a value of 0.0 will be returned."
        ::= { tnWarningAlarmLogBufferEntry 9 }

    tnWarningAlarmLogEntityType OBJECT-TYPE
        SYNTAX         TnEntityType
        MAX-ACCESS     read-only
        STATUS         current
        DESCRIPTION    "The entity type."
        ::= { tnWarningAlarmLogBufferEntry 10 }

    tnWarningAlarmLogCondition OBJECT-TYPE
        SYNTAX         TnCondition
        MAX-ACCESS     read-only
        STATUS         current
        DESCRIPTION    "The condition."
        ::= { tnWarningAlarmLogBufferEntry 11 }

    tnWarningAlarmLogObjectIDIpV6 OBJECT-TYPE
        SYNTAX         InetAddress
        MAX-ACCESS     read-only
        STATUS         current
        DESCRIPTION    "Denotes a generic Internet address."
        ::= { tnWarningAlarmLogBufferEntry 12 }

    tnWarningAlarmLogSlotProgrammedGenericType OBJECT-TYPE
        SYNTAX         SnmpAdminString (SIZE(0..255))
        MAX-ACCESS     read-only
        STATUS         current
        DESCRIPTION    "."
        ::= { tnWarningAlarmLogBufferEntry 13 }

-------------------------------------------------------------------
-- Active Alarm Info Table
-------------------------------------------------------------------
    tnActiveAlarmInfoTable OBJECT-TYPE
        SYNTAX         SEQUENCE OF TnActiveAlarmInfoEntry
        MAX-ACCESS     not-accessible
        STATUS         current
        DESCRIPTION    "."
        ::= { tnLogQueues 14 }

    tnActiveAlarmInfoEntry OBJECT-TYPE
        SYNTAX         TnActiveAlarmInfoEntry
        MAX-ACCESS     not-accessible
        STATUS         current
        DESCRIPTION    "."
        INDEX { tnActiveAlarmSerialNumber }
        ::= { tnActiveAlarmInfoTable 1 }

    TnActiveAlarmInfoEntry ::=
        SEQUENCE {
            tnActiveAlarmInfoData     SnmpAdminString
        }

    tnActiveAlarmInfoData OBJECT-TYPE
        SYNTAX         SnmpAdminString (SIZE(0..1024))
        MAX-ACCESS     read-only
        STATUS         current
        DESCRIPTION    "."
        ::= { tnActiveAlarmInfoEntry 1 }

-------------------------------------------------------------------
-- Alarm Category Config Tables
-------------------------------------------------------------------

-------------------------------------------------------------------
-- Per Object Alarm Category Config Table
-------------------------------------------------------------------
    tnPerObjectAlarmCategoryConfigTable OBJECT-TYPE
        SYNTAX         SEQUENCE OF TnPerObjectAlarmCategoryConfigEntry
        MAX-ACCESS     not-accessible
        STATUS         current
        DESCRIPTION    "."
        ::= { tnLogAlarmCategoryConfig 1 }

    tnPerObjectAlarmCategoryConfigEntry OBJECT-TYPE
        SYNTAX         TnPerObjectAlarmCategoryConfigEntry
        MAX-ACCESS     not-accessible
        STATUS         current
        DESCRIPTION    "."
        INDEX { tnAlarmCategoryObjectId,
                tnAlarmCategoryEntityType,
                tnAlarmCategoryCondition }
        ::= { tnPerObjectAlarmCategoryConfigTable 1 }

    TnPerObjectAlarmCategoryConfigEntry ::=
        SEQUENCE {
            tnAlarmCategoryObjectId            Unsigned32,
            tnAlarmCategoryEntityType          TnEntityType,
            tnAlarmCategoryCondition           TnCondition,
            tnPerObjectAlarmCategory           TnTrapCategory,
            tnPerObjectAlarmEntityTypeCategory TnTrapCategory,
            tnPerObjectAlarmDefaultCategory    TnTrapCategory
        }

    tnAlarmCategoryObjectId OBJECT-TYPE
        SYNTAX         Unsigned32
        MAX-ACCESS     not-accessible
        STATUS         current
        DESCRIPTION    "One of the following physical object instances:

                        NE
                        shelf
                        shelf/slot
                        shelf/slot/port
                        shelf/slot/port/direction."
        ::= { tnPerObjectAlarmCategoryConfigEntry 1 }

    tnAlarmCategoryEntityType OBJECT-TYPE
        SYNTAX         TnEntityType
        MAX-ACCESS     not-accessible
        STATUS         current
        DESCRIPTION    "The AID type."
        ::= { tnPerObjectAlarmCategoryConfigEntry 2 }

    tnAlarmCategoryCondition OBJECT-TYPE
        SYNTAX         TnCondition
        MAX-ACCESS     not-accessible
        STATUS         current
        DESCRIPTION    "The condition."
        ::= { tnPerObjectAlarmCategoryConfigEntry 3 }

    tnPerObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerObjectAlarmCategoryConfigEntry 4 }

    tnPerObjectAlarmEntityTypeCategory OBJECT-TYPE
        SYNTAX         TnTrapCategory
        MAX-ACCESS     read-only
        STATUS         current
        DESCRIPTION    "The entity type category."
        ::= { tnPerObjectAlarmCategoryConfigEntry 5 }

    tnPerObjectAlarmDefaultCategory OBJECT-TYPE
        SYNTAX         TnTrapCategory
        MAX-ACCESS     read-only
        STATUS         current
        DESCRIPTION    "The default category."
        ::= { tnPerObjectAlarmCategoryConfigEntry 6 }

-------------------------------------------------------------------
-- Alarm Profile Config Table
-------------------------------------------------------------------
    tnAlarmProfileConfigTable OBJECT-TYPE
        SYNTAX         SEQUENCE OF TnAlarmProfileConfigEntry
        MAX-ACCESS     not-accessible
        STATUS         current
        DESCRIPTION    "."
        ::= { tnLogAlarmCategoryConfig 2 }

    tnAlarmProfileConfigEntry OBJECT-TYPE
        SYNTAX         TnAlarmProfileConfigEntry
        MAX-ACCESS     not-accessible
        STATUS         current
        DESCRIPTION    "."
        INDEX { tnAlarmCategoryEntityType,
                tnAlarmCategoryCondition,
                tnAlarmCategoryDirection }
        ::= { tnAlarmProfileConfigTable 1 }

    TnAlarmProfileConfigEntry ::=
        SEQUENCE {
            tnAlarmCategoryDirection             AluWdmAlarmCategoryDirection,
            tnAlarmProfileConfigCategory         TnTrapCategory,
            tnAlarmProfileConfigDefaultCategory  TnTrapCategory,
            tnAlarmProfileConfigDescr            SnmpAdminString
        }

    tnAlarmCategoryDirection OBJECT-TYPE
        SYNTAX         AluWdmAlarmCategoryDirection
        MAX-ACCESS     not-accessible
        STATUS         current
        DESCRIPTION    "The direction to which the new category will be
                        applied."
        ::= { tnAlarmProfileConfigEntry 1 }

    tnAlarmProfileConfigCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)"
        ::= { tnAlarmProfileConfigEntry 2 }

    tnAlarmProfileConfigDefaultCategory OBJECT-TYPE
        SYNTAX         TnTrapCategory
        MAX-ACCESS     read-only
        STATUS         current
        DESCRIPTION    "The default category."
        ::= { tnAlarmProfileConfigEntry 3 }

    tnAlarmProfileConfigDescr OBJECT-TYPE
        SYNTAX         SnmpAdminString (SIZE(0..255))
        MAX-ACCESS     read-only
        STATUS         current
        DESCRIPTION    "A detailed description of entity type and
                        condition."
        ::= { tnAlarmProfileConfigEntry 4 }

--    obsolete
--    tnPerLogicObjectAlarmCategoryConfigTable OBJECT-TYPE ::= { tnLogAlarmCategoryConfig 3 }

-------------------------------------------------------------------
-- Per Sync Object Alarm Category Config Table
-------------------------------------------------------------------
    tnPerSyncObjectAlarmCategoryConfigTable OBJECT-TYPE
        SYNTAX         SEQUENCE OF TnPerSyncObjectAlarmCategoryConfigEntry
        MAX-ACCESS     not-accessible
        STATUS         current
        DESCRIPTION    "."
        ::= { tnLogAlarmCategoryConfig 4 }

    tnPerSyncObjectAlarmCategoryConfigEntry OBJECT-TYPE
        SYNTAX         TnPerSyncObjectAlarmCategoryConfigEntry
        MAX-ACCESS     not-accessible
        STATUS         current
        DESCRIPTION    "."
        INDEX { tnSyncAlarmCategoryObjectId,
                tnSyncAlarmCategoryEntityType,
                tnSyncAlarmCategoryCondition }
        ::= { tnPerSyncObjectAlarmCategoryConfigTable 1 }

    TnPerSyncObjectAlarmCategoryConfigEntry ::=
        SEQUENCE {
            tnSyncAlarmCategoryObjectId             Unsigned32,
            tnSyncAlarmCategoryEntityType           TnEntityType,
            tnSyncAlarmCategoryCondition            TnCondition,
            tnPerSyncObjectAlarmCategory            TnTrapCategory,
            tnPerSyncObjectAlarmEntityTypeCategory  TnTrapCategory,
            tnPerSyncObjectAlarmDefaultCategory     TnTrapCategory
        }

    tnSyncAlarmCategoryObjectId OBJECT-TYPE
        SYNTAX         Unsigned32
        MAX-ACCESS     not-accessible
        STATUS         current
        DESCRIPTION    "One of the following Sync object instances:
                        - shelf/slot/0/direction which means sync
                          objectId.
                        - shelf/slot/LineRef/direction which means
                          lineRef objectId.
                        - shelf/slot/100/direction which means syncOut
                          objectId.
                        direction should be none(0), TX(1), or RX(2)."
        ::= { tnPerSyncObjectAlarmCategoryConfigEntry 1 }

    tnSyncAlarmCategoryEntityType OBJECT-TYPE
        SYNTAX         TnEntityType
        MAX-ACCESS     not-accessible
        STATUS         current
        DESCRIPTION    "The AID type."
        ::= { tnPerSyncObjectAlarmCategoryConfigEntry 2 }

    tnSyncAlarmCategoryCondition OBJECT-TYPE
        SYNTAX         TnCondition
        MAX-ACCESS     not-accessible
        STATUS         current
        DESCRIPTION    "The condition."
        ::= { tnPerSyncObjectAlarmCategoryConfigEntry 3 }

    tnPerSyncObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerSyncObjectAlarmCategoryConfigEntry 4 }

    tnPerSyncObjectAlarmEntityTypeCategory OBJECT-TYPE
        SYNTAX         TnTrapCategory
        MAX-ACCESS     read-only
        STATUS         current
        DESCRIPTION    "The entity type category."
        ::= { tnPerSyncObjectAlarmCategoryConfigEntry 5 }

    tnPerSyncObjectAlarmDefaultCategory OBJECT-TYPE
        SYNTAX         TnTrapCategory
        MAX-ACCESS     read-only
        STATUS         current
        DESCRIPTION    "The default category."
        ::= { tnPerSyncObjectAlarmCategoryConfigEntry 6 }

--------------------------------------------------------------------------------
-- Per VTS Object Alarm Category Config Scalar
--------------------------------------------------------------------------------
    tnPerVtsObjectAlarmCategoryConfigAttributeTotal OBJECT-TYPE
        SYNTAX         Integer32
        MAX-ACCESS     read-only
        STATUS         current
        DESCRIPTION    "."
        ::= { tnLogAlarmCategoryConfig 5 }

-------------------------------------------------------------------
-- Per VTS Object Alarm Category Config Table
-------------------------------------------------------------------
    tnPerVtsObjectAlarmCategoryConfigTable OBJECT-TYPE
        SYNTAX         SEQUENCE OF TnPerVtsObjectAlarmCategoryConfigEntry
        MAX-ACCESS     not-accessible
        STATUS         current
        DESCRIPTION    "."
        ::= { tnLogAlarmCategoryConfig 6 }

    tnPerVtsObjectAlarmCategoryConfigEntry OBJECT-TYPE
        SYNTAX         TnPerVtsObjectAlarmCategoryConfigEntry
        MAX-ACCESS     not-accessible
        STATUS         current
        DESCRIPTION    "."
        INDEX { tnVtsAlarmCategoryObjectId,
                tnVtsAlarmCategoryDirection,
                tnVtsAlarmCategoryEntityType,
                tnVtsAlarmCategoryCondition }
        ::= { tnPerVtsObjectAlarmCategoryConfigTable 1 }

    TnPerVtsObjectAlarmCategoryConfigEntry ::=
        SEQUENCE {
            tnVtsAlarmCategoryObjectId             Unsigned32,
            tnVtsAlarmCategoryDirection            AluWdmAlarmCategoryDirection,
            tnVtsAlarmCategoryEntityType           TnEntityType,
            tnVtsAlarmCategoryCondition            TnCondition,
            tnPerVtsObjectAlarmCategory            TnTrapCategory,
            tnPerVtsObjectAlarmEntityTypeCategory  TnTrapCategory,
            tnPerVtsObjectAlarmDefaultCategory     TnTrapCategory
        }

    tnVtsAlarmCategoryObjectId OBJECT-TYPE
        SYNTAX         Unsigned32
        MAX-ACCESS     not-accessible
        STATUS         current
        DESCRIPTION    "The format for a VTS object instance is
                        shelf/slot/port/vts (1 byte each)."
        ::= { tnPerVtsObjectAlarmCategoryConfigEntry 1 }

    tnVtsAlarmCategoryDirection OBJECT-TYPE
        SYNTAX         AluWdmAlarmCategoryDirection
        MAX-ACCESS     not-accessible
        STATUS         current
        DESCRIPTION    "The direction to which the new category will be
                        applied."
        ::= { tnPerVtsObjectAlarmCategoryConfigEntry 2 }

    tnVtsAlarmCategoryEntityType OBJECT-TYPE
        SYNTAX         TnEntityType
        MAX-ACCESS     not-accessible
        STATUS         current
        DESCRIPTION    "The AID type."
        ::= { tnPerVtsObjectAlarmCategoryConfigEntry 3 }

    tnVtsAlarmCategoryCondition OBJECT-TYPE
        SYNTAX         TnCondition
        MAX-ACCESS     not-accessible
        STATUS         current
        DESCRIPTION    "The condition."
        ::= { tnPerVtsObjectAlarmCategoryConfigEntry 4 }

    tnPerVtsObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerVtsObjectAlarmCategoryConfigEntry 5 }

    tnPerVtsObjectAlarmEntityTypeCategory OBJECT-TYPE
        SYNTAX         TnTrapCategory
        MAX-ACCESS     read-only
        STATUS         current
        DESCRIPTION    "The entity type category."
        ::= { tnPerVtsObjectAlarmCategoryConfigEntry 6 }

    tnPerVtsObjectAlarmDefaultCategory OBJECT-TYPE
        SYNTAX         TnTrapCategory
        MAX-ACCESS     read-only
        STATUS         current
        DESCRIPTION    "The default category."
        ::= { tnPerVtsObjectAlarmCategoryConfigEntry 7 }

--------------------------------------------------------------------------------
-- Per CCM Object Alarm Category Config Scalar
--------------------------------------------------------------------------------
    tnPerCcmObjectAlarmCategoryConfigAttributeTotal OBJECT-TYPE
        SYNTAX         Integer32
        MAX-ACCESS     read-only
        STATUS         current
        DESCRIPTION    "."
        ::= { tnLogAlarmCategoryConfig 7 }

-------------------------------------------------------------------
-- Per CCM Object Alarm Category Config Table
-------------------------------------------------------------------
    tnPerCcmObjectAlarmCategoryConfigTable OBJECT-TYPE
        SYNTAX         SEQUENCE OF TnPerCcmObjectAlarmCategoryConfigEntry
        MAX-ACCESS     not-accessible
        STATUS         current
        DESCRIPTION    "."
        ::= { tnLogAlarmCategoryConfig 8 }

    tnPerCcmObjectAlarmCategoryConfigEntry OBJECT-TYPE
        SYNTAX         TnPerCcmObjectAlarmCategoryConfigEntry
        MAX-ACCESS     not-accessible
        STATUS         current
        DESCRIPTION    "."
        INDEX { tnCcmAlarmCategoryObjectId,
                tnCcmAlarmCategoryTribObjectId,
                tnCcmAlarmCategoryEntityType,
                tnCcmAlarmCategoryCondition }
        ::= { tnPerCcmObjectAlarmCategoryConfigTable 1 }

    TnPerCcmObjectAlarmCategoryConfigEntry ::=
        SEQUENCE {
            tnCcmAlarmCategoryObjectId             Unsigned32,
            tnCcmAlarmCategoryTribObjectId         Unsigned32,
            tnCcmAlarmCategoryEntityType           TnEntityType,
            tnCcmAlarmCategoryCondition            TnCondition,
            tnPerCcmObjectAlarmCategory            TnTrapCategory,
            tnPerCcmObjectAlarmEntityTypeCategory  TnTrapCategory,
            tnPerCcmObjectAlarmDefaultCategory     TnTrapCategory
        }

    tnCcmAlarmCategoryObjectId OBJECT-TYPE
        SYNTAX         Unsigned32
        MAX-ACCESS     not-accessible
        STATUS         current
        DESCRIPTION    "The format for a CCM object instance is
                        shelf/slot/md/ma (shelf 1 byte,slot 1 byte, md
                        5 bits ,ma 11 bits)."
        ::= { tnPerCcmObjectAlarmCategoryConfigEntry 1 }

    tnCcmAlarmCategoryTribObjectId OBJECT-TYPE
        SYNTAX         Unsigned32
        MAX-ACCESS     not-accessible
        STATUS         current
        DESCRIPTION    "The format for a CCM object instance is
                        mepid/direction/00 (mepid 2 bytes,direction 1 byte)."
        ::= { tnPerCcmObjectAlarmCategoryConfigEntry 2 }

    tnCcmAlarmCategoryEntityType OBJECT-TYPE
        SYNTAX         TnEntityType
        MAX-ACCESS     not-accessible
        STATUS         current
        DESCRIPTION    "The AID type."
        ::= { tnPerCcmObjectAlarmCategoryConfigEntry 3 }

    tnCcmAlarmCategoryCondition OBJECT-TYPE
        SYNTAX         TnCondition
        MAX-ACCESS     not-accessible
        STATUS         current
        DESCRIPTION    "The condition."
        ::= { tnPerCcmObjectAlarmCategoryConfigEntry 4 }

    tnPerCcmObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerCcmObjectAlarmCategoryConfigEntry 5 }

    tnPerCcmObjectAlarmEntityTypeCategory OBJECT-TYPE
        SYNTAX         TnTrapCategory
        MAX-ACCESS     read-only
        STATUS         current
        DESCRIPTION    "The entity type category."
        ::= { tnPerCcmObjectAlarmCategoryConfigEntry 6 }

    tnPerCcmObjectAlarmDefaultCategory OBJECT-TYPE
        SYNTAX         TnTrapCategory
        MAX-ACCESS     read-only
        STATUS         current
        DESCRIPTION    "The default category."
        ::= { tnPerCcmObjectAlarmCategoryConfigEntry 7 }

--------------------------------------------------------------------------------
-- Per TCM Object Alarm Category Config Scalar
--------------------------------------------------------------------------------
    tnPerTcmObjectAlarmCategoryConfigAttributeTotal OBJECT-TYPE
        SYNTAX         Integer32
        MAX-ACCESS     read-only
        STATUS         current
        DESCRIPTION    "."
        ::= { tnLogAlarmCategoryConfig 9 }

-------------------------------------------------------------------
-- Per TCM Object Alarm Category Config Table
-------------------------------------------------------------------
    tnPerTcmObjectAlarmCategoryConfigTable OBJECT-TYPE
        SYNTAX         SEQUENCE OF TnPerTcmObjectAlarmCategoryConfigEntry
        MAX-ACCESS     not-accessible
        STATUS         current
        DESCRIPTION    "."
        ::= { tnLogAlarmCategoryConfig 10 }

    tnPerTcmObjectAlarmCategoryConfigEntry OBJECT-TYPE
        SYNTAX         TnPerTcmObjectAlarmCategoryConfigEntry
        MAX-ACCESS     not-accessible
        STATUS         current
        DESCRIPTION    "."
        INDEX { tnTcmAlarmCategoryObjectId,
                tnTcmAlarmCategoryTribObjectId,
                tnTcmAlarmCategoryEntityType,
                tnTcmAlarmCategoryCondition }
        ::= { tnPerTcmObjectAlarmCategoryConfigTable 1 }

    TnPerTcmObjectAlarmCategoryConfigEntry ::=
        SEQUENCE {
            tnTcmAlarmCategoryObjectId             Unsigned32,
            tnTcmAlarmCategoryTribObjectId         Unsigned32,
            tnTcmAlarmCategoryEntityType           TnEntityType,
            tnTcmAlarmCategoryCondition            TnCondition,
            tnPerTcmObjectAlarmCategory            TnTrapCategory,
            tnPerTcmObjectAlarmEntityTypeCategory  TnTrapCategory,
            tnPerTcmObjectAlarmDefaultCategory     TnTrapCategory
        }

    tnTcmAlarmCategoryObjectId OBJECT-TYPE
        SYNTAX         Unsigned32
        MAX-ACCESS     not-accessible
        STATUS         current
        DESCRIPTION    "

            ------------------------------------------------------
            | Bit31-Bit24 | Bit23-Bit16 | Bit15-Bit3 | Bit2-Bit0 |
            --------------+-------------+------------+------------
            | 8 bits      | 8 bits      | 13 bits    | 3 bits    |
            --------------+-------------+------------+------------
            | shelf       | slot        | HO-ODU     | Reserved  |
            |             |             | Number     | as 0      |
            ------------------------------------------------------
                       "
        ::= { tnPerTcmObjectAlarmCategoryConfigEntry 1 }

    tnTcmAlarmCategoryTribObjectId OBJECT-TYPE
        SYNTAX         Unsigned32
        MAX-ACCESS     not-accessible
        STATUS         current
        DESCRIPTION    "

            ---------------------------------------------------------
            | Bit31-Bit23 | Bit22-Bit18 | Bit17-Bit16 | Bit15-Bit10 |
            --------------+-------------+-------------+-------------+
            | 9 bits      | 5 bits      | 2 bits      | 6 bits      |
            --------------+-------------+---------------+-----------+
            | LO-ODU ID   | HO-ODU      | Reserved    | Container   |
            |             | ODU Type    |             | Type        |
            ---------------------------------------------------------

            ------------------------------------------
            | Bit9-Bit7 | Bit6-Bit5     | Bit4-Bit0 |
            ------------+---------------+-----------+
            | 3 bits    | 2 bits        | 5 bits    |
            ------------+---------------+------------
            | TCM Level | TCM Direction | LO-ODU    |
            | (1-6)     | (AM=1, BM=2)  | ODU Type  |
            -----------------------------------------
                       "
        ::= { tnPerTcmObjectAlarmCategoryConfigEntry 2 }

    tnTcmAlarmCategoryEntityType OBJECT-TYPE
        SYNTAX         TnEntityType
        MAX-ACCESS     not-accessible
        STATUS         current
        DESCRIPTION    "The AID type."
        ::= { tnPerTcmObjectAlarmCategoryConfigEntry 3 }

    tnTcmAlarmCategoryCondition OBJECT-TYPE
        SYNTAX         TnCondition
        MAX-ACCESS     not-accessible
        STATUS         current
        DESCRIPTION    "The condition."
        ::= { tnPerTcmObjectAlarmCategoryConfigEntry 4 }

    tnPerTcmObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerTcmObjectAlarmCategoryConfigEntry 5 }

    tnPerTcmObjectAlarmEntityTypeCategory OBJECT-TYPE
        SYNTAX         TnTrapCategory
        MAX-ACCESS     read-only
        STATUS         current
        DESCRIPTION    "The entity type category."
        ::= { tnPerTcmObjectAlarmCategoryConfigEntry 6 }

    tnPerTcmObjectAlarmDefaultCategory OBJECT-TYPE
        SYNTAX         TnTrapCategory
        MAX-ACCESS     read-only
        STATUS         current
        DESCRIPTION    "The default category."
        ::= { tnPerTcmObjectAlarmCategoryConfigEntry 7 }

--------------------------------------------------------------------------------
-- Per PTP Object Alarm Category Config Scalar
--------------------------------------------------------------------------------
    tnPerPtpObjectAlarmCategoryConfigAttributeTotal OBJECT-TYPE
        SYNTAX         Integer32
        MAX-ACCESS     read-only
        STATUS         current
        DESCRIPTION    "."
        ::= { tnLogAlarmCategoryConfig 11 }

-------------------------------------------------------------------
-- Per PTP Object Alarm Category Config Table
-------------------------------------------------------------------
    tnPerPtpObjectAlarmCategoryConfigTable OBJECT-TYPE
        SYNTAX         SEQUENCE OF TnPerPtpObjectAlarmCategoryConfigEntry
        MAX-ACCESS     not-accessible
        STATUS         current
        DESCRIPTION    "."
        ::= { tnLogAlarmCategoryConfig 12 }

    tnPerPtpObjectAlarmCategoryConfigEntry OBJECT-TYPE
        SYNTAX         TnPerPtpObjectAlarmCategoryConfigEntry
        MAX-ACCESS     not-accessible
        STATUS         current
        DESCRIPTION    "."
        INDEX { tnPtpAlarmCategoryObjectId,
                tnPtpAlarmCategoryDirection,
                tnPtpAlarmCategoryEntityType,
                tnPtpAlarmCategoryCondition }
        ::= { tnPerPtpObjectAlarmCategoryConfigTable 1 }

    TnPerPtpObjectAlarmCategoryConfigEntry ::=
        SEQUENCE {
            tnPtpAlarmCategoryObjectId             Unsigned32,
            tnPtpAlarmCategoryDirection            AluWdmAlarmCategoryDirection,
            tnPtpAlarmCategoryEntityType           TnEntityType,
            tnPtpAlarmCategoryCondition            TnCondition,
            tnPerPtpObjectAlarmCategory            TnTrapCategory,
            tnPerPtpObjectAlarmEntityTypeCategory  TnTrapCategory,
            tnPerPtpObjectAlarmDefaultCategory     TnTrapCategory
        }

    tnPtpAlarmCategoryObjectId OBJECT-TYPE
        SYNTAX         Unsigned32
        MAX-ACCESS     not-accessible
        STATUS         current
        DESCRIPTION    "The format for a PTP object instance is
                        shelf/slot//ptpclock/ptpport/direction:
                          shelf:     1 byte;
                          slot:      1 byte;
                          ptpclock:  3 bits;
                          ptpport:  13 bits).
                        - ptpport equals to 0 for ptpclock objectId.
                        - ptpport not equals to 0 for ptpport objectId."
        ::= { tnPerPtpObjectAlarmCategoryConfigEntry 1 }

    tnPtpAlarmCategoryDirection OBJECT-TYPE
        SYNTAX         AluWdmAlarmCategoryDirection
        MAX-ACCESS     not-accessible
        STATUS         current
        DESCRIPTION    "The direction to which the new category will be
                        applied."
        ::= { tnPerPtpObjectAlarmCategoryConfigEntry 2 }

    tnPtpAlarmCategoryEntityType OBJECT-TYPE
        SYNTAX         TnEntityType
        MAX-ACCESS     not-accessible
        STATUS         current
        DESCRIPTION    "The AID type."
        ::= { tnPerPtpObjectAlarmCategoryConfigEntry 3 }

    tnPtpAlarmCategoryCondition OBJECT-TYPE
        SYNTAX         TnCondition
        MAX-ACCESS     not-accessible
        STATUS         current
        DESCRIPTION    "The condition."
        ::= { tnPerPtpObjectAlarmCategoryConfigEntry 4 }

    tnPerPtpObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerPtpObjectAlarmCategoryConfigEntry 5 }

    tnPerPtpObjectAlarmEntityTypeCategory OBJECT-TYPE
        SYNTAX         TnTrapCategory
        MAX-ACCESS     read-only
        STATUS         current
        DESCRIPTION    "The entity type category."
        ::= { tnPerPtpObjectAlarmCategoryConfigEntry 6 }

    tnPerPtpObjectAlarmDefaultCategory OBJECT-TYPE
        SYNTAX         TnTrapCategory
        MAX-ACCESS     read-only
        STATUS         current
        DESCRIPTION    "The default category."
        ::= { tnPerPtpObjectAlarmCategoryConfigEntry 7 }

--------------------------------------------------------------------------------
-- Per LAG Object Alarm Category Config Scalar
--------------------------------------------------------------------------------
    tnPerLagObjectAlarmCategoryConfigAttributeTotal OBJECT-TYPE
        SYNTAX         Integer32
        MAX-ACCESS     read-only
        STATUS         current
        DESCRIPTION    "."
        ::= { tnLogAlarmCategoryConfig 13 }

-------------------------------------------------------------------
-- Per LAG Object Alarm Category Config Table
-------------------------------------------------------------------
    tnPerLagObjectAlarmCategoryConfigTable OBJECT-TYPE
        SYNTAX         SEQUENCE OF TnPerLagObjectAlarmCategoryConfigEntry
        MAX-ACCESS     not-accessible
        STATUS         current
        DESCRIPTION    "."
        ::= { tnLogAlarmCategoryConfig 14 }

    tnPerLagObjectAlarmCategoryConfigEntry OBJECT-TYPE
        SYNTAX         TnPerLagObjectAlarmCategoryConfigEntry
        MAX-ACCESS     not-accessible
        STATUS         current
        DESCRIPTION    "."
        INDEX { tnLagAlarmCategoryObjectId,
                tnLagAlarmCategoryDirection,
                tnLagAlarmCategoryEntityType,
                tnLagAlarmCategoryCondition }
        ::= { tnPerLagObjectAlarmCategoryConfigTable 1 }

    TnPerLagObjectAlarmCategoryConfigEntry ::=
        SEQUENCE {
            tnLagAlarmCategoryObjectId             Unsigned32,
            tnLagAlarmCategoryDirection            AluWdmAlarmCategoryDirection,
            tnLagAlarmCategoryEntityType           TnEntityType,
            tnLagAlarmCategoryCondition            TnCondition,
            tnPerLagObjectAlarmCategory            TnTrapCategory,
            tnPerLagObjectAlarmEntityTypeCategory  TnTrapCategory,
            tnPerLagObjectAlarmDefaultCategory     TnTrapCategory
        }

    tnLagAlarmCategoryObjectId OBJECT-TYPE
        SYNTAX         Unsigned32
        MAX-ACCESS     not-accessible
        STATUS         current
        DESCRIPTION    "The format for a LAG object instance is
                        shelf/slot/lagIndex:
                          shelf:     1 byte;
                          slot:      1 byte;
                          lagIndex:  1 byte, (1..240)."
        ::= { tnPerLagObjectAlarmCategoryConfigEntry 1 }

    tnLagAlarmCategoryDirection OBJECT-TYPE
        SYNTAX         AluWdmAlarmCategoryDirection
        MAX-ACCESS     not-accessible
        STATUS         current
        DESCRIPTION    "The direction to which the new category will be
                        applied."
        ::= { tnPerLagObjectAlarmCategoryConfigEntry 2 }

    tnLagAlarmCategoryEntityType OBJECT-TYPE
        SYNTAX         TnEntityType
        MAX-ACCESS     not-accessible
        STATUS         current
        DESCRIPTION    "The AID type."
        ::= { tnPerLagObjectAlarmCategoryConfigEntry 3 }

    tnLagAlarmCategoryCondition OBJECT-TYPE
        SYNTAX         TnCondition
        MAX-ACCESS     not-accessible
        STATUS         current
        DESCRIPTION    "The condition."
        ::= { tnPerLagObjectAlarmCategoryConfigEntry 4 }

    tnPerLagObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerLagObjectAlarmCategoryConfigEntry 5 }

    tnPerLagObjectAlarmEntityTypeCategory OBJECT-TYPE
        SYNTAX         TnTrapCategory
        MAX-ACCESS     read-only
        STATUS         current
        DESCRIPTION    "The entity type category."
        ::= { tnPerLagObjectAlarmCategoryConfigEntry 6 }

    tnPerLagObjectAlarmDefaultCategory OBJECT-TYPE
        SYNTAX         TnTrapCategory
        MAX-ACCESS     read-only
        STATUS         current
        DESCRIPTION    "The default category."
        ::= { tnPerLagObjectAlarmCategoryConfigEntry 7 }

--------------------------------------------------------------------------------
-- Per OTN Object Alarm Category Config Scalar
--------------------------------------------------------------------------------
    tnPerOtnObjectAlarmCategoryConfigAttributeTotal OBJECT-TYPE
        SYNTAX         Integer32
        MAX-ACCESS     read-only
        STATUS         deprecated
        DESCRIPTION    "."
        ::= { tnLogAlarmCategoryConfig 15 }

-------------------------------------------------------------------
-- Per OTN Object Alarm Category Config Table
-------------------------------------------------------------------
    tnPerOtnObjectAlarmCategoryConfigTable OBJECT-TYPE
        SYNTAX         SEQUENCE OF TnPerOtnObjectAlarmCategoryConfigEntry
        MAX-ACCESS     not-accessible
        STATUS         deprecated
        DESCRIPTION    "."
        ::= { tnLogAlarmCategoryConfig 16 }

    tnPerOtnObjectAlarmCategoryConfigEntry OBJECT-TYPE
        SYNTAX         TnPerOtnObjectAlarmCategoryConfigEntry
        MAX-ACCESS     not-accessible
        STATUS         deprecated
        DESCRIPTION    "."
        INDEX { tnOtnAlarmCategoryObjectId,
                tnOtnAlarmCategoryTribObjectId,
                tnOtnAlarmCategoryEntityType,
                tnOtnAlarmCategoryCondition }
        ::= { tnPerOtnObjectAlarmCategoryConfigTable 1 }

    TnPerOtnObjectAlarmCategoryConfigEntry ::=
        SEQUENCE {
            tnOtnAlarmCategoryObjectId             Unsigned32,
            tnOtnAlarmCategoryTribObjectId         Unsigned32,
            tnOtnAlarmCategoryEntityType           TnEntityType,
            tnOtnAlarmCategoryCondition            TnCondition,
            tnPerOtnObjectAlarmCategory            TnTrapCategory,
            tnPerOtnObjectAlarmEntityTypeCategory  TnTrapCategory,
            tnPerOtnObjectAlarmDefaultCategory     TnTrapCategory
        }

    tnOtnAlarmCategoryObjectId OBJECT-TYPE
        SYNTAX         Unsigned32
        MAX-ACCESS     not-accessible
        STATUS         deprecated
        DESCRIPTION    "

            ------------------------------------------------------
            | Bit31-Bit24 | Bit23-Bit16 | Bit15-Bit3 | Bit2-Bit0 |
            --------------+-------------+------------+------------
            | 8 bits      | 8 bits      | 13 bits    | 3 bits    |
            --------------+-------------+------------+------------
            | shelf       | slot        | HO-ODU     | Direction |
            |             |             | Number     |           |
            ------------------------------------------------------
                       "
        ::= { tnPerOtnObjectAlarmCategoryConfigEntry 1 }

    tnOtnAlarmCategoryTribObjectId OBJECT-TYPE
        SYNTAX         Unsigned32
        MAX-ACCESS     not-accessible
        STATUS         deprecated
        DESCRIPTION    "

            -------------------------------------------------------------------
            | Bit31-Bit25 | Bit24-Bit16 | Bit15-Bit10 | Bit9-Bit5 | Bit4-Bit0 |
            --------------+-------------+-------------+-----------+------------
            | 7 bits      | 9 bits      | 6 bits      | 5 bits    | 5 bits    |
            --------------+-------------+-------------+-----------+------------
            | Reserved    | LO-ODU ID   | Container   | HO-ODU    | LO-ODU    |
            | for TCM     |             | Type        | ODU Type  | ODU Type  |
            -------------------------------------------------------------------
                       "
        ::= { tnPerOtnObjectAlarmCategoryConfigEntry 2 }

    tnOtnAlarmCategoryEntityType OBJECT-TYPE
        SYNTAX         TnEntityType
        MAX-ACCESS     not-accessible
        STATUS         deprecated
        DESCRIPTION    "The AID type."
        ::= { tnPerOtnObjectAlarmCategoryConfigEntry 3 }

    tnOtnAlarmCategoryCondition OBJECT-TYPE
        SYNTAX         TnCondition
        MAX-ACCESS     not-accessible
        STATUS         deprecated
        DESCRIPTION    "The condition."
        ::= { tnPerOtnObjectAlarmCategoryConfigEntry 4 }

    tnPerOtnObjectAlarmCategory OBJECT-TYPE
        SYNTAX         TnTrapCategory
        MAX-ACCESS     read-create
        STATUS         deprecated
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerOtnObjectAlarmCategoryConfigEntry 5 }

    tnPerOtnObjectAlarmEntityTypeCategory OBJECT-TYPE
        SYNTAX         TnTrapCategory
        MAX-ACCESS     read-only
        STATUS         deprecated
        DESCRIPTION    "The entity type category."
        ::= { tnPerOtnObjectAlarmCategoryConfigEntry 6 }

    tnPerOtnObjectAlarmDefaultCategory OBJECT-TYPE
        SYNTAX         TnTrapCategory
        MAX-ACCESS     read-only
        STATUS         deprecated
        DESCRIPTION    "The default category."
        ::= { tnPerOtnObjectAlarmCategoryConfigEntry 7 }

--------------------------------------------------------------------------------
-- Per Service Routing (SR) Service (SVC) Object Alarm Category Config Scalar
--------------------------------------------------------------------------------
    tnPerSrSvcObjectAlarmCategoryConfigAttributeTotal OBJECT-TYPE
        SYNTAX         Integer32
        MAX-ACCESS     read-only
        STATUS         current
        DESCRIPTION    "."
        ::= { tnLogAlarmCategoryConfig 17 }

-------------------------------------------------------------------
-- Per SR SVC Object Alarm Category Config Table
-------------------------------------------------------------------
    tnPerSrSvcObjectAlarmCategoryConfigTable OBJECT-TYPE
        SYNTAX         SEQUENCE OF TnPerSrSvcObjectAlarmCategoryConfigEntry
        MAX-ACCESS     not-accessible
        STATUS         current
        DESCRIPTION    "."
        ::= { tnLogAlarmCategoryConfig 18 }

    tnPerSrSvcObjectAlarmCategoryConfigEntry OBJECT-TYPE
        SYNTAX         TnPerSrSvcObjectAlarmCategoryConfigEntry
        MAX-ACCESS     not-accessible
        STATUS         current
        DESCRIPTION    "."
        INDEX { tnSysSwitchId,
                tnSvcId,
                tnSrSvcAlarmCategoryEntityType,
                tnSrSvcAlarmCategoryCondition }
        ::= { tnPerSrSvcObjectAlarmCategoryConfigTable 1 }

    TnPerSrSvcObjectAlarmCategoryConfigEntry ::=
        SEQUENCE {
            tnSrSvcAlarmCategoryEntityType           TnEntityType,
            tnSrSvcAlarmCategoryCondition            TnCondition,
            tnPerSrSvcObjectAlarmCategory            TnTrapCategory,
            tnPerSrSvcObjectAlarmEntityTypeCategory  TnTrapCategory,
            tnPerSrSvcObjectAlarmDefaultCategory     TnTrapCategory
        }

    tnSrSvcAlarmCategoryEntityType OBJECT-TYPE
        SYNTAX         TnEntityType
        MAX-ACCESS     not-accessible
        STATUS         current
        DESCRIPTION    "The AID type."
        ::= { tnPerSrSvcObjectAlarmCategoryConfigEntry 1 }

    tnSrSvcAlarmCategoryCondition OBJECT-TYPE
        SYNTAX         TnCondition
        MAX-ACCESS     not-accessible
        STATUS         current
        DESCRIPTION    "The condition."
        ::= { tnPerSrSvcObjectAlarmCategoryConfigEntry 2 }

    tnPerSrSvcObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerSrSvcObjectAlarmCategoryConfigEntry 3 }

    tnPerSrSvcObjectAlarmEntityTypeCategory OBJECT-TYPE
        SYNTAX         TnTrapCategory
        MAX-ACCESS     read-only
        STATUS         current
        DESCRIPTION    "The entity type category."
        ::= { tnPerSrSvcObjectAlarmCategoryConfigEntry 4 }

    tnPerSrSvcObjectAlarmDefaultCategory OBJECT-TYPE
        SYNTAX         TnTrapCategory
        MAX-ACCESS     read-only
        STATUS         current
        DESCRIPTION    "The default category."
        ::= { tnPerSrSvcObjectAlarmCategoryConfigEntry 5 }

--------------------------------------------------------------------------------
-- Per Service Routing (SR) Service Access Point (SAP) Object Alarm Category
-- Config Scalar
--------------------------------------------------------------------------------
    tnPerSrSapObjectAlarmCategoryConfigAttributeTotal OBJECT-TYPE
        SYNTAX         Integer32
        MAX-ACCESS     read-only
        STATUS         current
        DESCRIPTION    "."
        ::= { tnLogAlarmCategoryConfig 19 }

-------------------------------------------------------------------
-- Per SR SAP Object Alarm Category Config Table
-------------------------------------------------------------------
    tnPerSrSapObjectAlarmCategoryConfigTable OBJECT-TYPE
        SYNTAX         SEQUENCE OF TnPerSrSapObjectAlarmCategoryConfigEntry
        MAX-ACCESS     not-accessible
        STATUS         current
        DESCRIPTION    "."
        ::= { tnLogAlarmCategoryConfig 20 }

    tnPerSrSapObjectAlarmCategoryConfigEntry OBJECT-TYPE
        SYNTAX         TnPerSrSapObjectAlarmCategoryConfigEntry
        MAX-ACCESS     not-accessible
        STATUS         current
        DESCRIPTION    "."
        INDEX { tnSysSwitchId,
                tnSvcId,
                tnSapPortId,
                tnSapEncapValue,
                tnSrSapAlarmCategoryEntityType,
                tnSrSapAlarmCategoryCondition }
        ::= { tnPerSrSapObjectAlarmCategoryConfigTable 1 }

    TnPerSrSapObjectAlarmCategoryConfigEntry ::=
        SEQUENCE {
            tnSrSapAlarmCategoryEntityType           TnEntityType,
            tnSrSapAlarmCategoryCondition            TnCondition,
            tnPerSrSapObjectAlarmCategory            TnTrapCategory,
            tnPerSrSapObjectAlarmEntityTypeCategory  TnTrapCategory,
            tnPerSrSapObjectAlarmDefaultCategory     TnTrapCategory
        }

    tnSrSapAlarmCategoryEntityType OBJECT-TYPE
        SYNTAX         TnEntityType
        MAX-ACCESS     not-accessible
        STATUS         current
        DESCRIPTION    "The AID type."
        ::= { tnPerSrSapObjectAlarmCategoryConfigEntry 1 }

    tnSrSapAlarmCategoryCondition OBJECT-TYPE
        SYNTAX         TnCondition
        MAX-ACCESS     not-accessible
        STATUS         current
        DESCRIPTION    "The condition."
        ::= { tnPerSrSapObjectAlarmCategoryConfigEntry 2 }

    tnPerSrSapObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerSrSapObjectAlarmCategoryConfigEntry 3 }

    tnPerSrSapObjectAlarmEntityTypeCategory OBJECT-TYPE
        SYNTAX         TnTrapCategory
        MAX-ACCESS     read-only
        STATUS         current
        DESCRIPTION    "The entity type category."
        ::= { tnPerSrSapObjectAlarmCategoryConfigEntry 4 }

    tnPerSrSapObjectAlarmDefaultCategory OBJECT-TYPE
        SYNTAX         TnTrapCategory
        MAX-ACCESS     read-only
        STATUS         current
        DESCRIPTION    "The default category."
        ::= { tnPerSrSapObjectAlarmCategoryConfigEntry 5 }

--------------------------------------------------------------------------------
-- Per Service Routing (SR) Ethernet Ring Protection (ERP) Object Alarm
-- Category Config Scalar
--------------------------------------------------------------------------------
    tnPerSrErpObjectAlarmCategoryConfigAttributeTotal OBJECT-TYPE
        SYNTAX         Integer32
        MAX-ACCESS     read-only
        STATUS         current
        DESCRIPTION    "."
        ::= { tnLogAlarmCategoryConfig 21 }

-------------------------------------------------------------------
-- Per SR ERP Object Alarm Category Config Table
-------------------------------------------------------------------
    tnPerSrErpObjectAlarmCategoryConfigTable OBJECT-TYPE
        SYNTAX         SEQUENCE OF TnPerSrErpObjectAlarmCategoryConfigEntry
        MAX-ACCESS     not-accessible
        STATUS         current
        DESCRIPTION    "."
        ::= { tnLogAlarmCategoryConfig 22 }

    tnPerSrErpObjectAlarmCategoryConfigEntry OBJECT-TYPE
        SYNTAX         TnPerSrErpObjectAlarmCategoryConfigEntry
        MAX-ACCESS     not-accessible
        STATUS         current
        DESCRIPTION    "."
        INDEX { tnSysSwitchId,
                tnEthRingIndex,
                tnSrErpAlarmCategoryEntityType,
                tnSrErpAlarmCategoryCondition }
        ::= { tnPerSrErpObjectAlarmCategoryConfigTable 1 }

    TnPerSrErpObjectAlarmCategoryConfigEntry ::=
        SEQUENCE {
            tnSrErpAlarmCategoryEntityType           TnEntityType,
            tnSrErpAlarmCategoryCondition            TnCondition,
            tnPerSrErpObjectAlarmCategory            TnTrapCategory,
            tnPerSrErpObjectAlarmEntityTypeCategory  TnTrapCategory,
            tnPerSrErpObjectAlarmDefaultCategory     TnTrapCategory
        }

    tnSrErpAlarmCategoryEntityType OBJECT-TYPE
        SYNTAX         TnEntityType
        MAX-ACCESS     not-accessible
        STATUS         current
        DESCRIPTION    "The AID type."
        ::= { tnPerSrErpObjectAlarmCategoryConfigEntry 1 }

    tnSrErpAlarmCategoryCondition OBJECT-TYPE
        SYNTAX         TnCondition
        MAX-ACCESS     not-accessible
        STATUS         current
        DESCRIPTION    "The condition."
        ::= { tnPerSrErpObjectAlarmCategoryConfigEntry 2 }

    tnPerSrErpObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerSrErpObjectAlarmCategoryConfigEntry 3 }

    tnPerSrErpObjectAlarmEntityTypeCategory OBJECT-TYPE
        SYNTAX         TnTrapCategory
        MAX-ACCESS     read-only
        STATUS         current
        DESCRIPTION    "The entity type category."
        ::= { tnPerSrErpObjectAlarmCategoryConfigEntry 4 }

    tnPerSrErpObjectAlarmDefaultCategory OBJECT-TYPE
        SYNTAX         TnTrapCategory
        MAX-ACCESS     read-only
        STATUS         current
        DESCRIPTION    "The default category."
        ::= { tnPerSrErpObjectAlarmCategoryConfigEntry 5 }

--------------------------------------------------------------------------------
-- Per Service Routing (SR) Maintenance End Point (MEP) Object Alarm Category
-- Config Scalar
--------------------------------------------------------------------------------
    tnPerSrMepObjectAlarmCategoryConfigAttributeTotal OBJECT-TYPE
        SYNTAX         Integer32
        MAX-ACCESS     read-only
        STATUS         current
        DESCRIPTION    "."
        ::= { tnLogAlarmCategoryConfig 23 }

-------------------------------------------------------------------
-- Per SR MEP Object Alarm Category Config Table
-------------------------------------------------------------------
    tnPerSrMepObjectAlarmCategoryConfigTable OBJECT-TYPE
        SYNTAX         SEQUENCE OF TnPerSrMepObjectAlarmCategoryConfigEntry
        MAX-ACCESS     not-accessible
        STATUS         current
        DESCRIPTION    "."
        ::= { tnLogAlarmCategoryConfig 24 }

    tnPerSrMepObjectAlarmCategoryConfigEntry OBJECT-TYPE
        SYNTAX         TnPerSrMepObjectAlarmCategoryConfigEntry
        MAX-ACCESS     not-accessible
        STATUS         current
        DESCRIPTION    "."
        INDEX { dot1agCfmMdIndex,
                dot1agCfmMaIndex,
                dot1agCfmMepIdentifier,
                tnSrMepAlarmCategoryEntityType,
                tnSrMepAlarmCategoryCondition }
        ::= { tnPerSrMepObjectAlarmCategoryConfigTable 1 }

    TnPerSrMepObjectAlarmCategoryConfigEntry ::=
        SEQUENCE {
            tnSrMepAlarmCategoryEntityType           TnEntityType,
            tnSrMepAlarmCategoryCondition            TnCondition,
            tnPerSrMepObjectAlarmCategory            TnTrapCategory,
            tnPerSrMepObjectAlarmEntityTypeCategory  TnTrapCategory,
            tnPerSrMepObjectAlarmDefaultCategory     TnTrapCategory
        }

    tnSrMepAlarmCategoryEntityType OBJECT-TYPE
        SYNTAX         TnEntityType
        MAX-ACCESS     not-accessible
        STATUS         current
        DESCRIPTION    "The AID type."
        ::= { tnPerSrMepObjectAlarmCategoryConfigEntry 1 }

    tnSrMepAlarmCategoryCondition OBJECT-TYPE
        SYNTAX         TnCondition
        MAX-ACCESS     not-accessible
        STATUS         current
        DESCRIPTION    "The condition."
        ::= { tnPerSrMepObjectAlarmCategoryConfigEntry 2 }

    tnPerSrMepObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerSrMepObjectAlarmCategoryConfigEntry 3 }

    tnPerSrMepObjectAlarmEntityTypeCategory OBJECT-TYPE
        SYNTAX         TnTrapCategory
        MAX-ACCESS     read-only
        STATUS         current
        DESCRIPTION    "The entity type category."
        ::= { tnPerSrMepObjectAlarmCategoryConfigEntry 4 }

    tnPerSrMepObjectAlarmDefaultCategory OBJECT-TYPE
        SYNTAX         TnTrapCategory
        MAX-ACCESS     read-only
        STATUS         current
        DESCRIPTION    "The default category."
        ::= { tnPerSrMepObjectAlarmCategoryConfigEntry 5 }

--------------------------------------------------------------------------------
-- Per Service Routing (SR) Operations, Administration, and Management (OAM)
-- Object Alarm Category Config Scalar
--------------------------------------------------------------------------------
    tnPerSrOamTestObjectAlarmCategoryConfigAttributeTotal OBJECT-TYPE
        SYNTAX         Integer32
        MAX-ACCESS     read-only
        STATUS         current
        DESCRIPTION    "."
        ::= { tnLogAlarmCategoryConfig 25 }

-------------------------------------------------------------------
-- Per SR OAM Test Object Alarm Category Config Table
-------------------------------------------------------------------
    tnPerSrOamTestObjectAlarmCategoryConfigTable OBJECT-TYPE
        SYNTAX         SEQUENCE OF TnPerSrOamTestObjectAlarmCategoryConfigEntry
        MAX-ACCESS     not-accessible
        STATUS         current
        DESCRIPTION    "."
        ::= { tnLogAlarmCategoryConfig 26 }

    tnPerSrOamTestObjectAlarmCategoryConfigEntry OBJECT-TYPE
        SYNTAX         TnPerSrOamTestObjectAlarmCategoryConfigEntry
        MAX-ACCESS     not-accessible
        STATUS         current
        DESCRIPTION    "."
        INDEX { tnSysSwitchId,
                tnOamSaaCtlTestIndex,
                tnSrOamTestAlarmCategoryEntityType,
                tnSrOamTestAlarmCategoryCondition }
        ::= { tnPerSrOamTestObjectAlarmCategoryConfigTable 1 }

    TnPerSrOamTestObjectAlarmCategoryConfigEntry ::=
        SEQUENCE {
            tnSrOamTestAlarmCategoryEntityType           TnEntityType,
            tnSrOamTestAlarmCategoryCondition            TnCondition,
            tnPerSrOamTestObjectAlarmCategory            TnTrapCategory,
            tnPerSrOamTestObjectAlarmEntityTypeCategory  TnTrapCategory,
            tnPerSrOamTestObjectAlarmDefaultCategory     TnTrapCategory
        }

    tnSrOamTestAlarmCategoryEntityType OBJECT-TYPE
        SYNTAX         TnEntityType
        MAX-ACCESS     not-accessible
        STATUS         current
        DESCRIPTION    "The AID type."
        ::= { tnPerSrOamTestObjectAlarmCategoryConfigEntry 1 }

    tnSrOamTestAlarmCategoryCondition OBJECT-TYPE
        SYNTAX         TnCondition
        MAX-ACCESS     not-accessible
        STATUS         current
        DESCRIPTION    "The condition."
        ::= { tnPerSrOamTestObjectAlarmCategoryConfigEntry 2 }

    tnPerSrOamTestObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerSrOamTestObjectAlarmCategoryConfigEntry 3 }

    tnPerSrOamTestObjectAlarmEntityTypeCategory OBJECT-TYPE
        SYNTAX         TnTrapCategory
        MAX-ACCESS     read-only
        STATUS         current
        DESCRIPTION    "The entity type category."
        ::= { tnPerSrOamTestObjectAlarmCategoryConfigEntry 4 }

    tnPerSrOamTestObjectAlarmDefaultCategory OBJECT-TYPE
        SYNTAX         TnTrapCategory
        MAX-ACCESS     read-only
        STATUS         current
        DESCRIPTION    "The default category."
        ::= { tnPerSrOamTestObjectAlarmCategoryConfigEntry 5 }

--------------------------------------------------------------------------------
-- Per Remote Managed Devices (RMD) Object Alarm Category Config Scalar
--------------------------------------------------------------------------------
    tnPerRmdObjectAlarmCategoryConfigAttributeTotal OBJECT-TYPE
        SYNTAX         Integer32
        MAX-ACCESS     read-only
        STATUS         current
        DESCRIPTION    "."
        ::= { tnLogAlarmCategoryConfig 27 }

-------------------------------------------------------------------
-- Per RMD Object Alarm Category Config Table
-------------------------------------------------------------------
    tnPerRmdObjectAlarmCategoryConfigTable OBJECT-TYPE
        SYNTAX         SEQUENCE OF TnPerRmdObjectAlarmCategoryConfigEntry
        MAX-ACCESS     not-accessible
        STATUS         current
        DESCRIPTION    "."
        ::= { tnLogAlarmCategoryConfig 28 }

    tnPerRmdObjectAlarmCategoryConfigEntry OBJECT-TYPE
        SYNTAX         TnPerRmdObjectAlarmCategoryConfigEntry
        MAX-ACCESS     not-accessible
        STATUS         current
        DESCRIPTION    "."
        INDEX { tnSysSwitchId,
                tnRmdSystemId,
                tnRmdAlarmCategoryEntityType,
                tnRmdAlarmCategoryCondition }
        ::= { tnPerRmdObjectAlarmCategoryConfigTable 1 }

    TnPerRmdObjectAlarmCategoryConfigEntry ::=
        SEQUENCE {
            tnRmdAlarmCategoryEntityType           TnEntityType,
            tnRmdAlarmCategoryCondition            TnCondition,
            tnPerRmdObjectAlarmCategory            TnTrapCategory,
            tnPerRmdObjectAlarmEntityTypeCategory  TnTrapCategory,
            tnPerRmdObjectAlarmDefaultCategory     TnTrapCategory
        }

    tnRmdAlarmCategoryEntityType OBJECT-TYPE
        SYNTAX         TnEntityType
        MAX-ACCESS     not-accessible
        STATUS         current
        DESCRIPTION    "The AID type."
        ::= { tnPerRmdObjectAlarmCategoryConfigEntry 1 }

    tnRmdAlarmCategoryCondition OBJECT-TYPE
        SYNTAX         TnCondition
        MAX-ACCESS     not-accessible
        STATUS         current
        DESCRIPTION    "The condition."
        ::= { tnPerRmdObjectAlarmCategoryConfigEntry 2 }

    tnPerRmdObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerRmdObjectAlarmCategoryConfigEntry 3 }

    tnPerRmdObjectAlarmEntityTypeCategory OBJECT-TYPE
        SYNTAX         TnTrapCategory
        MAX-ACCESS     read-only
        STATUS         current
        DESCRIPTION    "The entity type category."
        ::= { tnPerRmdObjectAlarmCategoryConfigEntry 4 }

    tnPerRmdObjectAlarmDefaultCategory OBJECT-TYPE
        SYNTAX         TnTrapCategory
        MAX-ACCESS     read-only
        STATUS         current
        DESCRIPTION    "The default category."
        ::= { tnPerRmdObjectAlarmCategoryConfigEntry 5 }

--------------------------------------------------------------------------------
-- Per Remote Managed Devices (RMD) Maintenance End Point (MEP) Object Alarm
-- Category Config Scalar
--------------------------------------------------------------------------------
    tnPerRmdMepObjectAlarmCategoryConfigAttributeTotal OBJECT-TYPE
        SYNTAX         Integer32
        MAX-ACCESS     read-only
        STATUS         current
        DESCRIPTION    "."
        ::= { tnLogAlarmCategoryConfig 29 }

-------------------------------------------------------------------
-- Per RMD MEP Object Alarm Category Config Table
-------------------------------------------------------------------
    tnPerRmdMepObjectAlarmCategoryConfigTable OBJECT-TYPE
        SYNTAX         SEQUENCE OF TnPerRmdMepObjectAlarmCategoryConfigEntry
        MAX-ACCESS     not-accessible
        STATUS         current
        DESCRIPTION    "."
        ::= { tnLogAlarmCategoryConfig 30 }

    tnPerRmdMepObjectAlarmCategoryConfigEntry OBJECT-TYPE
        SYNTAX         TnPerRmdMepObjectAlarmCategoryConfigEntry
        MAX-ACCESS     not-accessible
        STATUS         current
        DESCRIPTION    "."
        INDEX { tnSysSwitchId,
                tnRmdSystemId,
                tnRmdCfmMepNumber,
                tnRmdMepAlarmCategoryEntityType,
                tnRmdMepAlarmCategoryCondition }
        ::= { tnPerRmdMepObjectAlarmCategoryConfigTable 1 }

    TnPerRmdMepObjectAlarmCategoryConfigEntry ::=
        SEQUENCE {
            tnRmdMepAlarmCategoryEntityType           TnEntityType,
            tnRmdMepAlarmCategoryCondition            TnCondition,
            tnPerRmdMepObjectAlarmCategory            TnTrapCategory,
            tnPerRmdMepObjectAlarmEntityTypeCategory  TnTrapCategory,
            tnPerRmdMepObjectAlarmDefaultCategory     TnTrapCategory
        }

    tnRmdMepAlarmCategoryEntityType OBJECT-TYPE
        SYNTAX         TnEntityType
        MAX-ACCESS     not-accessible
        STATUS         current
        DESCRIPTION    "The AID type."
        ::= { tnPerRmdMepObjectAlarmCategoryConfigEntry 1 }

    tnRmdMepAlarmCategoryCondition OBJECT-TYPE
        SYNTAX         TnCondition
        MAX-ACCESS     not-accessible
        STATUS         current
        DESCRIPTION    "The condition."
        ::= { tnPerRmdMepObjectAlarmCategoryConfigEntry 2 }

    tnPerRmdMepObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerRmdMepObjectAlarmCategoryConfigEntry 3 }

    tnPerRmdMepObjectAlarmEntityTypeCategory OBJECT-TYPE
        SYNTAX         TnTrapCategory
        MAX-ACCESS     read-only
        STATUS         current
        DESCRIPTION    "The entity type category."
        ::= { tnPerRmdMepObjectAlarmCategoryConfigEntry 4 }

    tnPerRmdMepObjectAlarmDefaultCategory OBJECT-TYPE
        SYNTAX         TnTrapCategory
        MAX-ACCESS     read-only
        STATUS         current
        DESCRIPTION    "The default category."
        ::= { tnPerRmdMepObjectAlarmCategoryConfigEntry 5 }

--------------------------------------------------------------------------------
-- Per Remote Managed Devices (RMD) Interface (IF) Object Alarm Category Config
-- Scalar
--------------------------------------------------------------------------------
    tnPerRmdIfObjectAlarmCategoryConfigAttributeTotal OBJECT-TYPE
        SYNTAX         Integer32
        MAX-ACCESS     read-only
        STATUS         current
        DESCRIPTION    "."
        ::= { tnLogAlarmCategoryConfig 31 }

-------------------------------------------------------------------
-- Per RMD IF Object Alarm Category Config Table
-------------------------------------------------------------------
    tnPerRmdIfObjectAlarmCategoryConfigTable OBJECT-TYPE
        SYNTAX         SEQUENCE OF TnPerRmdIfObjectAlarmCategoryConfigEntry
        MAX-ACCESS     not-accessible
        STATUS         current
        DESCRIPTION    "."
        ::= { tnLogAlarmCategoryConfig 32 }

    tnPerRmdIfObjectAlarmCategoryConfigEntry OBJECT-TYPE
        SYNTAX         TnPerRmdIfObjectAlarmCategoryConfigEntry
        MAX-ACCESS     not-accessible
        STATUS         current
        DESCRIPTION    "."
        INDEX { tnSysSwitchId,
                tnRmdSystemId,
                tnRmdIfIndex,
                tnRmdIfAlarmCategoryEntityType,
                tnRmdIfAlarmCategoryCondition }
        ::= { tnPerRmdIfObjectAlarmCategoryConfigTable 1 }

    TnPerRmdIfObjectAlarmCategoryConfigEntry ::=
        SEQUENCE {
            tnRmdIfAlarmCategoryEntityType           TnEntityType,
            tnRmdIfAlarmCategoryCondition            TnCondition,
            tnPerRmdIfObjectAlarmCategory            TnTrapCategory,
            tnPerRmdIfObjectAlarmEntityTypeCategory  TnTrapCategory,
            tnPerRmdIfObjectAlarmDefaultCategory     TnTrapCategory
        }

    tnRmdIfAlarmCategoryEntityType OBJECT-TYPE
        SYNTAX         TnEntityType
        MAX-ACCESS     not-accessible
        STATUS         current
        DESCRIPTION    "The AID type."
        ::= { tnPerRmdIfObjectAlarmCategoryConfigEntry 1 }

    tnRmdIfAlarmCategoryCondition OBJECT-TYPE
        SYNTAX         TnCondition
        MAX-ACCESS     not-accessible
        STATUS         current
        DESCRIPTION    "The condition."
        ::= { tnPerRmdIfObjectAlarmCategoryConfigEntry 2 }

    tnPerRmdIfObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerRmdIfObjectAlarmCategoryConfigEntry 3 }

    tnPerRmdIfObjectAlarmEntityTypeCategory OBJECT-TYPE
        SYNTAX         TnTrapCategory
        MAX-ACCESS     read-only
        STATUS         current
        DESCRIPTION    "The entity type category."
        ::= { tnPerRmdIfObjectAlarmCategoryConfigEntry 4 }

    tnPerRmdIfObjectAlarmDefaultCategory OBJECT-TYPE
        SYNTAX         TnTrapCategory
        MAX-ACCESS     read-only
        STATUS         current
        DESCRIPTION    "The default category."
        ::= { tnPerRmdIfObjectAlarmCategoryConfigEntry 5 }

--------------------------------------------------------------------------------
-- Per Remote managed Devices (RMD) Interface (IF) Medium Attachment Unit (MAU)
-- Object Alarm Category Config Scalar
--------------------------------------------------------------------------------
    tnPerRmdIfMauObjectAlarmCategoryConfigAttributeTotal OBJECT-TYPE
        SYNTAX         Integer32
        MAX-ACCESS     read-only
        STATUS         current
        DESCRIPTION    "."
        ::= { tnLogAlarmCategoryConfig 33 }

-------------------------------------------------------------------
-- Per RMD IF MAU Object Alarm Category Config Table
-------------------------------------------------------------------
    tnPerRmdIfMauObjectAlarmCategoryConfigTable OBJECT-TYPE
        SYNTAX         SEQUENCE OF TnPerRmdIfMauObjectAlarmCategoryConfigEntry
        MAX-ACCESS     not-accessible
        STATUS         current
        DESCRIPTION    "."
        ::= { tnLogAlarmCategoryConfig 34 }

    tnPerRmdIfMauObjectAlarmCategoryConfigEntry OBJECT-TYPE
        SYNTAX         TnPerRmdIfMauObjectAlarmCategoryConfigEntry
        MAX-ACCESS     not-accessible
        STATUS         current
        DESCRIPTION    "."
        INDEX { tnSysSwitchId,
                tnRmdSystemId,
                tnRmdIfIndex,
                tnRmdIfMauIndex,
                tnRmdIfMauAlarmCategoryEntityType,
                tnRmdIfMauAlarmCategoryCondition }
        ::= { tnPerRmdIfMauObjectAlarmCategoryConfigTable 1 }

    TnPerRmdIfMauObjectAlarmCategoryConfigEntry ::=
        SEQUENCE {
            tnRmdIfMauAlarmCategoryEntityType           TnEntityType,
            tnRmdIfMauAlarmCategoryCondition            TnCondition,
            tnPerRmdIfMauObjectAlarmCategory            TnTrapCategory,
            tnPerRmdIfMauObjectAlarmEntityTypeCategory  TnTrapCategory,
            tnPerRmdIfMauObjectAlarmDefaultCategory     TnTrapCategory
        }

    tnRmdIfMauAlarmCategoryEntityType OBJECT-TYPE
        SYNTAX         TnEntityType
        MAX-ACCESS     not-accessible
        STATUS         current
        DESCRIPTION    "The AID type."
        ::= { tnPerRmdIfMauObjectAlarmCategoryConfigEntry 1 }

    tnRmdIfMauAlarmCategoryCondition OBJECT-TYPE
        SYNTAX         TnCondition
        MAX-ACCESS     not-accessible
        STATUS         current
        DESCRIPTION    "The condition."
        ::= { tnPerRmdIfMauObjectAlarmCategoryConfigEntry 2 }

    tnPerRmdIfMauObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerRmdIfMauObjectAlarmCategoryConfigEntry 3 }

    tnPerRmdIfMauObjectAlarmEntityTypeCategory OBJECT-TYPE
        SYNTAX         TnTrapCategory
        MAX-ACCESS     read-only
        STATUS         current
        DESCRIPTION    "The entity type category."
        ::= { tnPerRmdIfMauObjectAlarmCategoryConfigEntry 4 }

    tnPerRmdIfMauObjectAlarmDefaultCategory OBJECT-TYPE
        SYNTAX         TnTrapCategory
        MAX-ACCESS     read-only
        STATUS         current
        DESCRIPTION    "The default category."
        ::= { tnPerRmdIfMauObjectAlarmCategoryConfigEntry 5 }

--------------------------------------------------------------------------------
-- Per Remote managed Devices (RMD) Ces Channel Object Alarm Category Config Scalar
--------------------------------------------------------------------------------
    tnPerRmdCesChannelObjectAlarmCategoryConfigAttributeTotal OBJECT-TYPE
        SYNTAX         Integer32
        MAX-ACCESS     read-only
        STATUS         current
        DESCRIPTION    "."
        ::= { tnLogAlarmCategoryConfig 35 }

-------------------------------------------------------------------
-- Per RMD Ces Channel Object Alarm Category Config Table
-------------------------------------------------------------------
    tnPerRmdCesChannelObjectAlarmCategoryConfigTable OBJECT-TYPE
        SYNTAX         SEQUENCE OF TnPerRmdCesChannelObjectAlarmCategoryConfigEntry
        MAX-ACCESS     not-accessible
        STATUS         current
        DESCRIPTION    "."
        ::= { tnLogAlarmCategoryConfig 36 }

    tnPerRmdCesChannelObjectAlarmCategoryConfigEntry OBJECT-TYPE
        SYNTAX         TnPerRmdCesChannelObjectAlarmCategoryConfigEntry
        MAX-ACCESS     not-accessible
        STATUS         current
        DESCRIPTION    "."
        INDEX { tnSysSwitchId,
                tnRmdSystemId,
                tnRmdTsopIwfChannelNumber,
                tnRmdCesChannelAlarmCategoryEntityType,
                tnRmdCesChannelAlarmCategoryCondition }
        ::= { tnPerRmdCesChannelObjectAlarmCategoryConfigTable 1 }

    TnPerRmdCesChannelObjectAlarmCategoryConfigEntry ::=
        SEQUENCE {
            tnRmdCesChannelAlarmCategoryEntityType           TnEntityType,
            tnRmdCesChannelAlarmCategoryCondition            TnCondition,
            tnPerRmdCesChannelObjectAlarmCategory            TnTrapCategory,
            tnPerRmdCesChannelObjectAlarmEntityTypeCategory  TnTrapCategory,
            tnPerRmdCesChannelObjectAlarmDefaultCategory     TnTrapCategory
        }

    tnRmdCesChannelAlarmCategoryEntityType OBJECT-TYPE
        SYNTAX         TnEntityType
        MAX-ACCESS     not-accessible
        STATUS         current
        DESCRIPTION    "The AID type."
        ::= { tnPerRmdCesChannelObjectAlarmCategoryConfigEntry 1 }

    tnRmdCesChannelAlarmCategoryCondition OBJECT-TYPE
        SYNTAX         TnCondition
        MAX-ACCESS     not-accessible
        STATUS         current
        DESCRIPTION    "The condition."
        ::= { tnPerRmdCesChannelObjectAlarmCategoryConfigEntry 2 }

    tnPerRmdCesChannelObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerRmdCesChannelObjectAlarmCategoryConfigEntry 3 }

    tnPerRmdCesChannelObjectAlarmEntityTypeCategory OBJECT-TYPE
        SYNTAX         TnTrapCategory
        MAX-ACCESS     read-only
        STATUS         current
        DESCRIPTION    "The entity type category."
        ::= { tnPerRmdCesChannelObjectAlarmCategoryConfigEntry 4 }

    tnPerRmdCesChannelObjectAlarmDefaultCategory OBJECT-TYPE
        SYNTAX         TnTrapCategory
        MAX-ACCESS     read-only
        STATUS         current
        DESCRIPTION    "The default category."
        ::= { tnPerRmdCesChannelObjectAlarmCategoryConfigEntry 5 }

--------------------------------------------------------------------------------
-- Per OTH Object Alarm Category Config Scalar
--------------------------------------------------------------------------------
    tnPerOthObjectAlarmCategoryConfigAttributeTotal OBJECT-TYPE
        SYNTAX         Integer32
        MAX-ACCESS     read-only
        STATUS         current
        DESCRIPTION    "."
        ::= { tnLogAlarmCategoryConfig 37 }

-------------------------------------------------------------------
-- Per OTH Object Alarm Category Config Table
-------------------------------------------------------------------
    tnPerOthObjectAlarmCategoryConfigTable OBJECT-TYPE
        SYNTAX         SEQUENCE OF TnPerOthObjectAlarmCategoryConfigEntry
        MAX-ACCESS     not-accessible
        STATUS         current
        DESCRIPTION    "."
        ::= { tnLogAlarmCategoryConfig 38 }

    tnPerOthObjectAlarmCategoryConfigEntry OBJECT-TYPE
        SYNTAX         TnPerOthObjectAlarmCategoryConfigEntry
        MAX-ACCESS     not-accessible
        STATUS         current
        DESCRIPTION    "."
        INDEX { tnOthAlarmCategoryObjectId,
                tnOthAlarmCategoryTribObjectId,
                tnOthAlarmCategoryDirection,
                tnOthAlarmCategoryEntityType,
                tnOthAlarmCategoryCondition }
        ::= { tnPerOthObjectAlarmCategoryConfigTable 1 }

    TnPerOthObjectAlarmCategoryConfigEntry ::=
        SEQUENCE {
            tnOthAlarmCategoryObjectId             Unsigned32,
            tnOthAlarmCategoryTribObjectId         Unsigned32,
            tnOthAlarmCategoryDirection            AluWdmAlarmCategoryDirection,
            tnOthAlarmCategoryEntityType           TnEntityType,
            tnOthAlarmCategoryCondition            TnCondition,
            tnPerOthObjectAlarmCategory            TnTrapCategory,
            tnPerOthObjectAlarmEntityTypeCategory  TnTrapCategory,
            tnPerOthObjectAlarmDefaultCategory     TnTrapCategory
        }

    tnOthAlarmCategoryObjectId OBJECT-TYPE
        SYNTAX         Unsigned32
        MAX-ACCESS     not-accessible
        STATUS         current
        DESCRIPTION    "

            ------------------------------------------------------
            | Bit31-Bit24 | Bit23-Bit16 | Bit15-Bit3 | Bit2-Bit0 |
            --------------+-------------+------------+------------
            | 8 bits      | 8 bits      | 13 bits    | 3 bits    |
            --------------+-------------+------------+------------
            | shelf       | slot        | HO-ODU     | Reserved  |
            |             |             | Number     | as 0      |
            ------------------------------------------------------
                       "
        ::= { tnPerOthObjectAlarmCategoryConfigEntry 1 }

    tnOthAlarmCategoryTribObjectId OBJECT-TYPE
        SYNTAX         Unsigned32
        MAX-ACCESS     not-accessible
        STATUS         current
        DESCRIPTION    "

            -----------------------------------------------------------
            | Bit31-Bit29 | Bit28-Bit27   | Bit26-Bit25 | Bit24-Bit16 |
            --------------+---------------+-------------+-------------+
            | 3 bits      | 2 bits        | 2 bits      | 9 bits      |
            --------------+---------------+-------------+-------------+
            | TCM Level   | TCM Direction | Reserved    | LO-ODU ID   |
            | (1-6)       | (AM=1, BM=2)  | as 0        |             |
            -----------------------------------------------------------

            ---------------------------------------
            | Bit15-Bit10 | Bit9-Bit5 | Bit4-Bit0 |
            --------------+-----------+-----------+
            | 6 bits      | 5 bits    | 5 bits    |
            --------------+-----------+------------
            | Container   | HO-ODU    | LO-ODU    |
            | Type        | ODU Type  | ODU Type  |
            ---------------------------------------
                       "
        ::= { tnPerOthObjectAlarmCategoryConfigEntry 2 }

    tnOthAlarmCategoryDirection OBJECT-TYPE
        SYNTAX         AluWdmAlarmCategoryDirection
        MAX-ACCESS     not-accessible
        STATUS         current
        DESCRIPTION    "The direction to which the new category will be
                        applied."
        ::= { tnPerOthObjectAlarmCategoryConfigEntry 3 }

    tnOthAlarmCategoryEntityType OBJECT-TYPE
        SYNTAX         TnEntityType
        MAX-ACCESS     not-accessible
        STATUS         current
        DESCRIPTION    "The AID type."
        ::= { tnPerOthObjectAlarmCategoryConfigEntry 4 }

    tnOthAlarmCategoryCondition OBJECT-TYPE
        SYNTAX         TnCondition
        MAX-ACCESS     not-accessible
        STATUS         current
        DESCRIPTION    "The condition."
        ::= { tnPerOthObjectAlarmCategoryConfigEntry 5 }

    tnPerOthObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerOthObjectAlarmCategoryConfigEntry 6 }

    tnPerOthObjectAlarmEntityTypeCategory OBJECT-TYPE
        SYNTAX         TnTrapCategory
        MAX-ACCESS     read-only
        STATUS         current
        DESCRIPTION    "The entity type category."
        ::= { tnPerOthObjectAlarmCategoryConfigEntry 7 }

    tnPerOthObjectAlarmDefaultCategory OBJECT-TYPE
        SYNTAX         TnTrapCategory
        MAX-ACCESS     read-only
        STATUS         current
        DESCRIPTION    "The default category."
        ::= { tnPerOthObjectAlarmCategoryConfigEntry 8 }

-------------------------------------------------------------------
-- Per Remote Management Device (RMD) Non Intrusive Monitor (NIM)
-- Object Alarm Category Config Scalar
-------------------------------------------------------------------
    tnPerRmdNimObjectAlarmCategoryConfigAttributeTotal OBJECT-TYPE
        SYNTAX         Integer32
        MAX-ACCESS     read-only
        STATUS         current
        DESCRIPTION    "."
        ::= { tnLogAlarmCategoryConfig 39 }

--------------------------------------------------------------------
-- Per RMD NIM Object Alarm Category Config Table
--------------------------------------------------------------------
    tnPerRmdNimObjectAlarmCategoryConfigTable OBJECT-TYPE
        SYNTAX         SEQUENCE OF TnPerRmdNimObjectAlarmCategoryConfigEntry
        MAX-ACCESS     not-accessible
        STATUS         current
        DESCRIPTION    "."
        ::= { tnLogAlarmCategoryConfig 40 }

    tnPerRmdNimObjectAlarmCategoryConfigEntry OBJECT-TYPE
        SYNTAX         TnPerRmdNimObjectAlarmCategoryConfigEntry
        MAX-ACCESS     not-accessible
        STATUS         current
        DESCRIPTION    "."
        INDEX { tnSysSwitchId,
                tnRmdSystemId,
                tnRmdIfIndex,
                tnRmdIfNimDirection,
                tnRmdNimAlarmCategoryEntityType,
                tnRmdNimAlarmCategoryCondition }
        ::= { tnPerRmdNimObjectAlarmCategoryConfigTable 1 }

    TnPerRmdNimObjectAlarmCategoryConfigEntry ::=
        SEQUENCE {
            tnRmdIfNimDirection                       TnRmdNimDirection,
            tnRmdNimAlarmCategoryEntityType           TnEntityType,
            tnRmdNimAlarmCategoryCondition            TnCondition,
            tnPerRmdNimObjectAlarmCategory            TnTrapCategory,
            tnPerRmdNimObjectAlarmEntityTypeCategory  TnTrapCategory,
            tnPerRmdNimObjectAlarmDefaultCategory     TnTrapCategory
        }

    tnRmdIfNimDirection OBJECT-TYPE
        SYNTAX         TnRmdNimDirection
        MAX-ACCESS     not-accessible
        STATUS         current
        DESCRIPTION    "The direction of the NIM."
        ::= { tnPerRmdNimObjectAlarmCategoryConfigEntry 1 }

    tnRmdNimAlarmCategoryEntityType OBJECT-TYPE
        SYNTAX         TnEntityType
        MAX-ACCESS     not-accessible
        STATUS         current
        DESCRIPTION    "The AID type."
        ::= { tnPerRmdNimObjectAlarmCategoryConfigEntry 2 }

    tnRmdNimAlarmCategoryCondition OBJECT-TYPE
        SYNTAX         TnCondition
        MAX-ACCESS     not-accessible
        STATUS         current
        DESCRIPTION    "The condition."
        ::= { tnPerRmdNimObjectAlarmCategoryConfigEntry 3 }

    tnPerRmdNimObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerRmdNimObjectAlarmCategoryConfigEntry 4 }

    tnPerRmdNimObjectAlarmEntityTypeCategory OBJECT-TYPE
        SYNTAX         TnTrapCategory
        MAX-ACCESS     read-only
        STATUS         current
        DESCRIPTION    "The entity type category."
        ::= { tnPerRmdNimObjectAlarmCategoryConfigEntry 5 }

    tnPerRmdNimObjectAlarmDefaultCategory OBJECT-TYPE
        SYNTAX         TnTrapCategory
        MAX-ACCESS     read-only
        STATUS         current
        DESCRIPTION    "The default category."
        ::= { tnPerRmdNimObjectAlarmCategoryConfigEntry 6 }

--------------------------------------------------------------------------------
-- Per Service Routing (SR) MPLS LSP Object Alarm
-- Category Config Scalar
--------------------------------------------------------------------------------
    tnPerMplsLspObjectAlarmCategoryConfigAttributeTotal OBJECT-TYPE
        SYNTAX         Integer32
        MAX-ACCESS     read-only
        STATUS         current
        DESCRIPTION    "."
        ::= { tnLogAlarmCategoryConfig 41 }

-------------------------------------------------------------------
-- Per SR ERP Object Alarm Category Config Table
-------------------------------------------------------------------
    tnPerMplsLspObjectAlarmCategoryConfigTable OBJECT-TYPE
        SYNTAX         SEQUENCE OF TnPerMplsLspObjectAlarmCategoryConfigEntry
        MAX-ACCESS     not-accessible
        STATUS         current
        DESCRIPTION    "."
        ::= { tnLogAlarmCategoryConfig 42 }

    tnPerMplsLspObjectAlarmCategoryConfigEntry OBJECT-TYPE
        SYNTAX         TnPerMplsLspObjectAlarmCategoryConfigEntry
        MAX-ACCESS     not-accessible
        STATUS         current
        DESCRIPTION    "."
        INDEX { tnSysSwitchId,
                vRtrID,
                vRtrMplsLspIndex,
                tnMplsLspAlarmCategoryEntityType,
                tnMplsLspAlarmCategoryCondition }
        ::= { tnPerMplsLspObjectAlarmCategoryConfigTable 1 }

    TnPerMplsLspObjectAlarmCategoryConfigEntry ::=
        SEQUENCE {
            tnMplsLspAlarmCategoryEntityType           TnEntityType,
            tnMplsLspAlarmCategoryCondition            TnCondition,
            tnPerMplsLspObjectAlarmCategory            TnTrapCategory,
            tnPerMplsLspObjectAlarmEntityTypeCategory  TnTrapCategory,
            tnPerMplsLspObjectAlarmDefaultCategory     TnTrapCategory }

    tnMplsLspAlarmCategoryEntityType OBJECT-TYPE
        SYNTAX         TnEntityType
        MAX-ACCESS     not-accessible
        STATUS         current
        DESCRIPTION    "The AID type."
        ::= { tnPerMplsLspObjectAlarmCategoryConfigEntry 1 }

    tnMplsLspAlarmCategoryCondition OBJECT-TYPE
        SYNTAX         TnCondition
        MAX-ACCESS     not-accessible
        STATUS         current
        DESCRIPTION    "The condition."
        ::= { tnPerMplsLspObjectAlarmCategoryConfigEntry 2 }

    tnPerMplsLspObjectAlarmCategory OBJECT-TYPE
        SYNTAX         TnTrapCategory
        MAX-ACCESS     read-create
        STATUS         current
        DESCRIPTION    "The category. The valid configurable values are:
                        criticalAlarms(1)
                        majorAlarms(2)
                        minorAlarms(3)
                        notAlarmed(7)
                        none(8)
                        notReported(10)
                        warningAlarms(12)
                        Setting the category to be equal to the default
                        category is the same as setting it to none. The
                        category is returned as none, as a result."
        ::= { tnPerMplsLspObjectAlarmCategoryConfigEntry 3 }

    tnPerMplsLspObjectAlarmEntityTypeCategory OBJECT-TYPE
        SYNTAX         TnTrapCategory
        MAX-ACCESS     read-only
        STATUS         current
        DESCRIPTION    "The entity type category."
        ::= { tnPerMplsLspObjectAlarmCategoryConfigEntry 4 }

    tnPerMplsLspObjectAlarmDefaultCategory OBJECT-TYPE
        SYNTAX         TnTrapCategory
        MAX-ACCESS     read-only
        STATUS         current
        DESCRIPTION    "The default category."
        ::= { tnPerMplsLspObjectAlarmCategoryConfigEntry 5 }

--------------------------------------------------------------------------------
-- Per Service Routing (SR) SDP BIND Object Alarm
-- Category Config Scalar
--------------------------------------------------------------------------------
    tnPerSdpBindObjectAlarmCategoryConfigAttributeTotal OBJECT-TYPE
        SYNTAX         Integer32
        MAX-ACCESS     read-only
        STATUS         current
        DESCRIPTION    "."
        ::= { tnLogAlarmCategoryConfig 43 }

-------------------------------------------------------------------
-- Per SR ERP Object Alarm Category Config Table
-------------------------------------------------------------------
    tnPerSdpBindObjectAlarmCategoryConfigTable OBJECT-TYPE
        SYNTAX         SEQUENCE OF TnPerSdpBindObjectAlarmCategoryConfigEntry
        MAX-ACCESS     not-accessible
        STATUS         current
        DESCRIPTION    "."
        ::= { tnLogAlarmCategoryConfig 44 }

    tnPerSdpBindObjectAlarmCategoryConfigEntry OBJECT-TYPE
        SYNTAX         TnPerSdpBindObjectAlarmCategoryConfigEntry
        MAX-ACCESS     not-accessible
        STATUS         current
        DESCRIPTION    "."
        INDEX { tnSysSwitchId,
                tnSvcId,
                sdpBindId,
                tnSdpBindAlarmCategoryEntityType,
                tnSdpBindAlarmCategoryCondition }
        ::= { tnPerSdpBindObjectAlarmCategoryConfigTable 1 }

    TnPerSdpBindObjectAlarmCategoryConfigEntry ::=
        SEQUENCE {
            tnSdpBindAlarmCategoryEntityType           TnEntityType,
            tnSdpBindAlarmCategoryCondition            TnCondition,
            tnPerSdpBindObjectAlarmCategory            TnTrapCategory,
            tnPerSdpBindObjectAlarmEntityTypeCategory  TnTrapCategory,
            tnPerSdpBindObjectAlarmDefaultCategory     TnTrapCategory }

    tnSdpBindAlarmCategoryEntityType OBJECT-TYPE
        SYNTAX         TnEntityType
        MAX-ACCESS     not-accessible
        STATUS         current
        DESCRIPTION    "The AID type."
        ::= { tnPerSdpBindObjectAlarmCategoryConfigEntry 1 }

    tnSdpBindAlarmCategoryCondition OBJECT-TYPE
        SYNTAX         TnCondition
        MAX-ACCESS     not-accessible
        STATUS         current
        DESCRIPTION    "The condition."
        ::= { tnPerSdpBindObjectAlarmCategoryConfigEntry 2 }

    tnPerSdpBindObjectAlarmCategory OBJECT-TYPE
        SYNTAX         TnTrapCategory
        MAX-ACCESS     read-create
        STATUS         current
        DESCRIPTION    "The category. The valid configurable values are:
                        criticalAlarms(1)
                        majorAlarms(2)
                        minorAlarms(3)
                        notAlarmed(7)
                        none(8)
                        notReported(10)
                        warningAlarms(12)
                        Setting the category to be equal to the default
                        category is the same as setting it to none. The
                        category is returned as none, as a result."
        ::= { tnPerSdpBindObjectAlarmCategoryConfigEntry 3 }

    tnPerSdpBindObjectAlarmEntityTypeCategory OBJECT-TYPE
        SYNTAX         TnTrapCategory
        MAX-ACCESS     read-only
        STATUS         current
        DESCRIPTION    "The entity type category."
        ::= { tnPerSdpBindObjectAlarmCategoryConfigEntry 4 }

    tnPerSdpBindObjectAlarmDefaultCategory OBJECT-TYPE
        SYNTAX         TnTrapCategory
        MAX-ACCESS     read-only
        STATUS         current
        DESCRIPTION    "The default category."
        ::= { tnPerSdpBindObjectAlarmCategoryConfigEntry 5 }

--------------------------------------------------------------------------------
-- Per Service Routing (SR) MPLS Intfc Object Alarm
-- Category Config Scalar
--------------------------------------------------------------------------------
    tnPerMplsIfObjectAlarmCategoryConfigAttributeTotal OBJECT-TYPE
        SYNTAX         Integer32
        MAX-ACCESS     read-only
        STATUS         current
        DESCRIPTION    "."
        ::= { tnLogAlarmCategoryConfig 45 }

-------------------------------------------------------------------
-- Per SR ERP Object Alarm Category Config Table
-------------------------------------------------------------------
    tnPerMplsIfObjectAlarmCategoryConfigTable OBJECT-TYPE
        SYNTAX         SEQUENCE OF TnPerMplsIfObjectAlarmCategoryConfigEntry
        MAX-ACCESS     not-accessible
        STATUS         current
        DESCRIPTION    "."
        ::= { tnLogAlarmCategoryConfig 46 }

    tnPerMplsIfObjectAlarmCategoryConfigEntry OBJECT-TYPE
        SYNTAX         TnPerMplsIfObjectAlarmCategoryConfigEntry
        MAX-ACCESS     not-accessible
        STATUS         current
        DESCRIPTION    "."
        INDEX { tnSysSwitchId,
                vRtrID,
                vRtrIfIndex,
                tnMplsIfAlarmCategoryEntityType,
                tnMplsIfAlarmCategoryCondition }
        ::= { tnPerMplsIfObjectAlarmCategoryConfigTable 1 }

    TnPerMplsIfObjectAlarmCategoryConfigEntry ::=
        SEQUENCE {
            tnMplsIfAlarmCategoryEntityType           TnEntityType,
            tnMplsIfAlarmCategoryCondition            TnCondition,
            tnPerMplsIfObjectAlarmCategory            TnTrapCategory,
            tnPerMplsIfObjectAlarmEntityTypeCategory  TnTrapCategory,
            tnPerMplsIfObjectAlarmDefaultCategory     TnTrapCategory }

    tnMplsIfAlarmCategoryEntityType OBJECT-TYPE
        SYNTAX         TnEntityType
        MAX-ACCESS     not-accessible
        STATUS         current
        DESCRIPTION    "The AID type."
        ::= { tnPerMplsIfObjectAlarmCategoryConfigEntry 1 }

    tnMplsIfAlarmCategoryCondition OBJECT-TYPE
        SYNTAX         TnCondition
        MAX-ACCESS     not-accessible
        STATUS         current
        DESCRIPTION    "The condition."
        ::= { tnPerMplsIfObjectAlarmCategoryConfigEntry 2 }

    tnPerMplsIfObjectAlarmCategory OBJECT-TYPE
        SYNTAX         TnTrapCategory
        MAX-ACCESS     read-create
        STATUS         current
        DESCRIPTION    "The category. The valid configurable values are:
                        criticalAlarms(1)
                        majorAlarms(2)
                        minorAlarms(3)
                        notAlarmed(7)
                        none(8)
                        notReported(10)
                        warningAlarms(12)
                        Setting the category to be equal to the default
                        category is the same as setting it to none. The
                        category is returned as none, as a result."
        ::= { tnPerMplsIfObjectAlarmCategoryConfigEntry 3 }

    tnPerMplsIfObjectAlarmEntityTypeCategory OBJECT-TYPE
        SYNTAX         TnTrapCategory
        MAX-ACCESS     read-only
        STATUS         current
        DESCRIPTION    "The entity type category."
        ::= { tnPerMplsIfObjectAlarmCategoryConfigEntry 4 }

    tnPerMplsIfObjectAlarmDefaultCategory OBJECT-TYPE
        SYNTAX         TnTrapCategory
        MAX-ACCESS     read-only
        STATUS         current
        DESCRIPTION    "The default category."
        ::= { tnPerMplsIfObjectAlarmCategoryConfigEntry 5 }

--------------------------------------------------------------------------------
-- Per Service Routing (SR) MPLS LSP PATH Object Alarm
-- Category Config Scalar
--------------------------------------------------------------------------------
    tnPerMplsLspPathObjectAlarmCategoryConfigAttributeTotal OBJECT-TYPE
        SYNTAX         Integer32
        MAX-ACCESS     read-only
        STATUS         current
        DESCRIPTION    "."
        ::= { tnLogAlarmCategoryConfig 47 }

-------------------------------------------------------------------
-- Per SR MPLS LSP PATH Object Alarm Category Config Table
-------------------------------------------------------------------
    tnPerMplsLspPathObjectAlarmCategoryConfigTable OBJECT-TYPE
        SYNTAX         SEQUENCE OF TnPerMplsLspPathObjectAlarmCategoryConfigEntry
        MAX-ACCESS     not-accessible
        STATUS         current
        DESCRIPTION    "."
        ::= { tnLogAlarmCategoryConfig 48 }

    tnPerMplsLspPathObjectAlarmCategoryConfigEntry OBJECT-TYPE
        SYNTAX         TnPerMplsLspPathObjectAlarmCategoryConfigEntry
        MAX-ACCESS     not-accessible
        STATUS         current
        DESCRIPTION    "."
        INDEX { tnSysSwitchId,
                vRtrID,
                vRtrMplsLspIndex,
                vRtrMplsTpLspPathIndex,
                tnMplsLspPathAlarmCategoryEntityType,
                tnMplsLspPathAlarmCategoryCondition }
        ::= { tnPerMplsLspPathObjectAlarmCategoryConfigTable 1 }

    TnPerMplsLspPathObjectAlarmCategoryConfigEntry ::=
        SEQUENCE {
            tnMplsLspPathAlarmCategoryEntityType           TnEntityType,
            tnMplsLspPathAlarmCategoryCondition            TnCondition,
            tnPerMplsLspPathObjectAlarmCategory            TnTrapCategory,
            tnPerMplsLspPathObjectAlarmEntityTypeCategory  TnTrapCategory,
            tnPerMplsLspPathObjectAlarmDefaultCategory     TnTrapCategory }

    tnMplsLspPathAlarmCategoryEntityType OBJECT-TYPE
        SYNTAX         TnEntityType
        MAX-ACCESS     not-accessible
        STATUS         current
        DESCRIPTION    "The AID type."
        ::= { tnPerMplsLspPathObjectAlarmCategoryConfigEntry 1 }

    tnMplsLspPathAlarmCategoryCondition OBJECT-TYPE
        SYNTAX         TnCondition
        MAX-ACCESS     not-accessible
        STATUS         current
        DESCRIPTION    "The condition."
        ::= { tnPerMplsLspPathObjectAlarmCategoryConfigEntry 2 }

    tnPerMplsLspPathObjectAlarmCategory OBJECT-TYPE
        SYNTAX         TnTrapCategory
        MAX-ACCESS     read-create
        STATUS         current
        DESCRIPTION    "The category. The valid configurable values are:
                        criticalAlarms(1)
                        majorAlarms(2)
                        minorAlarms(3)
                        notAlarmed(7)
                        none(8)
                        notReported(10)
                        warningAlarms(12)
                        Setting the category to be equal to the default
                        category is the same as setting it to none. The
                        category is returned as none, as a result."
        ::= { tnPerMplsLspPathObjectAlarmCategoryConfigEntry 3 }

    tnPerMplsLspPathObjectAlarmEntityTypeCategory OBJECT-TYPE
        SYNTAX         TnTrapCategory
        MAX-ACCESS     read-only
        STATUS         current
        DESCRIPTION    "The entity type category."
        ::= { tnPerMplsLspPathObjectAlarmCategoryConfigEntry 4 }

    tnPerMplsLspPathObjectAlarmDefaultCategory OBJECT-TYPE
        SYNTAX         TnTrapCategory
        MAX-ACCESS     read-only
        STATUS         current
        DESCRIPTION    "The default category."
        ::= { tnPerMplsLspPathObjectAlarmCategoryConfigEntry 5 }

--------------------------------------------------------------------------------
-- Per Wanif Object Alarm
-- Category Config Scalar
--------------------------------------------------------------------------------
    tnPerWanifObjectAlarmCategoryConfigAttributeTotal OBJECT-TYPE
        SYNTAX         Integer32
        MAX-ACCESS     read-only
        STATUS         current
        DESCRIPTION    "."
        ::= { tnLogAlarmCategoryConfig 49 }

-------------------------------------------------------------------
-- Per Wanif Object Alarm Category Config Table
-------------------------------------------------------------------
    tnPerWanifObjectAlarmCategoryConfigTable OBJECT-TYPE
        SYNTAX         SEQUENCE OF TnPerWanifObjectAlarmCategoryConfigEntry
        MAX-ACCESS     not-accessible
        STATUS         current
        DESCRIPTION    "."
        ::= { tnLogAlarmCategoryConfig 50 }

    tnPerWanifObjectAlarmCategoryConfigEntry OBJECT-TYPE
        SYNTAX         TnPerWanifObjectAlarmCategoryConfigEntry
        MAX-ACCESS     not-accessible
        STATUS         current
        DESCRIPTION    "."
        INDEX { tnWanifAlarmCategoryObjectId,
                tnWanifAlarmCategoryDirection,
                tnWanifAlarmCategoryEntityType,
                tnWanifAlarmCategoryCondition }
        ::= { tnPerWanifObjectAlarmCategoryConfigTable 1 }

    TnPerWanifObjectAlarmCategoryConfigEntry ::=
        SEQUENCE {
            tnWanifAlarmCategoryObjectId             Unsigned32,
            tnWanifAlarmCategoryDirection            AluWdmAlarmCategoryDirection,
            tnWanifAlarmCategoryEntityType           TnEntityType,
            tnWanifAlarmCategoryCondition            TnCondition,
            tnPerWanifObjectAlarmCategory            TnTrapCategory,
            tnPerWanifObjectAlarmEntityTypeCategory  TnTrapCategory,
            tnPerWanifObjectAlarmDefaultCategory     TnTrapCategory
        }

    tnWanifAlarmCategoryObjectId OBJECT-TYPE
        SYNTAX         Unsigned32
        MAX-ACCESS     not-accessible
        STATUS         current
        DESCRIPTION    "One of the following wanif object instances:
                        shelf(8b)/slot(8b)/res(3b)/wanif(10b)/res(3b)
                        shelf(8b)/slot(8b)/port(8b)/channel(4b)/res(4b)."
        ::= { tnPerWanifObjectAlarmCategoryConfigEntry 1 }

    tnWanifAlarmCategoryDirection OBJECT-TYPE
        SYNTAX         AluWdmAlarmCategoryDirection
        MAX-ACCESS     not-accessible
        STATUS         current
        DESCRIPTION    "The direction to which the new category will be
                        applied."
        ::= { tnPerWanifObjectAlarmCategoryConfigEntry 2 }

    tnWanifAlarmCategoryEntityType OBJECT-TYPE
        SYNTAX         TnEntityType
        MAX-ACCESS     not-accessible
        STATUS         current
        DESCRIPTION    "The AID type."
        ::= { tnPerWanifObjectAlarmCategoryConfigEntry 3 }

    tnWanifAlarmCategoryCondition OBJECT-TYPE
        SYNTAX         TnCondition
        MAX-ACCESS     not-accessible
        STATUS         current
        DESCRIPTION    "The condition."
        ::= { tnPerWanifObjectAlarmCategoryConfigEntry 4 }

    tnPerWanifObjectAlarmCategory OBJECT-TYPE
        SYNTAX         TnTrapCategory
        MAX-ACCESS     read-create
        STATUS         current
        DESCRIPTION    "The category.  The valid configurable values are:

                        criticalAlarms(1)
                        majorAlarms(2)
                        minorAlarms(3)
                        notAlarmed(7)
                        none(8)
                        notReported(10)
                        warningAlarms(12)

                        Setting the category to be equal to the default
                        category is the same as setting it to none.  The
                        category is returned as none, as a result."
        ::= { tnPerWanifObjectAlarmCategoryConfigEntry 5 }

    tnPerWanifObjectAlarmEntityTypeCategory OBJECT-TYPE
        SYNTAX         TnTrapCategory
        MAX-ACCESS     read-only
        STATUS         current
        DESCRIPTION    "The entity type category."
        ::= { tnPerWanifObjectAlarmCategoryConfigEntry 6 }

    tnPerWanifObjectAlarmDefaultCategory OBJECT-TYPE
        SYNTAX         TnTrapCategory
        MAX-ACCESS     read-only
        STATUS         current
        DESCRIPTION    "The default category."
        ::= { tnPerWanifObjectAlarmCategoryConfigEntry 7 }

--------------------------------------------------------------------------------
-- Per Packet Switch Object Alarm
-- Category Config Scalar
--------------------------------------------------------------------------------
    tnPerPacketSwitchObjectAlarmCategoryConfigAttributeTotal OBJECT-TYPE
        SYNTAX         Integer32
        MAX-ACCESS     read-only
        STATUS         current
        DESCRIPTION    "."
        ::= { tnLogAlarmCategoryConfig 51 }

-------------------------------------------------------------------
-- Per Packet Switch Object Alarm Category Config Table
-------------------------------------------------------------------
    tnPerPacketSwitchObjectAlarmCategoryConfigTable OBJECT-TYPE
        SYNTAX         SEQUENCE OF TnPerPacketSwitchObjectAlarmCategoryConfigEntry
        MAX-ACCESS     not-accessible
        STATUS         current
        DESCRIPTION    "."
        ::= { tnLogAlarmCategoryConfig 52 }

    tnPerPacketSwitchObjectAlarmCategoryConfigEntry OBJECT-TYPE
        SYNTAX         TnPerPacketSwitchObjectAlarmCategoryConfigEntry
        MAX-ACCESS     not-accessible
        STATUS         current
        DESCRIPTION    "."
        INDEX { tnSysSwitchId,
                tnPacketSwitchAlarmCategoryEntityType,
                tnPacketSwitchAlarmCategoryCondition }
        ::= { tnPerPacketSwitchObjectAlarmCategoryConfigTable 1 }

    TnPerPacketSwitchObjectAlarmCategoryConfigEntry ::=
        SEQUENCE {
            tnPacketSwitchAlarmCategoryEntityType           TnEntityType,
            tnPacketSwitchAlarmCategoryCondition            TnCondition,
            tnPerPacketSwitchObjectAlarmCategory            TnTrapCategory,
            tnPerPacketSwitchObjectAlarmEntityTypeCategory  TnTrapCategory,
            tnPerPacketSwitchObjectAlarmDefaultCategory     TnTrapCategory }

    tnPacketSwitchAlarmCategoryEntityType OBJECT-TYPE
        SYNTAX         TnEntityType
        MAX-ACCESS     not-accessible
        STATUS         current
        DESCRIPTION    "The AID type."
        ::= { tnPerPacketSwitchObjectAlarmCategoryConfigEntry 1 }

    tnPacketSwitchAlarmCategoryCondition OBJECT-TYPE
        SYNTAX         TnCondition
        MAX-ACCESS     not-accessible
        STATUS         current
        DESCRIPTION    "The condition."
        ::= { tnPerPacketSwitchObjectAlarmCategoryConfigEntry 2 }

    tnPerPacketSwitchObjectAlarmCategory OBJECT-TYPE
        SYNTAX         TnTrapCategory
        MAX-ACCESS     read-create
        STATUS         current
        DESCRIPTION    "The category. The valid configurable values are:

                        criticalAlarms(1)
                        majorAlarms(2)
                        minorAlarms(3)
                        notAlarmed(7)
                        none(8)
                        notReported(10)
                        warningAlarms(12)

                        Setting the category to be equal to the default
                        category is the same as setting it to none. The
                        category is returned as none, as a result."
        ::= { tnPerPacketSwitchObjectAlarmCategoryConfigEntry 3 }

    tnPerPacketSwitchObjectAlarmEntityTypeCategory OBJECT-TYPE
        SYNTAX         TnTrapCategory
        MAX-ACCESS     read-only
        STATUS         current
        DESCRIPTION    "The entity type category."
        ::= { tnPerPacketSwitchObjectAlarmCategoryConfigEntry 4 }

    tnPerPacketSwitchObjectAlarmDefaultCategory OBJECT-TYPE
        SYNTAX         TnTrapCategory
        MAX-ACCESS     read-only
        STATUS         current
        DESCRIPTION    "The default category."
        ::= { tnPerPacketSwitchObjectAlarmCategoryConfigEntry 5 }

-------------------------------------------------------------------
-- Alarm Severity Assignment Profile(ASAP) Management Scalar
-------------------------------------------------------------------
    tnAsapMgmtAttributeTotal OBJECT-TYPE
        SYNTAX         Integer32
        MAX-ACCESS     read-only
        STATUS         current
        DESCRIPTION    "."
        ::= { tnAsapManagement 1 }

-------------------------------------------------------------------
-- Alarm Severity Assignment Profile (ASAP) Management Table
-------------------------------------------------------------------
    tnAsapMgmtTable OBJECT-TYPE
        SYNTAX         SEQUENCE OF TnAsapMgmtEntry
        MAX-ACCESS     not-accessible
        STATUS         current
        DESCRIPTION    "."
        ::= { tnAsapManagement 2 }

    tnAsapMgmtEntry OBJECT-TYPE
        SYNTAX         TnAsapMgmtEntry
        MAX-ACCESS     not-accessible
        STATUS         current
        DESCRIPTION    "."
        INDEX { tnAsapName}
        ::= { tnAsapMgmtTable 1 }

    TnAsapMgmtEntry ::=
        SEQUENCE {
            tnAsapName         SnmpAdminString,
            tnAsapRowStatus    RowStatus,
            tnAsapType         AluWdmAsapType,
            tnAsapCloneFrom    SnmpAdminString,
            tnAsapNewName      SnmpAdminString,
            tnAsapDefaultFlag  INTEGER,
            tnAsapSysDefind    TruthValue
        }

    tnAsapName OBJECT-TYPE
        SYNTAX         SnmpAdminString (SIZE(0..40))
        MAX-ACCESS     not-accessible
        STATUS         current
        DESCRIPTION    "Profile name to access tnAsapMgmtTable."
        ::= { tnAsapMgmtEntry 1 }

    tnAsapRowStatus OBJECT-TYPE
        SYNTAX         RowStatus
        MAX-ACCESS     read-create
        STATUS         current
        DESCRIPTION    "Row status for tnAsapMgmtTable ."
        ::= { tnAsapMgmtEntry 2 }

    tnAsapType  OBJECT-TYPE
        SYNTAX         AluWdmAsapType
        MAX-ACCESS     read-create
        STATUS         current
        DESCRIPTION    "Different ASAP types."
        DEFVAL         { unknown }
        ::= { tnAsapMgmtEntry 3 }

    tnAsapCloneFrom OBJECT-TYPE
        SYNTAX         SnmpAdminString (SIZE(0..40))
        MAX-ACCESS     read-create
        STATUS         current
        DESCRIPTION    "tnAsapName is a Profile cloned from tnAsapCloneFrom."
        ::= { tnAsapMgmtEntry 4 }

    tnAsapNewName OBJECT-TYPE
        SYNTAX         SnmpAdminString (SIZE(0..40))
        MAX-ACCESS     read-create
        STATUS         current
        DESCRIPTION    "tnAsapNewName is a new name changed from tnAsapName."
        ::= { tnAsapMgmtEntry 5 }

    tnAsapDefaultFlag OBJECT-TYPE
        SYNTAX         INTEGER {
                         yes(1),
                         no(2)
                       }
        MAX-ACCESS     read-create
        STATUS         current
        DESCRIPTION    "tnAsapName is to be used as ASAP default for tnAsapType"
        ::= { tnAsapMgmtEntry 6 }

    tnAsapSysDefind OBJECT-TYPE
        SYNTAX         TruthValue
        MAX-ACCESS     read-create
        STATUS         current
        DESCRIPTION    "tnAsapName is System defined, and not User defined"
        ::= { tnAsapMgmtEntry 7 }

--    obsolete
--    tnAsapMgmtDetailAttributeTotal OBJECT-TYPE ::= { tnAsapManagement 3 }
--    tnAsapMgmtDetailTable OBJECT-TYPE ::= { tnAsapManagement 4 }

---------------------------------------------------------------------------
-- Alarm Severity Assignment Profile (ASAP) Management Detail Scalar
---------------------------------------------------------------------------
    tnAsapTypeIndexAttributeTotal OBJECT-TYPE
        SYNTAX         Integer32
        MAX-ACCESS     read-only
        STATUS         current
        DESCRIPTION    "."
        ::= { tnAsapManagement 5 }

--------------------------------------------------------------------------------
-- ASAP Index Table
--------------------------------------------------------------------------------
    tnAsapTypeIndexTable OBJECT-TYPE
        SYNTAX         SEQUENCE OF TnAsapTypeIndexEntry
        MAX-ACCESS     not-accessible
        STATUS         current
        DESCRIPTION    "."
        ::= { tnAsapManagement 6 }

    tnAsapTypeIndexEntry OBJECT-TYPE
        SYNTAX         TnAsapTypeIndexEntry
        MAX-ACCESS     not-accessible
        STATUS         current
        DESCRIPTION    "."
        INDEX { tnAsapTypeIndex }
        ::= { tnAsapTypeIndexTable 1 }

    TnAsapTypeIndexEntry ::=
        SEQUENCE {
            tnAsapTypeIndex     Unsigned32
        }

    tnAsapTypeIndex OBJECT-TYPE
        SYNTAX         Unsigned32 (1..50)
        MAX-ACCESS     not-accessible
        STATUS         current
        DESCRIPTION    "ASAP index
                     -------------------------------------
                     | AsapUnknown ------------------- 0  |
                     | AsapBits ---------------------- 1  |
                     | AsapNgige --------------------- 2  |
                     | AsapCbr ----------------------- 3  |
                     | AsapCom ----------------------- 4  |
                     | AsapDdr ----------------------- 5  |
                     | AsapE1 ------------------------ 6  |
                     | AsapEnv ----------------------- 7  |
                     | AsapEqpt ---------------------- 8  |
                     | AsapFcn ----------------------- 9  |
                     | AsapFe ------------------------ 10 |
                     | AsapLineref ------------------- 11 |
                     | AsapOcn ----------------------- 12 |
                     | AsapOch ----------------------- 13 |
                     | AsapOdu ----------------------- 14 |
                     | AsapOdutcm -------------------- 15 |
                     | AsapOms ----------------------- 16 |
                     | AsapOptsg --------------------- 17 |
                     | AsapOts ----------------------- 18 |
                     | AsapOtu------------------------ 19 |
                     | AsapPlk ----------------------- 20 |
                     | AsapProactivetest ------------- 21 |
                     | AsapPtpclock ------------------ 22 |
                     | AsapPtpport ------------------- 23 |
                     | AsapStmn ---------------------- 24 |
                     | AsapSync ---------------------- 25 |
                     | AsapTod ----------------------- 26 |
                     | AsapVts ----------------------- 27 |
                     | AsapPacket -------------------- 28 |
                     | AsapOtsig --------------------- 29 |
                     |------------------------------------"
        ::= { tnAsapTypeIndexEntry 1 }

---------------------------------------------------------------------------
-- Alarm Severity Assignment Profile (ASAP) Management Detail Scalar
---------------------------------------------------------------------------
    tnAsapMgmtDetailsAttributeTotal OBJECT-TYPE
        SYNTAX         Integer32
        MAX-ACCESS     read-only
        STATUS         current
        DESCRIPTION    "."
        ::= { tnAsapManagement 7 }

--------------------------------------------------------------------------
-- Alarm Severity Assignment Profile (ASAP) Management Details Table
--------------------------------------------------------------------------
    tnAsapMgmtDetailsTable OBJECT-TYPE
        SYNTAX         SEQUENCE OF TnAsapMgmtDetailsEntry
        MAX-ACCESS     not-accessible
        STATUS         current
        DESCRIPTION    "."
        ::= { tnAsapManagement 8 }

    tnAsapMgmtDetailsEntry OBJECT-TYPE
        SYNTAX         TnAsapMgmtDetailsEntry
        MAX-ACCESS     not-accessible
        STATUS         current
        DESCRIPTION    "."
        INDEX { tnAsapTypeIndex,
                tnAsapName,
                tnAsapDetailsCondition }
        ::= { tnAsapMgmtDetailsTable 1 }

    TnAsapMgmtDetailsEntry ::=
        SEQUENCE {
            tnAsapDetailsCondition      TnCondition,
            tnAsapDetailsAlarmSeverity  TnTrapCategory
        }

    tnAsapDetailsCondition OBJECT-TYPE
        SYNTAX         TnCondition
        MAX-ACCESS     not-accessible
        STATUS         current
        DESCRIPTION    "."
        ::= { tnAsapMgmtDetailsEntry 1 }

    tnAsapDetailsAlarmSeverity  OBJECT-TYPE
        SYNTAX         TnTrapCategory
        MAX-ACCESS     read-create
        STATUS         current
        DESCRIPTION    "ASAP severity."
        ::= { tnAsapMgmtDetailsEntry 2 }

-------------------------------------------------------------------
-- Conformance Group Definitions
-------------------------------------------------------------------
    tnLogScalarsGroup OBJECT-GROUP
        OBJECTS {
            tnCriticalAlarmLogTotal,
            tnMajorAlarmLogTotal,
            tnMinorAlarmLogTotal,
            tnStateChangeLogTotal,
            tnUserActionLogTotal,
            tnGeneralEventLogTotal,
            tnLogTotal,
            tnActiveAlarmTotal,
            tnPersistentLogTotal,
            tnActiveCriticalAlarmTotal,
            tnActiveMajorAlarmTotal,
            tnActiveMinorAlarmTotal,
            tnActiveOrMaskedAlarmTotal,
            tnNotAlarmedLogTotal,
            tnSecurityLogTotal,
            tnWarningAlarmLogTotal,
            tnActiveWarningAlarmTotal
        }
        STATUS         current
        DESCRIPTION    "."
        ::= { tnLogGroups 1 }

    tnCriticalAlarmLogGroup OBJECT-GROUP
        OBJECTS {
            tnCriticalAlarmLogType,
            tnCriticalAlarmLogTime,
            tnCriticalAlarmLogObjectIDType,
            tnCriticalAlarmLogObjectID,
            tnCriticalAlarmLogDescr,
            tnCriticalAlarmLogData,
            tnCriticalAlarmLogServiceAffecting,
            tnCriticalAlarmLogSlotProgrammedType,
            tnCriticalAlarmLogEntityType,
            tnCriticalAlarmLogCondition,
            tnCriticalAlarmLogObjectIDIpV6,
            tnCriticalAlarmLogSlotProgrammedGenericType
        }
        STATUS         current
        DESCRIPTION    "."
        ::= { tnLogGroups 2 }

    tnMajorAlarmLogGroup OBJECT-GROUP
        OBJECTS {
            tnMajorAlarmLogType,
            tnMajorAlarmLogTime,
            tnMajorAlarmLogObjectIDType,
            tnMajorAlarmLogObjectID,
            tnMajorAlarmLogDescr,
            tnMajorAlarmLogData,
            tnMajorAlarmLogServiceAffecting,
            tnMajorAlarmLogSlotProgrammedType,
            tnMajorAlarmLogEntityType,
            tnMajorAlarmLogCondition,
            tnMajorAlarmLogObjectIDIpV6,
            tnMajorAlarmLogSlotProgrammedGenericType
        }
        STATUS         current
        DESCRIPTION    "."
        ::= { tnLogGroups 3 }

    tnMinorAlarmLogGroup OBJECT-GROUP
        OBJECTS {
            tnMinorAlarmLogType,
            tnMinorAlarmLogTime,
            tnMinorAlarmLogObjectIDType,
            tnMinorAlarmLogObjectID,
            tnMinorAlarmLogDescr,
            tnMinorAlarmLogData,
            tnMinorAlarmLogServiceAffecting,
            tnMinorAlarmLogSlotProgrammedType,
            tnMinorAlarmLogEntityType,
            tnMinorAlarmLogCondition,
            tnMinorAlarmLogObjectIDIpV6,
            tnMinorAlarmLogSlotProgrammedGenericType
        }
        STATUS         current
        DESCRIPTION    "."
        ::= { tnLogGroups 4 }

    tnStateChangeLogGroup OBJECT-GROUP
        OBJECTS {
            tnStateChangeLogType,
            tnStateChangeLogTime,
            tnStateChangeLogObjectIDType,
            tnStateChangeLogObjectID,
            tnStateChangeLogDescr,
            tnStateChangeLogData,
            tnStateChangeLogSlotProgrammedType,
            tnStateChangeLogObjectIDIpV6,
            tnStateChangeLogSlotProgrammedGenericType
        }
        STATUS         current
        DESCRIPTION    "."
        ::= { tnLogGroups 5 }

    tnUserActionLogGroup OBJECT-GROUP
        OBJECTS {
            tnUserActionLogType,
            tnUserActionLogTime,
            tnUserActionLogObjectIDType,
            tnUserActionLogObjectID,
            tnUserActionLogDescr,
            tnUserActionLogChangedObject,
            tnUserActionLogData,
            tnUserActionLogObjectIDIpV6
        }
        STATUS         current
        DESCRIPTION    "."
        ::= { tnLogGroups 6 }

    tnGeneralEventLogGroup OBJECT-GROUP
        OBJECTS {
            tnGeneralEventLogType,
            tnGeneralEventLogTime,
            tnGeneralEventLogObjectIDType,
            tnGeneralEventLogObjectID,
            tnGeneralEventLogDescr,
            tnGeneralEventLogChangedObject,
            tnGeneralEventLogData,
            tnGeneralEventLogSlotProgrammedType,
            tnGeneralEventLogObjectIDIpV6,
            tnGeneralEventLogSlotProgrammedGenericType
        }
        STATUS         current
        DESCRIPTION    "."
        ::= { tnLogGroups 7 }

    tnLogGroup OBJECT-GROUP
        OBJECTS {
            tnLogType,
            tnLogTime,
            tnLogObjectIDType,
            tnLogObjectID,
            tnLogCategory,
            tnLogDescr,
            tnLogChangedObject,
            tnLogData,
            tnLogServiceAffecting,
            tnLogSlotProgrammedType,
            tnLogEntityType,
            tnLogCondition,
            tnLogObjectIDIpV6,
            tnLogSlotProgrammedGenericType
        }
        STATUS         current
        DESCRIPTION    "."
        ::= { tnLogGroups 8 }

    tnActiveAlarmGroup OBJECT-GROUP
        OBJECTS {
            tnActiveAlarmType,
            tnActiveAlarmTime,
            tnActiveAlarmObjectIDType,
            tnActiveAlarmObjectID,
            tnActiveAlarmCategory,
            tnActiveAlarmDescr,
            tnActiveAlarmData,
            tnActiveAlarmServiceAffecting,
            tnActiveAlarmSlotProgrammedType,
            tnActiveAlarmEntityType,
            tnActiveAlarmCondition,
            tnActiveAlarmSlotProgrammedGenericType
        }
        STATUS         current
        DESCRIPTION    "."
        ::= { tnLogGroups 9 }

    tnPersistentLogGroup OBJECT-GROUP
        OBJECTS {
            tnPersistentLogType,
            tnPersistentLogTime,
            tnPersistentLogObjectIDType,
            tnPersistentLogObjectID,
            tnPersistentLogCategory,
            tnPersistentLogDescr,
            tnPersistentLogChangedObject,
            tnPersistentLogData,
            tnPersistentLogServiceAffecting,
            tnPersistentLogSlotProgrammedType,
            tnPersistentLogObjectIDIpV6
        }
        STATUS         current
        DESCRIPTION    "."
        ::= { tnLogGroups 10 }

    tnActiveOrMaskedAlarmGroup OBJECT-GROUP
        OBJECTS {
            tnActiveOrMaskedAlarmType,
            tnActiveOrMaskedAlarmTime,
            tnActiveOrMaskedAlarmObjectIDType,
            tnActiveOrMaskedAlarmObjectID,
            tnActiveOrMaskedAlarmCategory,
            tnActiveOrMaskedAlarmDescr,
            tnActiveOrMaskedAlarmData,
            tnActiveOrMaskedAlarmServiceAffecting,
            tnActiveOrMaskedAlarmSlotProgrammedType,
            tnActiveOrMaskedAlarmIsMasked,
            tnActiveOrMaskedAlarmEntityType,
            tnActiveOrMaskedAlarmCondition
        }
        STATUS         current
        DESCRIPTION    "."
        ::= { tnLogGroups 11 }

    tnNotAlarmedLogGroup OBJECT-GROUP
        OBJECTS {
            tnNotAlarmedLogType,
            tnNotAlarmedLogTime,
            tnNotAlarmedLogObjectIDType,
            tnNotAlarmedLogObjectID,
            tnNotAlarmedLogDescr,
            tnNotAlarmedLogData,
            tnNotAlarmedLogServiceAffecting,
            tnNotAlarmedLogSlotProgrammedType,
            tnNotAlarmedLogEntityType,
            tnNotAlarmedLogCondition,
            tnNotAlarmedLogObjectIDIpV6,
            tnNotAlarmedLogSlotProgrammedGenericType
        }
        STATUS         current
        DESCRIPTION    "."
        ::= { tnLogGroups 12 }

    tnPerObjectAlarmCategoryConfigGroup OBJECT-GROUP
        OBJECTS {
            tnPerObjectAlarmCategory,
            tnPerObjectAlarmEntityTypeCategory,
            tnPerObjectAlarmDefaultCategory
        }
        STATUS         current
        DESCRIPTION    "."
        ::= { tnLogGroups 13 }

    tnAlarmProfileConfigGroup OBJECT-GROUP
        OBJECTS {
            tnAlarmProfileConfigCategory,
            tnAlarmProfileConfigDefaultCategory,
            tnAlarmProfileConfigDescr
        }
        STATUS         current
        DESCRIPTION    "."
        ::= { tnLogGroups 14 }

    tnSecurityLogGroup OBJECT-GROUP
        OBJECTS {
            tnSecurityLogType,
            tnSecurityLogTime,
            tnSecurityLogObjectIDType,
            tnSecurityLogObjectID,
            tnSecurityLogDescr,
            tnSecurityLogData,
            tnSecurityLogUserID,
            tnSecurityLogUserSessionNumber,
            tnSecurityLogHeaderType,
            tnSecurityLogUserPrivilege,
            tnSecurityLogUserDestinationAddress,
            tnSecurityLogResult,
            tnSecurityLogObjectIDIpV6
        }
        STATUS         current
        DESCRIPTION    "."
        ::= { tnLogGroups 15 }

    tnWarningAlarmLogGroup OBJECT-GROUP
        OBJECTS {
            tnWarningAlarmLogType,
            tnWarningAlarmLogTime,
            tnWarningAlarmLogObjectIDType,
            tnWarningAlarmLogObjectID,
            tnWarningAlarmLogDescr,
            tnWarningAlarmLogData,
            tnWarningAlarmLogServiceAffecting,
            tnWarningAlarmLogSlotProgrammedType,
            tnWarningAlarmLogEntityType,
            tnWarningAlarmLogCondition,
            tnWarningAlarmLogObjectIDIpV6,
            tnWarningAlarmLogSlotProgrammedGenericType
        }
        STATUS         current
        DESCRIPTION    "."
        ::= { tnLogGroups 16 }

--    obsolete
--    tnPerLogicObjectAlarmCategoryConfigGroup OBJECT-GROUP ::= { tnLogGroups 17 }

    tnPerSyncObjectAlarmCategoryConfigGroup OBJECT-GROUP
        OBJECTS {
            tnPerSyncObjectAlarmCategory,
            tnPerSyncObjectAlarmEntityTypeCategory,
            tnPerSyncObjectAlarmDefaultCategory
        }
        STATUS         current
        DESCRIPTION    "."
        ::= { tnLogGroups 18 }

    tnPerVtsObjectAlarmCategoryConfigScalarsGroup OBJECT-GROUP
        OBJECTS {
            tnPerVtsObjectAlarmCategoryConfigAttributeTotal
        }
        STATUS         current
        DESCRIPTION    "."
        ::= { tnLogGroups 19 }

    tnPerVtsObjectAlarmCategoryConfigGroup OBJECT-GROUP
        OBJECTS {
            tnPerVtsObjectAlarmCategory,
            tnPerVtsObjectAlarmEntityTypeCategory,
            tnPerVtsObjectAlarmDefaultCategory
        }
        STATUS         current
        DESCRIPTION    "."
        ::= { tnLogGroups 20 }

    tnPerCcmObjectAlarmCategoryConfigScalarsGroup OBJECT-GROUP
        OBJECTS {
            tnPerCcmObjectAlarmCategoryConfigAttributeTotal
        }
        STATUS         current
        DESCRIPTION    "."
        ::= { tnLogGroups 21 }

    tnPerCcmObjectAlarmCategoryConfigGroup OBJECT-GROUP
        OBJECTS {
            tnPerCcmObjectAlarmCategory,
            tnPerCcmObjectAlarmEntityTypeCategory,
            tnPerCcmObjectAlarmDefaultCategory
        }
        STATUS         current
        DESCRIPTION    "."
        ::= { tnLogGroups 22 }

    tnPerTcmObjectAlarmCategoryConfigScalarsGroup OBJECT-GROUP
        OBJECTS {
            tnPerTcmObjectAlarmCategoryConfigAttributeTotal
        }
        STATUS         current
        DESCRIPTION    "."
        ::= { tnLogGroups 23 }

    tnPerTcmObjectAlarmCategoryConfigGroup OBJECT-GROUP
        OBJECTS {
            tnPerTcmObjectAlarmCategory,
            tnPerTcmObjectAlarmEntityTypeCategory,
            tnPerTcmObjectAlarmDefaultCategory
        }
        STATUS         current
        DESCRIPTION    "."
        ::= { tnLogGroups 24 }

    tnPerPtpObjectAlarmCategoryConfigScalarsGroup OBJECT-GROUP
        OBJECTS {
            tnPerPtpObjectAlarmCategoryConfigAttributeTotal
        }
        STATUS         current
        DESCRIPTION    "."
        ::= { tnLogGroups 25 }

    tnPerPtpObjectAlarmCategoryConfigGroup OBJECT-GROUP
        OBJECTS {
            tnPerPtpObjectAlarmCategory,
            tnPerPtpObjectAlarmEntityTypeCategory,
            tnPerPtpObjectAlarmDefaultCategory
        }
        STATUS         current
        DESCRIPTION    "."
        ::= { tnLogGroups 26 }

    tnPerLagObjectAlarmCategoryConfigScalarsGroup OBJECT-GROUP
        OBJECTS {
            tnPerLagObjectAlarmCategoryConfigAttributeTotal
        }
        STATUS         current
        DESCRIPTION    "."
        ::= { tnLogGroups 27 }

    tnPerLagObjectAlarmCategoryConfigGroup OBJECT-GROUP
        OBJECTS {
            tnPerLagObjectAlarmCategory,
            tnPerLagObjectAlarmEntityTypeCategory,
            tnPerLagObjectAlarmDefaultCategory
        }
        STATUS         current
        DESCRIPTION    "."
        ::= { tnLogGroups 28 }

    tnPerOtnObjectAlarmCategoryConfigScalarsGroup OBJECT-GROUP
        OBJECTS {
            tnPerOtnObjectAlarmCategoryConfigAttributeTotal
        }
        STATUS         deprecated
        DESCRIPTION    "."
        ::= { tnLogGroups 29 }

    tnPerOtnObjectAlarmCategoryConfigGroup OBJECT-GROUP
        OBJECTS {
            tnPerOtnObjectAlarmCategory,
            tnPerOtnObjectAlarmEntityTypeCategory,
            tnPerOtnObjectAlarmDefaultCategory
        }
        STATUS         deprecated
        DESCRIPTION    "."
        ::= { tnLogGroups 30 }

    tnPerSrSvcObjectAlarmCategoryConfigScalarsGroup OBJECT-GROUP
        OBJECTS {
            tnPerSrSvcObjectAlarmCategoryConfigAttributeTotal
        }
        STATUS         current
        DESCRIPTION    "."
        ::= { tnLogGroups 31 }

    tnPerSrSvcObjectAlarmCategoryConfigGroup OBJECT-GROUP
        OBJECTS {
            tnPerSrSvcObjectAlarmCategory,
            tnPerSrSvcObjectAlarmEntityTypeCategory,
            tnPerSrSvcObjectAlarmDefaultCategory
        }
        STATUS         current
        DESCRIPTION    "."
        ::= { tnLogGroups 32 }

    tnPerSrSapObjectAlarmCategoryConfigScalarsGroup OBJECT-GROUP
        OBJECTS {
            tnPerSrSapObjectAlarmCategoryConfigAttributeTotal
        }
        STATUS         current
        DESCRIPTION    "."
        ::= { tnLogGroups 33 }

    tnPerSrSapObjectAlarmCategoryConfigGroup OBJECT-GROUP
        OBJECTS {
            tnPerSrSapObjectAlarmCategory,
            tnPerSrSapObjectAlarmEntityTypeCategory,
            tnPerSrSapObjectAlarmDefaultCategory
        }
        STATUS         current
        DESCRIPTION    "."
        ::= { tnLogGroups 34 }

    tnPerSrErpObjectAlarmCategoryConfigScalarsGroup OBJECT-GROUP
        OBJECTS {
            tnPerSrErpObjectAlarmCategoryConfigAttributeTotal
        }
        STATUS         current
        DESCRIPTION    "."
        ::= { tnLogGroups 35 }

    tnPerSrErpObjectAlarmCategoryConfigGroup OBJECT-GROUP
        OBJECTS {
            tnPerSrErpObjectAlarmCategory,
            tnPerSrErpObjectAlarmEntityTypeCategory,
            tnPerSrErpObjectAlarmDefaultCategory
        }
        STATUS         current
        DESCRIPTION    "."
        ::= { tnLogGroups 36 }

    tnPerSrMepObjectAlarmCategoryConfigScalarsGroup OBJECT-GROUP
        OBJECTS {
            tnPerSrMepObjectAlarmCategoryConfigAttributeTotal
        }
        STATUS         current
        DESCRIPTION    "."
        ::= { tnLogGroups 37 }

    tnPerSrMepObjectAlarmCategoryConfigGroup OBJECT-GROUP
        OBJECTS {
            tnPerSrMepObjectAlarmCategory,
            tnPerSrMepObjectAlarmEntityTypeCategory,
            tnPerSrMepObjectAlarmDefaultCategory
        }
        STATUS         current
        DESCRIPTION    "."
        ::= { tnLogGroups 38 }

    tnPerSrOamTestObjectAlarmCategoryConfigScalarsGroup OBJECT-GROUP
        OBJECTS {
            tnPerSrOamTestObjectAlarmCategoryConfigAttributeTotal
        }
        STATUS         current
        DESCRIPTION    "."
        ::= { tnLogGroups 39 }

    tnPerSrOamTestObjectAlarmCategoryConfigGroup OBJECT-GROUP
        OBJECTS {
            tnPerSrOamTestObjectAlarmCategory,
            tnPerSrOamTestObjectAlarmEntityTypeCategory,
            tnPerSrOamTestObjectAlarmDefaultCategory
        }
        STATUS         current
        DESCRIPTION    "."
        ::= { tnLogGroups 40 }

    tnPerRmdObjectAlarmCategoryConfigScalarsGroup OBJECT-GROUP
        OBJECTS {
            tnPerRmdObjectAlarmCategoryConfigAttributeTotal
        }
        STATUS         current
        DESCRIPTION    "."
        ::= { tnLogGroups 41 }

    tnPerRmdObjectAlarmCategoryConfigGroup OBJECT-GROUP
        OBJECTS {
            tnPerRmdObjectAlarmCategory,
            tnPerRmdObjectAlarmEntityTypeCategory,
            tnPerRmdObjectAlarmDefaultCategory
        }
        STATUS         current
        DESCRIPTION    "."
        ::= { tnLogGroups 42 }

    tnPerRmdMepObjectAlarmCategoryConfigScalarsGroup OBJECT-GROUP
        OBJECTS {
            tnPerRmdMepObjectAlarmCategoryConfigAttributeTotal
        }
        STATUS         current
        DESCRIPTION    "."
        ::= { tnLogGroups 43 }

    tnPerRmdMepObjectAlarmCategoryConfigGroup OBJECT-GROUP
        OBJECTS {
            tnPerRmdMepObjectAlarmCategory,
            tnPerRmdMepObjectAlarmEntityTypeCategory,
            tnPerRmdMepObjectAlarmDefaultCategory
        }
        STATUS         current
        DESCRIPTION    "."
        ::= { tnLogGroups 44 }

    tnPerRmdIfObjectAlarmCategoryConfigScalarsGroup OBJECT-GROUP
        OBJECTS {
            tnPerRmdIfObjectAlarmCategoryConfigAttributeTotal
        }
        STATUS         current
        DESCRIPTION    "."
        ::= { tnLogGroups 45 }

    tnPerRmdIfObjectAlarmCategoryConfigGroup OBJECT-GROUP
        OBJECTS {
            tnPerRmdIfObjectAlarmCategory,
            tnPerRmdIfObjectAlarmEntityTypeCategory,
            tnPerRmdIfObjectAlarmDefaultCategory
        }
        STATUS         current
        DESCRIPTION    "."
        ::= { tnLogGroups 46 }

    tnPerRmdIfMauObjectAlarmCategoryConfigScalarsGroup OBJECT-GROUP
        OBJECTS {
            tnPerRmdIfMauObjectAlarmCategoryConfigAttributeTotal
        }
        STATUS         current
        DESCRIPTION    "."
        ::= { tnLogGroups 47 }

    tnPerRmdIfMauObjectAlarmCategoryConfigGroup OBJECT-GROUP
        OBJECTS {
            tnPerRmdIfMauObjectAlarmCategory,
            tnPerRmdIfMauObjectAlarmEntityTypeCategory,
            tnPerRmdIfMauObjectAlarmDefaultCategory
        }
        STATUS         current
        DESCRIPTION    "."
        ::= { tnLogGroups 48 }

    tnPerRmdCesChannelObjectAlarmCategoryConfigScalarsGroup OBJECT-GROUP
        OBJECTS {
            tnPerRmdCesChannelObjectAlarmCategoryConfigAttributeTotal
        }
        STATUS         current
        DESCRIPTION    "."
        ::= { tnLogGroups 49 }

    tnPerRmdCesChannelObjectAlarmCategoryConfigGroup OBJECT-GROUP
        OBJECTS {
            tnPerRmdCesChannelObjectAlarmCategory,
            tnPerRmdCesChannelObjectAlarmEntityTypeCategory,
            tnPerRmdCesChannelObjectAlarmDefaultCategory
        }
        STATUS         current
        DESCRIPTION    "."
        ::= { tnLogGroups 50 }

    tnPerOthObjectAlarmCategoryConfigScalarsGroup OBJECT-GROUP
        OBJECTS {
            tnPerOthObjectAlarmCategoryConfigAttributeTotal
        }
        STATUS         current
        DESCRIPTION    "."
        ::= { tnLogGroups 51 }

    tnPerOthObjectAlarmCategoryConfigGroup OBJECT-GROUP
        OBJECTS {
            tnPerOthObjectAlarmCategory,
            tnPerOthObjectAlarmEntityTypeCategory,
            tnPerOthObjectAlarmDefaultCategory
        }
        STATUS         current
        DESCRIPTION    "."
        ::= { tnLogGroups 52 }

    tnPerRmdNimObjectAlarmCategoryConfigScalarsGroup OBJECT-GROUP
        OBJECTS {
            tnPerRmdNimObjectAlarmCategoryConfigAttributeTotal
        }
        STATUS         current
        DESCRIPTION    "."
        ::= { tnLogGroups 53 }

    tnPerRmdNimObjectAlarmCategoryConfigGroup OBJECT-GROUP
        OBJECTS {
            tnPerRmdNimObjectAlarmCategory,
            tnPerRmdNimObjectAlarmEntityTypeCategory,
            tnPerRmdNimObjectAlarmDefaultCategory
        }
        STATUS         current
        DESCRIPTION    "."
        ::= { tnLogGroups 54 }

    tnAsapMgmtGroup OBJECT-GROUP
        OBJECTS {
            tnAsapRowStatus,
            tnAsapType,
            tnAsapCloneFrom,
            tnAsapNewName,
            tnAsapDefaultFlag,
            tnAsapSysDefind
        }
        STATUS         current
        DESCRIPTION    "."
        ::= { tnLogGroups 55 }

--    obsolete
--    tnAsapMgmtDetailGroup OBJECT-GROUP ::= { tnLogGroups 56 }

    tnPerMplsLspObjectAlarmCategoryConfigScalarsGroup OBJECT-GROUP
        OBJECTS {
            tnPerMplsLspObjectAlarmCategoryConfigAttributeTotal
        }
        STATUS         current
        DESCRIPTION    "."
        ::= { tnLogGroups 57 }

    tnPerMplsLspObjectAlarmCategoryConfigGroup OBJECT-GROUP
        OBJECTS {
            tnPerMplsLspObjectAlarmCategory,
            tnPerMplsLspObjectAlarmEntityTypeCategory,
            tnPerMplsLspObjectAlarmDefaultCategory
        }
        STATUS         current
        DESCRIPTION    "."
        ::= { tnLogGroups 58 }

    tnPerSdpBindObjectAlarmCategoryConfigScalarsGroup OBJECT-GROUP
        OBJECTS {
            tnPerSdpBindObjectAlarmCategoryConfigAttributeTotal
        }
        STATUS         current
        DESCRIPTION    "."
        ::= { tnLogGroups 59 }

    tnPerSdpBindObjectAlarmCategoryConfigGroup OBJECT-GROUP
        OBJECTS {
            tnPerSdpBindObjectAlarmCategory,
            tnPerSdpBindObjectAlarmEntityTypeCategory,
            tnPerSdpBindObjectAlarmDefaultCategory
        }
        STATUS         current
        DESCRIPTION    "."
        ::= { tnLogGroups 60 }

    tnPerMplsIfObjectAlarmCategoryConfigScalarsGroup OBJECT-GROUP
        OBJECTS {
            tnPerMplsIfObjectAlarmCategoryConfigAttributeTotal
        }
        STATUS         current
        DESCRIPTION    "."
        ::= { tnLogGroups 61 }

    tnPerMplsIfObjectAlarmCategoryConfigGroup OBJECT-GROUP
        OBJECTS {
            tnPerMplsIfObjectAlarmCategory,
            tnPerMplsIfObjectAlarmEntityTypeCategory,
            tnPerMplsIfObjectAlarmDefaultCategory
        }
        STATUS         current
        DESCRIPTION    "."
        ::= { tnLogGroups 62 }

    tnPerMplsLspPathObjectAlarmCategoryConfigScalarsGroup OBJECT-GROUP
        OBJECTS {
            tnPerMplsLspPathObjectAlarmCategoryConfigAttributeTotal
        }
        STATUS         current
        DESCRIPTION    "."
        ::= { tnLogGroups 63 }

    tnPerMplsLspPathObjectAlarmCategoryConfigGroup OBJECT-GROUP
        OBJECTS {
            tnPerMplsLspPathObjectAlarmCategory,
            tnPerMplsLspPathObjectAlarmEntityTypeCategory,
            tnPerMplsLspPathObjectAlarmDefaultCategory
        }
        STATUS         current
        DESCRIPTION    "."
        ::= { tnLogGroups 64 }

    tnAsapTypeIndexScalarsGroup OBJECT-GROUP
        OBJECTS {
            tnAsapTypeIndexAttributeTotal
        }
        STATUS         current
        DESCRIPTION    "."
        ::= { tnLogGroups 65 }

    tnAsapTypeIndexGroup OBJECT-GROUP
        OBJECTS {
            tnAsapTypeIndex
        }
        STATUS         current
        DESCRIPTION    "."
        ::= { tnLogGroups 66 }

    tnAsapMgmtDetailsScalarsGroup OBJECT-GROUP
        OBJECTS {
            tnAsapMgmtDetailsAttributeTotal
        }
        STATUS         current
        DESCRIPTION    "."
        ::= { tnLogGroups 67 }

    tnAsapMgmtDetailsGroup OBJECT-GROUP
        OBJECTS {
            tnAsapDetailsAlarmSeverity
        }
        STATUS         current
        DESCRIPTION    "."
        ::= { tnLogGroups 68 }

    tnAsapMgmtScalarsGroup OBJECT-GROUP
        OBJECTS {
            tnAsapMgmtAttributeTotal
        }
        STATUS         current
        DESCRIPTION    "."
        ::= { tnLogGroups 69 }

--    obsolete
--    tnAsapMgmtDetailScalarsGroup OBJECT-GROUP ::= { tnLogGroups 70 }

    tnPerWanifObjectAlarmCategoryConfigScalarsGroup OBJECT-GROUP
        OBJECTS {
            tnPerWanifObjectAlarmCategoryConfigAttributeTotal
        }
        STATUS         current
        DESCRIPTION    "."
        ::= { tnLogGroups 71 }

    tnPerWanifObjectAlarmCategoryConfigGroup OBJECT-GROUP
        OBJECTS {
            tnPerWanifObjectAlarmCategory,
            tnPerWanifObjectAlarmEntityTypeCategory,
            tnPerWanifObjectAlarmDefaultCategory
        }
        STATUS         current
        DESCRIPTION    "."
        ::= { tnLogGroups 72 }

    tnPerPacketSwitchObjectAlarmCategoryConfigScalarsGroup OBJECT-GROUP
        OBJECTS {
            tnPerPacketSwitchObjectAlarmCategoryConfigAttributeTotal
        }
        STATUS         current
        DESCRIPTION    "."
        ::= { tnLogGroups 73 }

    tnPerPacketSwitchObjectAlarmCategoryConfigGroup OBJECT-GROUP
        OBJECTS {
            tnPerPacketSwitchObjectAlarmCategory,
            tnPerPacketSwitchObjectAlarmEntityTypeCategory,
            tnPerPacketSwitchObjectAlarmDefaultCategory
        }
        STATUS         current
        DESCRIPTION    "."
        ::= { tnLogGroups 74 }

    tnActiveAlarmInfoGroup OBJECT-GROUP
        OBJECTS {
            tnActiveAlarmInfoData
        }
        STATUS         current
        DESCRIPTION    "."
        ::= { tnLogGroups 75 }

-------------------------------------------------------------------
-- Compliance Statements (mandatory)
-------------------------------------------------------------------
    tnLogCompliance MODULE-COMPLIANCE
        STATUS         current
        DESCRIPTION    "."
        MODULE
        MANDATORY-GROUPS  {
            tnLogScalarsGroup,
            tnCriticalAlarmLogGroup,
            tnMajorAlarmLogGroup,
            tnMinorAlarmLogGroup,
            tnStateChangeLogGroup,
            tnUserActionLogGroup,
            tnGeneralEventLogGroup,
            tnLogGroup,
            tnActiveAlarmGroup,
            tnPersistentLogGroup,
            tnActiveOrMaskedAlarmGroup,
            tnNotAlarmedLogGroup,
            tnPerObjectAlarmCategoryConfigGroup,
            tnAlarmProfileConfigGroup,
            tnSecurityLogGroup,
            tnWarningAlarmLogGroup,
--            obsolete
--            tnPerLogicObjectAlarmCategoryConfigGroup,
            tnPerSyncObjectAlarmCategoryConfigGroup,
            tnPerVtsObjectAlarmCategoryConfigScalarsGroup,
            tnPerVtsObjectAlarmCategoryConfigGroup,
            tnPerCcmObjectAlarmCategoryConfigScalarsGroup,
            tnPerCcmObjectAlarmCategoryConfigGroup,
            tnPerTcmObjectAlarmCategoryConfigScalarsGroup,
            tnPerTcmObjectAlarmCategoryConfigGroup,
            tnPerPtpObjectAlarmCategoryConfigScalarsGroup,
            tnPerPtpObjectAlarmCategoryConfigGroup,
            tnPerLagObjectAlarmCategoryConfigScalarsGroup,
            tnPerLagObjectAlarmCategoryConfigGroup,
            tnPerOtnObjectAlarmCategoryConfigScalarsGroup,  -- deprecated
            tnPerOtnObjectAlarmCategoryConfigGroup,         -- deprecated
            tnPerSrSvcObjectAlarmCategoryConfigScalarsGroup,
            tnPerSrSvcObjectAlarmCategoryConfigGroup,
            tnPerSrSapObjectAlarmCategoryConfigScalarsGroup,
            tnPerSrSapObjectAlarmCategoryConfigGroup,
            tnPerSrErpObjectAlarmCategoryConfigScalarsGroup,
            tnPerSrErpObjectAlarmCategoryConfigGroup,
            tnPerSrMepObjectAlarmCategoryConfigScalarsGroup,
            tnPerSrMepObjectAlarmCategoryConfigGroup,
            tnPerSrOamTestObjectAlarmCategoryConfigScalarsGroup,
            tnPerSrOamTestObjectAlarmCategoryConfigGroup,
            tnPerRmdObjectAlarmCategoryConfigScalarsGroup,
            tnPerRmdObjectAlarmCategoryConfigGroup,
            tnPerRmdMepObjectAlarmCategoryConfigScalarsGroup,
            tnPerRmdMepObjectAlarmCategoryConfigGroup,
            tnPerRmdIfObjectAlarmCategoryConfigScalarsGroup,
            tnPerRmdIfObjectAlarmCategoryConfigGroup,
            tnPerRmdIfMauObjectAlarmCategoryConfigScalarsGroup,
            tnPerRmdIfMauObjectAlarmCategoryConfigGroup,
            tnPerRmdCesChannelObjectAlarmCategoryConfigScalarsGroup,
            tnPerRmdCesChannelObjectAlarmCategoryConfigGroup,
            tnPerOthObjectAlarmCategoryConfigScalarsGroup,
            tnPerOthObjectAlarmCategoryConfigGroup,
            tnPerRmdNimObjectAlarmCategoryConfigScalarsGroup,
            tnPerRmdNimObjectAlarmCategoryConfigGroup,
            tnAsapMgmtGroup,
--            obsolete
--            tnAsapMgmtDetailGroup,
            tnPerMplsLspObjectAlarmCategoryConfigScalarsGroup,
            tnPerMplsLspObjectAlarmCategoryConfigGroup,
            tnPerSdpBindObjectAlarmCategoryConfigScalarsGroup,
            tnPerSdpBindObjectAlarmCategoryConfigGroup,
            tnPerMplsIfObjectAlarmCategoryConfigScalarsGroup,
            tnPerMplsIfObjectAlarmCategoryConfigGroup,
            tnPerMplsLspPathObjectAlarmCategoryConfigScalarsGroup,
            tnPerMplsLspPathObjectAlarmCategoryConfigGroup,
            tnAsapTypeIndexScalarsGroup,
            tnAsapTypeIndexGroup,
            tnAsapMgmtDetailsScalarsGroup,
            tnAsapMgmtDetailsGroup,
            tnAsapMgmtScalarsGroup,
--            obsolete
--            tnAsapMgmtDetailScalarsGroup,
            tnPerWanifObjectAlarmCategoryConfigScalarsGroup,
            tnPerWanifObjectAlarmCategoryConfigGroup,
            tnPerPacketSwitchObjectAlarmCategoryConfigScalarsGroup,
            tnPerPacketSwitchObjectAlarmCategoryConfigGroup,
            tnActiveAlarmInfoGroup
        }
        ::= { tnLogCompliances 1 }

END -- DEFINITION OF TROPIC-LOG-MIB
