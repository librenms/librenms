TROPIC-BREAKER-MIB DEFINITIONS ::= BEGIN

-- (c) Copyright 2023 Nokia Networks.  All rights reserved.
-- This software is the confidential and proprietary property of
-- Nokia and may only be used in accordance with the terms of the
-- license agreement provided with this software.

IMPORTS
      OBJECT-TYPE, MODULE-IDENTITY,
      Integer32, Unsigned32                   FROM SNMPv2-SMI
      MODULE-COMPLIANCE, OBJECT-GROUP         FROM SNMPv2-CONF
      tnShelfIndex                            FROM TROPIC-SHELF-MIB
      tnSlotIndex                             FROM TROPIC-SLOT-MIB
      tnMiscModules, tnBreakerMIB             FROM TROPIC-GLOBAL-REG;

  tnBreakerMibModule MODULE-IDENTITY
      LAST-UPDATED    "202302171200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION "."

      REVISION    "202302171200Z"
      DESCRIPTION "Added the following tnPowerFilterTable:
                   tnPowerFilterConsumed
                   tnPowerFilterEfficiency."

      REVISION    "201802231200Z"
      DESCRIPTION "Updated the contact info."

      REVISION    "201611161200Z"
      DESCRIPTION "Updated the contact info."

      REVISION    "201305211200Z"
      DESCRIPTION "Marked the following as obsolete:
                   tnBreakerEvents
                   tnBreakerTable."

      REVISION    "201209131200Z"
      DESCRIPTION "Added the following tnPowerFilterTable:
                   tnPowerFilterCardPower."

      REVISION    "201105231200Z"
      DESCRIPTION "Updated DESCRIPTION for tnPowerFilterAmpRating."

      REVISION    "201104141200Z"
      DESCRIPTION "Changed UNITS of tnPowerFilterAmpRating from (amps)
                   to (1/10 amps)."

      REVISION    "201010181200Z"
      DESCRIPTION "Marked tnBreakerVersion as obsolete."

      REVISION    "200908131200Z"
      DESCRIPTION "Updated DESCRIPTION for tnPowerFilterAmpRating."

      ::= { tnMiscModules 2 }

  tnBreakerConf        OBJECT IDENTIFIER ::= { tnBreakerMIB 1 }
  tnBreakerGroups      OBJECT IDENTIFIER ::= { tnBreakerConf 1 }
  tnBreakerCompliances OBJECT IDENTIFIER ::= { tnBreakerConf 2 }
  tnBreakerObjs        OBJECT IDENTIFIER ::= { tnBreakerMIB 2 }
  tnBreakerBasics      OBJECT IDENTIFIER ::= { tnBreakerObjs 1 }
--  obsolete
--  tnBreakerEvents      OBJECT IDENTIFIER ::= { tnBreakerMIB 3 }

--------------------------------------------------------------------------------
-- Breaker Table
--------------------------------------------------------------------------------
--    obsolete
--    tnBreakerTable OBJECT-TYPE ::= { tnBreakerBasics 1 }

--------------------------------------------------------------------------------
-- Power Filter Table
--------------------------------------------------------------------------------
    tnPowerFilterTable OBJECT-TYPE
        SYNTAX         SEQUENCE OF TnPowerFilterEntry
        MAX-ACCESS     not-accessible
        STATUS         current
        DESCRIPTION    "."
        ::= { tnBreakerBasics 2 }

    tnPowerFilterEntry OBJECT-TYPE
        SYNTAX         TnPowerFilterEntry
        MAX-ACCESS     not-accessible
        STATUS         current
        DESCRIPTION    "."
        INDEX { tnShelfIndex,
                tnSlotIndex }
        ::= { tnPowerFilterTable 1 }

    TnPowerFilterEntry ::= SEQUENCE {
        tnPowerFilterAmpRating     Integer32,
        tnPowerFilterCardPower     OCTET STRING,
        tnPowerFilterConsumed      Unsigned32,
        tnPowerFilterEfficiency    Unsigned32
    }

    tnPowerFilterAmpRating OBJECT-TYPE
        SYNTAX         Integer32
        UNITS          "1/10 amps"
        MAX-ACCESS     read-only
        STATUS         current
        DESCRIPTION    "Applicable to the 1830 PSS-32 and PSS-4."
        DEFVAL         { 0 }
        ::= { tnPowerFilterEntry 1 }

    tnPowerFilterCardPower OBJECT-TYPE
        SYNTAX         OCTET STRING (SIZE(0..100))
        UNITS          "watts"
        MAX-ACCESS     read-only
        STATUS         current
        DESCRIPTION    "Power filter card power."
        DEFVAL         { "" }
        ::= { tnPowerFilterEntry 2 }

    tnPowerFilterConsumed OBJECT-TYPE
        SYNTAX         Unsigned32
        UNITS          "watts"
        MAX-ACCESS     read-only
        STATUS         current
        DESCRIPTION    "."
        ::= { tnPowerFilterEntry 3 }

    tnPowerFilterEfficiency OBJECT-TYPE
        SYNTAX         Unsigned32
        UNITS          "watts"
        MAX-ACCESS     read-only
        STATUS         current
        DESCRIPTION    "."
        ::= { tnPowerFilterEntry 4 }

--------------------------------------------------------------------------------
-- Conformance Group Definitions
--------------------------------------------------------------------------------
--    obsolete
--    tnBreakerGroup  OBJECT-GROUP ::= { tnBreakerGroups 1 }

    tnPowerFilterGroup  OBJECT-GROUP
        OBJECTS {
            tnPowerFilterAmpRating,
            tnPowerFilterCardPower,
            tnPowerFilterConsumed,
            tnPowerFilterEfficiency
        }
        STATUS         current
        DESCRIPTION    "."
        ::= { tnBreakerGroups 2 }

--------------------------------------------------------------------------------
-- Compliance Statements (mandatory)
--------------------------------------------------------------------------------
    tnBreakerCompliance MODULE-COMPLIANCE
        STATUS         current
        DESCRIPTION    "."
        MODULE
        MANDATORY-GROUPS {
--            obsolete
--            tnBreakerGroup,
            tnPowerFilterGroup
        }
        ::= { tnBreakerCompliances 1 }

END -- DEFINITION OF TROPIC-BREAKER-MIB
