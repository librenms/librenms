TN-RMD-IF-MIB DEFINITIONS ::= BEGIN

-- (c) Copyright 2023 Nokia Networks.  All rights reserved.
-- This software is the confidential and proprietary property of
-- Nokia and may only be used in accordance with the terms of the
-- license agreement provided with this software.

IMPORTS
    SnmpAdminString
        FROM SNMP-FRAMEWORK-MIB
    MODULE-IDENTITY, OBJECT-TYPE, Integer32, Unsigned32, Counter64
        FROM SNMPv2-SMI
    MacAddress, TruthValue, TEXTUAL-CONVENTION
        FROM SNMPv2-TC
    InterfaceIndex, IANAifType
        FROM IF-MIB
    tnRmdObjs, tnRmdMIBModules
        FROM TROPIC-GLOBAL-REG
    tnRmdSystemId
        FROM TN-RMD-SYSTEM-MIB
    tnSysSwitchId
        FROM TROPIC-SYSTEM-MIB
    VlanIdOrNone
        FROM IEEE8021-CFM-MIB
    ;

tnRmdIfMibModule MODULE-IDENTITY
    LAST-UPDATED    "202011131200Z"
    ORGANIZATION    "Nokia"
    CONTACT-INFO    "Nokia
                     Attn: Jeff Donnelly
                     600 Mountain Avenue
                     New Providence, NJ 07974

                     Phone: +1 732 221 6408
                     Email: jeff.donnelly@nokia.com"

    DESCRIPTION "Interface MIB for Remote Managed Devices (RMDs)."

    REVISION    "202011131200Z"
    DESCRIPTION "Added the following to tnRmdIfLoopbackTable:
                 tnRmdIfEvcLoopBack
                 tnRmdIfEvcLoopBackVlanId."

    REVISION    "201802231200Z"
    DESCRIPTION "Updated the contact info."

    REVISION    "201611160000Z"
    DESCRIPTION "Updated the contact info."

    REVISION    "201309240000Z"
    DESCRIPTION "1) Added the following textual conventions:
                    TnRmdTrafficState
                    TnRmdAutoNegotiationConfigState.
                 2) Changed the SYNTAX of the following:
                    tnRmdIfTraffic
                    tnRmdIfMauAutoNegotiation
                    tnRmdIfMauAutoNegotiationFallback."

    REVISION    "201211280000Z"
    DESCRIPTION "Initial revision."

    ::= { tnRmdMIBModules 3 }


tnRmdIfObjects  OBJECT IDENTIFIER ::= { tnRmdObjs 3 }


-- =============================================================
-- Textual Conventions
-- =============================================================

TnRmdIfOperationalState ::= TEXTUAL-CONVENTION
    STATUS current
    DESCRIPTION
        "Represents the operational state of an interface

         down : the interface is operationally down.
         up   : the interface is operationally up."
    SYNTAX INTEGER {
              down    (0),
              up      (1)
           }

TnRmdAutoNegotiationStatus ::= TEXTUAL-CONVENTION
    STATUS current
    DESCRIPTION
        "The auto-negotiation read-only status of an interface of an RMD."
    SYNTAX INTEGER {
           anStatusError(0),
           anStatusConfiguring(1),
           anStatusComplete(2),
           anStatusDisabled(3),
           anStatusParallelDetectFail(4),
           anStatusNotAvailable(254),
           anStatusNotApplicable(255)
           }

TnRmdFrameForwardingMode ::= TEXTUAL-CONVENTION
    STATUS current
    DESCRIPTION
        "The frame forwarding mode of an RMD."
    SYNTAX INTEGER {
           ffmStoreAndForward(0),
           ffmCutThrough(1),
           ffmNotApplicable(255)
           }

TnRmdDuplexMode ::= TEXTUAL-CONVENTION
    STATUS current
    DESCRIPTION
        "Represents a duplex mode of an interface of an RMD."
    SYNTAX INTEGER {
           duplexHalf(0),
           duplexFull(1),
           duplexAuto(2),
           duplexNotAvailable(254),
           duplexNotApplicable(255)
           }

-- TnRmdIdlIngressMode ::= TEXTUAL-CONVENTION
--     STATUS current
--     DESCRIPTION
--         "IDL ingress mode of an interface of an RMD."
--     SYNTAX INTEGER {
--            idlIngressEnabled(0),
--            idlIngressDisabled(1)
--            }

TnRmdInterfaceSpeed ::= TEXTUAL-CONVENTION
    STATUS current
    DESCRIPTION
        "The speed of an interface of an RMD."
    SYNTAX INTEGER {
           ifSpeedTenMbs(0),
           ifSpeedHundredMbs(1),
           ifSpeedOneGbs(2),
           ifSpeedTenGbs(3),
           ifSpeedAuto(4),
           ifSpeedNotAvailable(254),
           ifSpeedNotApplicable(255)
           }

TnRmdLoopbackMode ::= TEXTUAL-CONVENTION
    STATUS current
    DESCRIPTION
        "Loopback modes.
          - loopbackDiagnosticMode :
            Unchanged source and destination MAC addresses.
          - loopbackReplaceMode :
            The destination MAC address is copied from the source MAC
            address, and the source MAC address is replaced by the
            system MAC address.
          - loopbackSwapMode :
            The source and destination MAC addresses are swapped."
    SYNTAX INTEGER {
           loopbackDiagnosticMode(0),
           loopbackReplaceMode(1),
           loopbackSwapMode(2),
           loopbackNotAvailable(254),
           loopbackNotApplicable(255)
           }

TnRmdLptStatus ::= TEXTUAL-CONVENTION
    STATUS current
    DESCRIPTION
        "The Link Pass-Through status of an interface of an RMD."
    SYNTAX INTEGER {
           lptStatusUp(1),
           lptStatusDown(2),
           lptStatusNotApplicable(255)
           }

TnRmdMasterSlaveRole ::= TEXTUAL-CONVENTION
    STATUS current
    DESCRIPTION
        "Represents a master-slave role of an interface of an RMD."
    SYNTAX INTEGER {
           msMaster(0),
           msSlave(1),
           msAuto(2),
           msNotAvailable(254),
           msNotApplicable(255)
           }

TnRmdMdixMode ::= TEXTUAL-CONVENTION
    STATUS current
    DESCRIPTION
        "Represents the MDI/MDIX mode of an RMD."
    SYNTAX INTEGER {
           mdi(0),
           mdix(1),
           mdiNotAvailable(254),
           mdiNotApplicable(255)
           }

TnRmdNimDirection ::= TEXTUAL-CONVENTION
    STATUS current
    DESCRIPTION
        "NIM direction."
    SYNTAX INTEGER {
           nimRx(0),
           nimTx(1)
           }

TnRmdPauseMode ::= TEXTUAL-CONVENTION
    STATUS current
    DESCRIPTION
        "Represents a pause mode of an interface of an RMD."
    SYNTAX INTEGER {
           pauseDisabled(0),
           pauseEnabled(1),
           pauseTxEnabledRxDisabled(2),
           pauseTxDisabledRxEnabled(3),
           pauseAuto(4),
           pauseNotAvailable(254),
           pauseNotApplicable(255)
           }

-- TnRmdTdmIfRate ::= TEXTUAL-CONVENTION
--     STATUS current
--     DESCRIPTION
--         "The rate of a TDM interface."
--     SYNTAX INTEGER {
--            tdmIf155Mbps(0),
--            tdmIf622Mbps(1)
--            }

TnRmdTrafficState ::= TEXTUAL-CONVENTION
     STATUS current
     DESCRIPTION
         "Traffic state of an interface of an RMD."
     SYNTAX INTEGER {
            trafficStateEnabled(1),
            trafficStateDisabled(2),
            trafficStateNotAvailable(254),
            trafficStateNotApplicable(255)
            }

TnRmdAutoNegotiationConfigState ::= TEXTUAL-CONVENTION
     STATUS current
     DESCRIPTION
        "The auto-negotiation states of an interface of an RMD."
    SYNTAX INTEGER {
           anStatusEnabled(1),
           anStatusDisabled(2),
           anStatusNotAvailable(254),
           anStatusNotApplicable(255)
           }

--------------------------------------------------------------------------------
-- RMD Interfaces Table Scalar
--------------------------------------------------------------------------------
tnRmdIfAttributeTotal OBJECT-TYPE
    SYNTAX         Integer32
    MAX-ACCESS     read-only
    STATUS         current
    DESCRIPTION    "."
    ::= { tnRmdIfObjects 1 }

-- =============================================================
-- tnRmdSystemInterfacesTable
-- =============================================================

tnRmdSystemInterfacesTable OBJECT-TYPE
    SYNTAX      SEQUENCE OF TnRmdSystemInterfacesEntry
    MAX-ACCESS  not-accessible
    STATUS      current
    DESCRIPTION
        "A table containing the common settings for all interfaces of
         all RMDs."
    ::= { tnRmdIfObjects 2 }

tnRmdSystemInterfacesEntry OBJECT-TYPE
    SYNTAX      TnRmdSystemInterfacesEntry
    MAX-ACCESS  not-accessible
    STATUS      current
    DESCRIPTION
        "A list of objects containing the common settings for all
         interfaces of an RMD."
    INDEX  { tnSysSwitchId, tnRmdSystemId }
    ::= { tnRmdSystemInterfacesTable 1 }

TnRmdSystemInterfacesEntry ::=
    SEQUENCE {
        tnRmdSystemInterfacesFrameForwardingMode  TnRmdFrameForwardingMode
    }

tnRmdSystemInterfacesFrameForwardingMode OBJECT-TYPE
    SYNTAX      TnRmdFrameForwardingMode
    MAX-ACCESS  read-write
    STATUS      current
    DESCRIPTION
        "The frame forwarding mode on all interfaces of the RMD."
    ::= { tnRmdSystemInterfacesEntry 1 }


-- =============================================================
-- tnRmdSystemLoopbackTable
-- =============================================================

tnRmdSystemLoopbackTable OBJECT-TYPE
    SYNTAX      SEQUENCE OF TnRmdSystemLoopbackEntry
    MAX-ACCESS  not-accessible
    STATUS      current
    DESCRIPTION
        "A table containing the default loopback modes of all RMDs."
    ::= { tnRmdIfObjects 3 }

tnRmdSystemLoopbackEntry OBJECT-TYPE
    SYNTAX      TnRmdSystemLoopbackEntry
    MAX-ACCESS  not-accessible
    STATUS      current
    DESCRIPTION
        "A list of objects containing the default loopback mode
         of an RMD."
    INDEX  { tnSysSwitchId, tnRmdSystemId }
    ::= { tnRmdSystemLoopbackTable 1 }

TnRmdSystemLoopbackEntry ::=
    SEQUENCE {
        tnRmdSystemDefaultLoopbackMode  TnRmdLoopbackMode
    }

tnRmdSystemDefaultLoopbackMode OBJECT-TYPE
    SYNTAX      TnRmdLoopbackMode
    MAX-ACCESS  read-write
    STATUS      current
    DESCRIPTION
        "The default loopback mode of the RMD.
         This mode applies in case no loopback mode can be provisioned
         at the level where the loopback is provisioned."
    ::= { tnRmdSystemLoopbackEntry 1 }


-- =============================================================
-- tnRmdIfTable
-- =============================================================

tnRmdIfTable OBJECT-TYPE
    SYNTAX      SEQUENCE OF TnRmdIfEntry
    MAX-ACCESS  not-accessible
    STATUS      current
    DESCRIPTION
        "A table containing the parameters of the interfaces of all RMDs."
    ::= { tnRmdIfObjects 4 }

tnRmdIfEntry OBJECT-TYPE
    SYNTAX      TnRmdIfEntry
    MAX-ACCESS  not-accessible
    STATUS      current
    DESCRIPTION
        "A list of objects containing the parameters of an interface of
         an RMD."
    INDEX  { tnSysSwitchId, tnRmdSystemId, tnRmdIfIndex }
    ::= { tnRmdIfTable 1 }

TnRmdIfEntry ::=
    SEQUENCE {
        tnRmdIfIndex                  InterfaceIndex,
        tnRmdIfType                   IANAifType,
        tnRmdIfMacAddress             MacAddress,
        tnRmdIfTraffic                TnRmdTrafficState,
        tnRmdIfLinkPassThrough        TruthValue,
        tnRmdIfLinkPassThroughStatus  TnRmdLptStatus,
        tnRmdIfOperationalState       TnRmdIfOperationalState
    }

tnRmdIfIndex OBJECT-TYPE
    SYNTAX      InterfaceIndex
    MAX-ACCESS  not-accessible
    STATUS      current
    DESCRIPTION
        "Unique number identifying the interface."
    ::= { tnRmdIfEntry 1 }

tnRmdIfType OBJECT-TYPE
    SYNTAX      IANAifType
    MAX-ACCESS  read-only
    STATUS      current
    DESCRIPTION
        "The type of the interface."
    ::= { tnRmdIfEntry 2 }

tnRmdIfMacAddress OBJECT-TYPE
    SYNTAX      MacAddress
    MAX-ACCESS  read-only
    STATUS      current
    DESCRIPTION
        "The MAC address of the interface."
    ::= { tnRmdIfEntry 3 }

tnRmdIfTraffic OBJECT-TYPE
    SYNTAX      TnRmdTrafficState
    MAX-ACCESS  read-write
    STATUS      current
    DESCRIPTION
        "Indicates whether traffic is enabled for the interface."
    ::= { tnRmdIfEntry 4 }

tnRmdIfLinkPassThrough OBJECT-TYPE
    SYNTAX      TruthValue
    MAX-ACCESS  read-write
    STATUS      current
    DESCRIPTION
        "Indicates whether Link Pass-Through is enabled, i.e. whether the
         other interface of the Two-Port MAC Relay relays defects to this
         interface."
    ::= { tnRmdIfEntry 5 }

tnRmdIfLinkPassThroughStatus OBJECT-TYPE
    SYNTAX      TnRmdLptStatus
    MAX-ACCESS  read-only
    STATUS      current
    DESCRIPTION
        "Indicates the Link Pass-Through status of the interface."
    ::= { tnRmdIfEntry 6 }

tnRmdIfOperationalState OBJECT-TYPE
    SYNTAX      TnRmdIfOperationalState
    MAX-ACCESS  read-only
    STATUS      current
    DESCRIPTION
        "Indicates the operational state of the interface."
    ::= { tnRmdIfEntry 7 }


-- =============================================================
-- tnRmdIfMauTable
-- =============================================================

tnRmdIfMauTable OBJECT-TYPE
    SYNTAX      SEQUENCE OF TnRmdIfMauEntry
    MAX-ACCESS  not-accessible
    STATUS      current
    DESCRIPTION
        "A table containing the parameters of the MAUs of all interfaces
         of all RMDs."
    ::= { tnRmdIfObjects 5 }

tnRmdIfMauEntry OBJECT-TYPE
    SYNTAX      TnRmdIfMauEntry
    MAX-ACCESS  not-accessible
    STATUS      current
    DESCRIPTION
        "A list of objects containing the parameters of a MAU of an
         interface of an RMD."
    INDEX  { tnSysSwitchId, tnRmdSystemId, tnRmdIfIndex, tnRmdIfMauIndex }
    ::= { tnRmdIfMauTable 1 }

TnRmdIfMauEntry ::=
    SEQUENCE {
        tnRmdIfMauIndex                       Integer32,
        tnRmdIfMauAutoNegotiation             TnRmdAutoNegotiationConfigState,
        tnRmdIfMauAutoNegotiationStatus       TnRmdAutoNegotiationStatus,
        tnRmdIfMauAutoNegotiationFallback     TnRmdAutoNegotiationConfigState,
        tnRmdIfMauProvisionedSpeed            TnRmdInterfaceSpeed,
        tnRmdIfMauProvisionedDuplexMode       TnRmdDuplexMode,
        tnRmdIfMauProvisionedPauseMode        TnRmdPauseMode,
        tnRmdIfMauProvisionedMasterSlaveRole  TnRmdMasterSlaveRole,
        tnRmdIfMauActualSpeed                 TnRmdInterfaceSpeed,
        tnRmdIfMauActualDuplexMode            TnRmdDuplexMode,
        tnRmdIfMauActualPauseMode             TnRmdPauseMode,
        tnRmdIfMauActualMasterSlaveRole       TnRmdMasterSlaveRole,
        tnRmdIfMauMdixMode                    TnRmdMdixMode
    }

tnRmdIfMauIndex OBJECT-TYPE
    SYNTAX      Integer32 (1..2147483647)
    MAX-ACCESS  not-accessible
    STATUS      current
    DESCRIPTION
        "Unique number identifying the MAU within the scope of the
         containing interface."
    ::= { tnRmdIfMauEntry 1 }

tnRmdIfMauAutoNegotiation OBJECT-TYPE
    SYNTAX      TnRmdAutoNegotiationConfigState
    MAX-ACCESS  read-write
    STATUS      current
    DESCRIPTION
        "Indicates whether auto-negotiation is enabled for the MAU."
    ::= { tnRmdIfMauEntry 2 }

tnRmdIfMauAutoNegotiationStatus OBJECT-TYPE
    SYNTAX      TnRmdAutoNegotiationStatus
    MAX-ACCESS  read-only
    STATUS      current
    DESCRIPTION
        "The auto-negotiation status of the MAU."
    ::= { tnRmdIfMauEntry 3 }

tnRmdIfMauAutoNegotiationFallback OBJECT-TYPE
    SYNTAX      TnRmdAutoNegotiationConfigState
    MAX-ACCESS  read-write
    STATUS      current
    DESCRIPTION
        "Indicates whether auto-negotiation fallback is enabled
         for the MAU."
    ::= { tnRmdIfMauEntry 4 }

tnRmdIfMauProvisionedSpeed OBJECT-TYPE
    SYNTAX      TnRmdInterfaceSpeed
    MAX-ACCESS  read-write
    STATUS      current
    DESCRIPTION
        "The provisioned speed of the MAU."
    ::= { tnRmdIfMauEntry 5 }

tnRmdIfMauProvisionedDuplexMode OBJECT-TYPE
    SYNTAX      TnRmdDuplexMode
    MAX-ACCESS  read-write
    STATUS      current
    DESCRIPTION
        "The provisioned duplex mode of the MAU."
    ::= { tnRmdIfMauEntry 6 }

tnRmdIfMauProvisionedPauseMode OBJECT-TYPE
    SYNTAX      TnRmdPauseMode
    MAX-ACCESS  read-write
    STATUS      current
    DESCRIPTION
        "The provisioned pause mode of the MAU."
    ::= { tnRmdIfMauEntry 7 }

tnRmdIfMauProvisionedMasterSlaveRole OBJECT-TYPE
    SYNTAX      TnRmdMasterSlaveRole
    MAX-ACCESS  read-write
    STATUS      current
    DESCRIPTION
        "The provisioned master-slave role of the MAU."
    ::= { tnRmdIfMauEntry 8 }

tnRmdIfMauActualSpeed OBJECT-TYPE
    SYNTAX      TnRmdInterfaceSpeed
    MAX-ACCESS  read-only
    STATUS      current
    DESCRIPTION
        "The actual speed of the MAU."
    ::= { tnRmdIfMauEntry 9 }

tnRmdIfMauActualDuplexMode OBJECT-TYPE
    SYNTAX      TnRmdDuplexMode
    MAX-ACCESS  read-only
    STATUS      current
    DESCRIPTION
        "The actual duplex mode of the MAU."
    ::= { tnRmdIfMauEntry 10 }

tnRmdIfMauActualPauseMode OBJECT-TYPE
    SYNTAX      TnRmdPauseMode
    MAX-ACCESS  read-only
    STATUS      current
    DESCRIPTION
        "The actual pause mode of the MAU."
    ::= { tnRmdIfMauEntry 11 }

tnRmdIfMauActualMasterSlaveRole OBJECT-TYPE
    SYNTAX      TnRmdMasterSlaveRole
    MAX-ACCESS  read-only
    STATUS      current
    DESCRIPTION
        "The actual master-slave role of the MAU."
    ::= { tnRmdIfMauEntry 12 }

tnRmdIfMauMdixMode OBJECT-TYPE
    SYNTAX      TnRmdMdixMode
    MAX-ACCESS  read-only
    STATUS      current
    DESCRIPTION
        "The MDI/MDIX mode of the MAU."
    ::= { tnRmdIfMauEntry 13 }


-- =============================================================
-- tnRmdIfMsaTable
-- =============================================================

tnRmdIfMsaTable OBJECT-TYPE
    SYNTAX      SEQUENCE OF TnRmdIfMsaEntry
    MAX-ACCESS  not-accessible
    STATUS      current
    DESCRIPTION
        "A table containing the MSA inventory of all MAUs of all
         interfaces of all RMDs."
    ::= { tnRmdIfObjects 6 }

tnRmdIfMsaEntry OBJECT-TYPE
    SYNTAX      TnRmdIfMsaEntry
    MAX-ACCESS  not-accessible
    STATUS      current
    DESCRIPTION
        "A list of objects containing the MSA inventory of a MAU
         of an interface of an RMD."
    INDEX  { tnSysSwitchId,
             tnRmdSystemId,
             tnRmdIfIndex,
             tnRmdIfMauIndex }
    ::= { tnRmdIfMsaTable 1 }

TnRmdIfMsaEntry ::=
    SEQUENCE {
        tnRmdIfMsaModuleVendorSerNo             SnmpAdminString,
        tnRmdIfMsaModuleVendor                  SnmpAdminString,
        tnRmdIfMsaWavelength                    Unsigned32,
        tnRmdIfMsaModuleType                    SnmpAdminString,
        tnRmdIfMsaCLEI                          SnmpAdminString,
        tnRmdIfMsaUnitPartNum                   SnmpAdminString,
        tnRmdIfMsaSWPartNum                     SnmpAdminString,
        tnRmdIfMsaFactoryID                     SnmpAdminString,
        tnRmdIfMsaDate                          SnmpAdminString,
        tnRmdIfMsaExtraData                     SnmpAdminString,
        tnRmdIfMsaMaximumCaseTemperature        Integer32,
        tnRmdIfMsaInterchangeabilityMarking     SnmpAdminString,
        tnRmdIfMsaAcronymCode                   SnmpAdminString
    }

tnRmdIfMsaModuleVendorSerNo OBJECT-TYPE
    SYNTAX         SnmpAdminString (SIZE(0..18))
    MAX-ACCESS     read-only
    STATUS         current
    DESCRIPTION    "Module vendor serial number."
    ::= { tnRmdIfMsaEntry 1 }

tnRmdIfMsaModuleVendor OBJECT-TYPE
    SYNTAX         SnmpAdminString (SIZE(0..16))
    MAX-ACCESS     read-only
    STATUS         current
    DESCRIPTION    "Module vendor."
    ::= { tnRmdIfMsaEntry 2 }

tnRmdIfMsaWavelength OBJECT-TYPE
    SYNTAX         Unsigned32
    MAX-ACCESS     read-only
    STATUS         current
    DESCRIPTION    "XFP/SFP wavelength."
    ::= { tnRmdIfMsaEntry 3 }

tnRmdIfMsaModuleType OBJECT-TYPE
    SYNTAX         SnmpAdminString
    MAX-ACCESS     read-only
    STATUS         current
    DESCRIPTION    "Module type."
    ::= { tnRmdIfMsaEntry 4 }

tnRmdIfMsaCLEI OBJECT-TYPE
    SYNTAX         SnmpAdminString
    MAX-ACCESS     read-only
    STATUS         current
    DESCRIPTION    "CLEI."
    ::= { tnRmdIfMsaEntry 5 }

tnRmdIfMsaUnitPartNum OBJECT-TYPE
    SYNTAX         SnmpAdminString
    MAX-ACCESS     read-only
    STATUS         current
    DESCRIPTION    "Unit part number."
    ::= { tnRmdIfMsaEntry 6 }

tnRmdIfMsaSWPartNum OBJECT-TYPE
    SYNTAX         SnmpAdminString
    MAX-ACCESS     read-only
    STATUS         current
    DESCRIPTION    "Software part number."
    ::= { tnRmdIfMsaEntry 7 }

tnRmdIfMsaFactoryID OBJECT-TYPE
    SYNTAX         SnmpAdminString
    MAX-ACCESS     read-only
    STATUS         current
    DESCRIPTION    "Factory ID."
    ::= { tnRmdIfMsaEntry 8 }

tnRmdIfMsaDate OBJECT-TYPE
    SYNTAX         SnmpAdminString
    MAX-ACCESS     read-only
    STATUS         current
    DESCRIPTION    "Date."
    ::= { tnRmdIfMsaEntry 9 }

tnRmdIfMsaExtraData OBJECT-TYPE
    SYNTAX         SnmpAdminString
    MAX-ACCESS     read-only
    STATUS         current
    DESCRIPTION    "Extra data."
    ::= { tnRmdIfMsaEntry 10 }

tnRmdIfMsaMaximumCaseTemperature OBJECT-TYPE
    SYNTAX         Integer32
    MAX-ACCESS     read-only
    STATUS         current
    DESCRIPTION    "Maximum case temperature."
    ::= { tnRmdIfMsaEntry 11 }

tnRmdIfMsaInterchangeabilityMarking OBJECT-TYPE
    SYNTAX         SnmpAdminString (SIZE(0..6))
    MAX-ACCESS     read-only
    STATUS         current
    DESCRIPTION    "Interchangeability marking."
    ::= { tnRmdIfMsaEntry 12 }

tnRmdIfMsaAcronymCode OBJECT-TYPE
    SYNTAX         SnmpAdminString (SIZE(0..12))
    MAX-ACCESS     read-only
    STATUS         current
    DESCRIPTION    "Acronym code."
    ::= { tnRmdIfMsaEntry 13 }


-- =============================================================
-- tnRmdIfDdmTable
-- =============================================================

tnRmdIfDdmTable OBJECT-TYPE
    SYNTAX      SEQUENCE OF TnRmdIfDdmEntry
    MAX-ACCESS  not-accessible
    STATUS      current
    DESCRIPTION
        "A table containing the Digital Diagnostic Monitoring (DDM) parameters
         of all MAUs of all interfaces of all RMDs."
    ::= { tnRmdIfObjects 7 }

tnRmdIfDdmEntry OBJECT-TYPE
    SYNTAX      TnRmdIfDdmEntry
    MAX-ACCESS  not-accessible
    STATUS      current
    DESCRIPTION
        "A list of objects containing the DDM parameters of a
         MAU of an interface of an RMD."
    INDEX  { tnSysSwitchId,
             tnRmdSystemId,
             tnRmdIfIndex,
             tnRmdIfMauIndex }
    ::= { tnRmdIfDdmTable 1 }

TnRmdIfDdmEntry ::=
    SEQUENCE {
         tnRmdIfDdmTemperature                   Integer32,
         tnRmdIfDdmTempLowWarning                Integer32,
         tnRmdIfDdmTempLowAlarm                  Integer32,
         tnRmdIfDdmTempHiWarning                 Integer32,
         tnRmdIfDdmTempHiAlarm                   Integer32,
         tnRmdIfDdmSupplyVoltage                 Integer32,
         tnRmdIfDdmSupplyVoltageLowWarning       Integer32,
         tnRmdIfDdmSupplyVoltageLowAlarm         Integer32,
         tnRmdIfDdmSupplyVoltageHiWarning        Integer32,
         tnRmdIfDdmSupplyVoltageHiAlarm          Integer32,
         tnRmdIfDdmTxBiasCurrent                 Integer32,
         tnRmdIfDdmTxBiasCurrentLowWarning       Integer32,
         tnRmdIfDdmTxBiasCurrentLowAlarm         Integer32,
         tnRmdIfDdmTxBiasCurrentHiWarning        Integer32,
         tnRmdIfDdmTxBiasCurrentHiAlarm          Integer32,
         tnRmdIfDdmTxOutputPower                 Integer32,
         tnRmdIfDdmTxOutputPowerLowWarning       Integer32,
         tnRmdIfDdmTxOutputPowerLowAlarm         Integer32,
         tnRmdIfDdmTxOutputPowerHiWarning        Integer32,
         tnRmdIfDdmTxOutputPowerHiAlarm          Integer32,
         tnRmdIfDdmRxOpticalPower                Integer32,
         tnRmdIfDdmRxOpticalPowerLowWarning      Integer32,
         tnRmdIfDdmRxOpticalPowerLowAlarm        Integer32,
         tnRmdIfDdmRxOpticalPowerHiWarning       Integer32,
         tnRmdIfDdmRxOpticalPowerHiAlarm         Integer32,
         tnRmdIfDdmRxOpticalPowerType            INTEGER,
         tnRmdIfDdmExternallyCalibrated          TruthValue,
         tnRmdIfDdmExtCalRxPower4                Unsigned32,
         tnRmdIfDdmExtCalRxPower3                Unsigned32,
         tnRmdIfDdmExtCalRxPower2                Unsigned32,
         tnRmdIfDdmExtCalRxPower1                Unsigned32,
         tnRmdIfDdmExtCalRxPower0                Unsigned32,
         tnRmdIfDdmExtCalTxLaserBiasSlope        Unsigned32,
         tnRmdIfDdmExtCalTxLaserBiasOffset       Integer32,
         tnRmdIfDdmExtCalTxPowerSlope            Unsigned32,
         tnRmdIfDdmExtCalTxPowerOffset           Integer32,
         tnRmdIfDdmExtCalTemperatureSlope        Unsigned32,
         tnRmdIfDdmExtCalTemperatureOffset       Integer32,
         tnRmdIfDdmExtCalVoltageSlope            Unsigned32,
         tnRmdIfDdmExtCalVoltageOffset           Integer32
   }

tnRmdIfDdmTemperature                 OBJECT-TYPE
    SYNTAX      Integer32
    MAX-ACCESS  read-only
    STATUS      current
    DESCRIPTION
        "The value of tnRmdIfDdmTemperature indicates the current temperature
         of the interface in degrees Celsius."
    ::= { tnRmdIfDdmEntry 1 }

tnRmdIfDdmTempLowWarning              OBJECT-TYPE
    SYNTAX      Integer32
    MAX-ACCESS  read-only
    STATUS      current
    DESCRIPTION
        "The value of tnRmdIfDdmTempLowWarning indicates the temperature
         of the interface in degrees Celsius that triggers a low-warning."
    ::= { tnRmdIfDdmEntry 2 }

tnRmdIfDdmTempLowAlarm                OBJECT-TYPE
    SYNTAX      Integer32
    MAX-ACCESS  read-only
    STATUS      current
    DESCRIPTION
        "The value of tnRmdIfDdmTempLowAlarm indicates the temperature
         of the interface in degrees Celsius that triggers a low-alarm."
    ::= { tnRmdIfDdmEntry 3 }

tnRmdIfDdmTempHiWarning               OBJECT-TYPE
    SYNTAX      Integer32
    MAX-ACCESS  read-only
    STATUS      current
    DESCRIPTION
        "The value of tnRmdIfDdmTempHiWarning indicates the temperature
         of the interface in degrees Celsius that triggers a hi-warning."
    ::= { tnRmdIfDdmEntry 4 }

tnRmdIfDdmTempHiAlarm                 OBJECT-TYPE
    SYNTAX      Integer32
    MAX-ACCESS  read-only
    STATUS      current
    DESCRIPTION
        "The value of tnRmdIfDdmTempHiAlarm indicates the temperature
         of the interface in degrees Celsius that triggers a hi-alarm."
    ::= { tnRmdIfDdmEntry 5 }

tnRmdIfDdmSupplyVoltage               OBJECT-TYPE
    SYNTAX      Integer32
    MAX-ACCESS  read-only
    STATUS      current
    DESCRIPTION
        "The value of tnRmdIfDdmSupplyVoltage indicates the current supply
         voltage of the interface in micro-Volts (uV)."
    ::= { tnRmdIfDdmEntry 6 }

tnRmdIfDdmSupplyVoltageLowWarning     OBJECT-TYPE
    SYNTAX      Integer32
    MAX-ACCESS  read-only
    STATUS      current
    DESCRIPTION
        "The value of tnRmdIfDdmSupplyVoltageLowWarning indicates the supply
         voltage of the interface in micro-Volts (uV) that triggers a low-warning."
    ::= { tnRmdIfDdmEntry 7 }

tnRmdIfDdmSupplyVoltageLowAlarm       OBJECT-TYPE
    SYNTAX      Integer32
    MAX-ACCESS  read-only
    STATUS      current
    DESCRIPTION
        "The value of tnRmdIfDdmSupplyVoltageLowAlarm indicates the supply
         voltage of the interface in micro-Volts (uV) that triggers a low-alarm."
    ::= { tnRmdIfDdmEntry 8 }

tnRmdIfDdmSupplyVoltageHiWarning      OBJECT-TYPE
    SYNTAX      Integer32
    MAX-ACCESS  read-only
    STATUS      current
    DESCRIPTION
        "The value of tnRmdIfDdmSupplyVoltageHiWarning indicates the supply
         voltage of the interface in micro-Volts (uV) that triggers a hi-warning."
    ::= { tnRmdIfDdmEntry 9 }

tnRmdIfDdmSupplyVoltageHiAlarm        OBJECT-TYPE
    SYNTAX      Integer32
    MAX-ACCESS  read-only
    STATUS      current
    DESCRIPTION
        "The value of tnRmdIfDdmSupplyVoltageHiAlarm indicates the supply
         voltage of the interface in micro-Volts (uV) that triggers a hi-alarm."
    ::= { tnRmdIfDdmEntry 10 }

tnRmdIfDdmTxBiasCurrent               OBJECT-TYPE
    SYNTAX      Integer32
    MAX-ACCESS  read-only
    STATUS      current
    DESCRIPTION
        "The value of tnRmdIfDdmTxBiasCurrent indicates the current Transmit
         Bias Current of the interface in micro-Amperes (uA)."
    ::= { tnRmdIfDdmEntry 11 }

tnRmdIfDdmTxBiasCurrentLowWarning     OBJECT-TYPE
    SYNTAX      Integer32
    MAX-ACCESS  read-only
    STATUS      current
    DESCRIPTION
        "The value of tnRmdIfDdmTxBiasCurrentLowWarning indicates the Transmit
         Bias Current of the interface in micro-Amperes (uA) that triggers a
         low-warning."
    ::= { tnRmdIfDdmEntry 12 }

tnRmdIfDdmTxBiasCurrentLowAlarm       OBJECT-TYPE
    SYNTAX      Integer32
    MAX-ACCESS  read-only
    STATUS      current
    DESCRIPTION
        "The value of tnRmdIfDdmTxBiasCurrentLowAlarm indicates the Transmit
         Bias Current of the interface in micro-Amperes (uA) that triggers a
         low-alarm."
    ::= { tnRmdIfDdmEntry 13 }

tnRmdIfDdmTxBiasCurrentHiWarning      OBJECT-TYPE
    SYNTAX      Integer32
    MAX-ACCESS  read-only
    STATUS      current
    DESCRIPTION
        "The value of tnRmdIfDdmTxBiasCurrentHiWarning indicates the Transmit
         Bias Current of the interface in micro-Amperes (uA) that triggers a
         hi-warning."
    ::= { tnRmdIfDdmEntry 14 }

tnRmdIfDdmTxBiasCurrentHiAlarm        OBJECT-TYPE
    SYNTAX      Integer32
    MAX-ACCESS  read-only
    STATUS      current
    DESCRIPTION
        "The value of tnRmdIfDdmTxBiasCurrentHiAlarm indicates the Transmit
         Bias Current of the interface in micro-Amperes (uA) that triggers a
         hi-alarm."
    ::= { tnRmdIfDdmEntry 15 }

tnRmdIfDdmTxOutputPower               OBJECT-TYPE
    SYNTAX      Integer32
    MAX-ACCESS  read-only
    STATUS      current
    DESCRIPTION
        "The value of tnRmdIfDdmTxOutputPower indicates the current Output
         Power of the interface in one tenths of a micro-Watt (uW).

         For example:
         Using the SNMP value of 790, and using units of tenths of microwatt,
         790 becomes 79 microwatts or 0.079 milliwatts. Converting to dBm:
               10 x log10(0.079) = -11.0 dBm"

    ::= { tnRmdIfDdmEntry 16 }

tnRmdIfDdmTxOutputPowerLowWarning     OBJECT-TYPE
    SYNTAX      Integer32
    MAX-ACCESS  read-only
    STATUS      current
    DESCRIPTION
        "The value of tnRmdIfDdmTxOutputPowerLowWarning indicates the Output Power
         of the interface in one tenths of a micro-Watt (uW) that triggers a
         low-warning."

    ::= { tnRmdIfDdmEntry 17 }

tnRmdIfDdmTxOutputPowerLowAlarm       OBJECT-TYPE
    SYNTAX      Integer32
    MAX-ACCESS  read-only
    STATUS      current
    DESCRIPTION
        "The value of tnRmdIfDdmTxOutputPowerLowAlarm indicates the Output Power
         of the interface in one tenths of a micro-Watt (uW) that triggers a
         low-alarm."
    ::= { tnRmdIfDdmEntry 18 }

tnRmdIfDdmTxOutputPowerHiWarning      OBJECT-TYPE
    SYNTAX      Integer32
    MAX-ACCESS  read-only
    STATUS      current
    DESCRIPTION
        "The value of tnRmdIfDdmTxOutputPowerHiWarning indicates the Output Power
         of the interface in one tenths of a micro-Watt (uW) that triggers a
         hi-alarm."
    ::= { tnRmdIfDdmEntry 19 }

tnRmdIfDdmTxOutputPowerHiAlarm        OBJECT-TYPE
    SYNTAX      Integer32
    MAX-ACCESS  read-only
    STATUS      current
    DESCRIPTION
        "The value of tnRmdIfDdmTxOutputPowerHiAlarm indicates the Output Power
         of the interface in one tenths of a micro-Watt (uW) that triggers a
         hi-alarm."
    ::= { tnRmdIfDdmEntry 20 }

tnRmdIfDdmRxOpticalPower              OBJECT-TYPE
    SYNTAX      Integer32
    MAX-ACCESS  read-only
    STATUS      current
    DESCRIPTION
        "The value of tnRmdIfDdmRxOpticalPower indicates the current Received
         Optical Power of the interface in one tenths of a micro-Watt (uW).

         For example:
         Using the SNMP value of 790, and using units of tenths of microwatt,
         790 becomes 79 microwatts or 0.079 milliwatts. Converting to dBm:
               10 x log10(0.079) = -11.0 dBm"
    ::= { tnRmdIfDdmEntry 21 }

tnRmdIfDdmRxOpticalPowerLowWarning    OBJECT-TYPE
    SYNTAX      Integer32
    MAX-ACCESS  read-only
    STATUS      current
    DESCRIPTION
        "The value of tnRmdIfDdmRxOpticalPowerLowWarning indicates the Received
         Optical Power of the SFP/XFP in one tenths of a micro-Watt (uW) that
         triggers a low-warning."
    ::= { tnRmdIfDdmEntry 22 }

tnRmdIfDdmRxOpticalPowerLowAlarm      OBJECT-TYPE
    SYNTAX      Integer32
    MAX-ACCESS  read-only
    STATUS      current
    DESCRIPTION
        "The value of tnRmdIfDdmRxOpticalPowerLowAlarm indicates the Received
         Optical Power of the SFP/XFP in one tenths of a micro-Watt (uW) that
         triggers a low-alarm."
    ::= { tnRmdIfDdmEntry 23 }

tnRmdIfDdmRxOpticalPowerHiWarning     OBJECT-TYPE
    SYNTAX      Integer32
    MAX-ACCESS  read-only
    STATUS      current
    DESCRIPTION
        "The value of tnRmdIfDdmRxOpticalPowerHiWarning indicates the Received
         Optical Power of the SFP/XFP in one tenths of a micro-Watt (uW) that
         triggers a hi-warning."
    ::= { tnRmdIfDdmEntry 24 }

tnRmdIfDdmRxOpticalPowerHiAlarm       OBJECT-TYPE
    SYNTAX      Integer32
    MAX-ACCESS  read-only
    STATUS      current
    DESCRIPTION
        "The value of tnRmdIfDdmRxOpticalPowerHiAlarm indicates the Received
         Optical Power of the SFP/XFP in one tenths of a micro-Watt (uW) that
         triggers a hi-alarm."
    ::= { tnRmdIfDdmEntry 25 }

tnRmdIfDdmRxOpticalPowerType          OBJECT-TYPE
    SYNTAX      INTEGER {
                    oma      (0),   -- Optical Modulation Amplitude
                    average  (1)    -- Average rx optical power
                }
    MAX-ACCESS  read-only
    STATUS      current
    DESCRIPTION
        "The value of tnRmdIfDdmRxOpticalPowerType indicates whether the
         tnRmdIfDdmRxOpticalPower was taken as an average, or as an Optical
         Modulation Amplitude (OMA)."
    ::= { tnRmdIfDdmEntry 26 }

tnRmdIfDdmExternallyCalibrated        OBJECT-TYPE
    SYNTAX      TruthValue
    MAX-ACCESS  read-only
    STATUS      current
    DESCRIPTION
        "The value of tnRmdIfDdmExternallyCalibrated indicates whether the
         SFP was externally calibrated (true) or internally calibrated (false)."
    ::= { tnRmdIfDdmEntry 27 }

tnRmdIfDdmExtCalRxPower4              OBJECT-TYPE
    SYNTAX      Unsigned32
    MAX-ACCESS  read-only
    STATUS      current
    DESCRIPTION
        "The value of tnRmdIfDdmExtCalRxPower4 indicates the Rx_PWR(4)
         value as specified in Table 3.16 in the SFF Committee Standard's
         document SFF-8472 Rev 10.2."
    REFERENCE "SFF-8472 Rev 10.2"
    ::= { tnRmdIfDdmEntry 28 }

tnRmdIfDdmExtCalRxPower3              OBJECT-TYPE
    SYNTAX      Unsigned32
    MAX-ACCESS  read-only
    STATUS      current
    DESCRIPTION
        "The value of tnRmdIfDdmExtCalRxPower3 indicates the Rx_PWR(3)
         value as specified in Table 3.16 in the SFF Committee Standard's
         document SFF-8462 Rev 10.2."
    REFERENCE "SFF-8472 Rev 10.2"
    ::= { tnRmdIfDdmEntry 29 }

tnRmdIfDdmExtCalRxPower2              OBJECT-TYPE
    SYNTAX      Unsigned32
    MAX-ACCESS  read-only
    STATUS      current
    DESCRIPTION
        "The value of tnRmdIfDdmExtCalRxPower2 indicates the Rx_PWR(2)
         value as specified in Table 3.16 in the SFF Committee Standard's
         document SFF-8472 Rev 10.2."
    REFERENCE "SFF-8472 Rev 10.2"
    ::= { tnRmdIfDdmEntry 30 }

tnRmdIfDdmExtCalRxPower1              OBJECT-TYPE
    SYNTAX      Unsigned32
    MAX-ACCESS  read-only
    STATUS      current
    DESCRIPTION
        "The value of tnRmdIfDdmExtCalRxPower1 indicates the Rx_PWR(1)
         value as specified in Table 3.16 in the SFF Committee Standard's
         document SFF-8472 Rev 10.2."
    REFERENCE "SFF-8472 Rev 10.2"
    ::= { tnRmdIfDdmEntry 31 }

tnRmdIfDdmExtCalRxPower0              OBJECT-TYPE
    SYNTAX      Unsigned32
    MAX-ACCESS  read-only
    STATUS      current
    DESCRIPTION
        "The value of tnRmdIfDdmExtCalRxPower0 indicates the Rx_PWR(0)
         value as specified in Table 3.16 in the SFF Committee Standard's
         document SFF-8472 Rev 10.2."
    REFERENCE "SFF-8472 Rev 10.2"
    ::= { tnRmdIfDdmEntry 32 }

tnRmdIfDdmExtCalTxLaserBiasSlope      OBJECT-TYPE
    SYNTAX      Unsigned32 (0..65535)
    MAX-ACCESS  read-only
    STATUS      current
    DESCRIPTION
        "The value of tnRmdIfDdmExtCalTxLaserBiasSlope indicates the
         Tx_l(Slope) value as specified in Table 3.16 in the SFF
         Committee Standard's document SFF-8472 Rev 10.2."
    REFERENCE "SFF-8472 Rev 10.2"
    ::= { tnRmdIfDdmEntry 33 }

tnRmdIfDdmExtCalTxLaserBiasOffset     OBJECT-TYPE
    SYNTAX      Integer32 (-32767..32768)
    MAX-ACCESS  read-only
    STATUS      current
    DESCRIPTION
        "The value of tnRmdIfDdmExtCalTxLaserBiasOffset indicates the
         Tx_l(Offset) value as specified in Table 3.16 in the SFF
         Committee Standard's document SFF-8472 Rev 10.2."
    REFERENCE "SFF-8472 Rev 10.2"
    ::= { tnRmdIfDdmEntry 34 }

tnRmdIfDdmExtCalTxPowerSlope          OBJECT-TYPE
    SYNTAX      Unsigned32 (0..65535)
    MAX-ACCESS  read-only
    STATUS      current
    DESCRIPTION
        "The value of tnRmdIfDdmExtCalTxPowerSlope indicates the
         Tx_PWR(Slope) value as specified in Table 3.16 in the
         SFF Committee Standard's document SFF-8472 Rev 10.2."
    REFERENCE "SFF-8472 Rev 10.2"
    ::= { tnRmdIfDdmEntry 35 }

tnRmdIfDdmExtCalTxPowerOffset         OBJECT-TYPE
    SYNTAX      Integer32 (-32767..32768)
    MAX-ACCESS  read-only
    STATUS      current
    DESCRIPTION
        "The value of tnRmdIfDdmExtCalTxPowerOffset indicates the
         Tx_PWR(Offset) value as specified in Table 3.16 in the
         SFF Committee Standard's document SFF-8472 Rev 10.2."
    REFERENCE "SFF-8472 Rev 10.2"
    ::= { tnRmdIfDdmEntry 36 }

tnRmdIfDdmExtCalTemperatureSlope      OBJECT-TYPE
    SYNTAX      Unsigned32 (0..65535)
    MAX-ACCESS  read-only
    STATUS      current
    DESCRIPTION
        "The value of tnRmdIfDdmExtCalTemperatureSlope indicates the
         T(Slope) value as specified in Table 3.16 in the SFF
         Committee Standard's document SFF-8472 Rev 10.2."
    REFERENCE "SFF-8472 Rev 10.2"
    ::= { tnRmdIfDdmEntry 37 }

tnRmdIfDdmExtCalTemperatureOffset     OBJECT-TYPE
    SYNTAX      Integer32 (-32767..32768)
    MAX-ACCESS  read-only
    STATUS      current
    DESCRIPTION
        "The value of tnRmdIfDdmExtCalTemperatureOffset indicates the
         T(Offset) value as specified in Table 3.16 in the SFF
         Committee Standard's document SFF-8472 Rev 10.2."
    REFERENCE "SFF-8472 Rev 10.2"
    ::= { tnRmdIfDdmEntry 38 }

tnRmdIfDdmExtCalVoltageSlope          OBJECT-TYPE
    SYNTAX      Unsigned32 (0..65535)
    MAX-ACCESS  read-only
    STATUS      current
    DESCRIPTION
        "The value of tnRmdIfDdmExtCalVoltageSlope indicates the V(Slope)
        value as specified in Table 3.16 in the SFF Committee Standard's
        document SFF-8472 Rev 10.2."
    REFERENCE "SFF-8472 Rev 10.2"
    ::= { tnRmdIfDdmEntry 39 }

tnRmdIfDdmExtCalVoltageOffset         OBJECT-TYPE
    SYNTAX      Integer32 (-32767..32768)
    MAX-ACCESS  read-only
    STATUS      current
    DESCRIPTION
        "The value of tnRmdIfDdmExtCalVoltageOffset indicates the V(Slope)
        value as specified in Table 3.16 in the SFF Committee Standard's
        document SFF-8472 Rev 10.2."
    REFERENCE "SFF-8472 Rev 10.2"
    ::= { tnRmdIfDdmEntry 40 }


-- =============================================================
-- tnRmdIfLoopbackTable
-- =============================================================

tnRmdIfLoopbackTable OBJECT-TYPE
    SYNTAX      SEQUENCE OF TnRmdIfLoopbackEntry
    MAX-ACCESS  not-accessible
    STATUS      current
    DESCRIPTION
        "A table containing the loopback data of all interfaces of all RMDs."
    ::= { tnRmdIfObjects 8 }

tnRmdIfLoopbackEntry OBJECT-TYPE
    SYNTAX      TnRmdIfLoopbackEntry
    MAX-ACCESS  not-accessible
    STATUS      current
    DESCRIPTION
        "A list of objects containing the loopback data of an interface of
         an RMD."
    INDEX  { tnSysSwitchId, tnRmdSystemId, tnRmdIfIndex }
    ::= { tnRmdIfLoopbackTable 1 }

TnRmdIfLoopbackEntry ::=
    SEQUENCE {
        tnRmdIfLoopbackIn          TruthValue,
        tnRmdIfLoopbackOut         TruthValue,
        tnRmdIfEvcLoopBack         TruthValue,
        tnRmdIfEvcLoopBackVlanId   VlanIdOrNone
    }

tnRmdIfLoopbackIn OBJECT-TYPE
    SYNTAX      TruthValue
    MAX-ACCESS  read-write
    STATUS      current
    DESCRIPTION
        "Indicates whether an ingoing loopback is enabled for
         the interface."
    ::= { tnRmdIfLoopbackEntry 1 }

tnRmdIfLoopbackOut OBJECT-TYPE
    SYNTAX      TruthValue
    MAX-ACCESS  read-write
    STATUS      current
    DESCRIPTION
        "Indicates whether an outgoing loopback is enabled for the interface."
    ::= { tnRmdIfLoopbackEntry 2 }

tnRmdIfEvcLoopBack OBJECT-TYPE
    SYNTAX TruthValue
    MAX-ACCESS read-write
    STATUS current
    DESCRIPTION
        "Indicates whether an EVC(flow) loopback is enabled for the interface."
    ::= { tnRmdIfLoopbackEntry 3 }


tnRmdIfEvcLoopBackVlanId OBJECT-TYPE
    SYNTAX VlanIdOrNone
    MAX-ACCESS read-write
    STATUS current
    DESCRIPTION
        "The ID of the VLAN to which the EVC-loopback is related."
    ::= { tnRmdIfLoopbackEntry 4 }

-- =============================================================
-- tnRmdIfIdlTable
-- =============================================================
--
-- tnRmdIfIdlTable OBJECT-TYPE
--     SYNTAX      SEQUENCE OF TnRmdIfIdlEntry
--     MAX-ACCESS  not-accessible
--     STATUS      current
--     DESCRIPTION
--         "A table containing the IDL data of all interfaces of all RMDs."
--     ::= { tnRmdIfObjects 9 }

-- tnRmdIfIdlEntry OBJECT-TYPE
--     SYNTAX      TnRmdIfIdlEntry
--     MAX-ACCESS  not-accessible
--     STATUS      current
--     DESCRIPTION
--         "A list of objects containing the IDL data of an interface of
--          an RMD."
--     INDEX  { tnRmdSystemId, tnRmdIfIndex }
--     ::= { tnRmdIfIdlTable 1 }
--
-- TnRmdIfIdlEntry ::=
--     SEQUENCE {
--         tnRmdIfIdlIngressMode  TnRmdIdlIngressMode,
--     }
--
-- tnRmdIfIdlIngressMode OBJECT-TYPE
--     SYNTAX      TnRmdIdlIngressMode
--     MAX-ACCESS  read-write
--     STATUS      current
--     DESCRIPTION
--         "Indicates whether IDL frames can ingress via the interface."
--     ::= { tnRmdIfIdlEntry 1 }


-- =============================================================
-- tnRmdIfCountersTable
-- =============================================================

tnRmdIfCountersTable OBJECT-TYPE
    SYNTAX      SEQUENCE OF TnRmdIfCountersEntry
    MAX-ACCESS  not-accessible
    STATUS      current
    DESCRIPTION
        "A table containing the counters of all interfaces of all RMDs."
    ::= { tnRmdIfObjects 10 }

tnRmdIfCountersEntry OBJECT-TYPE
    SYNTAX      TnRmdIfCountersEntry
    MAX-ACCESS  not-accessible
    STATUS      current
    DESCRIPTION
        "A list of objects containing the counters of all interfaces
         of an RMD."
    INDEX  { tnSysSwitchId, tnRmdSystemId, tnRmdIfIndex }
    ::= { tnRmdIfCountersTable 1 }

TnRmdIfCountersEntry ::=
    SEQUENCE {
        tnRmdIfCountersRxNrCorrectFrames                  Counter64,
        tnRmdIfCountersRxNrCorrectBytes                   Counter64,
        tnRmdIfCountersRxNrErroredFcsFrames               Counter64,
        tnRmdIfCountersRxNrLengthErrorOrOtherErrorFrames  Counter64,
        tnRmdIfCountersRxNrDiscardedFrames                Counter64,
        tnRmdIfCountersRxNrDroppedQueueOverflowFrames     Counter64,
        tnRmdIfCountersTxNrFrames                         Counter64,
        tnRmdIfCountersTxNrBytes                          Counter64,
        tnRmdIfCountersReset                              TruthValue
    }

tnRmdIfCountersRxNrCorrectFrames OBJECT-TYPE
    SYNTAX      Counter64
    MAX-ACCESS  read-only
    STATUS      current
    DESCRIPTION
        "Number of correctly received frames for this interface."
    ::= { tnRmdIfCountersEntry 1 }

tnRmdIfCountersRxNrCorrectBytes OBJECT-TYPE
    SYNTAX      Counter64
    MAX-ACCESS  read-only
    STATUS      current
    DESCRIPTION
        "Number of correctly received bytes for this interface."
    ::= { tnRmdIfCountersEntry 2 }

tnRmdIfCountersRxNrErroredFcsFrames OBJECT-TYPE
    SYNTAX      Counter64
    MAX-ACCESS  read-only
    STATUS      current
    DESCRIPTION
        "Number of received frames for this interface which were
         errored FCS frames."
    ::= { tnRmdIfCountersEntry 3 }

tnRmdIfCountersRxNrLengthErrorOrOtherErrorFrames OBJECT-TYPE
    SYNTAX      Counter64
    MAX-ACCESS  read-only
    STATUS      current
    DESCRIPTION
        "Number of received frames for this interface which had
         a length or other error."
    ::= { tnRmdIfCountersEntry 4 }

tnRmdIfCountersRxNrDiscardedFrames OBJECT-TYPE
    SYNTAX      Counter64
    MAX-ACCESS  read-only
    STATUS      current
    DESCRIPTION
        "Number of received frames for this interface which were
         discarded."
    ::= { tnRmdIfCountersEntry 5 }

tnRmdIfCountersRxNrDroppedQueueOverflowFrames OBJECT-TYPE
    SYNTAX      Counter64
    MAX-ACCESS  read-only
    STATUS      current
    DESCRIPTION
        "Number of received frames for this interface which were
         dropped due to queue overflow."
    ::= { tnRmdIfCountersEntry 6 }

tnRmdIfCountersTxNrFrames OBJECT-TYPE
    SYNTAX      Counter64
    MAX-ACCESS  read-only
    STATUS      current
    DESCRIPTION
        "Number of transmitted frames for this interface."
    ::= { tnRmdIfCountersEntry 7 }

tnRmdIfCountersTxNrBytes OBJECT-TYPE
    SYNTAX      Counter64
    MAX-ACCESS  read-only
    STATUS      current
    DESCRIPTION
        "Number of transmitted bytes for this interface."
    ::= { tnRmdIfCountersEntry 8 }

tnRmdIfCountersReset OBJECT-TYPE
    SYNTAX      TruthValue
    MAX-ACCESS  read-write
    STATUS      current
    DESCRIPTION
        "Setting of this object to 'true' invokes a reset of the counters
         for this interface.
         Setting of this object to value 'false' has no effect.

         This object is merely used to invoke a reset, and its actual
         value has no meaning."
    ::= { tnRmdIfCountersEntry 9 }


-- =============================================================
-- tnRmdTdmIfTable
-- =============================================================
--
-- tnRmdTdmIfTable OBJECT-TYPE
--     SYNTAX      SEQUENCE OF TnRmdTdmIfEntry
--     MAX-ACCESS  not-accessible
--     STATUS      current
--     DESCRIPTION
--         "A table containing the parameters of all TDM interfaces
--          of all RMDs."
--     ::= { tnRmdIfObjects 11 }
--
-- tnRmdTdmIfEntry OBJECT-TYPE
--     SYNTAX      TnRmdTdmIfEntry
--     MAX-ACCESS  not-accessible
--     STATUS      current
--     DESCRIPTION
--         "A list of objects containing the parameters of a TDM
--          interface of an RMD."
--     INDEX  { tnRmdSystemId, tnRmdIfIndex }
--     ::= { tnRmdTdmIfTable 1 }
--
-- TnRmdTdmIfEntry ::=
--     SEQUENCE {
--         tnRmdTdmIfRate  TnRmdTdmIfRate
--     }
--
-- tnRmdTdmIfRate OBJECT-TYPE
--     SYNTAX      TnRmdTdmIfRate
--     MAX-ACCESS  read-write
--     STATUS      current
--     DESCRIPTION
--         "The rate of the TDM interface."
--     ::= { tnRmdTdmIfEntry 1 }


-- =============================================================
-- tnRmdTdmIfNimTable
-- =============================================================
--
-- tnRmdTdmIfNimTable OBJECT-TYPE
--     SYNTAX      SEQUENCE OF TnRmdTdmIfNimEntry
--     MAX-ACCESS  not-accessible
--     STATUS      current
--     DESCRIPTION
--         "A table containing the data of all NIMs of all TDM
--          interfaces of all RMDs."
--     ::= { tnRmdIfObjects 12 }
--
-- tnRmdTdmIfNimEntry OBJECT-TYPE
--     SYNTAX      TnRmdTdmIfNimEntry
--     MAX-ACCESS  not-accessible
--     STATUS      current
--     DESCRIPTION
--         "A list of objects containing the data of a NIM of a
--          TDM interface of an RMD."
--     INDEX  { tnRmdSystemId,
--              tnRmdIfIndex,
--              tnRmdTdmIfNimDirection }
--     ::= { tnRmdTdmIfNimTable 1 }
--
--     SEQUENCE {
--         tnRmdTdmIfNimDirection  TnRmdNimDirection,
--         tnRmdTdmIfNimJ0String   OCTET STRING
--     }
--
-- tnRmdTdmIfNimDirection OBJECT-TYPE
--     SYNTAX      TnRmdNimDirection
--     MAX-ACCESS  not-accessible
--     STATUS      current
--     DESCRIPTION
--         "The direction of the NIM."
--     ::= { tnRmdTdmIfNimEntry 1 }
--
-- tnRmdTdmIfNimJ0String OBJECT-TYPE
--     SYNTAX      OCTET STRING (SIZE(64))
--     MAX-ACCESS  read-only
--     STATUS      current
--     DESCRIPTION
--         "The received J0 string."
--     ::= { tnRmdTdmIfNimEntry 2 }
--
--
-- =============================================================
-- tnRmdTdmIfNimCountersTable
-- =============================================================
--
-- tnRmdTdmIfNimCountersTable OBJECT-TYPE
--     SYNTAX      SEQUENCE OF TnRmdTdmIfNimCountersEntry
--     MAX-ACCESS  not-accessible
--     STATUS      current
--     DESCRIPTION
--         "A table containing the counters of all TDM interface NIMs
--          of all RMDs."
--     ::= { tnRmdIfObjects 13 }
--
-- tnRmdTdmIfNimCountersEntry OBJECT-TYPE
--     SYNTAX      TnRmdTdmIfNimCountersEntry
--     MAX-ACCESS  not-accessible
--     STATUS      current
--     DESCRIPTION
--         "A list of objects containing the counters of a TDM interface
--          NIM of an RMD."
--     INDEX  { tnRmdSystemId,
--              tnRmdIfIndex,
--              tnRmdTdmIfNimDirection }
--     ::= { tnRmdTdmIfNimCountersTable 1 }
--
-- TnRmdTdmIfNimCountersEntry ::=
--     SEQUENCE {
--         tnRmdTdmIfNimCountersB1Errors  Counter64,
--         tnRmdTdmIfNimCountersReset     TruthValue
--     }
--
-- tnRmdTdmIfNimCountersB1Errors OBJECT-TYPE
--     SYNTAX      Counter64
--     MAX-ACCESS  read-only
--     STATUS      current
--     DESCRIPTION
--         "The B1 error count."
--     ::= { tnRmdTdmIfNimCountersEntry 1 }
--
-- tnRmdTdmIfNimCountersReset OBJECT-TYPE
--     SYNTAX      TruthValue
--     MAX-ACCESS  read-write
--     STATUS      current
--     DESCRIPTION
--         "Setting of this object to 'true' invokes a reset of the counters
--          for this NIM.
--          Setting of this object to value 'false' has no effect.
--
--          This object is merely used to invoke a reset, and its actual
--          value has no meaning."
--     ::= { tnRmdTdmIfNimCountersEntry 2 }

END
