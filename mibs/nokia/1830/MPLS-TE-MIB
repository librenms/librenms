-- Extracted from draft-ietf-mpls-te-mib-04.txt
--
--  MPLS Traffic Engineering Management Information Base Using
--                             SMIv2
--                               
--                 draft-ietf-mpls-te-mib-04.txt


MPLS-TE-MIB DEFINITIONS ::= BEGIN


IMPORTS
   MODULE-IDENTITY, OBJECT-TYPE, NOTIFICATION-TYPE,
   IpAddress,
   experimental, Integer32, Unsigned32
--   experimental, Integer32
      FROM SNMPv2-SMI
      
   MODULE-COMPLIANCE, OBJECT-GROUP, NOTIFICATION-GROUP
      FROM SNMPv2-CONF
      
   TEXTUAL-CONVENTION, TruthValue, RowStatus, RowPointer,
   StorageType, DisplayString
--   StorageType, DisplayString, Unsigned32
      FROM SNMPv2-TC

   InterfaceIndexOrZero
      FROM IF-MIB
      
--   MplsBitRate, MplsBurstSize, MplsLSPID
--      FROM MPLS-LSR-MIB
      
    InetAddressIPv4, InetAddressIPv6
       FROM INET-ADDRESS-MIB;


mplsTeMIB MODULE-IDENTITY
   LAST-UPDATED
      "201504301200Z"  -- 30 April 2015 12:00:00 EST
   ORGANIZATION
      "Multiprotocol Label Switching (MPLS) Working Group"
   CONTACT-INFO
        "        Cheenu Srinivasan
         Postal: Tachion Networks, Inc.
                 Monmouth Park Corporate Center I
                 Building C, 185 Monmouth Park Highway
                 West Long Branch, NJ 07764
         Tel:    +1-732-542-7750 x1234
         Email:  cheenu@tachion.com
        
                 Arun Viswanathan
         Postal: Force10 Networks, Inc.
                 1440 McCarthy Blvd
                 Milpitas, CA 95035
         Tel:    +1-408-571-3516
         Email:  arun@force10networks.com
        
                 Thomas D. Nadeau
         Postal: Cisco Systems, Inc.
                 250 Apollo Drive
                 Chelmsford, MA 01824
         Tel:    +1-978-244-3051
         Email:  tnadeau@cisco.com"
   DESCRIPTION
        "This MIB module contains managed object definitions
         for MPLS Traffic Engineering (TE) as defined in:
         Extensions to RSVP for LSP Tunnels, Awduche et al,
         Internet Draft <draft-mpls-rsvp-lsp-tunnel-02.txt>,
         March 1999; Constraint-Based LSP Setup using LDP, B.
         Jamoussi, Internet Draft <draft-ietf-mpls-cr-ldp-
         01.txt>, Feb. 1999; Requirements for Traffic
         Engineering Over MPLS, Awduche, D., J. Malcolm, J.,
         Agogbua, J., O'Dell, M., J. McManus, <rfc2702.txt>,
         September 1999."
        
   
   -- Revision history.
   REVISION        "201504301200Z"
   DESCRIPTION     "Added support for MIBs in MPLS-TE-MIB"

   REVISION
        "200007141200Z"  -- 14 July 2000 12:00:00 EST
   DESCRIPTION
        "Updates based on MPLS WG feedback"
   REVISION
        "200005261200Z"  -- 26 May 2000 12:00:00 EST
   DESCRIPTION
        "Updates based on MPLS WG feedback"
   REVISION
        "200003031200Z"  -- 3 March 2000 12:00:00 EST
   DESCRIPTION
        "Updates based on MPLS WG feedback"
   REVISION
        "199907161200Z"  -- 16 July 1999 12:00:00 EST
   DESCRIPTION
        "Initial draft version."
   
   ::= { experimental 95 }


-- Textual Conventions.

-- NOTE: These TC's are defined here for now instead of importing from
--       the MPLS-LSR-MIB

MplsLSPID ::= TEXTUAL-CONVENTION
   STATUS        current
   DESCRIPTION
       "An identifier that is assigned to each LSP and is
        used to uniquely identify it.  This is assigned at
        the head end of the LSP and can be used by all LSRs
        to identify this LSP.  This value is piggybacked by
        the signaling protocol when this LSP is signaled
        within the network.  This identifier can then be
        used at each LSR to identify which labels are being
        swapped to other labels for this LSP.  For IPv4
        addresses this results in a 6-octet long cookie."
   SYNTAX        OCTET STRING (SIZE (0..31))

MplsBitRate ::= TEXTUAL-CONVENTION
   DISPLAY-HINT "d"
   STATUS      current
   DESCRIPTION
       "An estimate of bandwidth in units of 1,000 bits per
        second.  If this object reports a value of 'n' then
        the rate of the object is somewhere in the range of
        'n-500' to 'n+499'. For objects which do not vary in
        bitrate, or for those where no accurate estimation
        can be made, this object should contain the nominal
        bitrate."
   SYNTAX  Integer32 (1..2147483647)

MplsBurstSize ::= TEXTUAL-CONVENTION
   DISPLAY-HINT "d"
   STATUS      current
   DESCRIPTION
       "The number of octets of MPLS data that the stream
        may send back-to-back without concern for policing."
   SYNTAX  Integer32 (1..2147483647)

-- the actual TC's for the MPLS-TE-MIB start here

MplsTunnelIndex ::= TEXTUAL-CONVENTION
   STATUS        current
   DESCRIPTION
        "Index into mplsTunnelTable."
   SYNTAX        Integer32 (0..65535)

-- Top level components of this MIB.

-- tables, scalars
mplsTeObjects       OBJECT IDENTIFIER ::= { mplsTeMIB 1 }
-- traps
mplsTeNotifications OBJECT IDENTIFIER ::= { mplsTeMIB 2 }
mplsTeNotifyPrefix  OBJECT IDENTIFIER ::= { mplsTeNotifications 0 }
-- conformance
mplsTeConformance   OBJECT IDENTIFIER ::= { mplsTeMIB 3 }


-- MPLS tunnel table.

mplsTunnelIndexNext OBJECT-TYPE
   SYNTAX        Integer32 (0..65535)
   MAX-ACCESS    read-only
   STATUS        current
   DESCRIPTION
        "This object contains the next appropriate value to
         be used for mplsTunnelIndex when creating entries in
         mplsTunnelTable. If the number of unassigned entries
         is exhausted, a retrival operation will return a
         value of 0.  This object may also return a value of
         0 when the LSR is unable to accept conceptual row
         creation, for example, if the mplsTunnelTable is
         implemented as read-only. To obtain the value of
         mplsTunnelIndex for a new entry, the manager must
         first issue a management protocol retrieval
         operation to obtain the current value of this
         object. The agent should modify the value to reflect
         the next unassigned index after each retrieval
         operation. After a manager retrieves a value the
         agent will determine through its local policy when
         this index value will be made available for reuse."
   ::= { mplsTeObjects 1 }

mplsTunnelTable OBJECT-TYPE
   SYNTAX        SEQUENCE OF MplsTunnelEntry
   MAX-ACCESS    not-accessible
   STATUS        current
   DESCRIPTION
        "The mplsTunnelTable allows new MPLS tunnels to be
         created between an LSR and a remote endpoint, and
         existing tunnels to be reconfigured or removed.
         Note that only point-to-point tunnel segments are
         supported, although multi-point-to-point and point-
         to-multi-point connections are supported by an LSR
         acting as a cross-connect.  Each MPLS tunnel can
         thus have one out-segment originating at this LSR
         and/or one in-segment terminating at this LSR."
   ::= { mplsTeObjects 2 }

mplsTunnelEntry OBJECT-TYPE
   SYNTAX        MplsTunnelEntry
   MAX-ACCESS    not-accessible
   STATUS        current
   DESCRIPTION
        "An entry in this table represents an MPLS tunnel.
         An entry can be created by a network administrator
         or by an SNMP agent as instructed by an MPLS
         signaling protocol. Whenever a new entry is created
         with mplsTunnelIsIf set to true(1), then a
         corresponding entry is created in ifTable as well
         (see RFC 2233). The ifType of this entry is
         mplsTunnel(150)."
   REFERENCE
        "1. RFC 2233 - The Interfaces Group MIB using SMIv2,
         McCloghrie, K., and F. Kastenholtz, Nov. 1997
         2. RFC 1700 - Assigned Numbers, Reynolds, J. and J.
         Postel, Oct. 1994"
   INDEX         { mplsTunnelIndex, mplsTunnelInstance,
                mplsTunnelIngressLSRId }
      ::= { mplsTunnelTable 1 }

MplsTunnelEntry ::= SEQUENCE {
      mplsTunnelIndex                 MplsTunnelIndex,
      mplsTunnelInstance              MplsTunnelIndex,
      mplsTunnelIngressLSRId          Unsigned32,
      mplsTunnelName                  DisplayString,
      mplsTunnelDescr                 DisplayString,
      mplsTunnelIsIf                  TruthValue,
      mplsTunnelIfIndex               InterfaceIndexOrZero,
      mplsTunnelXCPointer             RowPointer,
      mplsTunnelSignallingProto       INTEGER,
      mplsTunnelSetupPrio             INTEGER,
      mplsTunnelHoldingPrio           INTEGER,
      mplsTunnelSessionAttributes     BITS,
      mplsTunnelOwner                 INTEGER,
      mplsTunnelLocalProtectInUse     TruthValue,
      mplsTunnelResourcePointer       RowPointer,
      mplsTunnelInstancePriority      Integer32,
      mplsTunnelHopTableIndex         Integer32,
      mplsTunnelARHopTableIndex       Integer32,
      mplsTunnelAdminStatus           INTEGER,
      mplsTunnelOperStatus            INTEGER,
      mplsTunnelRowStatus             RowStatus,
      mplsTunnelStorageType           StorageType
   }

mplsTunnelIndex OBJECT-TYPE
   SYNTAX        MplsTunnelIndex
   MAX-ACCESS    accessible-for-notify
   STATUS        current
   DESCRIPTION
        "Uniquely identifies this row."
   ::= { mplsTunnelEntry 1 }

mplsTunnelInstance OBJECT-TYPE
   SYNTAX        MplsTunnelIndex
   MAX-ACCESS    accessible-for-notify
   STATUS        current
   DESCRIPTION
        "Uniquely identifies an instance of a tunnel. It is
         useful to identify multiple instances of tunnels for
         the purposes of backup and parallel tunnels."
   ::= { mplsTunnelEntry 2 }

mplsTunnelIngressLSRId OBJECT-TYPE
   SYNTAX        Unsigned32 (0..4294967295)
   MAX-ACCESS    accessible-for-notify
   STATUS        current
   DESCRIPTION
        "The purpose of this object is to uniquely identity a
         tunnel within a network. When the MPLS signalling
         protoocol is rsvp(2) this value should mimic the
         Extended Tunnel Id field in the Session object. When
         the MPLS signalling protoocol is crldp(3) this value
         should mimic the Ingress LSR Router ID field in the
         LSPID TLV object."
   REFERENCE
        "1. RSVP-TE: Extensions to RSVP for LSP Tunnels,
         Awduche et al, Internet Draft <draft-mpls-rsvp-lsp-
         tunnel-05.txt>, February 2000.,
         2. Constraint-Based LSP Setup using LDP, Jamoussi,
         Internet Draft <draft-ietf-mpls-cr-ldp-03.txt>,
         September 1999."
   ::= { mplsTunnelEntry 3 }

mplsTunnelName OBJECT-TYPE
   SYNTAX        DisplayString
   MAX-ACCESS    read-create
   STATUS        current
   DESCRIPTION
        "The canonical name assigned to the tunnel. This name
         can be used to refer to the tunnel on the LSR's
         console port.  If mplsTunnelIsIf is set to true then
         the ifName of the interface corresponding to this
         tunnel should have a value equal to mplsTunnelName.
         Also see the description of ifName in RFC 2233."
   REFERENCE
        "RFC 2233 - The Interfaces Group MIB using SMIv2,
         McCloghrie, K., and F. Kastenholtz, Nov. 1997"
   ::= { mplsTunnelEntry 4 }

mplsTunnelDescr OBJECT-TYPE
   SYNTAX        DisplayString
   MAX-ACCESS    read-create
   STATUS        current
   DESCRIPTION
        "A textual string containing information about the
         tunnel.  If there is no description this object
         contains a zero length string."
   ::= { mplsTunnelEntry 5 }


mplsTunnelIsIf OBJECT-TYPE
   SYNTAX        TruthValue
   MAX-ACCESS    read-create
   STATUS        current
   DESCRIPTION
        "Denotes whether or not this tunnel corresponds to an
         interface represented in the interfaces group table.
         Note that if this variable is set to true then the
         ifName of the interface corresponding to this tunnel
         should have a value equal to mplsTunnelName.  Also
         see the description of ifName in RFC 2233."
   REFERENCE
        "RFC 2233 - The Interfaces Group MIB using SMIv2,
         McCloghrie, K., and F. Kastenholtz, Nov. 1997"
   DEFVAL        { false }
   ::= { mplsTunnelEntry 6 }

mplsTunnelIfIndex OBJECT-TYPE
   SYNTAX        InterfaceIndexOrZero
   MAX-ACCESS    read-only
   STATUS        current
   DESCRIPTION
        "If mplsTunnelIsIf is set to true, then this value
         contains the LSR-assigned ifIndex which corresponds
         to an entry in the interfaces table.  Otherwise this
         variable should contain the value of zero indicating
         that a valid ifIndex was not assigned to this tunnel
         interface."
   REFERENCE
        "RFC 2233 - The Interfaces Group MIB using SMIv2,
         McCloghrie, K., and F. Kastenholtz, Nov. 1997"
   ::= { mplsTunnelEntry 7 }

mplsTunnelXCPointer OBJECT-TYPE
   SYNTAX        RowPointer
   MAX-ACCESS    read-create
   STATUS        current
   DESCRIPTION
        "This variable points to a row in the mplsXCTable.
         This table identifies the segments that compose this
         tunnel, their characteristics, and relationships to
         each other. A value of zeroDotZero indicates that no
         LSP has been associated with this tunnel yet."
   REFERENCE
        "Srinivasan, C., Viswanathan, A., and T. Nadeau, MPLS
         Label Switch Router Management Information Base
         Using SMIv2, Internet Draft <draft-ietf-mpls-lsr-mib-
         04.txt>, April 26, 2000."
   ::= { mplsTunnelEntry 8 }

mplsTunnelSignallingProto OBJECT-TYPE
   SYNTAX        INTEGER {
          none(1),
          rsvp(2),
          crldp(3),
          other(4)
       }
   MAX-ACCESS    read-create
   STATUS        current
   DESCRIPTION
        "The signaling protocol, if any, which was used to
         setup this tunnel."
   DEFVAL        { none }
   ::= { mplsTunnelEntry 9 }

mplsTunnelSetupPrio OBJECT-TYPE
   SYNTAX        INTEGER (0..7)
   MAX-ACCESS    read-create
   STATUS        current
   DESCRIPTION
        "Indicates the setup priority of this tunnel."
   REFERENCE
        "1. RSVP-TE: Extensions to RSVP for LSP Tunnels,
         Awduche et al, Internet Draft <draft-mpls-rsvp-lsp-
         tunnel-05.txt>, February 2000.,
         2. Constraint-Based LSP Setup using LDP, Jamoussi,
         Internet Draft <draft-ietf-mpls-cr-ldp-03.txt>,
         September 1999."
   ::= { mplsTunnelEntry 10 }

mplsTunnelHoldingPrio OBJECT-TYPE
   SYNTAX        INTEGER (0..7)
   MAX-ACCESS    read-create
   STATUS        current
   DESCRIPTION
        "Indicates the holding priority for this tunnel."
   REFERENCE
        "1. RSVP-TE: Extensions to RSVP for LSP Tunnels,
         Awduche et al, Internet Draft <draft-mpls-rsvp-lsp-
         tunnel-05.txt>, February 2000.,
         2. Constraint-Based LSP Setup using LDP, Jamoussi,
         Internet Draft <draft-ietf-mpls-cr-ldp-03.txt>,
         September 1999."
   ::= { mplsTunnelEntry 11 }

mplsTunnelSessionAttributes OBJECT-TYPE
   SYNTAX      BITS {
          fastReroute (0),
          mergingPermitted (1),
          isPersistent (2),
          localProtectionAvailable (3),
          isPinned (4)
      }
   MAX-ACCESS    read-create
   STATUS        current
   DESCRIPTION
        "This bitmask indicates optional session values for
         this tunnel. The following describes these
         bitfields:
          
          fastReroute          This flag indicates that the
                               any tunnel hop may choose to
                               reroute this tunnel without
                               tearing it down.
          
          mergingPermitted     This flag permits transit
                               routers to merge this session
                               with other RSVP sessions for
                               the purpose of reducing
                               resource overhead on
                               downstream transit routers,
                               thereby providing better
                               network scalability.
          
          isPersistant         Indicates whether this tunnel
                               should be restored
                               automatically after a failure
                               occurs.
          
          localProtectionAvailable This flag permits transit
                               routers to use a local repair
                               mechanism which may result in
                               violation of the explicit
                               routing of this tunnel. When a
                               fault is detected on an
                               adjacent downstream link or
                               node, a transit router can
                               reroute traffic for fast
                               service restoration.
                               
          isPinned             This flag indicates whether
                               the loose-routed hops of this
                               tunnel are to be pinned."
   REFERENCE
        "1. RSVP-TE: Extensions to RSVP for LSP Tunnels,
         Awduche et al, Internet Draft <draft-mpls-rsvp-lsp-
         tunnel-05.txt>, February 2000."
   DEFVAL        { { } }
   ::= { mplsTunnelEntry 12 }

mplsTunnelOwner OBJECT-TYPE
   SYNTAX        INTEGER {
         admin(1), -- represents all management entities
         rsvp(2),
         crldp(3),
         policyAgent(4),
         other(5)
      }
   MAX-ACCESS    read-create
   STATUS        current
   DESCRIPTION
        "Indicates which protocol created and is responsible
         for managing this tunnel. Values rsvp(2) and
         crldp(3) should not be used at the head-end of a
         MPLS tunnel."
   ::= { mplsTunnelEntry 13 }

mplsTunnelLocalProtectInUse  OBJECT-TYPE
   SYNTAX        TruthValue
   MAX-ACCESS    read-create
   STATUS        current
   DESCRIPTION
        "Indicates that the local repair mechanism is in use
         to maintain this tunnel (usually in the face of an
         outage of the link it was previously routed over)."
   ::= { mplsTunnelEntry 14 }

mplsTunnelResourcePointer OBJECT-TYPE
   SYNTAX        RowPointer
   MAX-ACCESS    read-create
   STATUS        current
   DESCRIPTION
        "This variable represents a pointer to the traffic
         parameter specification for this tunnel.  This value
         may point at an entry in the mplsTunnelResourceEntry
         to indicate which mplsTunnelResourceEntry is to be
         assigned to this segment.  This value may optionally
         point at an externally defined traffic parameter
         specification table.  A value of zeroDotZero
         indicates best-effort treatment.  By having the same
         value of this object, two or more segments can
         indicate resource sharing."
   ::= { mplsTunnelEntry 15 }

mplsTunnelInstancePriority OBJECT-TYPE
   SYNTAX        Integer32 (0..2147483647)
   MAX-ACCESS    read-create
   STATUS        current
   DESCRIPTION
        "This value indicates which priority, in descending
         order with 0 indicating the lowest priority, within
         a group of tunnel instances. A group of tunnel
         instances is defined as a set of tunnels with the
         same mplsTunnelIndex in this table, but with a
         different mplsTunnelInstance.  Tunnel group
         priorities are used to denote the priority at which
         a particular tunnel instance will supercede another.
         Instances of tunnels containing the same
         mplsTunnelInstancePriority will be used for load
         sharing."
   DEFVAL        { 0 }
   ::= { mplsTunnelEntry 16 }

mplsTunnelHopTableIndex OBJECT-TYPE
   SYNTAX        Integer32 (0..2147483647)
   MAX-ACCESS    read-create
   STATUS        current
   DESCRIPTION
        "Index into the mplsTunnelHopTable entry that
         specifies the explicit route hops for this tunnel."
   ::= { mplsTunnelEntry 17 }

mplsTunnelARHopTableIndex OBJECT-TYPE
   SYNTAX        Integer32 (0..2147483647)
   MAX-ACCESS    read-only
   STATUS        current
   DESCRIPTION
        "Index into the mplsTunnelARHopTable entry that
         specifies the actual hops traversed by the tunnel."
   ::= { mplsTunnelEntry 18 }

mplsTunnelAdminStatus OBJECT-TYPE
   SYNTAX        INTEGER {
         up(1),     -- ready to pass packets
         down(2),
         testing(3) -- in some test mode
      }
   MAX-ACCESS    read-create
   STATUS        current
   DESCRIPTION
        "Indicates the desired operational status of this
         tunnel."
   ::= { mplsTunnelEntry 19 }

mplsTunnelOperStatus OBJECT-TYPE
   SYNTAX        INTEGER {
         up(1),            -- ready to pass packets
         down(2),
         testing(3),       -- in some test mode
         unknown(4),       -- status cannot be determined
         dormant(5),
         notPresent(6),    -- some component is missing
         lowerLayerDown(7) -- down due to the state of
                         -- lower layer interfaces
      }
   MAX-ACCESS    read-only
   STATUS        current
   DESCRIPTION
        "Indicates the actual operational status of this
         tunnel, which is typically but not limited to, a
         function of the state of individual segments of this
         tunnel."
   ::= { mplsTunnelEntry 20 }

mplsTunnelRowStatus OBJECT-TYPE
   SYNTAX        RowStatus
   MAX-ACCESS    read-create
   STATUS        current
   DESCRIPTION
        "This variable is used to create, modify, and/or
         delete a row in this table."
   ::= { mplsTunnelEntry 21 }

mplsTunnelStorageType OBJECT-TYPE
   SYNTAX        StorageType
   MAX-ACCESS    read-create
   STATUS        current
   DESCRIPTION
        "This variable indicates the storage type for this
         object."
   ::= { mplsTunnelEntry 22 }

-- End of mplsTunnelTable


-- Maximum number of tunnel hops supported.

mplsTunnelMaxHops OBJECT-TYPE
   SYNTAX        Integer32 (1..2147483647)
   MAX-ACCESS    read-only
   STATUS        current
   DESCRIPTION
        "The maximum number of hops that can be specified for
         a tunnel on this device."
   ::= { mplsTeObjects 3 }


-- Tunnel hop table.

mplsTunnelHopIndexNext OBJECT-TYPE
   SYNTAX        Integer32 (0..2147483647)
   MAX-ACCESS    read-only
   STATUS        current
   DESCRIPTION
        "This object contains an appropriate value to be used
         for mplsTunnelHopListIndex when creating entries in
         the mplsTunnelHopTable.  If the number of unassigned
         entries is exhausted, a retrival operation will
         return a value of 0.  This object may also return a
         value of 0 when the LSR is unable to accept
         conceptual row creation, for example, if the
         mplsTunnelHopTable is implemented as read-only.  To
         obtain the value of mplsTunnelHopListIndex for a new
         entry in the mplsTunnelHopTable, the manager issues
         a management protocol retrieval operation to obtain
         the current value of mplsTunnelHopIndex.  After each
         retrieval operation, the agent should modify the
         value to reflect the next unassigned index.  After a
         manager retrieves a value the agent will determine
         through its local policy when this index value will
         be made available for reuse."
   ::= { mplsTeObjects 4 }

mplsTunnelHopTable  OBJECT-TYPE
   SYNTAX        SEQUENCE OF MplsTunnelHopEntry
   MAX-ACCESS    not-accessible
   STATUS        current
   DESCRIPTION
        "The mplsTunnelHopTable is used to indicate the hops,
         strict or loose, for an MPLS tunnel defined in
         mplsTunnelTable, when it is established via
         signaling, for the outgoing direction of the tunnel.
         Each row in this table is indexed primarily by the
         same index, mplsTunnelIndex, as the row of the
         corresponding tunnel in mplsTunnelTable.  Each row
         also has a secondary index mplsTunnelHopIndex
         corresponding to the next hop that this row
         corresponds to.  The first row in the table is the
         first hop after the origination point of the tunnel.
         In case we want to specify a particular interface on
         the originating LSR of an outgoing tunnel by which
         we want packets to exit the LSR, we specify this as
         the first hop for this tunnel in
         mplsTunnelHopTable."
   ::= { mplsTeObjects 5 }

mplsTunnelHopEntry  OBJECT-TYPE
   SYNTAX        MplsTunnelHopEntry
   MAX-ACCESS    not-accessible
   STATUS        current
   DESCRIPTION
        "An entry in this table represents a tunnel hop.  An
         entry is created by a network administrator for
         signaled ERLSP set up by an MPLS signaling
         protocol."
   INDEX { mplsTunnelHopListIndex, mplsTunnelHopIndex }
      ::= { mplsTunnelHopTable 1 }

MplsTunnelHopEntry ::= SEQUENCE {
      mplsTunnelHopListIndex          Integer32,
      mplsTunnelHopIndex              Integer32,
      mplsTunnelHopAddrType           INTEGER,
--      mplsTunnelHopIpv4Addr           InetAddressIPv4,
      mplsTunnelHopIpv4Addr           IpAddress,
      mplsTunnelHopIpv4PrefixLen      INTEGER,
      mplsTunnelHopIpv6Addr           InetAddressIPv6,
      mplsTunnelHopIpv6PrefixLen      INTEGER,
      mplsTunnelHopAsNumber           INTEGER,
      mplsTunnelHopLspId              MplsLSPID,
      mplsTunnelHopStrictOrLoose      INTEGER,
      mplsTunnelHopRowStatus          RowStatus,
      mplsTunnelHopStorageType        StorageType
   }

mplsTunnelHopListIndex OBJECT-TYPE
   SYNTAX        Integer32 (1..2147483647)
   MAX-ACCESS    not-accessible
   STATUS        current
   DESCRIPTION
        "Primary index into this table identifying a
         particular explicit route object."
   ::= { mplsTunnelHopEntry 1 }

mplsTunnelHopIndex OBJECT-TYPE
   SYNTAX        Integer32 (1..2147483647)
   MAX-ACCESS    not-accessible
   STATUS        current
   DESCRIPTION
        "Secondary index into this table identifying a
         particular hop."
   ::= { mplsTunnelHopEntry 2 }

mplsTunnelHopAddrType OBJECT-TYPE
   SYNTAX        INTEGER {
          ipV4(1),
          ipV6(2),
          asNumber(3),
          lspid(4)
      }
   MAX-ACCESS    read-create
   STATUS        current
   DESCRIPTION
        "Denotes the address type of this tunnel hop."
   DEFVAL        { ipV4 }
   ::= { mplsTunnelHopEntry 3 }

mplsTunnelHopIpv4Addr OBJECT-TYPE
--   SYNTAX        InetAddressIPv4
   SYNTAX        IpAddress
   MAX-ACCESS    read-create
   STATUS        current
   DESCRIPTION
        "If mplsTunnelHopAddrType is set to ipV4(1), then
         this value will contain the IPv4 address of this
         hop. This object is otherwise insignificant and
         should contain a value of 0."
   ::= { mplsTunnelHopEntry 4 }

mplsTunnelHopIpv4PrefixLen OBJECT-TYPE
   SYNTAX        INTEGER (1..32)
   MAX-ACCESS    read-create
   STATUS        current
   DESCRIPTION
        "If mplsTunnelHopAddrType is ipV4(1), then the prefix
         length for this hop's IPv4 address is contained
         herein. This object is otherwise insignificant and
         should contain a value of 0."
   ::= { mplsTunnelHopEntry 5 }

mplsTunnelHopIpv6Addr OBJECT-TYPE
   SYNTAX        InetAddressIPv6
   MAX-ACCESS    read-create
   STATUS        current
   DESCRIPTION
        "If the mplsTunnelHopAddrType is set to ipV6(2), then
         this variable contains the IPv6 address of this hop.
         This object is otherwise insignificant and should
         contain a value of 0."
   ::= { mplsTunnelHopEntry 6 }

mplsTunnelHopIpv6PrefixLen OBJECT-TYPE
   SYNTAX        INTEGER (1..128)
   MAX-ACCESS    read-create
   STATUS        current
   DESCRIPTION
        "If mplsTunnelHopAddrType is set to ipV6(2), this
         value will contain the prefix length for this hop's
         IPv6 address. This object is otherwise insignificant
         and should contain a value of 0."
   ::= { mplsTunnelHopEntry 7 }

mplsTunnelHopAsNumber OBJECT-TYPE
   SYNTAX        INTEGER (0..65535)
   MAX-ACCESS    read-create
   STATUS        current
   DESCRIPTION
        "If mplsTunnelHopAddrType is set to asNumber(3), then
         this value will contain the AS number of this hop.
         This object is otherwise insignificant and should
         contain a value of 0 to indicate this fact."
   ::= { mplsTunnelHopEntry 8 }

mplsTunnelHopLspId OBJECT-TYPE
   SYNTAX        MplsLSPID
   MAX-ACCESS    read-create
   STATUS        current
   DESCRIPTION
        "If mplsTunnelHopAddrType is set to lspid(4), then
         this value will contain the LSPID of a tunnel of
         this hop. The present tuunel being configured is
         'tunneled' through this hop (using label stacking).
         This object is otherwise insignificant and should
         contain a value of 0 to indicate this fact."
   ::= { mplsTunnelHopEntry 9 }

mplsTunnelHopStrictOrLoose OBJECT-TYPE
   SYNTAX        INTEGER {
          strict(1),
          loose(2)
      }
   MAX-ACCESS    read-create
   STATUS        current
   DESCRIPTION
        "Denotes whether this tunnel hop is routed in a
         strict or loose fashion."
   ::= { mplsTunnelHopEntry 10 }
   
mplsTunnelHopRowStatus OBJECT-TYPE
   SYNTAX        RowStatus
   MAX-ACCESS    read-create
   STATUS        current
   DESCRIPTION
        "This variable is used to create, modify, and/or
         delete a row in this table."
   ::= { mplsTunnelHopEntry 11 }
   
mplsTunnelHopStorageType OBJECT-TYPE
   SYNTAX        StorageType
   MAX-ACCESS    read-create
   STATUS        current
   DESCRIPTION
        "This variable indicates the storage type for this
         object."
   ::= { mplsTunnelHopEntry 12 }

-- End of mplsTunnelHopTable

-- Begin of mplsTunnelResourceTable

mplsTunnelResourceIndexNext OBJECT-TYPE
   SYNTAX        Integer32 (0..2147483647)
   MAX-ACCESS    read-only
   STATUS        current
   DESCRIPTION
        "This object contains the next appropriate value to
         be used for mplsTunnelResourceIndex when creating
         entries in the mplsTunnelResourceTable. If the
         number of unassigned entries is exhausted, a
         retrival operation will return a value of 0.  This
         object may also return a value of 0 when the LSR is
         unable to accept conceptual row creation, for
         example, if the mplsTunnelTable is implemented as
         read-only.  To obtain the mplsTunnelResourceIndex
         value for a new entry, the manager must first issue
         a management protocol retrieval operation to obtain
         the current value of this object. The agent should
         modify the value to reflect the next unassigned
         index after each retrieval operation. After a
         manager retrieves a value the agent will determine
         through its local policy when this index value will
         be made available for reuse."
   ::= { mplsTeObjects 6 }

mplsTunnelResourceTable OBJECT-TYPE
   SYNTAX        SEQUENCE OF MplsTunnelResourceEntry
   MAX-ACCESS    not-accessible
   STATUS        current
   DESCRIPTION
        "The mplsTunnelResourceTable allows a manager to
         specify which resources are desired for an MPLS
         tunnel.  This table also allows several tunnels to
         point to a single entry in this table, implying that
         these tunnels should share resources."
   ::= { mplsTeObjects 7 }

mplsTunnelResourceEntry OBJECT-TYPE
   SYNTAX        MplsTunnelResourceEntry
   MAX-ACCESS    not-accessible
   STATUS        current
   DESCRIPTION
        "An entry in this table represents a set of resources
         for an MPLS tunnel.  An entry can be created by a
         network administrator or by an SNMP agent as
         instructed by any MPLS signaling protocol."
   INDEX         { mplsTunnelResourceIndex }
      ::= { mplsTunnelResourceTable 1 }

MplsTunnelResourceEntry ::= SEQUENCE {
      mplsTunnelResourceIndex                Integer32,
      mplsTunnelResourceMaxRate              MplsBitRate,
      mplsTunnelResourceMeanRate             MplsBitRate,
      mplsTunnelResourceMaxBurstSize         MplsBurstSize,
      mplsTunnelResourceRowStatus            RowStatus,
      mplsTunnelResourceStorageType          StorageType
   }

mplsTunnelResourceIndex OBJECT-TYPE
   SYNTAX        Integer32 (1..2147483647)
   MAX-ACCESS    not-accessible
   STATUS        current
   DESCRIPTION
        "Uniquely identifies this row."
   ::= { mplsTunnelResourceEntry 1 }

mplsTunnelResourceMaxRate OBJECT-TYPE
   SYNTAX        MplsBitRate
   UNITS         "bits per second"
   MAX-ACCESS    read-create
   STATUS        current
   DESCRIPTION
        "The maximum rate in bits/second.  Note that setting
         mplsTunnelResourceMaxRate,
         mplsTunnelResourceMeanRate, and
         mplsTunnelResourceMaxBurstSize to 0 indicates best-
         effort treatment.
         This object is copied to an instance of
         mplsTSpecMaxRate in mplsTSpecTable the index of
         which is copied into the corresponding
         mplsInSegmentTSpecIndex."
   REFERENCE
        "Srinivasan, C., Viswanathan, A., and T. Nadeau, MPLS
         Label Switch Router Management Information Base
         Using SMIv2, Internet Draft <draft-ietf-mpls-lsr-mib-
         04.txt>, April 26,  2000."
   ::= { mplsTunnelResourceEntry 2 }

mplsTunnelResourceMeanRate OBJECT-TYPE
   SYNTAX        MplsBitRate
   UNITS         "bits per second"
   MAX-ACCESS    read-create
   STATUS        current
   DESCRIPTION
        "This object is copied into an instance of
         mplsTSpecMeanRate in the mplsTSpecTable. The index
         of this table is then copied into the corresponding
         mplsInSegmentTSpecIndex.
        
         When resource allocation is performed as requested
         by this TSpec object, it is copied into an entry in
         mplsTSpecTable [LSRMIB]: mplsTunnelInMeanRate to
         mplsTSpecMeanRate. The mplsTSpecDirection of this
         entry is set to 'in'(1).  The mplsTSpecIndex value
         of this entry is copied to mplsInSegmentTSpecIndex
         of the corresponding in-segment entry."
         
   REFERENCE
        "Srinivasan, C., Viswanathan, A., and T. Nadeau, MPLS
         Label Switch Router Management Information Base
         Using SMIv2, Internet Draft <draft-ietf-mpls-lsr-mib-
         04.txt>, April 26,  2000."
   ::= { mplsTunnelResourceEntry 3 }

mplsTunnelResourceMaxBurstSize OBJECT-TYPE
   SYNTAX        MplsBurstSize
   UNITS         "bytes"
   MAX-ACCESS    read-create
   STATUS        current
   DESCRIPTION
        "The maximum burst size in bytes.  This object is
         copied to mplsInSegmentMaxBurstSize of the
         corresponding in-segment.
        
         When resource allocation is performed as requested
         by this TSpec object, it is copied into an entry in
         mplsTSpecTable [LSRMIB]: mplsTunnelInMaxBurstSize to
         mplsTSpecMaxBurstSize. The mplsTSpecDirection of
         this entry is set to 'in'(1).  The mplsTSpecIndex
         value of this entry is copied to
         mplsInSegmentTSpecIndex of the corresponding in-
         segment entry."
   REFERENCE
        "Srinivasan, C., Viswanathan, A., and T. Nadeau, MPLS
         Label Switch Router Management Information Base
         Using SMIv2, Internet Draft <draft-ietf-mpls-lsr-mib-
         04.txt>, April 26, 2000."
   ::= { mplsTunnelResourceEntry 4 }

mplsTunnelResourceRowStatus OBJECT-TYPE
   SYNTAX        RowStatus
   MAX-ACCESS    read-create
   STATUS        current
   DESCRIPTION
        "This variable is used to create, modify, and/or
         delete a row in this table."
   ::= { mplsTunnelResourceEntry 5 }

mplsTunnelResourceStorageType OBJECT-TYPE
   SYNTAX        StorageType
   MAX-ACCESS    read-create
   STATUS        current
   DESCRIPTION
        "This variable indicates the storage type for this
         object."
   ::= { mplsTunnelResourceEntry 6 }


-- End mplsTunnelResourceTable

-- Tunnel Actual Route Hop table.

mplsTunnelARHopTable  OBJECT-TYPE
   SYNTAX        SEQUENCE OF MplsTunnelARHopEntry
   MAX-ACCESS    not-accessible
   STATUS        current
   DESCRIPTION
        "The mplsTunnelARHopTable is used to indicate the
         hops, strict or loose, for an MPLS tunnel defined in
         mplsTunnelTable, as reported by the MPLS signaling
         protocol, for the outgoing direction of the tunnel.
         Each row in this table is indexed primarily by the
         same indices, mplsTunnelIndex and
         mplsTunnelInstance, as the row of the corresponding
         tunnel in mplsTunnelTable.  Each row also has a
         third index mplsTunnelARHopIndex, corresponding to
         the next hop that this row corresponds to.  The
         first row in the table is the first hop after the
         origination point of the tunnel.  In case we want to
         specify a particular interface on the originating
         LSR of an outgoing tunnel by which we want packets
         to exit the LSR, we specify this as the first hop
         for this tunnel in mplsTunnelARHopTable.
        
         Please note that since the information necessary to
         build entries within this table are not provided by
         some MPLS signaling protocols, implementation of
         this table is optional. Furthermore, since the
         information in this table is actually provided by
         the MPLS signaling protocol after the path has been
         set-up, the entries in this table are provided only
         for observation, and hence, all variables in this
         table are accessible exclusively as read-only."
   ::= { mplsTeObjects 8 }

mplsTunnelARHopEntry  OBJECT-TYPE
   SYNTAX        MplsTunnelARHopEntry
   MAX-ACCESS    not-accessible
   STATUS        current
   DESCRIPTION
        "An entry in this table represents a tunnel hop.  An
         entry is created by a network administrator for
         signaled ERLSP set up by an MPLS signaling
         protocol."
   INDEX { mplsTunnelARHopListIndex, mplsTunnelARHopIndex }
      ::= { mplsTunnelARHopTable 1 }

MplsTunnelARHopEntry ::= SEQUENCE {
      mplsTunnelARHopListIndex          Integer32,
      mplsTunnelARHopIndex              Integer32,
      mplsTunnelARHopAddrType           INTEGER,
--      mplsTunnelARHopIpv4Addr           InetAddressIPv4,
      mplsTunnelARHopIpv4Addr           IpAddress,
      mplsTunnelARHopIpv4PrefixLen      INTEGER,
      mplsTunnelARHopIpv6Addr           InetAddressIPv6,
      mplsTunnelARHopIpv6PrefixLen      INTEGER,
      mplsTunnelARHopAsNumber           INTEGER,
      mplsTunnelARHopStrictOrLoose      INTEGER
   }

mplsTunnelARHopListIndex OBJECT-TYPE
   SYNTAX        Integer32 (1..2147483647)
   MAX-ACCESS    not-accessible
   STATUS        current
   DESCRIPTION
        "Primary index into this table identifying a
         particular recorded hop list."
   ::= { mplsTunnelARHopEntry 1 }

mplsTunnelARHopIndex OBJECT-TYPE
   SYNTAX        Integer32 (1..2147483647)
   MAX-ACCESS    not-accessible
   STATUS        current
   DESCRIPTION
        "Secondary index into this table identifying the
         particular hop."
   ::= { mplsTunnelARHopEntry 2 }

mplsTunnelARHopAddrType OBJECT-TYPE
   SYNTAX        INTEGER {
          ipV4(1),
          ipV6(2),
          asNumber(3)
      }
   MAX-ACCESS    read-only
   STATUS        current
   DESCRIPTION
        "Denotes the address type of this tunnel hop."
   DEFVAL        { ipV4 }
   ::= { mplsTunnelARHopEntry 3 }

mplsTunnelARHopIpv4Addr OBJECT-TYPE
--   SYNTAX        InetAddressIPv4
   SYNTAX        IpAddress
   MAX-ACCESS    read-only
   STATUS        current
   DESCRIPTION
        "If mplsTunnelARHopAddrType is set to ipV4(1), then
         this value will contain the IPv4 address of this
         hop. This object is otherwise insignificant and
         should contain a value of 0."
   ::= { mplsTunnelARHopEntry 4 }

mplsTunnelARHopIpv4PrefixLen OBJECT-TYPE
   SYNTAX        INTEGER (1..32)
   MAX-ACCESS    read-only
   STATUS        current
   DESCRIPTION
        "If mplsTunnelARHopAddrType is ipV4(1), then the
         prefix length for this hop's IPv4 address is
         contained herein. This object is otherwise
         insignificant and should contain a value of 0."
   ::= { mplsTunnelARHopEntry 5 }

mplsTunnelARHopIpv6Addr OBJECT-TYPE
   SYNTAX        InetAddressIPv6
   MAX-ACCESS    read-only
   STATUS        current
   DESCRIPTION
        "If the mplsTunnelARHopAddrType is set to ipV6(2),
         then this variable contains the IPv6 address of this
         hop.  This object is otherwise insignificant and
         should contain a value of 0."
   ::= { mplsTunnelARHopEntry 6 }

mplsTunnelARHopIpv6PrefixLen OBJECT-TYPE
   SYNTAX        INTEGER (1..128)
   MAX-ACCESS    read-only
   STATUS        current
   DESCRIPTION
        "If mplsTunnelARHopAddrType is set to ipV6(2), this
         value will contain the prefix length for this hop's
         IPv6 address. This object is otherwise insignificant
         and should contain a value of 0."
   ::= { mplsTunnelARHopEntry 7 }

mplsTunnelARHopAsNumber OBJECT-TYPE
   SYNTAX        INTEGER (0..65535)
   MAX-ACCESS    read-only
   STATUS        current
   DESCRIPTION
        "If mplsTunnelARHopAddrType is set to asNumber(3),
         then this value will contain the AS number of this
         hop. This object is otherwise insignificant and
         should contain a value of 0 to indicate this fact."
   ::= { mplsTunnelARHopEntry 8 }

mplsTunnelARHopStrictOrLoose OBJECT-TYPE
   SYNTAX        INTEGER {
          strict(1),
          loose(2)
      }
   MAX-ACCESS    read-only
   STATUS        current
   DESCRIPTION
        "Denotes whether this is tunnel hop is routed in a
         strict or loose fashion."
   ::= { mplsTunnelARHopEntry 9 }
   
-- End of mplsTunnelARHopTable

mplsTunnelTrapEnable OBJECT-TYPE
   SYNTAX        TruthValue
   MAX-ACCESS    read-write
   STATUS        current
   DESCRIPTION
        "If this object is true, then it enables the
         generation of mplsTunnelUp and mplsTunnelDown traps,
         otherwise these traps are not emitted."
   DEFVAL { false }
   ::= { mplsTeObjects 9 }

-- Notifications.

mplsTunnelUp NOTIFICATION-TYPE
   OBJECTS     { mplsTunnelIndex,
                 mplsTunnelInstance,
                 mplsTunnelAdminStatus,
                 mplsTunnelOperStatus
               }
   STATUS      current
   DESCRIPTION
        "This notification is generated when a
         mplsTunnelOperStatus object for one of the
         configured tunnels is about to leave the down state
         and transition into some other state (but not into
         the notPresent state).  This other state is
         indicated by the included value of
         mplsTunnelOperStatus."
   ::= { mplsTeNotifyPrefix 1 }

mplsTunnelDown NOTIFICATION-TYPE
   OBJECTS     { mplsTunnelIndex,
                 mplsTunnelInstance,
                 mplsTunnelAdminStatus,
                 mplsTunnelOperStatus
               }
   STATUS      current
   DESCRIPTION
        "This notification is generated when a
         mplsTunnelOperStatus object for one of the
         configured tunnels is about to enter the down state
         from some other state (but not from the notPresent
         state).  This other state is indicated by the
         included value of mplsTunnelOperStatus."
   ::= { mplsTeNotifyPrefix 2 }

   mplsTunnelRerouted NOTIFICATION-TYPE
   OBJECTS     { mplsTunnelIndex,
                 mplsTunnelInstance,
                 mplsTunnelAdminStatus,
                 mplsTunnelOperStatus
               }
   STATUS      current
   DESCRIPTION
        "This notification is generated when a tunnel is
         rerouted or re-optimized. If the Actual Path is
         used, then this object MAY contain the new path for
         this tunnel some time after this trap is issued by
         the agent."
    ::= { mplsTeNotifyPrefix 3 }

mplsTunnelReoptimized NOTIFICATION-TYPE
   OBJECTS     {
      mplsTunnelIndex,
      mplsTunnelInstance,
      mplsTunnelIngressLSRId,
      mplsTunnelAdminStatus,
      mplsTunnelOperStatus
   }
   STATUS      current
   DESCRIPTION
        "This notification is generated when a tunnel is
          reoptimized. If the actual path is used, then this
          object MAY contain the new path for this tunnel
          some time after this trap is issued by the agent."
    ::= { mplsTeNotifyPrefix 4 }

-- End of notifications.


-- Module compliance.

mplsTeGroups
   OBJECT IDENTIFIER ::= { mplsTeConformance 1 }

mplsTeCompliances
   OBJECT IDENTIFIER ::= { mplsTeConformance 2 }

mplsTeModuleCompliance MODULE-COMPLIANCE
   STATUS current
   DESCRIPTION
        "Compliance statement for agents that support the
         MPLS TE MIB."
   MODULE -- this module

      -- The mandatory group has to be implemented by all
      -- LSRs that originate/terminate ESLSPs/tunnels.
      -- In addition, depending on the type of tunnels
      -- supported, other groups become mandatory as
      -- explained below.

      MANDATORY-GROUPS    { mplsTunnelGroup }

          
      GROUP mplsTunnelManualGroup
      DESCRIPTION
          "This group is mandatory for devices which support
           manual configuration of tunnels, in addition to
           mplsTunnelGroup.  The following constraints apply:
           mplsTunnelSignallingProto should be at least read-
           only with a value of none(1)."

      GROUP mplsTunnelSignaledGroup
      DESCRIPTION
          "This group is mandatory for devices which support
           signaled tunnel set up, in addition to
           mplsTunnelGroup.  The following constraints apply:
           mplsTunnelSignallingProto should be at least read-
           only returning a value of ldp(2), or rsvp(3)."

      GROUP mplsTunnelIsNotIntfcGroup
      DESCRIPTION
          "This group is mandatory for devices which support
           tunnels that are not interfaces, in addition to
           mplsTunnelGroup.  The following constraints apply:
           mplsTunnelIsIf must at least be read-only
           returning false(1)."

      GROUP mplsTunnelIsIntfcGroup
      DESCRIPTION
          "This group is mandatory for devices which support
           tunnels that are interfaces, in addition to
           mplsTunnelGroup.  The following constraints apply:
           mplsTunnelIsIf must at least be read-only
           returning true(2)."

      GROUP mplsTunnelOptionalGroup
      DESCRIPTION
          "Objects in this group are optional."
      

      -- mplsTunnelTable

      OBJECT      mplsTunnelName
      MIN-ACCESS  read-only
      DESCRIPTION
          "Write access is not required."

      OBJECT      mplsTunnelDescr
      MIN-ACCESS  read-only
      DESCRIPTION
          "Write access is not required."

      OBJECT      mplsTunnelIsIf
      MIN-ACCESS  read-only
      DESCRIPTION
          "Write access is not required."

      OBJECT      mplsTunnelIfIndex
      DESCRIPTION
          "Write access is not required."

      OBJECT      mplsTunnelXCPointer
      MIN-ACCESS  read-only
      DESCRIPTION
          "Write access is not required."

      OBJECT      mplsTunnelSignallingProto
      MIN-ACCESS  read-only
      DESCRIPTION
          "Write access is not required."

      OBJECT      mplsTunnelSetupPrio
      MIN-ACCESS  read-only
      DESCRIPTION
          "Write access is not required."

      OBJECT      mplsTunnelHoldingPrio
      MIN-ACCESS  read-only
      DESCRIPTION
          "Write access is not required."
      
      OBJECT      mplsTunnelSessionAttributes
      MIN-ACCESS  read-only
      DESCRIPTION
          "Write access is not required."
      
      OBJECT      mplsTunnelOwner
      MIN-ACCESS  read-only
      DESCRIPTION
          "Write access is not required."

      OBJECT      mplsTunnelLocalProtectInUse
      MIN-ACCESS  read-only
      DESCRIPTION
          "Write access is not required."

      OBJECT      mplsTunnelResourcePointer
      MIN-ACCESS  read-only
      DESCRIPTION
          "Write access is not required."

      OBJECT      mplsTunnelInstancePriority
      MIN-ACCESS  read-only
      DESCRIPTION
          "Write access is not required."
      
      OBJECT      mplsTunnelHopTableIndex
      MIN-ACCESS  read-only
      DESCRIPTION
          "Write access is not required."

      OBJECT      mplsTunnelARHopTableIndex
      DESCRIPTION
          "Write access is not required."
      
      OBJECT      mplsTunnelAdminStatus
      SYNTAX      INTEGER { up (1), down (2) }
      MIN-ACCESS  read-only
      DESCRIPTION
          "Only up and down states must be supported. Write
           access is not required."

      OBJECT      mplsTunnelOperStatus
      SYNTAX      INTEGER { up (1), down (2) }
      DESCRIPTION
          "Only up and down states must be supported. Write
           access is not required."

      OBJECT      mplsTunnelRowStatus
      SYNTAX      INTEGER { active(1), notInService(2),
                       createAndGo(4), destroy(6) }
      MIN-ACCESS  read-only
      DESCRIPTION
          "The notReady(3) and createAndWait(5) states need
           not be supported. Write access is not required."
      
      OBJECT      mplsTunnelStorageType
      SYNTAX      INTEGER { other(1) }
      MIN-ACCESS  read-only
      DESCRIPTION
          "Only other (1) needs to be supported."

      -- mplsTunnelHopTable

      OBJECT      mplsTunnelHopAddrType
      MIN-ACCESS  read-only
      DESCRIPTION
          "Write access is not required."

      OBJECT      mplsTunnelHopIpv4Addr
      MIN-ACCESS  read-only
      DESCRIPTION
          "Write access is not required."

      OBJECT      mplsTunnelHopIpv4PrefixLen
      MIN-ACCESS  read-only
      DESCRIPTION
          "Write access is not required."

      OBJECT      mplsTunnelHopIpv6Addr
      MIN-ACCESS  read-only
      DESCRIPTION
          "Write access is not required."

      OBJECT      mplsTunnelHopIpv6PrefixLen
      MIN-ACCESS  read-only
      DESCRIPTION
          "Write access is not required."

      OBJECT      mplsTunnelHopAsNumber
      MIN-ACCESS  read-only
      DESCRIPTION
          "Write access is not required."
      
      OBJECT      mplsTunnelHopLspId
      MIN-ACCESS  read-only
      DESCRIPTION
          "Write access is not required."

      OBJECT      mplsTunnelHopStrictOrLoose
      SYNTAX      INTEGER { strict(1) }
      MIN-ACCESS  read-only
      DESCRIPTION
          "loose(2) need not be supported. Write access is
           not required."

      OBJECT      mplsTunnelHopRowStatus
      SYNTAX      INTEGER { active(1), notInService(2),
                       createAndGo(4), destroy(6) }
      MIN-ACCESS  read-only
      DESCRIPTION
          "The notReady(3) and createAndWait(5) states need
           not be supported. Write access is not required."
      
      OBJECT      mplsTunnelHopStorageType
      SYNTAX      INTEGER { other(1) }
      MIN-ACCESS  read-only
      DESCRIPTION
          "Only other (1) needs to be supported."

   -- mplsTunnelResourceTable
      
      OBJECT      mplsTunnelResourceMaxRate
      MIN-ACCESS  read-only
      DESCRIPTION
          "Write access is not required."

      OBJECT      mplsTunnelResourceMeanRate
      MIN-ACCESS  read-only
      DESCRIPTION
          "Write access is not required."

      OBJECT      mplsTunnelResourceMaxBurstSize
      MIN-ACCESS  read-only
      DESCRIPTION
          "Write access is not required."

      OBJECT      mplsTunnelResourceRowStatus
      SYNTAX      INTEGER { active(1), notInService(2),
                       createAndGo(4), destroy(6) }
      MIN-ACCESS  read-only
      DESCRIPTION
          "The notReady(3) and createAndWait(5) states need
           not be supported. Write access is not required."

      OBJECT      mplsTunnelResourceStorageType
      SYNTAX      INTEGER { other(1) }
      MIN-ACCESS  read-only
      DESCRIPTION
          "Only other (1) needs to be supported."

   ::= { mplsTeCompliances 1 }


-- Units of conformance.

mplsTunnelGroup OBJECT-GROUP
   OBJECTS { mplsTunnelIndexNext,
             mplsTunnelName,
             mplsTunnelDescr,
             mplsTunnelOwner,
             mplsTunnelXCPointer,
             mplsTunnelIfIndex,
             mplsTunnelHopTableIndex,
             mplsTunnelARHopTableIndex,
             mplsTunnelAdminStatus,
             mplsTunnelOperStatus,
             mplsTunnelRowStatus,
             mplsTunnelTrapEnable,
             mplsTunnelStorageType,
             mplsTunnelMaxHops,
             mplsTunnelResourcePointer,
             mplsTunnelInstancePriority
           }
   STATUS  current
   DESCRIPTION
        "Necessary, but not sufficient, set of objects to
         implement tunnels.  In addition, depending on the
         type of the tunnels supported (for example, manually
         configured or signaled, persistent or non-
         persistent, etc.), the following other groups
         defined below are mandatory: mplsTunnelManualGroup
         and/or mplsTunnelSignaledGroup,
         mplsTunnelIsNotIntfcGroup and/or
         mplsTunnelIsIntfcGroup."
   ::= { mplsTeGroups 1 }

mplsTunnelManualGroup  OBJECT-GROUP
   OBJECTS { mplsTunnelSignallingProto }
   STATUS  current
   DESCRIPTION
        "Object(s) needed to implement manually configured
         tunnels."
   ::= { mplsTeGroups 2 }

mplsTunnelSignaledGroup OBJECT-GROUP
   OBJECTS { mplsTunnelSetupPrio,
             mplsTunnelHoldingPrio,
             mplsTunnelSignallingProto,
             mplsTunnelLocalProtectInUse,
             mplsTunnelSessionAttributes,
             mplsTunnelHopIndexNext,
             mplsTunnelHopAddrType,
             mplsTunnelHopIpv4Addr,
             mplsTunnelHopIpv4PrefixLen,
             mplsTunnelHopIpv6Addr,
             mplsTunnelHopIpv6PrefixLen,
             mplsTunnelHopAsNumber,
             mplsTunnelHopLspId,
             mplsTunnelHopStrictOrLoose,
             mplsTunnelHopRowStatus,
             mplsTunnelHopStorageType
           }
   STATUS  current
   DESCRIPTION
        "Object needed to implement signaled tunnels."
   ::= { mplsTeGroups 3 }

mplsTunnelIsIntfcGroup OBJECT-GROUP
   OBJECTS { mplsTunnelIsIf }
   STATUS  current
   DESCRIPTION
        "Objects needed to implement tunnels that are
         interfaces."
   ::= { mplsTeGroups 4 }

mplsTunnelIsNotIntfcGroup OBJECT-GROUP
   OBJECTS { mplsTunnelIsIf }
   STATUS  current
   DESCRIPTION
        "Objects needed to implement tunnels that are not
         interfaces."
   ::= { mplsTeGroups 5 }

mplsTunnelOptionalGroup OBJECT-GROUP
   OBJECTS { mplsTunnelResourceIndexNext,
             mplsTunnelResourceMaxRate,
             mplsTunnelResourceMeanRate,
             mplsTunnelResourceMaxBurstSize,
             mplsTunnelResourceRowStatus,
             mplsTunnelResourceStorageType,
             mplsTunnelARHopAddrType,
             mplsTunnelARHopIpv4Addr,
             mplsTunnelARHopIpv4PrefixLen,
             mplsTunnelARHopIpv6Addr,
             mplsTunnelARHopIpv6PrefixLen,
             mplsTunnelARHopAsNumber,
             mplsTunnelARHopStrictOrLoose
           }
   STATUS  current
   DESCRIPTION
        "The objects in this group are optional."
   ::= { mplsTeGroups 6 }

mplsTeNotificationGroup NOTIFICATION-GROUP
   NOTIFICATIONS { mplsTunnelUp,
                   mplsTunnelDown,
                   mplsTunnelRerouted
                 }
   STATUS  current
   DESCRIPTION
        "Set of notifications implemented in this module.
         None is mandatory."
   ::= { mplsTeGroups 7 }

-- End of MPLS-TE-MIB
END
