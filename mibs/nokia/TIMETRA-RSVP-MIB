TIMETRA-RSVP-MIB DEFINITIONS ::= BEGIN

IMPORTS
    CounterBasedGauge64
                                                         FROM HCNUM-TC
    InterfaceIndex, ifIndex
                                                         FROM IF-MIB
    InetAddress, InetAddressType
                                                         FROM INET-ADDRESS-MIB
    MplsLabel
                                                         FROM MPLS-LSR-MIB
    rsvpIfEnabled, rsvpIfEntry,
    rsvpNbrProtocol
                                                         FROM RSVP-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    Unsigned32
                                                         FROM SNMPv2-SMI
    RowStatus, TEXTUAL-CONVENTION,
    TimeInterval, TimeStamp, TruthValue
                                                         FROM SNMPv2-TC
    timetraSRMIBModules, tmnxSRConfs,
    tmnxSRNotifyPrefix, tmnxSRObjs
                                                         FROM TIMETRA-GLOBAL-MIB
    vRtrPimNgMvpnUMHPEStandbyAddr,
    vRtrPimNgMvpnUMHPEStandbyAdrTyp
                                                         FROM TIMETRA-PIM-NG-MIB
    TNamedItem, TNamedItemOrEmpty,
    TmnxAdminState, TmnxOperState,
    TmnxRsvpDSTEClassType,
    TmnxRsvpSessionNameString
                                                         FROM TIMETRA-TC-MIB
    vRtrID, vRtrIfIndex
                                                         FROM TIMETRA-VRTR-MIB
    ;

timetraRsvpMIBModule             MODULE-IDENTITY
    LAST-UPDATED "201601010000Z"
    ORGANIZATION "Nokia"
    CONTACT-INFO
        "Nokia SROS Support
         Web: http://www.nokia.com"
    DESCRIPTION
        "This document is the SNMP MIB module to manage and provision RSVP
         extensions for the Nokia SROS device.

         Copyright 2000-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201601010000Z"
    DESCRIPTION
        "Rev 14.0               1 Jan 2016 00:00
         14.0 release of the TIMETRA-RSVP-MIB."

    REVISION    "201401010000Z"
    DESCRIPTION
        "Rev 12.0               1 Jan 2014 00:00
         12.0 release of the TIMETRA-RSVP-MIB."

    REVISION    "201102010000Z"
    DESCRIPTION
        "Rev 9.0                1 Feb 2011 00:00
         9.0 release of the TIMETRA-RSVP-MIB."

    REVISION    "200902280000Z"
    DESCRIPTION
        "Rev 7.0                28 Feb 2009 00:00
         7.0 release of the TIMETRA-RSVP-MIB."

    REVISION    "200807010000Z"
    DESCRIPTION
        "Rev 6.1                01 Jul 2008 00:00
         6.1 release of the TIMETRA-RSVP-MIB."

    REVISION    "200801010000Z"
    DESCRIPTION
        "Rev 6.0                01 Jan 2008 00:00
         6.0 release of the TIMETRA-RSVP-MIB."

    REVISION    "200501240000Z"
    DESCRIPTION
        "Rev 2.1                24 Jan 2005 00:00
         2.1 release of the TIMETRA-RSVP-MIB."

    REVISION    "200401150000Z"
    DESCRIPTION
        "Rev 2.0                15 Jan 2004 00:00
         2.0 release of the TIMETRA-RSVP-MIB."

    REVISION    "200308150000Z"
    DESCRIPTION
        "Rev 1.2                15 Aug 2003 00:00
         1.2 release of the TIMETRA-RSVP-MIB."

    REVISION    "200301200000Z"
    DESCRIPTION
        "Rev 1.0                20 Jan 2003 00:00
         1.0 Release of the TIMETRA-RSVP-MIB."

    REVISION    "200008140000Z"
    DESCRIPTION
        "Rev 0.1                14 Aug 2000 00:00
         Initial version of the TIMETRA-RSVP-MIB."

    ::= { timetraSRMIBModules 7 }

TmnxRsvpSessionFailCode          ::= TEXTUAL-CONVENTION
    STATUS      current
    DESCRIPTION
        "TmnxRsvpSessionFailCode is an enumerated integer that defines the
         reason for RSVP session failure."
    SYNTAX      INTEGER {
        noError                (0),
        admissionControlError  (1),
        noSenderTemplate       (2),
        conflictingResvStyle   (3),
        unknownResvStyle       (4),
        conflictingSourcePorts (5),
        unknownClassObject     (6),
        unknownCTypeObject     (7),
        badERO                 (8),
        badObjectLength        (9),
        badSubobjectLength     (10),
        badLabel               (11),
        rroRoutingLoop         (12),
        rsvpIpTtlMismatch      (13),
        integrityError         (14),
        missingMandatoryObject (15),
        missingObjectClass     (16),
        wrongObjectOrder       (17),
        badAdspecParms         (18),
        badTspecParms          (19),
        badFlowspecParms       (20)
    }

TmnxRsvpDSTETeClass              ::= TEXTUAL-CONVENTION
    STATUS      current
    DESCRIPTION
        "TmnxRsvpDSTETeClass is an unsigned integer in the range of (0..7) that
         defines the traffic engineering (TE) class."
    SYNTAX      Unsigned32 (0..7)

TmnxRsvpDSTEBwPercent            ::= TEXTUAL-CONVENTION
    STATUS      current
    DESCRIPTION
        "TmnxRsvpDSTEBwPercent is an unsigned integer in the range of (0..100)
         that defines the percentage bandwidth for a class type (CT)."
    SYNTAX      Unsigned32 (0..100)

TmnxRsvpTEThresholdLevel         ::= TEXTUAL-CONVENTION
    STATUS      current
    DESCRIPTION
        "TmnxRsvpTEThresholdLevel is an integer in the range of (-1|0..100)
         that defines the traffic engineering (TE) threshold level."
    SYNTAX      Integer32 (-1 | 0..100)

TmnxRsvpAuthenticationType       ::= TEXTUAL-CONVENTION
    STATUS      current
    DESCRIPTION
        "The value TmnxRsvpAuthenticationType provides the authentication type."
    SYNTAX      INTEGER {
        none (0),
        md5  (1)
    }

tmnxRsvpObjs                     OBJECT IDENTIFIER ::= { tmnxSRObjs 7 }

vRtrRsvpGeneralTable             OBJECT-TYPE
    SYNTAX      SEQUENCE OF VRtrRsvpGeneralEntry
    MAX-ACCESS  not-accessible
    STATUS      current
    DESCRIPTION
        "The vRtrRsvpGeneralTable contains objects for general control and
         management of an RSVP protocol instance within a virtual router."
    ::= { tmnxRsvpObjs 1 }

vRtrRsvpGeneralEntry             OBJECT-TYPE
    SYNTAX      VRtrRsvpGeneralEntry
    MAX-ACCESS  not-accessible
    STATUS      current
    DESCRIPTION
        "Each row entry represents an instance of the MPLS protocol running
         within a virtual router.  Entries in this table cannot be
         created and deleted via SNMP SET operations.  An entry in this table
         is created by the agent when vRtrRsvpStatus in the vRtrConfTable is
         set to 'create'.  The entry is destroyed when vRtrRsvpStatus is set
         to 'delete'"
    INDEX       { vRtrID }
    ::= { vRtrRsvpGeneralTable 1 }

VRtrRsvpGeneralEntry             ::= SEQUENCE
{
    vRtrRsvpGeneralLastChange        TimeStamp,
    vRtrRsvpGeneralAdminState        TmnxAdminState,
    vRtrRsvpGeneralOperState         TmnxOperState,
    vRtrRsvpGeneralKeepMultiplier    Unsigned32,
    vRtrRsvpGeneralRefreshTime       Unsigned32,
    vRtrRsvpGeneralMsgPacing         TruthValue,
    vRtrRsvpGeneralMsgPacingMaxBurst Unsigned32,
    vRtrRsvpGeneralMsgPacingPeriod   Unsigned32,
    vRtrRsvpGeneralRefreshBypass     TruthValue,
    vRtrRsvpGenRapidRetransmitTime   Unsigned32,
    vRtrRsvpGenRapidRetryLimit       Unsigned32,
    vRtrRsvpGenGracefulShutdown      TruthValue,
    vRtrRsvpGenPreemptionTimer       Unsigned32,
    vRtrRsvpGenTEThresholdUpdate     TruthValue,
    vRtrRsvpGenTEUpdateOnCacFail     TruthValue,
    vRtrRsvpGenTEUpdateTimer         Unsigned32,
    vRtrRsvpGenImplicitNull          TruthValue,
    vRtrRsvpGenNodeIdInRro           INTEGER,
    vRtrRsvpGenP2PMrgPntAbrtTimer    Unsigned32,
    vRtrRsvpGenP2MPMrgPntAbrtTimer   Unsigned32,
    vRtrRsvpGeneralGrHlprMaxRcvryTm  Unsigned32,
    vRtrRsvpGeneralGrHlprMaxRstrtTm  Unsigned32,
    vRtrRsvpGenEntropyLblCapability  TruthValue
}

vRtrRsvpGeneralLastChange        OBJECT-TYPE
    SYNTAX      TimeStamp
    MAX-ACCESS  read-only
    STATUS      current
    DESCRIPTION
        "The sysUpTime when this row was last modified."
    ::= { vRtrRsvpGeneralEntry 1 }

vRtrRsvpGeneralAdminState        OBJECT-TYPE
    SYNTAX      TmnxAdminState
    MAX-ACCESS  read-create
    STATUS      current
    DESCRIPTION
        "When vRtrRsvpGeneralAdminState is set to 'inService', the agent
         attempts to enable the RSVP protocol instance on this router.

         When vRtrRsvpGeneralAdminState is set to 'outOfService', the agent
         attempts to disable the RSVP protocol instance on this router."
    DEFVAL      { outOfService }
    ::= { vRtrRsvpGeneralEntry 2 }

vRtrRsvpGeneralOperState         OBJECT-TYPE
    SYNTAX      TmnxOperState
    MAX-ACCESS  read-only
    STATUS      current
    DESCRIPTION
        "vRtrRsvpGeneralOperState indicates the current operating state of this
         RSVP protocol instance on this router."
    ::= { vRtrRsvpGeneralEntry 3 }

vRtrRsvpGeneralKeepMultiplier    OBJECT-TYPE
    SYNTAX      Unsigned32 (1..255)
    MAX-ACCESS  read-create
    STATUS      current
    DESCRIPTION
        "The value of vRtrRsvpGeneralKeepMultiplier is used by RSVP to declare
         either a reservation down or the neighbor as down.

         When vRtrRsvpIfKeepMultiplier is set to the value of zero (0), the
         value of vRtrRsvpGeneralKeepMultiplier is applied to RSVP running on
         that specific interface."
    DEFVAL      { 3 }
    ::= { vRtrRsvpGeneralEntry 4 }

vRtrRsvpGeneralRefreshTime       OBJECT-TYPE
    SYNTAX      Unsigned32 (1..65535)
    UNITS       "seconds"
    MAX-ACCESS  read-create
    STATUS      current
    DESCRIPTION
        "The value of vRtrRsvpGeneralRefreshTime controls the interval between
         the successive Path and Resv refresh messages. RSVP declares the
         session down after it misses ((keep-multiplier + 0.5) * 1.5 *
         refresh-time)) consecutive refresh messages.

         When the value of vRtrRsvpIfRefreshTime is set to zero (0), the value
         of vRtrRsvpGeneralRefreshTime is applied to that specific RSVP
         interface."
    DEFVAL      { 30 }
    ::= { vRtrRsvpGeneralEntry 5 }

vRtrRsvpGeneralMsgPacing         OBJECT-TYPE
    SYNTAX      TruthValue
    MAX-ACCESS  read-create
    STATUS      current
    DESCRIPTION
        "Setting the value of vRtrRsvpGeneralMsgPacing to 'true', enables RSVP
         message pacing wherein a specified number of RSVP messages are sent
         within a specified interval.

         Setting the value of vRtrRsvpGeneralMsgPacing to 'false', disables
         RSVP message pacing."
    DEFVAL      { false }
    ::= { vRtrRsvpGeneralEntry 6 }

vRtrRsvpGeneralMsgPacingMaxBurst OBJECT-TYPE
    SYNTAX      Unsigned32 (100..1000)
    MAX-ACCESS  read-create
    STATUS      current
    DESCRIPTION
        "When RSVP message pacing is enabled (i.e. when
         vRtrRsvpGeneralMsgPacing is set to 'true'), the value of
         vRtrRsvpGeneralMsgPacingMaxBurst specifies the maximum number of RSVP
         messages that are sent during a configured interval under normal
         operating conditions.

         The value specified for this object must be in multiples of 10.

         This variable is not valid if RSVP message pacing is disabled (i.e.
         when vRtrRsvpGeneralMsgPacing is set to 'false')"
    DEFVAL      { 650 }
    ::= { vRtrRsvpGeneralEntry 7 }

vRtrRsvpGeneralMsgPacingPeriod   OBJECT-TYPE
    SYNTAX      Unsigned32 (100..1000)
    UNITS       "milliseconds"
    MAX-ACCESS  read-create
    STATUS      current
    DESCRIPTION
        "When RSVP message pacing is enabled (i.e. when
         vRtrRsvpGeneralMsgPacing is set to 'true'), the value of
         vRtrRsvpGeneralMsgPacingPeriod specifies the interval (in
         milliseconds) during which a configured number of RSVP messages are
         sent.

         This variable is not valid if RSVP message pacing is disabled (i.e.
         when vRtrRsvpGeneralMsgPacing is set to 'false')"
    DEFVAL      { 100 }
    ::= { vRtrRsvpGeneralEntry 8 }

vRtrRsvpGeneralRefreshBypass     OBJECT-TYPE
    SYNTAX      TruthValue
    MAX-ACCESS  read-create
    STATUS      current
    DESCRIPTION
        "The value of vRtrRsvpGeneralRefreshBypass specifies whether the
         refresh reduction capabilities over all bypass tunnels originating
         on the PLR node is enabled.  Since a bypass tunnel may merge with
         the primary LSP path in a node downstream of the next-hop, there
         is no direct interface between the PLR and the MP node and it is
         possible that the latter will not accept summary refresh messages
         received over the bypass.

         When the value of vRtrRsvpGeneralRefreshBypass is 'false', the summary
         refresh messages on the node for all primary LSPs over the bypass
         tunnels they are associated with, is disabled."
    DEFVAL      { false }
    ::= { vRtrRsvpGeneralEntry 9 }

vRtrRsvpGenRapidRetransmitTime   OBJECT-TYPE
    SYNTAX      Unsigned32 (1..100)
    UNITS       "deciseconds"
    MAX-ACCESS  read-create
    STATUS      current
    DESCRIPTION
        "The value of vRtrRsvpGenRapidRetransmitTime specifies the value
         of the rapid retransmission interval.  This is used in the
         retransmission mechanism based on an exponential backoff timer
         in order to handle unacknowledged message objects.

         vRtrRsvpGenRapidRetransmitTime must be smaller than the regular
         refresh interval vRtrRsvpGeneralRefreshTime."
    DEFVAL      { 5 }
    ::= { vRtrRsvpGeneralEntry 10 }

vRtrRsvpGenRapidRetryLimit       OBJECT-TYPE
    SYNTAX      Unsigned32 (1..6)
    MAX-ACCESS  read-create
    STATUS      current
    DESCRIPTION
        "The value of vRtrRsvpGenRapidRetryLimit specifies the rapid retry
         limit.  This is used in the retransmission mechanism based on an
         exponential backoff timer in order to handle unacknowledged message
         objects.  The node stops retransmission of unacknowledged RSVP
         messages whenever the updated backoff interval exceeds the value of
         vRtrRsvpGeneralRefreshTime or the number of retransmissions reaches
         the value of the vRtrRsvpGenRapidRetryLimit, whichever comes first."
    DEFVAL      { 3 }
    ::= { vRtrRsvpGeneralEntry 11 }

vRtrRsvpGenGracefulShutdown      OBJECT-TYPE
    SYNTAX      TruthValue
    MAX-ACCESS  read-create
    STATUS      current
    DESCRIPTION
        "The value of vRtrRsvpGenGracefulShutdown specifies whether
         graceful shutdown of the RSVP node is enabled. When this object
         has a value of 'true', graceful shutdown is enabled.  When its
         value is 'false', graceful shutdown is disabled."
    DEFVAL      { false }
    ::= { vRtrRsvpGeneralEntry 12 }

vRtrRsvpGenPreemptionTimer       OBJECT-TYPE
    SYNTAX      Unsigned32 (0..1800)
    UNITS       "seconds"
    MAX-ACCESS  read-create
    STATUS      current
    DESCRIPTION
        "The value of vRtrRsvpGenPreemptionTimer specifies the time a
         node holds on to a reservation for which it has triggered the
         soft preemption procedure.  The preempting node starts a preemption
         timer for each preempted LSP path. While  this timer is on, the
         node continues to refresh the Path and Resv for the preempted
         LSP path.  When the timer expires, the node tears down the LSP
         path if the head-end node has not already done so.

         A value of 0 means that the node does not hold on to the reservation
         at all.  "
    DEFVAL      { 300 }
    ::= { vRtrRsvpGeneralEntry 13 }

vRtrRsvpGenTEThresholdUpdate     OBJECT-TYPE
    SYNTAX      TruthValue
    MAX-ACCESS  read-create
    STATUS      current
    DESCRIPTION
        "The value of vRtrRsvpGenTEThresholdUpdate specifies if threshold based
         IGP Traffic Engineering (TE) is enabled or disabled."
    DEFVAL      { false }
    ::= { vRtrRsvpGeneralEntry 14 }

vRtrRsvpGenTEUpdateOnCacFail     OBJECT-TYPE
    SYNTAX      TruthValue
    MAX-ACCESS  read-create
    STATUS      current
    DESCRIPTION
        "The value of vRtrRsvpGenTEUpdateOnCacFail specifies if IGP TE update
         on Connection Admission Control (CAC) failure during LSP setup is
         enabled or disabled."
    DEFVAL      { false }
    ::= { vRtrRsvpGeneralEntry 15 }

vRtrRsvpGenTEUpdateTimer         OBJECT-TYPE
    SYNTAX      Unsigned32 (0..300)
    UNITS       "seconds"
    MAX-ACCESS  read-create
    STATUS      current
    DESCRIPTION
        "The value of vRtrRsvpGenTEUpdateTimer specifies the time interval to
         wait before a forced update of bandwidth to sync the bandwidth can be
         triggered. The update only happens when a bandwidth change occurs that
         does not cross any of the existing thresholds."
    DEFVAL      { 0 }
    ::= { vRtrRsvpGeneralEntry 16 }

vRtrRsvpGenImplicitNull          OBJECT-TYPE
    SYNTAX      TruthValue
    MAX-ACCESS  read-create
    STATUS      current
    DESCRIPTION
        "The value of vRtrRsvpGenImplicitNull specifies whether or not to
         signal implicit null values for all label switched paths associated
         with this RSVP when this node is an egress Label Edge Router (LER).
         When the value is 'true' implicit null values are signaled."
    DEFVAL      { false }
    ::= { vRtrRsvpGeneralEntry 17 }

vRtrRsvpGenNodeIdInRro           OBJECT-TYPE
    SYNTAX      INTEGER {
        include (1),
        exclude (2)
    }
    MAX-ACCESS  read-create
    STATUS      current
    DESCRIPTION
        "The value of vRtrRsvpGenNodeIdInRro specifies whether or not the
         nodeId is included in Record Route Object (RRO)."
    DEFVAL      { exclude }
    ::= { vRtrRsvpGeneralEntry 18 }

vRtrRsvpGenP2PMrgPntAbrtTimer    OBJECT-TYPE
    SYNTAX      Unsigned32 (0..65535)
    UNITS       "seconds"
    MAX-ACCESS  read-create
    STATUS      current
    DESCRIPTION
        "The value of vRtrRsvpGenP2PMrgPntAbrtTimer specifies the time in
         seconds, MPLS will wait to clean up all the point-to-point (P2P) LSP
         paths which have the Incoming Label Mapping (ILM) on the failed
         interface and which have not already received a Path refresh over the
         bypass LSP. When the value of vRtrRsvpGenP2PMrgPntAbrtTimer is set to
         higher than zero, it will come into effect when a node activates
         Merge-Point procedure on one or more P2P LSP path. As soon an ingress
         interface goes operationally down, the Merge-Point Node starts the
         abort timer.

         Setting the value of vRtrRsvpGenP2PMrgPntAbrtTimer to 0 disables merge
         point abort timer."
    DEFVAL      { 0 }
    ::= { vRtrRsvpGeneralEntry 19 }

vRtrRsvpGenP2MPMrgPntAbrtTimer   OBJECT-TYPE
    SYNTAX      Unsigned32 (0..65535)
    UNITS       "seconds"
    MAX-ACCESS  read-create
    STATUS      current
    DESCRIPTION
        "The value of vRtrRsvpGenP2MPMrgPntAbrtTimer specifies the time in
         seconds, MPLS will wait to clean up all the point-to-multi-point
         (P2MP) source to leaf (S2L) LSP paths which have the Incoming Label
         Mapping (ILM) on the failed interface and which have not already
         received a Path refresh over the bypass LSP. When the value of
         vRtrRsvpGenP2MPMrgPntAbrtTimer is set to higher than zero, it will
         come into effect when a node activates Merge-Point procedure on one or
         more P2MP S2L LSP path. As soon an ingress interface goes
         operationally down, the Merge-Point Node starts the abort timer.

         Setting the value of vRtrRsvpGenP2MPMrgPntAbrtTimer to 0 disables
         merge point abort timer."
    DEFVAL      { 0 }
    ::= { vRtrRsvpGeneralEntry 20 }

vRtrRsvpGeneralGrHlprMaxRcvryTm  OBJECT-TYPE
    SYNTAX      Unsigned32 (1..1800)
    UNITS       "seconds"
    MAX-ACCESS  read-create
    STATUS      current
    DESCRIPTION
        "The value of vRtrRsvpGeneralGrHlprMaxRcvryTm specifies the maximum
         time in seconds, a graceful helper will wait for session recovery.
         This value is compared with the neighbor's advertised recovery time
         and the minimum of the two is used.  This value is used to cap the
         recovery time advertised by the neighbor."
    DEFVAL      { 300 }
    ::= { vRtrRsvpGeneralEntry 21 }

vRtrRsvpGeneralGrHlprMaxRstrtTm  OBJECT-TYPE
    SYNTAX      Unsigned32 (1..300)
    UNITS       "seconds"
    MAX-ACCESS  read-create
    STATUS      current
    DESCRIPTION
        "The value of vRtrRsvpGeneralGrHlprMaxRstrtTm specifies the maximum
         time in seconds a graceful helper will waits for session restart after
         it has determined that the neighbor is down. This value is compared
         with the neighbor's advertised restart time and the minimum of the two
         is used. This is used to cap the restart time advertised by the
         neighbor."
    DEFVAL      { 120 }
    ::= { vRtrRsvpGeneralEntry 22 }

vRtrRsvpGenEntropyLblCapability  OBJECT-TYPE
    SYNTAX      TruthValue
    MAX-ACCESS  read-create
    STATUS      current
    DESCRIPTION
        "The value of vRtrRsvpGenEntropyLblCapability specifies whether entropy
         label capability is enabled or not on the RSVP node. When the value of
         vRtrRsvpGenEntropyLblCapability is set to 'true', the egress LER will
         advertise that it is capable of receiving and processing the entropy
         label."
    DEFVAL      { false }
    ::= { vRtrRsvpGeneralEntry 23 }

vRtrRsvpGeneralStatTable         OBJECT-TYPE
    SYNTAX      SEQUENCE OF VRtrRsvpGeneralStatEntry
    MAX-ACCESS  not-accessible
    STATUS      current
    DESCRIPTION
        "The vRtrRsvpGeneralStatTable contains statistics for an RSVP protocol
         instance within a virtual router."
    ::= { tmnxRsvpObjs 2 }

vRtrRsvpGeneralStatEntry         OBJECT-TYPE
    SYNTAX      VRtrRsvpGeneralStatEntry
    MAX-ACCESS  not-accessible
    STATUS      current
    DESCRIPTION
        "Each row entry represents a collection of statistics for an instance
         of the RSVP protocol running within a virtual router.

         Entries cannot be created and deleted via SNMP SET operations."
    AUGMENTS    { vRtrRsvpGeneralEntry }
    ::= { vRtrRsvpGeneralStatTable 1 }

VRtrRsvpGeneralStatEntry         ::= SEQUENCE
{
    vRtrRsvpGeneralPsbTimeouts       Counter32,
    vRtrRsvpGeneralRsbTimeouts       Counter32,
    vRtrRsvpGeneralGrhPsbTimeouts    Counter32,
    vRtrRsvpGeneralGrhRsbTimeouts    Counter32
}

vRtrRsvpGeneralPsbTimeouts       OBJECT-TYPE
    SYNTAX      Counter32
    MAX-ACCESS  read-only
    STATUS      current
    DESCRIPTION
        "The value of vRtrRsvpGeneralPsbTimeouts gives the total number of PSB
         timeouts."
    ::= { vRtrRsvpGeneralStatEntry 1 }

vRtrRsvpGeneralRsbTimeouts       OBJECT-TYPE
    SYNTAX      Counter32
    MAX-ACCESS  read-only
    STATUS      current
    DESCRIPTION
        "The value of vRtrRsvpGeneralRsbTimeouts gives the total number of RSB
         timeouts."
    ::= { vRtrRsvpGeneralStatEntry 2 }

vRtrRsvpGeneralGrhPsbTimeouts    OBJECT-TYPE
    SYNTAX      Counter32
    MAX-ACCESS  read-only
    STATUS      current
    DESCRIPTION
        "The value of vRtrRsvpGeneralGrhPsbTimeouts indicates the total number
         of PSB timeouts that occurred due to the session not being recovered
         during recovery phase of the graceful restart procedure."
    ::= { vRtrRsvpGeneralStatEntry 3 }

vRtrRsvpGeneralGrhRsbTimeouts    OBJECT-TYPE
    SYNTAX      Counter32
    MAX-ACCESS  read-only
    STATUS      current
    DESCRIPTION
        "The value of vRtrRsvpGeneralGrhRsbTimeouts indicates the total number
         of RSB timeouts that occurred due to the session not being recovered
         during recovery phase of the graceful restart procedure."
    ::= { vRtrRsvpGeneralStatEntry 4 }

vRtrRsvpIfTable                  OBJECT-TYPE
    SYNTAX      SEQUENCE OF VRtrRsvpIfEntry
    MAX-ACCESS  not-accessible
    STATUS      current
    DESCRIPTION
        "The vRtrRsvpIfTable provides an extension of the rsvpIfTable in the
         RSVP-MIB."
    ::= { tmnxRsvpObjs 3 }

vRtrRsvpIfEntry                  OBJECT-TYPE
    SYNTAX      VRtrRsvpIfEntry
    MAX-ACCESS  not-accessible
    STATUS      current
    DESCRIPTION
        "Each row entry in the vRtrRsvpIfTable represents additional columns
         for attributes specific to the Nokia 7x50 SR RSVP implementation."
    AUGMENTS    { rsvpIfEntry }
    ::= { vRtrRsvpIfTable 1 }

VRtrRsvpIfEntry                  ::= SEQUENCE
{
    vRtrRsvpIfLastEnabledTime        TimeStamp,
    vRtrRsvpIfVRtrIfIndex            InterfaceIndex,
    vRtrRsvpIfAggregate              TruthValue,
    vRtrRsvpIfAuthenticationKey      OCTET STRING,
    vRtrRsvpIfHelloInterval          Unsigned32,
    vRtrRsvpIfSubscription           Unsigned32,
    vRtrRsvpIfKeepMultiplier         Unsigned32,
    vRtrRsvpIfRefreshTime            Unsigned32,
    vRtrRsvpIfOperState              TmnxOperState,
    vRtrRsvpIfActiveSessionCount     Counter32,
    vRtrRsvpIfActiveReservationCount Counter32,
    vRtrRsvpIfTotalSessionCount      Counter32,
    vRtrRsvpIfBandwidth              Unsigned32,
    vRtrRsvpIfReservedBandwidth      Unsigned32,
    vRtrRsvpIfAuthentication         TruthValue,
    vRtrRsvpIfAuthChallenge          TruthValue,
    vRtrRsvpIfAuthKeyId              Counter64,
    vRtrRsvpIfAuthRxSeqNum           Counter64,
    vRtrRsvpIfAuthTxSeqNum           Counter64,
    vRtrRsvpIfAuthWindowSize         Counter32,
    vRtrRsvpIfRefreshReduction       TruthValue,
    vRtrRsvpIfReliableDelivery       TruthValue,
    vRtrRsvpIfBfdEnabled             TruthValue,
    vRtrRsvpIfGracefulShutdown       TruthValue,
    vRtrRsvpIfDSTECt0BwPercent       TmnxRsvpDSTEBwPercent,
    vRtrRsvpIfDSTECt1BwPercent       TmnxRsvpDSTEBwPercent,
    vRtrRsvpIfDSTECt2BwPercent       TmnxRsvpDSTEBwPercent,
    vRtrRsvpIfDSTECt3BwPercent       TmnxRsvpDSTEBwPercent,
    vRtrRsvpIfDSTECt4BwPercent       TmnxRsvpDSTEBwPercent,
    vRtrRsvpIfDSTECt5BwPercent       TmnxRsvpDSTEBwPercent,
    vRtrRsvpIfDSTECt6BwPercent       TmnxRsvpDSTEBwPercent,
    vRtrRsvpIfDSTECt7BwPercent       TmnxRsvpDSTEBwPercent,
    vRtrRsvpIfInheritance            Unsigned32,
    vRtrRsvpIfDSTEBC0Bw              Counter64,
    vRtrRsvpIfDSTEBC1Bw              Counter64,
    vRtrRsvpIfDSTEBC2Bw              Counter64,
    vRtrRsvpIfDSTEBC3Bw              Counter64,
    vRtrRsvpIfDSTEBC4Bw              Counter64,
    vRtrRsvpIfDSTEBC5Bw              Counter64,
    vRtrRsvpIfDSTEBC6Bw              Counter64,
    vRtrRsvpIfDSTEBC7Bw              Counter64,
    vRtrRsvpIfImplicitNull           TruthValue,
    vRtrRsvpIfIgpUpdatePending       TruthValue,
    vRtrRsvpIfIgpNextUpdate          Unsigned32,
    vRtrRsvpIfGraceHelper            TruthValue,
    vRtrRsvpIfMaxResvBandwidth       Unsigned32,
    vRtrRsvpIfAuthKeyChain           TNamedItemOrEmpty,
    vRtrRsvpIfReservedBandwidth64    CounterBasedGauge64,
    vRtrRsvpIfMaxReservedBandwidth64 CounterBasedGauge64
}

vRtrRsvpIfLastEnabledTime        OBJECT-TYPE
    SYNTAX      TimeStamp
    MAX-ACCESS  read-only
    STATUS      current
    DESCRIPTION
        "The vRtrRsvpIfLastEnabledTime variable contains the sysUpTime value
         when rsvpIfEnabled was last set to enabled (1) to run the RSVP
         protocol on this interface."
    ::= { vRtrRsvpIfEntry 1 }

vRtrRsvpIfVRtrIfIndex            OBJECT-TYPE
    SYNTAX      InterfaceIndex
    MAX-ACCESS  read-only
    STATUS      current
    DESCRIPTION
        "The vRtrRsvpIfVRtrIfIndex contains the value of vRtrIfIndex for the
         entry in the vRtrIfTable associated with this RSVP interface."
    ::= { vRtrRsvpIfEntry 2 }

vRtrRsvpIfAggregate              OBJECT-TYPE
    SYNTAX      TruthValue
    MAX-ACCESS  read-create
    STATUS      current
    DESCRIPTION
        "Aggregate messages are used to pack multiple RSVP messages into
         a single packet to reduce the network overhead.  When
         vRtrRsvpIfAggregate is set to 'true', RSVP negotiates with each
         neighbor and gets consensus before sending aggregate messages."
    DEFVAL      { false }
    ::= { vRtrRsvpIfEntry 3 }

vRtrRsvpIfAuthenticationKey      OBJECT-TYPE
    SYNTAX      OCTET STRING (SIZE (0..16))
    MAX-ACCESS  read-create
    STATUS      current
    DESCRIPTION
        "The value of vRtrRsvpIfAuthenticationKey specifies the
         authentication key to be used on this RSVP interface.  It is used
         along with vRtrRsvpIfAuthentication which specifies whether
         authentication using MD5 message based digest protocol is
         enabled.

         The authentication key can be any combination of
         letters or numbers.  Note that the string may contain embedded
         nulls.

         An SNMP get request on this object should return an OCTET STRING of
         length 0.

         vRtrRsvpIfAuthentication and vRtrRsvpIfAuthenticationKey, which
         indicate whether or not authentication is enabled, must be set
         together in the same SNMP request PDU or else the set request fails
         with an inconsistentValue error.

         By default, authentication is disabled and vRtrRsvpIfAuthenticationKey
         is set to the empty string, ''H."
    DEFVAL      { ''H }
    ::= { vRtrRsvpIfEntry 4 }

vRtrRsvpIfHelloInterval          OBJECT-TYPE
    SYNTAX      Unsigned32 (0..60000)
    UNITS       "milliseconds"
    MAX-ACCESS  read-create
    STATUS      current
    DESCRIPTION
        "The value of vRtrRsvpIfHelloInterval specifies the length of time,
         in seconds, between the Hello packets that the router sends on
         the interface. This value must be the same for all routers
         attached to a common network.  When vRtrRsvpIfHelloInterval is
         set to a value of zero (0), the sending of hello messages is
         disabled."
    DEFVAL      { 3000 }
    ::= { vRtrRsvpIfEntry 5 }

vRtrRsvpIfSubscription           OBJECT-TYPE
    SYNTAX      Unsigned32 (0..1000)
    MAX-ACCESS  read-create
    STATUS      current
    DESCRIPTION
        "The value of vRtrRsvpIfSubscription specifies the percentage of the
         link bandwidth that RSVP can use for reservation.  When the value
         of vRtrRsvpIfSubscription is set to zero (0), no new sessions are
         permitted on this interface.  Over subscription, > 100% is also
         allowed on the interface."
    DEFVAL      { 100 }
    ::= { vRtrRsvpIfEntry 6 }

vRtrRsvpIfKeepMultiplier         OBJECT-TYPE
    SYNTAX      Unsigned32 (0..255)
    MAX-ACCESS  read-create
    STATUS      obsolete
    DESCRIPTION
        "The value of vRtrRsvpIfKeepMultiplier is used by RSVP to declare
         either a reservation down or the neighbor as down.

         When vRtrRsvpIfKeepMultiplier is set to the value of zero (0), the
         value of vRtrRsvpGeneralKeepMultiplier is applied to RSVP running on
         this interface."
    DEFVAL      { 0 }
    ::= { vRtrRsvpIfEntry 7 }

vRtrRsvpIfRefreshTime            OBJECT-TYPE
    SYNTAX      Unsigned32 (0..65535)
    UNITS       "seconds"
    MAX-ACCESS  read-create
    STATUS      obsolete
    DESCRIPTION
        "The value of vRtrRsvpIfRefreshTime controls the interval between the
         successive Path and Resv refresh messages. RSVP declares the session
         down after it misses ((keep-multiplier + 0.5) * 1.5 * refresh-time))
         consecutive refresh messages.

         When the value of vRtrRsvpIfRefreshTime is set to zero (0), the value
         of vRtrRsvpGeneralRefreshTime is applied to that specific RSVP
         interface."
    DEFVAL      { 0 }
    ::= { vRtrRsvpIfEntry 8 }

vRtrRsvpIfOperState              OBJECT-TYPE
    SYNTAX      TmnxOperState
    MAX-ACCESS  read-only
    STATUS      current
    DESCRIPTION
        "vRtrRsvpIfOperState indicates the current operating state of the RSVP
         protocol on this interface. When the TIMETRA-VRTR-MIB::vRtrIfPortID
         object of this interface is set to a loopback port identifier, the
         operational state is not relevant and an SNMP GET request on this
         object will return 'unknown'."
    ::= { vRtrRsvpIfEntry 9 }

vRtrRsvpIfActiveSessionCount     OBJECT-TYPE
    SYNTAX      Counter32
    MAX-ACCESS  read-only
    STATUS      current
    DESCRIPTION
        "The total number of active RSVP sessions on this interface. This count
         includes sessions that have requested bandwidth as well as sessions
         that have not requested any bandwidth."
    ::= { vRtrRsvpIfEntry 10 }

vRtrRsvpIfActiveReservationCount OBJECT-TYPE
    SYNTAX      Counter32
    MAX-ACCESS  read-only
    STATUS      current
    DESCRIPTION
        "The total number of active RSVP sessions that have reserved bandwidth."
    ::= { vRtrRsvpIfEntry 11 }

vRtrRsvpIfTotalSessionCount      OBJECT-TYPE
    SYNTAX      Counter32
    MAX-ACCESS  read-only
    STATUS      current
    DESCRIPTION
        "The total number of RSVP sessions on this interface. This count
         includes sessions that are active as well as sessions that have been
         signalled but a response has not yet been received."
    ::= { vRtrRsvpIfEntry 12 }

vRtrRsvpIfBandwidth              OBJECT-TYPE
    SYNTAX      Unsigned32
    UNITS       "megabps"
    MAX-ACCESS  read-only
    STATUS      current
    DESCRIPTION
        "The value of vRtrRsvpIfBandwidth indicates the interface bandwidth in
         megabits per second (Mbps) for the RSVP protocol on this interface.
         This is typically the port Speed."
    ::= { vRtrRsvpIfEntry 13 }

vRtrRsvpIfReservedBandwidth      OBJECT-TYPE
    SYNTAX      Unsigned32
    UNITS       "megabps"
    MAX-ACCESS  read-only
    STATUS      obsolete
    DESCRIPTION
        "The value of vRtrRsvpIfReservedBandwidth indicates the amount of
         bandwidth in megabits per second (Mbps) to reserved by the
         RSVP sessions on this interface.  A value of zero (0) indicates
         that no bandwidth is reserved.

         This object is replaced by vRtrRsvpIfReservedBandwidth64.

         This object will be deprecated in 20.2 release."
    ::= { vRtrRsvpIfEntry 14 }

vRtrRsvpIfAuthentication         OBJECT-TYPE
    SYNTAX      TruthValue
    MAX-ACCESS  read-create
    STATUS      current
    DESCRIPTION
        "The value of vRtrRsvpIfAuthentication specifies whether authentication
         is enabled. When the value is 'true', authentication using MD5 message
         based digest protocol is enabled and vRtrRsvpIfAuthenticationKey
         specifies the authentication key to be used.

         When the value of vRtrRsvpIfAuthentication is 'false', authentication
         using MD5 message based digest protocol is disabled and
         vRtrRsvpIfAuthenticationKey is an empty string.

         vRtrRsvpIfAuthentication and vRtrRsvpIfAuthenticationKey, which
         indicates whether or not authentication is enabled, must be set
         together in the same SNMP request PDU when vRtrRsvpIfAuthentication is
         'true' or else the set request fails with an inconsistentValue error."
    DEFVAL      { false }
    ::= { vRtrRsvpIfEntry 15 }

vRtrRsvpIfAuthChallenge          OBJECT-TYPE
    SYNTAX      TruthValue
    MAX-ACCESS  read-create
    STATUS      obsolete
    DESCRIPTION
        "The value of vRtrRsvpIfAuthChallenge specifies if RSVP integrity
         challenge/response handshake is to be performed with RSVP neighbors.

         By default, integrity handshake with neighbors is disabled and the
         value is set to 'false'."
    DEFVAL      { false }
    ::= { vRtrRsvpIfEntry 16 }

vRtrRsvpIfAuthKeyId              OBJECT-TYPE
    SYNTAX      Counter64
    MAX-ACCESS  read-only
    STATUS      current
    DESCRIPTION
        "The value of vRtrRsvpIfAuthKeyId indicates a number that must be
         unique for a given sender.  A locally unique key identifier is
         generated using some combination of the address of the sending
         interface and the key number."
    ::= { vRtrRsvpIfEntry 17 }

vRtrRsvpIfAuthRxSeqNum           OBJECT-TYPE
    SYNTAX      Counter64
    MAX-ACCESS  read-only
    STATUS      current
    DESCRIPTION
        "The value of vRtrRsvpIfAuthRxSeqNum indicates a monotonically
         increasing, unique sequence number for the receiver."
    ::= { vRtrRsvpIfEntry 18 }

vRtrRsvpIfAuthTxSeqNum           OBJECT-TYPE
    SYNTAX      Counter64
    MAX-ACCESS  read-only
    STATUS      current
    DESCRIPTION
        "The value of vRtrRsvpIfAuthTxSeqNum indicates a monotonically
         increasing, unique sequence number for the sender."
    ::= { vRtrRsvpIfEntry 19 }

vRtrRsvpIfAuthWindowSize         OBJECT-TYPE
    SYNTAX      Counter32
    MAX-ACCESS  read-only
    STATUS      current
    DESCRIPTION
        "The value of vRtrRsvpIfAuthWindowSize indicates the receiver's
         tolerance to out-of-order message delivery.  At the receiver,
         packets reordered within vRtrRsvpIfAuthWindowSize would only
         be accepted."
    ::= { vRtrRsvpIfEntry 20 }

vRtrRsvpIfRefreshReduction       OBJECT-TYPE
    SYNTAX      TruthValue
    MAX-ACCESS  read-create
    STATUS      current
    DESCRIPTION
        "The value of vRtrRsvpIfRefreshReduction specifies whether the use
         of the RSVP overhead refresh reduction capabilities on this RSVP
         interface is enabled.  When the value of vRtrRsvpIfRefreshReduction
         is 'true' refresh reduction capabilities are enabled."
    DEFVAL      { false }
    ::= { vRtrRsvpIfEntry 21 }

vRtrRsvpIfReliableDelivery       OBJECT-TYPE
    SYNTAX      TruthValue
    MAX-ACCESS  read-create
    STATUS      current
    DESCRIPTION
        "The value of vRtrRsvpIfReliableDelivery specifies whether reliable
         delivery of RSVP messages over the RSVP interface is enabled.  When
         the value of vRtrRsvpIfReliableDelivery is 'true' reliable delivery
         of RSVP messages over RSVP interface is enabled.

         vRtrRsvpIfReliableDelivery is not valid if vRtrRsvpIfRefreshReduction
         is disabled, i.e. when vRtrRsvpIfRefreshReduction is set to 'false'."
    DEFVAL      { false }
    ::= { vRtrRsvpIfEntry 22 }

vRtrRsvpIfBfdEnabled             OBJECT-TYPE
    SYNTAX      TruthValue
    MAX-ACCESS  read-create
    STATUS      current
    DESCRIPTION
        "The value of vRtrRsvpIfBfdEnabled specifies whether Bi-directional
         Forwarding Detection is enabled on this RSVP interface.

         When the value is 'true', this RSVP interface can establish BFD
         sessions and use BFD as a signalling mechanism. When it is 'false', it
         cannot use BFD."
    DEFVAL      { false }
    ::= { vRtrRsvpIfEntry 23 }

vRtrRsvpIfGracefulShutdown       OBJECT-TYPE
    SYNTAX      TruthValue
    MAX-ACCESS  read-create
    STATUS      current
    DESCRIPTION
        "The value of vRtrRsvpIfGracefulShutdown specifies whether graceful
         shutdown of the RSVP interface is enabled. When this object has a
         value of 'true', graceful shutdown is enabled on the interface. When
         its value is 'false', graceful shutdown is disabled on the interface."
    DEFVAL      { false }
    ::= { vRtrRsvpIfEntry 24 }

vRtrRsvpIfDSTECt0BwPercent       OBJECT-TYPE
    SYNTAX      TmnxRsvpDSTEBwPercent
    MAX-ACCESS  read-create
    STATUS      current
    DESCRIPTION
        "The value of vRtrRsvpIfDSTECt0BwPercent specifies the percentage
         of link bandwidth for class type (CT) 0.  A bandwidth percentage
         is specified for each Class Type and the sum of all the bandwidth
         percentages must not exceed 100%.  Bandwidth percentages for all 8
         class types must be set together in the same SNMP request PDU or
         else the set request fails with an inconsistentValue error."
    DEFVAL      { 0 }
    ::= { vRtrRsvpIfEntry 25 }

vRtrRsvpIfDSTECt1BwPercent       OBJECT-TYPE
    SYNTAX      TmnxRsvpDSTEBwPercent
    MAX-ACCESS  read-create
    STATUS      current
    DESCRIPTION
        "The value of vRtrRsvpIfDSTECt1BwPercent specifies the percentage link
         bandwidth for CT 1."
    DEFVAL      { 0 }
    ::= { vRtrRsvpIfEntry 26 }

vRtrRsvpIfDSTECt2BwPercent       OBJECT-TYPE
    SYNTAX      TmnxRsvpDSTEBwPercent
    MAX-ACCESS  read-create
    STATUS      current
    DESCRIPTION
        "The value of vRtrRsvpIfDSTECt2BwPercent specifies the percentage link
         bandwidth for CT 2."
    DEFVAL      { 0 }
    ::= { vRtrRsvpIfEntry 27 }

vRtrRsvpIfDSTECt3BwPercent       OBJECT-TYPE
    SYNTAX      TmnxRsvpDSTEBwPercent
    MAX-ACCESS  read-create
    STATUS      current
    DESCRIPTION
        "The value of vRtrRsvpIfDSTECt3BwPercent specifies the percentage link
         bandwidth for CT 3."
    DEFVAL      { 0 }
    ::= { vRtrRsvpIfEntry 28 }

vRtrRsvpIfDSTECt4BwPercent       OBJECT-TYPE
    SYNTAX      TmnxRsvpDSTEBwPercent
    MAX-ACCESS  read-create
    STATUS      current
    DESCRIPTION
        "The value of vRtrRsvpIfDSTECt4BwPercent specifies the percentage link
         bandwidth for CT 4."
    DEFVAL      { 0 }
    ::= { vRtrRsvpIfEntry 29 }

vRtrRsvpIfDSTECt5BwPercent       OBJECT-TYPE
    SYNTAX      TmnxRsvpDSTEBwPercent
    MAX-ACCESS  read-create
    STATUS      current
    DESCRIPTION
        "The value of vRtrRsvpIfDSTECt5BwPercent specifies the percentage link
         bandwidth for CT 5."
    DEFVAL      { 0 }
    ::= { vRtrRsvpIfEntry 30 }

vRtrRsvpIfDSTECt6BwPercent       OBJECT-TYPE
    SYNTAX      TmnxRsvpDSTEBwPercent
    MAX-ACCESS  read-create
    STATUS      current
    DESCRIPTION
        "The value of vRtrRsvpIfDSTECt6BwPercent specifies the percentage link
         bandwidth for CT 6."
    DEFVAL      { 0 }
    ::= { vRtrRsvpIfEntry 31 }

vRtrRsvpIfDSTECt7BwPercent       OBJECT-TYPE
    SYNTAX      TmnxRsvpDSTEBwPercent
    MAX-ACCESS  read-create
    STATUS      current
    DESCRIPTION
        "The value of vRtrRsvpIfDSTECt7BwPercent specifies the percentage link
         bandwidth for CT 7."
    DEFVAL      { 0 }
    ::= { vRtrRsvpIfEntry 32 }

vRtrRsvpIfInheritance            OBJECT-TYPE
    SYNTAX      Unsigned32
    MAX-ACCESS  read-create
    STATUS      current
    DESCRIPTION
        "A bit within vRtrRsvpIfInheritance specifies whether to inherit the
         operational values of the corresponding inherited objects from
         vRtrRsvpGeneralTable or use the administratively set values.

         Non mask bits will always have value of zero, and any attempt to
         change the value will be silently discarded.

         This object is a bit-mask, with the following positions:

         vRtrRsvpIfDSTECt0BwPercent                0x40000

         When the bit has value of one, then all bandwidths for CTs
         (vRtrRsvpIfDSTECt0BwPercent,..vRtrRsvpIfDSTECt7BwPercent)
         administrative and operational values are either the DEFVAL values or
         the most recently SET values. The mask bit for object
         vRtrRsvpIfDSTECt0BwPercent will be set to one when set is performed on
         the objects vRtrRsvpIfDSTECt0BwPercent,..vRtrRsvpIfDSTECt7BwPercent.
         Any attempt to set the mask bit to one will be silently discarded.

         When the bit is set to zero, then all bandwidths for CTs
         administrative and operational value are inherited from the
         corresponding bandwidths for CTs in vRtrRsvpDSTETable.
         vRtrRsvpDSTETable is augment of vRtrRsvpGeneralTable.


         vRtrRsvpIfTEThresholdLevelUp1                0x80000

         When the bit has value of one, then all Up threshold values
         (vRtrRsvpIfTEThresholdLevelUp1,..vRtrRsvpIfTEThresholdLevelUp16) are
         either the DEFVAL values or the most recently SET values. The mask bit
         for object vRtrRsvpIfTEThresholdLevelUp1 will be set to one when set
         is performed on the objects
         vRtrRsvpIfTEThresholdLevelUp1,..vRtrRsvpIfTEThresholdLevelUp16. Any
         attempt to set the mask bit to one will be silently discarded.


         When the bit is set to zero, then all the Up threshold values are
         inherited from the corresponding Up thresholds in
         vRtrRsvpGenTEThresholdTable. vRtrRsvpGenTEThresholdTable is augment of
         vRtrRsvpGeneralTable.

         vRtrRsvpIfTEThresholdLevelDn1                0x100000

         When the bit has value of one, then all Down threshold values
         (vRtrRsvpIfTEThresholdLevelDn1,..vRtrRsvpIfTEThresholdLevelDn16) are
         either the DEFVAL values or the most recently SET values. The mask bit
         for object vRtrRsvpIfTEThresholdLevelDn1 will be set to one when set
         is performed on the objects
         vRtrRsvpIfTEThresholdLevelDn1,..vRtrRsvpIfTEThresholdLevelDn16. Any
         attempt to set the mask bit to one will be silently discarded.

         When the bit is set to zero, then all the Down threshold values are
         inherited from the corresponding Down thresholds in
         vRtrRsvpGenTEThresholdTable. vRtrRsvpGenTEThresholdTable is augment of
         vRtrRsvpGeneralTable.

         vRtrRsvpIfImplicitNull                       0x200000

         When the bit has value of one, then value of vRtrRsvpIfImplicitNull
         is either the DEFVAL or the most recently SET value. The mask bit for
         object vRtrRsvpIfImplicitNull  will be set to one when set is
         performed on the object vRtrRsvpIfImplicitNull. Any attempt to set
         the mask bit to one will be silently discarded.

         When the bit is set to zero, then value of vRtrRsvpIfImplicitNull is
         inherited  from the corresponding implicit null object in
         vRtrRsvpGeneralTable."
    DEFVAL      { 0 }
    ::= { vRtrRsvpIfEntry 33 }

vRtrRsvpIfDSTEBC0Bw              OBJECT-TYPE
    SYNTAX      Counter64
    UNITS       "kilobps"
    MAX-ACCESS  read-only
    STATUS      current
    DESCRIPTION
        "The value of vRtrRsvpIfDSTEBC0Bw indicates Bandwidth Constraint (BC)
         for Class Type 0 (CT0)."
    ::= { vRtrRsvpIfEntry 34 }

vRtrRsvpIfDSTEBC1Bw              OBJECT-TYPE
    SYNTAX      Counter64
    UNITS       "kilobps"
    MAX-ACCESS  read-only
    STATUS      current
    DESCRIPTION
        "The value of vRtrRsvpIfDSTEBC1Bw indicates the bandwidth constraint
         for CT 1."
    ::= { vRtrRsvpIfEntry 35 }

vRtrRsvpIfDSTEBC2Bw              OBJECT-TYPE
    SYNTAX      Counter64
    UNITS       "kilobps"
    MAX-ACCESS  read-only
    STATUS      current
    DESCRIPTION
        "The value of vRtrRsvpIfDSTEBC2Bw indicates the bandwidth constraint
         for CT 2."
    ::= { vRtrRsvpIfEntry 36 }

vRtrRsvpIfDSTEBC3Bw              OBJECT-TYPE
    SYNTAX      Counter64
    UNITS       "kilobps"
    MAX-ACCESS  read-only
    STATUS      current
    DESCRIPTION
        "The value of vRtrRsvpIfDSTEBC3Bw indicates the bandwidth constraint
         for CT 3."
    ::= { vRtrRsvpIfEntry 37 }

vRtrRsvpIfDSTEBC4Bw              OBJECT-TYPE
    SYNTAX      Counter64
    UNITS       "kilobps"
    MAX-ACCESS  read-only
    STATUS      current
    DESCRIPTION
        "The value of vRtrRsvpIfDSTEBC4Bw indicates the bandwidth constraint
         for CT 4."
    ::= { vRtrRsvpIfEntry 38 }

vRtrRsvpIfDSTEBC5Bw              OBJECT-TYPE
    SYNTAX      Counter64
    UNITS       "kilobps"
    MAX-ACCESS  read-only
    STATUS      current
    DESCRIPTION
        "The value of vRtrRsvpIfDSTEBC5Bw indicates the bandwidth constraint
         for CT 5."
    ::= { vRtrRsvpIfEntry 39 }

vRtrRsvpIfDSTEBC6Bw              OBJECT-TYPE
    SYNTAX      Counter64
    UNITS       "kilobps"
    MAX-ACCESS  read-only
    STATUS      current
    DESCRIPTION
        "The value of vRtrRsvpIfDSTEBC6Bw indicates the bandwidth constraint
         for CT 6."
    ::= { vRtrRsvpIfEntry 40 }

vRtrRsvpIfDSTEBC7Bw              OBJECT-TYPE
    SYNTAX      Counter64
    UNITS       "kilobps"
    MAX-ACCESS  read-only
    STATUS      current
    DESCRIPTION
        "The value of vRtrRsvpIfDSTEBC7Bw indicates the bandwidth constraint
         for CT 7."
    ::= { vRtrRsvpIfEntry 41 }

vRtrRsvpIfImplicitNull           OBJECT-TYPE
    SYNTAX      TruthValue
    MAX-ACCESS  read-create
    STATUS      current
    DESCRIPTION
        "The value of vRtrRsvpIfImplicitNull specifies whether or not to
         signal implicit null values for all label switched paths associated
         with this RSVP interface when this node is an egress Label Edge
         Router (LER).  When the value is 'true' implicit null values are
         signaled."
    DEFVAL      { false }
    ::= { vRtrRsvpIfEntry 42 }

vRtrRsvpIfIgpUpdatePending       OBJECT-TYPE
    SYNTAX      TruthValue
    MAX-ACCESS  read-only
    STATUS      current
    DESCRIPTION
        "The value of vRtrRsvpIfIgpUpdatePending indicates if the TE update
         which is to be sent to IGP on any bandwidth change is pending for the
         interface.

         When the value of vRtrRsvpIfIgpUpdatePending is 'true' IGP TE update
         is pending for a bandwidth change on the interface."
    ::= { vRtrRsvpIfEntry 43 }

vRtrRsvpIfIgpNextUpdate          OBJECT-TYPE
    SYNTAX      Unsigned32
    UNITS       "seconds"
    MAX-ACCESS  read-only
    STATUS      current
    DESCRIPTION
        "The value of vRtrRsvpIfIgpNextUpdate indicates the time remaining in
         seconds before the next TE update would be sent to IGP for the
         interface.

         The value of vRtrRsvpIfIgpNextUpdate is applicable only when the value
         of vRtrRsvpIfIgpUpdatePending is 'true'."
    ::= { vRtrRsvpIfEntry 44 }

vRtrRsvpIfGraceHelper            OBJECT-TYPE
    SYNTAX      TruthValue
    MAX-ACCESS  read-create
    STATUS      current
    DESCRIPTION
        "The value of vRtrRsvpIfGraceHelper specifies whether graceful restart
         helper mode is enabled or disabled. When the graceful restart helper
         mode when enabled, the system will advertise Restart capability object
         which will allow neighboring router to request for a grace period
         during which the system will continue to use previously established
         RSVP session. This is typically used when a neighboring router's
         control plane restarts but its forwarding plane is expected to
         continue to forward traffic.

         The system will advertise Restart capability object with value of the
         restart, and the recovery times always set to 0."
    DEFVAL      { false }
    ::= { vRtrRsvpIfEntry 45 }

vRtrRsvpIfMaxResvBandwidth       OBJECT-TYPE
    SYNTAX      Unsigned32
    UNITS       "megabps"
    MAX-ACCESS  read-only
    STATUS      obsolete
    DESCRIPTION
        "The value of vRtrRsvpIfMaxResvBandwidth indicates the amount
         of bandwidth in megabits per second (Mbps) available to be
         reserved for the RSVP protocol on this interface.  This is
         typically the (port Speed * subscription Percentage).

         This object is replaced by vRtrRsvpIfMaxReservedBandwidth64.

         This object will be deprecated in 20.2 release."
    ::= { vRtrRsvpIfEntry 46 }

vRtrRsvpIfAuthKeyChain           OBJECT-TYPE
    SYNTAX      TNamedItemOrEmpty
    MAX-ACCESS  read-create
    STATUS      current
    DESCRIPTION
        "The value of vRtrRsvpIfAuthKeyChain specifies the keychain which will
         be used to sign and/or authenticate the RSVP protocol stream.

         The keychain name is defined by tmnxKeyChainName and is the index for
         TIMETRA-SECURITY-MIB::tmnxKeyChainTable."
    DEFVAL      { ''H }
    ::= { vRtrRsvpIfEntry 47 }

vRtrRsvpIfReservedBandwidth64    OBJECT-TYPE
    SYNTAX      CounterBasedGauge64
    UNITS       "megabps"
    MAX-ACCESS  read-only
    STATUS      current
    DESCRIPTION
        "The value of vRtrRsvpIfReservedBandwidth64 indicates the amount of
         bandwidth in megabits per second (Mbps) to reserved by the
         RSVP sessions on this interface.  A value of zero (0) indicates
         that no bandwidth is reserved."
    ::= { vRtrRsvpIfEntry 48 }

vRtrRsvpIfMaxReservedBandwidth64 OBJECT-TYPE
    SYNTAX      CounterBasedGauge64
    UNITS       "megabps"
    MAX-ACCESS  read-only
    STATUS      current
    DESCRIPTION
        "The value of vRtrRsvpIfMaxReservedBandwidth64 indicates the amount
         of bandwidth in megabits per second (Mbps) available to be
         reserved for the RSVP protocol on this interface.  This is
         typically the (port Speed * subscription Percentage)."
    ::= { vRtrRsvpIfEntry 49 }

vRtrRsvpIfStatTable              OBJECT-TYPE
    SYNTAX      SEQUENCE OF VRtrRsvpIfStatEntry
    MAX-ACCESS  not-accessible
    STATUS      current
    DESCRIPTION
        "The vRtrRsvpIfStatTable contains objects for reporting statistics
         associated with an interface running RSVP."
    ::= { tmnxRsvpObjs 4 }

vRtrRsvpIfStatEntry              OBJECT-TYPE
    SYNTAX      VRtrRsvpIfStatEntry
    MAX-ACCESS  not-accessible
    STATUS      current
    DESCRIPTION
        "Each row entry represents an interface running the RSVP protocol
         within a virtual router.  Entries in this table cannot be
         created and deleted via SNMP SET operations.  An entry in this table
         is created by the agent when the RSVP protocol is configured on
         a virtual router interface.  The entry is destroyed when RSVP is
         removed from the interface."
    INDEX       {
        vRtrID,
        vRtrIfIndex
    }
    ::= { vRtrRsvpIfStatTable 1 }

VRtrRsvpIfStatEntry              ::= SEQUENCE
{
    vRtrRsvpIfStatTxPaths            Counter64,
    vRtrRsvpIfStatTxPathErrors       Counter64,
    vRtrRsvpIfStatTxPathTears        Counter64,
    vRtrRsvpIfStatTxResvs            Counter64,
    vRtrRsvpIfStatTxResvErrors       Counter64,
    vRtrRsvpIfStatTxResvTears        Counter64,
    vRtrRsvpIfStatTxResvConfirms     Counter64,
    vRtrRsvpIfStatTxBundles          Counter64,
    vRtrRsvpIfStatTxAcks             Counter64,
    vRtrRsvpIfStatTxHelloReqs        Counter64,
    vRtrRsvpIfStatTxSRefreshes       Counter64,
    vRtrRsvpIfStatTxPkts             Counter64,
    vRtrRsvpIfStatTxErrorPkts        Counter64,
    vRtrRsvpIfStatTxTotalPkts        Counter64,
    vRtrRsvpIfStatRxPaths            Counter64,
    vRtrRsvpIfStatRxPathErrors       Counter64,
    vRtrRsvpIfStatRxPathTears        Counter64,
    vRtrRsvpIfStatRxResvs            Counter64,
    vRtrRsvpIfStatRxResvErrors       Counter64,
    vRtrRsvpIfStatRxResvTears        Counter64,
    vRtrRsvpIfStatRxResvConfirms     Counter64,
    vRtrRsvpIfStatRxBundles          Counter64,
    vRtrRsvpIfStatRxAcks             Counter64,
    vRtrRsvpIfStatRxHelloReqs        Counter64,
    vRtrRsvpIfStatRxSRefreshes       Counter64,
    vRtrRsvpIfStatRxPkts             Counter64,
    vRtrRsvpIfStatRxErrorPkts        Counter64,
    vRtrRsvpIfStatRxTotalPkts        Counter64,
    vRtrRsvpIfStatHelloTimeout       Counter32,
    vRtrRsvpIfStatTxAuthErrors       Counter64,
    vRtrRsvpIfStatRxAuthErrors       Counter64
}

vRtrRsvpIfStatTxPaths            OBJECT-TYPE
    SYNTAX      Counter64
    MAX-ACCESS  read-only
    STATUS      current
    DESCRIPTION
        "The total number of RSVP PATH messages that have been transmitted from
         this RSVP interface."
    ::= { vRtrRsvpIfStatEntry 1 }

vRtrRsvpIfStatTxPathErrors       OBJECT-TYPE
    SYNTAX      Counter64
    MAX-ACCESS  read-only
    STATUS      current
    DESCRIPTION
        "The total number of RSVP PATH ERROR messages that have been
         transmitted from this RSVP interface."
    ::= { vRtrRsvpIfStatEntry 2 }

vRtrRsvpIfStatTxPathTears        OBJECT-TYPE
    SYNTAX      Counter64
    MAX-ACCESS  read-only
    STATUS      current
    DESCRIPTION
        "The total number of RSVP PATH TEAR messages that have been transmitted
         from this RSVP interface."
    ::= { vRtrRsvpIfStatEntry 3 }

vRtrRsvpIfStatTxResvs            OBJECT-TYPE
    SYNTAX      Counter64
    MAX-ACCESS  read-only
    STATUS      current
    DESCRIPTION
        "The total number of RSVP RESV messages that have been transmitted from
         this RSVP interface."
    ::= { vRtrRsvpIfStatEntry 4 }

vRtrRsvpIfStatTxResvErrors       OBJECT-TYPE
    SYNTAX      Counter64
    MAX-ACCESS  read-only
    STATUS      current
    DESCRIPTION
        "The total number of RSVP RESV ERROR messages that have been
         transmitted from this RSVP interface."
    ::= { vRtrRsvpIfStatEntry 5 }

vRtrRsvpIfStatTxResvTears        OBJECT-TYPE
    SYNTAX      Counter64
    MAX-ACCESS  read-only
    STATUS      current
    DESCRIPTION
        "The total number of RSVP RESV TEAR messages that have been transmitted
         from this RSVP interface."
    ::= { vRtrRsvpIfStatEntry 6 }

vRtrRsvpIfStatTxResvConfirms     OBJECT-TYPE
    SYNTAX      Counter64
    MAX-ACCESS  read-only
    STATUS      current
    DESCRIPTION
        "The total number of RSVP RESV CONFIRM messages that have been
         transmitted from this RSVP interface."
    ::= { vRtrRsvpIfStatEntry 7 }

vRtrRsvpIfStatTxBundles          OBJECT-TYPE
    SYNTAX      Counter64
    MAX-ACCESS  read-only
    STATUS      current
    DESCRIPTION
        "The total number of RSVP bundled packets that have been transmitted on
         this RSVP interface."
    ::= { vRtrRsvpIfStatEntry 8 }

vRtrRsvpIfStatTxAcks             OBJECT-TYPE
    SYNTAX      Counter64
    MAX-ACCESS  read-only
    STATUS      current
    DESCRIPTION
        "The total number of RSVP ACK messages that have been transmitted on
         this RSVP interface when refresh reduction is enabled."
    ::= { vRtrRsvpIfStatEntry 9 }

vRtrRsvpIfStatTxHelloReqs        OBJECT-TYPE
    SYNTAX      Counter64
    MAX-ACCESS  read-only
    STATUS      current
    DESCRIPTION
        "The total number of RSVP HELLO REQ packets that have been transmitted
         on this RSVP interface."
    ::= { vRtrRsvpIfStatEntry 10 }

vRtrRsvpIfStatTxSRefreshes       OBJECT-TYPE
    SYNTAX      Counter64
    MAX-ACCESS  read-only
    STATUS      current
    DESCRIPTION
        "The total number of summary refresh, SREFRESH, messages that have been
         transmitted on this RSVP interface when refresh reduction is enabled."
    ::= { vRtrRsvpIfStatEntry 11 }

vRtrRsvpIfStatTxPkts             OBJECT-TYPE
    SYNTAX      Counter64
    MAX-ACCESS  read-only
    STATUS      current
    DESCRIPTION
        "The total number of error free RSVP packets that have been transmitted
         on this RSVP interface."
    ::= { vRtrRsvpIfStatEntry 12 }

vRtrRsvpIfStatTxErrorPkts        OBJECT-TYPE
    SYNTAX      Counter64
    MAX-ACCESS  read-only
    STATUS      current
    DESCRIPTION
        "The total number of RSVP packets with errors that have been
         transmitted on this RSVP interface."
    ::= { vRtrRsvpIfStatEntry 13 }

vRtrRsvpIfStatTxTotalPkts        OBJECT-TYPE
    SYNTAX      Counter64
    MAX-ACCESS  read-only
    STATUS      current
    DESCRIPTION
        "The total number of RSVP packets, including error packets, that have
         been transmitted on this RSVP interface."
    ::= { vRtrRsvpIfStatEntry 14 }

vRtrRsvpIfStatRxPaths            OBJECT-TYPE
    SYNTAX      Counter64
    MAX-ACCESS  read-only
    STATUS      current
    DESCRIPTION
        "The total number of RSVP PATH messages that have been received on this
         RSVP interface."
    ::= { vRtrRsvpIfStatEntry 15 }

vRtrRsvpIfStatRxPathErrors       OBJECT-TYPE
    SYNTAX      Counter64
    MAX-ACCESS  read-only
    STATUS      current
    DESCRIPTION
        "The total number of RSVP PATH ERROR messages that have been
         transmitted on this RSVP interface."
    ::= { vRtrRsvpIfStatEntry 16 }

vRtrRsvpIfStatRxPathTears        OBJECT-TYPE
    SYNTAX      Counter64
    MAX-ACCESS  read-only
    STATUS      current
    DESCRIPTION
        "The total number of RSVP PATH TEAR messages that have been received on
         this RSVP interface."
    ::= { vRtrRsvpIfStatEntry 17 }

vRtrRsvpIfStatRxResvs            OBJECT-TYPE
    SYNTAX      Counter64
    MAX-ACCESS  read-only
    STATUS      current
    DESCRIPTION
        "The total number of RSVP RESV messages that have been received on this
         RSVP interface."
    ::= { vRtrRsvpIfStatEntry 18 }

vRtrRsvpIfStatRxResvErrors       OBJECT-TYPE
    SYNTAX      Counter64
    MAX-ACCESS  read-only
    STATUS      current
    DESCRIPTION
        "The total number of RSVP RESV ERROR messages that have been received
         on this RSVP interface."
    ::= { vRtrRsvpIfStatEntry 19 }

vRtrRsvpIfStatRxResvTears        OBJECT-TYPE
    SYNTAX      Counter64
    MAX-ACCESS  read-only
    STATUS      current
    DESCRIPTION
        "The total number of RSVP RESV TEAR messages that have been received on
         this RSVP interface."
    ::= { vRtrRsvpIfStatEntry 20 }

vRtrRsvpIfStatRxResvConfirms     OBJECT-TYPE
    SYNTAX      Counter64
    MAX-ACCESS  read-only
    STATUS      current
    DESCRIPTION
        "The total number of RSVP RESV CONFIRM messages that have been received
         on this RSVP interface."
    ::= { vRtrRsvpIfStatEntry 21 }

vRtrRsvpIfStatRxBundles          OBJECT-TYPE
    SYNTAX      Counter64
    MAX-ACCESS  read-only
    STATUS      current
    DESCRIPTION
        "The total number of RSVP bundled packets received on this
         RSVP interface.  Bundled packets are sent when refresh
         reduction is enabled."
    ::= { vRtrRsvpIfStatEntry 22 }

vRtrRsvpIfStatRxAcks             OBJECT-TYPE
    SYNTAX      Counter64
    MAX-ACCESS  read-only
    STATUS      current
    DESCRIPTION
        "The total number of RSVP ACK messages received when refresh reduction
         is enabled on this RSVP interface."
    ::= { vRtrRsvpIfStatEntry 23 }

vRtrRsvpIfStatRxHelloReqs        OBJECT-TYPE
    SYNTAX      Counter64
    MAX-ACCESS  read-only
    STATUS      current
    DESCRIPTION
        "The total number of RSVP HELLO REQ messages received on this RSVP
         interface."
    ::= { vRtrRsvpIfStatEntry 24 }

vRtrRsvpIfStatRxSRefreshes       OBJECT-TYPE
    SYNTAX      Counter64
    MAX-ACCESS  read-only
    STATUS      current
    DESCRIPTION
        "The total number of RSVP summary refresh, SREFRESH, messages received
         on this RSVP interface."
    ::= { vRtrRsvpIfStatEntry 25 }

vRtrRsvpIfStatRxPkts             OBJECT-TYPE
    SYNTAX      Counter64
    MAX-ACCESS  read-only
    STATUS      current
    DESCRIPTION
        "The total number of error free RSVP packets received on this RSVP
         interface."
    ::= { vRtrRsvpIfStatEntry 26 }

vRtrRsvpIfStatRxErrorPkts        OBJECT-TYPE
    SYNTAX      Counter64
    MAX-ACCESS  read-only
    STATUS      current
    DESCRIPTION
        "The total number of RSVP packets with errors received on this RSVP
         interface."
    ::= { vRtrRsvpIfStatEntry 27 }

vRtrRsvpIfStatRxTotalPkts        OBJECT-TYPE
    SYNTAX      Counter64
    MAX-ACCESS  read-only
    STATUS      current
    DESCRIPTION
        "The total number of RSVP packets, including errors, received on this
         RSVP interface."
    ::= { vRtrRsvpIfStatEntry 28 }

vRtrRsvpIfStatHelloTimeout       OBJECT-TYPE
    SYNTAX      Counter32
    MAX-ACCESS  read-only
    STATUS      current
    DESCRIPTION
        "The total number of hello messages that timed out on this RSVP
         interface."
    ::= { vRtrRsvpIfStatEntry 29 }

vRtrRsvpIfStatTxAuthErrors       OBJECT-TYPE
    SYNTAX      Counter64
    MAX-ACCESS  read-only
    STATUS      current
    DESCRIPTION
        "The total number of RSVP packets with MD5 errors sent by this RSVP
         interface."
    ::= { vRtrRsvpIfStatEntry 30 }

vRtrRsvpIfStatRxAuthErrors       OBJECT-TYPE
    SYNTAX      Counter64
    MAX-ACCESS  read-only
    STATUS      current
    DESCRIPTION
        "The total number of RSVP packets with MD5 errors received on this RSVP
         interface."
    ::= { vRtrRsvpIfStatEntry 31 }

vRtrRsvpSessionTable             OBJECT-TYPE
    SYNTAX      SEQUENCE OF VRtrRsvpSessionEntry
    MAX-ACCESS  not-accessible
    STATUS      current
    DESCRIPTION
        "The vRtrRsvpSessionTable contains objects for reporting sessions
         associated with the RSVP protocol running in a virtual router."
    ::= { tmnxRsvpObjs 5 }

vRtrRsvpSessionEntry             OBJECT-TYPE
    SYNTAX      VRtrRsvpSessionEntry
    MAX-ACCESS  not-accessible
    STATUS      current
    DESCRIPTION
        "Each row entry represents a session of the RSVP protocol
         within a virtual router.  Entries in this table cannot be
         created and deleted via SNMP SET operations.  An entry in
         this table is created by the agent when the RSVP protocol
         establishes a session.  The entry is destroyed when the RSVP
         session is removed."
    INDEX       {
        vRtrID,
        vRtrRsvpSessionIndex
    }
    ::= { vRtrRsvpSessionTable 1 }

VRtrRsvpSessionEntry             ::= SEQUENCE
{
    vRtrRsvpSessionIndex             Unsigned32,
    vRtrRsvpSessionState             TmnxOperState,
    vRtrRsvpSessionName              TmnxRsvpSessionNameString,
    vRtrRsvpSessionSetupPriority     Unsigned32,
    vRtrRsvpSessionHoldPriority      Unsigned32,
    vRtrRsvpSessionFlags             Unsigned32,
    vRtrRsvpSessionEndpointAddress   IpAddress,
    vRtrRsvpSessionLspId             Unsigned32,
    vRtrRsvpSessionSenderAddress     IpAddress,
    vRtrRsvpSessionType              INTEGER,
    vRtrRsvpSessionLocalProtectAvailable TruthValue,
    vRtrRsvpSessionLocalProtectInUse TruthValue,
    vRtrRsvpSessionStyle             INTEGER,
    vRtrRsvpSessionTunnelId          Unsigned32,
    vRtrRsvpSessionExtTunnelId       IpAddress,
    vRtrRsvpSessionNextHopIpAddress  IpAddress,
    vRtrRsvpSessionDetourIndex       Unsigned32,
    vRtrRsvpSessionDetourPLRId       IpAddress,
    vRtrRsvpSessionDetourAvoidNodeId IpAddress,
    vRtrRsvpSessionPreviousHop       IpAddress,
    vRtrRsvpSessionFailCode          TmnxRsvpSessionFailCode,
    vRtrRsvpSessionFailNodeAddr      IpAddress,
    vRtrRsvpSessionXCIndex           Integer32,
    vRtrRsvpSessionBypassIndex       Unsigned32,
    vRtrRsvpSessionBypassAvoid       IpAddress,
    vRtrRsvpSessionBypassActive      TruthValue,
    vRtrRsvpSessionBypassDnstrmLabel MplsLabel,
    vRtrRsvpSessionSubGrpId          Unsigned32,
    vRtrRsvpSessionSubGrpOrgIdType   InetAddressType,
    vRtrRsvpSessionSubGrpOrgIdAddr   InetAddress,
    vRtrRsvpSessionLeafAddrType      InetAddressType,
    vRtrRsvpSessionLeafAddr          InetAddress,
    vRtrRsvpSessionP2mpId            Unsigned32,
    vRtrRsvpSessionClassType         TmnxRsvpDSTEClassType,
    vRtrRsvpSessionFrrProperties     BITS,
    vRtrRsvpSessionExNodeAddrType    InetAddressType,
    vRtrRsvpSessionExNodeAddr        InetAddress,
    vRtrRsvpSessionBypassInterArea   TruthValue,
    vRtrRsvpSessionBypassPathCost    Unsigned32,
    vRtrRsvpSessBypLastResigAttempt  TimeStamp,
    vRtrRsvpSessBypLastResigReason   INTEGER,
    vRtrRsvpSessBypLastResigStatus   INTEGER,
    vRtrRsvpSBLastResigStatusReason  INTEGER,
    vRtrRsvpSessionLspAttributeFlags BITS
}

vRtrRsvpSessionIndex             OBJECT-TYPE
    SYNTAX      Unsigned32
    MAX-ACCESS  not-accessible
    STATUS      current
    DESCRIPTION
        "The unique value that identifies this RSVP session for the RSVP
         protocol for this virtual router in the system. it is a unique value
         among entries with the same value of vRtrID."
    ::= { vRtrRsvpSessionEntry 1 }

vRtrRsvpSessionState             OBJECT-TYPE
    SYNTAX      TmnxOperState
    MAX-ACCESS  read-only
    STATUS      current
    DESCRIPTION
        "The current operational state of this RSVP session."
    ::= { vRtrRsvpSessionEntry 2 }

vRtrRsvpSessionName              OBJECT-TYPE
    SYNTAX      TmnxRsvpSessionNameString
    MAX-ACCESS  read-only
    STATUS      current
    DESCRIPTION
        "The administrative name assigned to this RSVP session by the agent."
    ::= { vRtrRsvpSessionEntry 3 }

vRtrRsvpSessionSetupPriority     OBJECT-TYPE
    SYNTAX      Unsigned32 (0..7)
    MAX-ACCESS  read-only
    STATUS      current
    DESCRIPTION
        "The value of vRtrRsvpSessionSetupPriority is the setup priority
         used for this RSVP session when there is not enough bandwidth
         available to setup this session.  If the setup priority is greater
         than the hold priority for another established session, then this
         session can preempt the existing session.  A value of zero (0) is
         the highest priority and a value of seven (7) is the lowest
         priority."
    ::= { vRtrRsvpSessionEntry 4 }

vRtrRsvpSessionHoldPriority      OBJECT-TYPE
    SYNTAX      Unsigned32 (0..7)
    MAX-ACCESS  read-only
    STATUS      current
    DESCRIPTION
        "The value of vRtrRsvpSessionHoldPriority is the hold priority
         to be used for this RSVP session when there is insufficient
         bandwidth available to setup another session.  The other session's
         setup priority is compared against this session's hold priority.
         If its setup priority is higher than this session's hold priority,
         this session may be preempted by the other session.  A value of
         zero (0) is the highest priority and a value of seven (7) is the
         lowest priority."
    ::= { vRtrRsvpSessionEntry 5 }

vRtrRsvpSessionFlags             OBJECT-TYPE
    SYNTAX      Unsigned32
    MAX-ACCESS  read-only
    STATUS      current
    DESCRIPTION
        "vRtrRsvpSessionFlags is a bit-mask that indicates the current
         setting of the attribute flags for this RSVP session.  Session
         attributes include local protection, label recording, reservation
         styles, bandwidth protection desired and node protection desired.

         If a bit is set, has a value of one (1), the attribute is enabled or
         true for this RSVP session.

         Bit positions:
         --    localProtection    - 0x01
         --    labelRecording     - 0x02
         --    styleSE            - 0x04
         --    bwProtection       - 0x08
         --    nodeProtection     - 0x10
         --    softPreemption     - 0x40    "
    ::= { vRtrRsvpSessionEntry 6 }

vRtrRsvpSessionEndpointAddress   OBJECT-TYPE
    SYNTAX      IpAddress
    MAX-ACCESS  read-only
    STATUS      current
    DESCRIPTION
        "The value of vRtrRsvpSessionEndpointAddress is the IP address of the
         egress node for the tunnel supporting this session."
    ::= { vRtrRsvpSessionEntry 7 }

vRtrRsvpSessionLspId             OBJECT-TYPE
    SYNTAX      Unsigned32 (1..65535)
    MAX-ACCESS  read-only
    STATUS      current
    DESCRIPTION
        "The value of vRtrRsvpSessionLspId is a unique ID assigned by the
         agent to this RSVP session.  It is derived from the
         vRtrMplsLspIndex of the MPLS LSP associated with this RSVP
         session."
    ::= { vRtrRsvpSessionEntry 8 }

vRtrRsvpSessionSenderAddress     OBJECT-TYPE
    SYNTAX      IpAddress
    MAX-ACCESS  read-only
    STATUS      current
    DESCRIPTION
        "vRtrRsvpSessionSenderAddress is the IP address of the sender node
         for the tunnel supporting this session.  It is derived from the
         source address of the associated MPLS LSP definition."
    ::= { vRtrRsvpSessionEntry 9 }

vRtrRsvpSessionType              OBJECT-TYPE
    SYNTAX      INTEGER {
        unknown                (1),
        originating            (2),
        transit                (3),
        terminating            (4),
        detour                 (5),
        detourTransit          (6),
        detourTerminating      (7),
        bypassTunnel           (8),
        manualBypass           (9),
        p2mpS2lSubLspOrig      (10),
        p2mpS2lSubLspTransit   (11),
        p2mpS2lSubLspTerminate (12),
        s2lBypassTunnel        (13)
    }
    MAX-ACCESS  read-only
    STATUS      current
    DESCRIPTION
        "The value of vRtrRsvpSessionType indicates this node's position in the
         path of this RSVP session."
    ::= { vRtrRsvpSessionEntry 10 }

vRtrRsvpSessionLocalProtectAvailable OBJECT-TYPE
    SYNTAX      TruthValue
    MAX-ACCESS  read-only
    STATUS      current
    DESCRIPTION
        "When vRtrRsvpSessionLocalProtectAvailable has a value of 'true', the
         link downstream from this node is protected via a local repair
         mechanism"
    ::= { vRtrRsvpSessionEntry 11 }

vRtrRsvpSessionLocalProtectInUse OBJECT-TYPE
    SYNTAX      TruthValue
    MAX-ACCESS  read-only
    STATUS      current
    DESCRIPTION
        "When vRtrRsvpSessionLocalProtectInUse has a value of 'true', a local
         protection mechanism is in use to maintain the tunnel supporting this
         RSVP session."
    ::= { vRtrRsvpSessionEntry 12 }

vRtrRsvpSessionStyle             OBJECT-TYPE
    SYNTAX      INTEGER {
        unknown (1),
        styleSE (2),
        styleFF (3)
    }
    MAX-ACCESS  read-only
    STATUS      current
    DESCRIPTION
        "The value of vRtrRsvpSessionStyle indicates the reservation style
         used for this RSVP session.  The value 'styleSE' represents shared
         explicit style.  The value 'styleFF' represents fixed filter style."
    ::= { vRtrRsvpSessionEntry 13 }

vRtrRsvpSessionTunnelId          OBJECT-TYPE
    SYNTAX      Unsigned32
    MAX-ACCESS  read-only
    STATUS      current
    DESCRIPTION
        "vRtrRsvpSessionTunnelId is the mplsTunnelIndex for the associated row
         entry in the mplsTunnelTable supporting this RSVP session."
    ::= { vRtrRsvpSessionEntry 14 }

vRtrRsvpSessionExtTunnelId       OBJECT-TYPE
    SYNTAX      IpAddress
    MAX-ACCESS  read-only
    STATUS      current
    DESCRIPTION
        "vRtrRsvpSessionExtTunnelId is the IP address of the ingress node of
         the tunnel supporting this RSVP session."
    ::= { vRtrRsvpSessionEntry 15 }

vRtrRsvpSessionNextHopIpAddress  OBJECT-TYPE
    SYNTAX      IpAddress
    MAX-ACCESS  read-only
    STATUS      current
    DESCRIPTION
        "vRtrRsvpSessionNextHopIpAddress is the IP address of the next-hop for
         this RSVP session."
    ::= { vRtrRsvpSessionEntry 16 }

vRtrRsvpSessionDetourIndex       OBJECT-TYPE
    SYNTAX      Unsigned32
    MAX-ACCESS  read-only
    STATUS      current
    DESCRIPTION
        "vRtrRsvpSessionDetourIndex is the vRtrRsvpSessionIndex of the RSVP
         session that serves as a detour for this RSVP session.
         vRtrRsvpSessionDetourIndex is 0 if there is no detour for this RSVP
         session."
    ::= { vRtrRsvpSessionEntry 17 }

vRtrRsvpSessionDetourPLRId       OBJECT-TYPE
    SYNTAX      IpAddress
    MAX-ACCESS  read-only
    STATUS      current
    DESCRIPTION
        "vRtrRsvpSessionDetourPLRId is the IP address that identifies the
         beginning point of detour which is a PLR. Any local address on the PLR
         can be used."
    ::= { vRtrRsvpSessionEntry 18 }

vRtrRsvpSessionDetourAvoidNodeId OBJECT-TYPE
    SYNTAX      IpAddress
    MAX-ACCESS  read-only
    STATUS      current
    DESCRIPTION
        "vRtrRsvpSessionDetourAvoidNodeId is the router ID of the immediate
         downstream node that the PLR is trying to avoid."
    ::= { vRtrRsvpSessionEntry 19 }

vRtrRsvpSessionPreviousHop       OBJECT-TYPE
    SYNTAX      IpAddress
    MAX-ACCESS  read-only
    STATUS      current
    DESCRIPTION
        "vRtrRsvpSessionPreviousHop is the IP address of the node that
         forwarded the RSVP PATH message."
    ::= { vRtrRsvpSessionEntry 20 }

vRtrRsvpSessionFailCode          OBJECT-TYPE
    SYNTAX      TmnxRsvpSessionFailCode
    MAX-ACCESS  read-only
    STATUS      current
    DESCRIPTION
        "The value of vRtrRsvpSessionFailCode indicates the reason for RSVP
         session failure. A value of 0 indicates that no failure has occurred."
    ::= { vRtrRsvpSessionEntry 21 }

vRtrRsvpSessionFailNodeAddr      OBJECT-TYPE
    SYNTAX      IpAddress
    MAX-ACCESS  read-only
    STATUS      current
    DESCRIPTION
        "The value of vRtrRsvpSessionFailNodeAddr indicates the IP address of
         the node at which the RSVP session failed. When no failure has
         occurred, this value is 0."
    ::= { vRtrRsvpSessionEntry 22 }

vRtrRsvpSessionXCIndex           OBJECT-TYPE
    SYNTAX      Integer32 (1..2147483647)
    MAX-ACCESS  read-only
    STATUS      current
    DESCRIPTION
        "The value of vRtrRsvpSessionXCIndex indicates the index into the
         mplsXCTable which identifies the cross-connect entry associated with
         this RSVP session."
    ::= { vRtrRsvpSessionEntry 23 }

vRtrRsvpSessionBypassIndex       OBJECT-TYPE
    SYNTAX      Unsigned32
    MAX-ACCESS  read-only
    STATUS      current
    DESCRIPTION
        "vRtrRsvpSessionBypassIndex is the vRtrRsvpSessionIndex of the RSVP
         session that serves as a bypass tunnel (facility backup) for this RSVP
         session. vRtrRsvpSessionBypassIndex is 0 if there is no bypass tunnel
         for this RSVP session."
    ::= { vRtrRsvpSessionEntry 24 }

vRtrRsvpSessionBypassAvoid       OBJECT-TYPE
    SYNTAX      IpAddress
    MAX-ACCESS  read-only
    STATUS      current
    DESCRIPTION
        "vRtrRsvpSessionBypassAvoid is the router ID of the immediate
         downstream node or the IP address of the link that the PLR is trying
         to avoid."
    ::= { vRtrRsvpSessionEntry 25 }

vRtrRsvpSessionBypassActive      OBJECT-TYPE
    SYNTAX      TruthValue
    MAX-ACCESS  read-only
    STATUS      current
    DESCRIPTION
        "The value of vRtrRsvpSessionBypassActive is 'true', if a protected LSP
         is actively using the bypass tunnel represented by this RSVP session."
    ::= { vRtrRsvpSessionEntry 26 }

vRtrRsvpSessionBypassDnstrmLabel OBJECT-TYPE
    SYNTAX      MplsLabel
    MAX-ACCESS  read-only
    STATUS      current
    DESCRIPTION
        "If the LSP associated with this RSVP session is protected by a bypass
         tunnel (vRtrRsvpSessionBypassIndex for the session is a non-zero
         value), then vRtrRsvpSessionBypassDnstrmLabel is the ingress label
         that the Merge Point advertises for the LSP."
    ::= { vRtrRsvpSessionEntry 27 }

vRtrRsvpSessionSubGrpId          OBJECT-TYPE
    SYNTAX      Unsigned32
    MAX-ACCESS  read-only
    STATUS      current
    DESCRIPTION
        "The value of vRtrRsvpSessionSubGrpId indicates the identifier for sub
         group."
    ::= { vRtrRsvpSessionEntry 28 }

vRtrRsvpSessionSubGrpOrgIdType   OBJECT-TYPE
    SYNTAX      InetAddressType
    MAX-ACCESS  read-only
    STATUS      current
    DESCRIPTION
        "The value of vRtrRsvpSessionSubGrpOrgIdType indicates the type of
         vRtrRsvpSessionSubGrpOrgIdAddr."
    ::= { vRtrRsvpSessionEntry 29 }

vRtrRsvpSessionSubGrpOrgIdAddr   OBJECT-TYPE
    SYNTAX      InetAddress (SIZE (0|4))
    MAX-ACCESS  read-only
    STATUS      current
    DESCRIPTION
        "The value of vRtrRsvpSessionSubGrpOrgIdAddr indicates the IP address
         of the sub group originator. "
    ::= { vRtrRsvpSessionEntry 30 }

vRtrRsvpSessionLeafAddrType      OBJECT-TYPE
    SYNTAX      InetAddressType
    MAX-ACCESS  read-only
    STATUS      current
    DESCRIPTION
        "The value of vRtrRsvpSessionLeafAddrType indicates the type of
         vRtrRsvpSessionLeafAddr."
    ::= { vRtrRsvpSessionEntry 31 }

vRtrRsvpSessionLeafAddr          OBJECT-TYPE
    SYNTAX      InetAddress (SIZE (0|4))
    MAX-ACCESS  read-only
    STATUS      current
    DESCRIPTION
        "The value of vRtrRsvpSessionLeafAddr indicates the IP address of the
         leaf address."
    ::= { vRtrRsvpSessionEntry 32 }

vRtrRsvpSessionP2mpId            OBJECT-TYPE
    SYNTAX      Unsigned32
    MAX-ACCESS  read-only
    STATUS      current
    DESCRIPTION
        "The value of vRtrRsvpSessionP2mpId indicates a unique identifier known
         as point to multipoint (P2MP) identifier (ID)."
    ::= { vRtrRsvpSessionEntry 33 }

vRtrRsvpSessionClassType         OBJECT-TYPE
    SYNTAX      TmnxRsvpDSTEClassType
    MAX-ACCESS  read-only
    STATUS      current
    DESCRIPTION
        "The value of vRtrRsvpSessionClassType indicates the class type for
         this RSVP session."
    ::= { vRtrRsvpSessionEntry 34 }

vRtrRsvpSessionFrrProperties     OBJECT-TYPE
    SYNTAX      BITS {
        srlgNotStrict (0),
        srlgDisjoint  (1)
    }
    MAX-ACCESS  read-only
    STATUS      current
    DESCRIPTION
        "The value of vRtrRsvpSessionFrrProperties indicates criteria or
         constraints that were used at the time of computation of the FRR
         bypass tunnel or detour session associated with any primary LSP path
         on the system. This is applicable only for sessions being protected by
         FRR bypass tunnels or detours.

         Currently vRtrRsvpSessionFrrProperties has bits defined for SRLG
         properties only as follows:

         srlgNotStrict       - If set, implies that SRLG is Not Strict
         srlgDisjoint        - If set, implies that SRLG is Disjoint"
    ::= { vRtrRsvpSessionEntry 35 }

vRtrRsvpSessionExNodeAddrType    OBJECT-TYPE
    SYNTAX      InetAddressType
    MAX-ACCESS  read-only
    STATUS      current
    DESCRIPTION
        "The value of vRtrRsvpSessionExNodeAddrType indicates the type of
         vRtrRsvpSessionExNodeAddr."
    ::= { vRtrRsvpSessionEntry 36 }

vRtrRsvpSessionExNodeAddr        OBJECT-TYPE
    SYNTAX      InetAddress (SIZE (0|4))
    MAX-ACCESS  read-only
    STATUS      current
    DESCRIPTION
        "The value of vRtrRsvpSessionExNodeAddr indicates the address of the
         node to be avoided as signaled in the EXCLUDE_ROUTE object(XRO). If no
         XRO is signaled, this address will be 0.0.0.0."
    ::= { vRtrRsvpSessionEntry 37 }

vRtrRsvpSessionBypassInterArea   OBJECT-TYPE
    SYNTAX      TruthValue
    MAX-ACCESS  read-only
    STATUS      current
    DESCRIPTION
        "The value of vRtrRsvpSessionBypassInterArea indicates whether the
         bypass tunnel is either inter-area or intra-area.

         This value of vRtrRsvpSessionBypassInterArea is applicable only when
         the value of vRtrRsvpSessionType is 'bypassTunnel', 'manualBypass' or
         's2lBypassTunnel'."
    ::= { vRtrRsvpSessionEntry 38 }

vRtrRsvpSessionBypassPathCost    OBJECT-TYPE
    SYNTAX      Unsigned32
    MAX-ACCESS  read-only
    STATUS      current
    DESCRIPTION
        "The value of vRtrRsvpSessionBypassPathCost indicates the path cost for
         this bypass tunnel."
    ::= { vRtrRsvpSessionEntry 39 }

vRtrRsvpSessBypLastResigAttempt  OBJECT-TYPE
    SYNTAX      TimeStamp
    MAX-ACCESS  read-only
    STATUS      current
    DESCRIPTION
        "The value of vRtrRsvpSessBypLastResigAttempt indicates the sysUpTime
         when an attempt was last made to resignal this bypass tunnel."
    ::= { vRtrRsvpSessionEntry 40 }

vRtrRsvpSessBypLastResigReason   OBJECT-TYPE
    SYNTAX      INTEGER {
        none           (0),
        timerExpiry    (1),
        manualResignal (2)
    }
    MAX-ACCESS  read-only
    STATUS      current
    DESCRIPTION
        "The value of vRtrRsvpSessBypLastResigReason indicates the reason for
         the last resignal attempt for this bypass tunnel."
    ::= { vRtrRsvpSessionEntry 41 }

vRtrRsvpSessBypLastResigStatus   OBJECT-TYPE
    SYNTAX      INTEGER {
        none         (0),
        notAttempted (1),
        failed       (2),
        successful   (3)
    }
    MAX-ACCESS  read-only
    STATUS      current
    DESCRIPTION
        "The value of vRtrRsvpSessBypLastResigStatus indicates the status of
         the last resignal attempt for this bypass tunnel."
    ::= { vRtrRsvpSessionEntry 42 }

vRtrRsvpSBLastResigStatusReason  OBJECT-TYPE
    SYNTAX      INTEGER {
        none                (0),
        pathOptimal         (1),
        noConnectedPlrs     (2),
        nodeProtRetryInProg (3),
        resignalInProg      (4),
        nodeProtRetryBypass (5),
        resignalBypass      (6),
        cspfFailed          (7),
        setupFailed         (8)
    }
    MAX-ACCESS  read-only
    STATUS      current
    DESCRIPTION
        "The value of vRtrRsvpSBLastResigStatusReason indicates the reason why
         the last resignal attempt for this bypass tunnel was not attempted or
         failed."
    ::= { vRtrRsvpSessionEntry 43 }

vRtrRsvpSessionLspAttributeFlags OBJECT-TYPE
    SYNTAX      BITS {
        reserved0 (0),
        reserved1 (1),
        reserved2 (2),
        reserved3 (3),
        reserved4 (4),
        reserved5 (5),
        reserved6 (6),
        reserved7 (7),
        reserved8 (8),
        elc       (9)
    }
    MAX-ACCESS  read-only
    STATUS      current
    DESCRIPTION
        "The value of vRtrRsvpSessionLspAttributeFlags indicates the set of
         properties for LSP Attribute for this RSVP Session.

         The bits are defined as follows :

         elc - If set, implies that entropy label capability is enabled on the
               remote end."
    ::= { vRtrRsvpSessionEntry 44 }

vRtrRsvpSessionStatTable         OBJECT-TYPE
    SYNTAX      SEQUENCE OF VRtrRsvpSessionStatEntry
    MAX-ACCESS  not-accessible
    STATUS      current
    DESCRIPTION
        "The vRtrRsvpSessionStatTable contains statistics for an RSVP session."
    ::= { tmnxRsvpObjs 6 }

vRtrRsvpSessionStatEntry         OBJECT-TYPE
    SYNTAX      VRtrRsvpSessionStatEntry
    MAX-ACCESS  not-accessible
    STATUS      current
    DESCRIPTION
        "Each row entry represents a collection of statistics for an RSVP
         session.

         Entries cannot be created and deleted via SNMP SET operations."
    AUGMENTS    { vRtrRsvpSessionEntry }
    ::= { vRtrRsvpSessionStatTable 1 }

VRtrRsvpSessionStatEntry         ::= SEQUENCE
{
    vRtrRsvpSessionTxPaths           Counter64,
    vRtrRsvpSessionRxPaths           Counter64,
    vRtrRsvpSessionTxResvs           Counter64,
    vRtrRsvpSessionRxResvs           Counter64,
    vRtrRsvpSessionDetourTimeUp      TimeInterval,
    vRtrRsvpSessionDetourAge         TimeInterval,
    vRtrRsvpSessionBypassTimeUp      TimeInterval,
    vRtrRsvpSessionBypassAge         TimeInterval,
    vRtrRsvpSessionBypassLspCount    Gauge32,
    vRtrRsvpSessionTxSrefreshPaths   Counter64,
    vRtrRsvpSessionRxSrefreshPaths   Counter64,
    vRtrRsvpSessionTxSrefreshResvs   Counter64,
    vRtrRsvpSessionRxSrefreshResvs   Counter64
}

vRtrRsvpSessionTxPaths           OBJECT-TYPE
    SYNTAX      Counter64
    MAX-ACCESS  read-only
    STATUS      current
    DESCRIPTION
        "The total number of RSVP PATH messages transmitted for this RSVP
         session."
    ::= { vRtrRsvpSessionStatEntry 1 }

vRtrRsvpSessionRxPaths           OBJECT-TYPE
    SYNTAX      Counter64
    MAX-ACCESS  read-only
    STATUS      current
    DESCRIPTION
        "The total number of RSVP PATH messages received for this RSVP session."
    ::= { vRtrRsvpSessionStatEntry 2 }

vRtrRsvpSessionTxResvs           OBJECT-TYPE
    SYNTAX      Counter64
    MAX-ACCESS  read-only
    STATUS      current
    DESCRIPTION
        "The total number of RSVP RESV messages transmitted for this RSVP
         session."
    ::= { vRtrRsvpSessionStatEntry 3 }

vRtrRsvpSessionRxResvs           OBJECT-TYPE
    SYNTAX      Counter64
    MAX-ACCESS  read-only
    STATUS      current
    DESCRIPTION
        "The total number of RSVP RESV messages received for this RSVP session."
    ::= { vRtrRsvpSessionStatEntry 4 }

vRtrRsvpSessionDetourTimeUp      OBJECT-TYPE
    SYNTAX      TimeInterval
    MAX-ACCESS  read-only
    STATUS      current
    DESCRIPTION
        "vRtrRsvpSessionDetourTimeUp is the total time in 10-millisecond units
         that the detour LSP has been operational."
    ::= { vRtrRsvpSessionStatEntry 5 }

vRtrRsvpSessionDetourAge         OBJECT-TYPE
    SYNTAX      TimeInterval
    MAX-ACCESS  read-only
    STATUS      current
    DESCRIPTION
        "vRtrRsvpSessionDetourAge  is the age (i.e., time from creation
         till now) of this detour LSP in 10-millisecond periods."
    ::= { vRtrRsvpSessionStatEntry 6 }

vRtrRsvpSessionBypassTimeUp      OBJECT-TYPE
    SYNTAX      TimeInterval
    MAX-ACCESS  read-only
    STATUS      current
    DESCRIPTION
        "vRtrRsvpSessionBypassTimeUp is the total time in 10-millisecond units
         that the bypass tunnel has been operational."
    ::= { vRtrRsvpSessionStatEntry 7 }

vRtrRsvpSessionBypassAge         OBJECT-TYPE
    SYNTAX      TimeInterval
    MAX-ACCESS  read-only
    STATUS      current
    DESCRIPTION
        "vRtrRsvpSessionBypassAge is the age (i.e., time from creation till
         now) of this bypass tunnel in 10-millisecond periods."
    ::= { vRtrRsvpSessionStatEntry 8 }

vRtrRsvpSessionBypassLspCount    OBJECT-TYPE
    SYNTAX      Gauge32
    MAX-ACCESS  read-only
    STATUS      current
    DESCRIPTION
        "vRtrRsvpSessionBypassLspCount indicates the number of LSPs that are
         protected by this bypass tunnel."
    ::= { vRtrRsvpSessionStatEntry 9 }

vRtrRsvpSessionTxSrefreshPaths   OBJECT-TYPE
    SYNTAX      Counter64
    MAX-ACCESS  read-only
    STATUS      current
    DESCRIPTION
        "The value of vRtrRsvpSessionTxSrefreshPaths indicates the number of
         times PATH refresh for the session was sent as a part of a Srefresh
         message."
    ::= { vRtrRsvpSessionStatEntry 10 }

vRtrRsvpSessionRxSrefreshPaths   OBJECT-TYPE
    SYNTAX      Counter64
    MAX-ACCESS  read-only
    STATUS      current
    DESCRIPTION
        "The value of vRtrRsvpSessionRxSrefreshPaths indicates the number of
         times PATH was refreshed using message ID from full PATH refresh or
         Srefresh message for this RSVP session."
    ::= { vRtrRsvpSessionStatEntry 11 }

vRtrRsvpSessionTxSrefreshResvs   OBJECT-TYPE
    SYNTAX      Counter64
    MAX-ACCESS  read-only
    STATUS      current
    DESCRIPTION
        "The value of vRtrRsvpSessionTxSrefreshResvs indicates the number of
         times RESV refresh for the session was sent as a part of a Srefresh
         message."
    ::= { vRtrRsvpSessionStatEntry 12 }

vRtrRsvpSessionRxSrefreshResvs   OBJECT-TYPE
    SYNTAX      Counter64
    MAX-ACCESS  read-only
    STATUS      current
    DESCRIPTION
        "The value of vRtrRsvpSessionRxSrefreshResvs indicates the number of
         times RESV was refreshed using message ID from full RESV refresh or
         Srefresh message for this RSVP session."
    ::= { vRtrRsvpSessionStatEntry 13 }

tmnxRsvpNotificationObjects      OBJECT IDENTIFIER ::= { tmnxRsvpObjs 7 }

vRtrRsvpIfNbrDownReasonCode      OBJECT-TYPE
    SYNTAX      INTEGER {
        linkDown         (1),
        helloTimedOut    (2),
        instanceMismatch (3),
        bfdDown          (4)
    }
    MAX-ACCESS  accessible-for-notify
    STATUS      current
    DESCRIPTION
        "Used by vRtrRsvpIfNbrStateDown notification,
         vRtrRsvpIfNbrDownReasonCode specifies the reason for a RSVP interface
         neighbor becoming inactive."
    ::= { tmnxRsvpNotificationObjects 1 }

vRtrRsvpPEFailOverReasonCode     OBJECT-TYPE
    SYNTAX      INTEGER {
        tunnelDown     (1),
        ufdSessionDown (2)
    }
    MAX-ACCESS  accessible-for-notify
    STATUS      current
    DESCRIPTION
        "Used by vRtrRsvpPEFailOverPriToStdBy notification.
         vRtrRsvpPEFailOverReasonCode specifies the reason for Provider Edge
         (PE) switch over."
    ::= { tmnxRsvpNotificationObjects 2 }

vRtrRsvpSessionTypeTable         OBJECT-TYPE
    SYNTAX      SEQUENCE OF VRtrRsvpSessionTypeEntry
    MAX-ACCESS  not-accessible
    STATUS      current
    DESCRIPTION
        "The vRtrRsvpSessionTypeTable is a read-only table that contains
         objects for reporting sessions associated with the RSVP protocol
         running in a virtual router.  This table is created at the same
         time entries in vRtrRsvpSessionTable are created.  This table
         serves the purpose of grouping together all the sessions of a
         particular type."
    ::= { tmnxRsvpObjs 8 }

vRtrRsvpSessionTypeEntry         OBJECT-TYPE
    SYNTAX      VRtrRsvpSessionTypeEntry
    MAX-ACCESS  not-accessible
    STATUS      current
    DESCRIPTION
        "Each row entry represents a session for the RSVP protocol within
         a virtual router.  Entries in this table cannot be created and
         deleted via SNMP SET operations.  An entry in this table is
         created by the agent when the RSVP protocol establishes a session.
         The entry is destroyed when the RSVP session is removed."
    INDEX       {
        vRtrID,
        vRtrRsvpSessionType,
        vRtrRsvpSessionIndex
    }
    ::= { vRtrRsvpSessionTypeTable 1 }

VRtrRsvpSessionTypeEntry         ::= SEQUENCE
{ vRtrRsvpSessionTypeName          TmnxRsvpSessionNameString }

vRtrRsvpSessionTypeName          OBJECT-TYPE
    SYNTAX      TmnxRsvpSessionNameString
    MAX-ACCESS  read-only
    STATUS      current
    DESCRIPTION
        "The value of vRtrRsvpSessionTypeName indicates vRtrRsvpSessionName,
         the administrative name assigned to this RSVP session by the agent."
    ::= { vRtrRsvpSessionTypeEntry 1 }

vRtrRsvpProtectedSessionTable    OBJECT-TYPE
    SYNTAX      SEQUENCE OF VRtrRsvpProtectedSessionEntry
    MAX-ACCESS  not-accessible
    STATUS      current
    DESCRIPTION
        "The vRtrRsvpProtectedSessionTable is a read-only table that contains
         objects for reporting sessions associated with the RSVP protocol
         running in a virtual router which are protected by bypass tunnel."
    ::= { tmnxRsvpObjs 9 }

vRtrRsvpProtectedSessionEntry    OBJECT-TYPE
    SYNTAX      VRtrRsvpProtectedSessionEntry
    MAX-ACCESS  not-accessible
    STATUS      current
    DESCRIPTION
        "Each row entry represents a session that is protected by a bypass
         tunnel associated with the RSVP protocol running in a virtual
         router.  Entries in this table cannot be created and deleted via
         SNMP SET operations.  An entry in this table is created by the agent
         when an RSVP session is associated with a bypass tunnel that can
         protect it.  The entry is destroyed when the association is
         removed, which happens when either the session itself goes down
         or the bypass tunnel that is protecting it goes down."
    INDEX       {
        vRtrID,
        vRtrRsvpSessionIndex,
        vRtrRsvpProtectedSessionPLRIndex,
        vRtrRsvpProtectedSessionSessIndex
    }
    ::= { vRtrRsvpProtectedSessionTable 1 }

VRtrRsvpProtectedSessionEntry    ::= SEQUENCE
{
    vRtrRsvpProtectedSessionPLRIndex Unsigned32,
    vRtrRsvpProtectedSessionSessIndex Unsigned32,
    vRtrRsvpProtectedSessionName     TmnxRsvpSessionNameString
}

vRtrRsvpProtectedSessionPLRIndex OBJECT-TYPE
    SYNTAX      Unsigned32
    MAX-ACCESS  not-accessible
    STATUS      current
    DESCRIPTION
        "vRtrRsvpProtectedSessionPLRIndex is a unique number that identifies an
         instance of protection provided by the bypass tunnel."
    ::= { vRtrRsvpProtectedSessionEntry 1 }

vRtrRsvpProtectedSessionSessIndex OBJECT-TYPE
    SYNTAX      Unsigned32
    MAX-ACCESS  not-accessible
    STATUS      current
    DESCRIPTION
        "vRtrRsvpProtectedSessionSessIndex is the vRtrRsvpSessionIndex for the
         session protected by this bypass tunnel"
    ::= { vRtrRsvpProtectedSessionEntry 2 }

vRtrRsvpProtectedSessionName     OBJECT-TYPE
    SYNTAX      TmnxRsvpSessionNameString
    MAX-ACCESS  read-only
    STATUS      current
    DESCRIPTION
        "The value of vRtrRsvpProtectedSessionName indicates
         vRtrRsvpSessionName, the administrative name assigned to this RSVP
         session by the agent."
    ::= { vRtrRsvpProtectedSessionEntry 3 }

vRtrRsvpNbrTable                 OBJECT-TYPE
    SYNTAX      SEQUENCE OF VRtrRsvpNbrEntry
    MAX-ACCESS  not-accessible
    STATUS      current
    DESCRIPTION
        "The vRtrRsvpNbrTable is a read-only table that contains objects
         describing the neighbors associated with the RSVP protocol running in
         a virtual router."
    ::= { tmnxRsvpObjs 10 }

vRtrRsvpNbrEntry                 OBJECT-TYPE
    SYNTAX      VRtrRsvpNbrEntry
    MAX-ACCESS  not-accessible
    STATUS      current
    DESCRIPTION
        "Each row entry represents a single RSVP neighbor associated
         with the RSVP protocol running in a virtual router.  Entries
         in this table cannot be created and deleted via SNMP SET
         operations.  An entry in this table is created by the agent
         when an RSVP neighbor comes up.  The entry is destroyed when
         the neighbor goes down."
    INDEX       {
        vRtrID,
        vRtrRsvpIfVRtrIfIndex,
        vRtrRsvpNbrAddressType,
        vRtrRsvpNbrAddress
    }
    ::= { vRtrRsvpNbrTable 1 }

VRtrRsvpNbrEntry                 ::= SEQUENCE
{
    vRtrRsvpNbrAddressType           InetAddressType,
    vRtrRsvpNbrAddress               InetAddress,
    vRtrRsvpNbrOperState             TmnxOperState,
    vRtrRsvpNbrLastOperChange        TimeInterval,
    vRtrRsvpNbrFlags                 BITS,
    vRtrRsvpNbrSrcInstance           Unsigned32,
    vRtrRsvpNbrDstInstance           Unsigned32,
    vRtrRsvpNbrHelloRefreshTimeRem   Unsigned32,
    vRtrRsvpNbrHelloTimeoutTimeRem   Unsigned32,
    vRtrRsvpNbrHelloTimeoutCnt       Counter32,
    vRtrRsvpNbrInstanceMismatchCnt   Counter32,
    vRtrRsvpNbrSrefreshTimeRem       Unsigned32,
    vRtrRsvpNbrEpochNum              Unsigned32,
    vRtrRsvpNbrMaxMsgId              Unsigned32,
    vRtrRsvpNbrOutofOrderMsgs        Counter32,
    vRtrRsvpNbrRetransmittedMsgs     Counter32,
    vRtrRsvpNbrGrState               INTEGER,
    vRtrRsvpNbrGrHelperInvkCnt       Counter32,
    vRtrRsvpNbrGrHelperTimeRem       Unsigned32,
    vRtrRsvpNbrGrRestartCap          TruthValue,
    vRtrRsvpNbrGrRestartTime         Unsigned32,
    vRtrRsvpNbrGrRecoveryTime        Unsigned32
}

vRtrRsvpNbrAddressType           OBJECT-TYPE
    SYNTAX      InetAddressType
    MAX-ACCESS  not-accessible
    STATUS      current
    DESCRIPTION
        "The value of vRtrRsvpNbrAddressType indicates the type of
         vRtrRsvpNbrAddress. "
    ::= { vRtrRsvpNbrEntry 1 }

vRtrRsvpNbrAddress               OBJECT-TYPE
    SYNTAX      InetAddress (SIZE (4|16))
    MAX-ACCESS  not-accessible
    STATUS      current
    DESCRIPTION
        "The value of vRtrRsvpNbrAddress indicates the address of the RSVP
         neighbor."
    ::= { vRtrRsvpNbrEntry 2 }

vRtrRsvpNbrOperState             OBJECT-TYPE
    SYNTAX      TmnxOperState
    MAX-ACCESS  read-only
    STATUS      current
    DESCRIPTION
        "The value of vRtrRsvpNbrOperState indicates the current operational
         state of the RSVP neighbor."
    ::= { vRtrRsvpNbrEntry 3 }

vRtrRsvpNbrLastOperChange        OBJECT-TYPE
    SYNTAX      TimeInterval
    MAX-ACCESS  read-only
    STATUS      current
    DESCRIPTION
        "The value of vRtrRsvpNbrLastOperChange indicates the time interval
         which has elapsed since the RSVP neighbor's operational state last
         changed."
    ::= { vRtrRsvpNbrEntry 4 }

vRtrRsvpNbrFlags                 OBJECT-TYPE
    SYNTAX      BITS {
        localRefreshReduction  (0),
        localReliableDelivery  (1),
        remoteRefreshReduction (2),
        remoteMessageId        (3)
    }
    MAX-ACCESS  read-only
    STATUS      current
    DESCRIPTION
        "The value of vRtrRsvpNbrFlags indicates the set of properties for this
         RSVP neighbor. The bits are defined as follows :

         localRefreshReduction  - If set, implies that refresh reduction is
                                  configured locally for this neighbor.
         localReliableDelivery  - If set, implies that reliable delivery is
                                  configured locally for this neighbor.
         remoteRefreshReduction - If set, implies that the refresh reduction
                                  is supported on the remote end.
         remoteMessageId        - If set, implies that message ID object is
                                  supported on the remote end."
    ::= { vRtrRsvpNbrEntry 5 }

vRtrRsvpNbrSrcInstance           OBJECT-TYPE
    SYNTAX      Unsigned32
    MAX-ACCESS  read-only
    STATUS      current
    DESCRIPTION
        "The value of vRtrRsvpNbrSrcInstance indicates the source instance for
         this neighbor."
    ::= { vRtrRsvpNbrEntry 6 }

vRtrRsvpNbrDstInstance           OBJECT-TYPE
    SYNTAX      Unsigned32
    MAX-ACCESS  read-only
    STATUS      current
    DESCRIPTION
        "The value of vRtrRsvpNbrDstInstance indicates the destination instance
         for this neighbor."
    ::= { vRtrRsvpNbrEntry 7 }

vRtrRsvpNbrHelloRefreshTimeRem   OBJECT-TYPE
    SYNTAX      Unsigned32
    UNITS       "seconds"
    MAX-ACCESS  read-only
    STATUS      current
    DESCRIPTION
        "The value of vRtrRsvpNbrHelloRefreshTimeRem indicates the time
         remaining in the hello refresh timer. When the hello refresh timer
         expires, a Hello message is sent to the neighbor."
    ::= { vRtrRsvpNbrEntry 8 }

vRtrRsvpNbrHelloTimeoutTimeRem   OBJECT-TYPE
    SYNTAX      Unsigned32
    UNITS       "seconds"
    MAX-ACCESS  read-only
    STATUS      current
    DESCRIPTION
        "The value of vRtrRsvpNbrHelloTimeoutTimeRem indicates the time
         remaining in the hello timeout timer. If a Hello message is not
         received from the neighbor before this timer expires, the neighbor is
         considered operationally down."
    ::= { vRtrRsvpNbrEntry 9 }

vRtrRsvpNbrHelloTimeoutCnt       OBJECT-TYPE
    SYNTAX      Counter32
    MAX-ACCESS  read-only
    STATUS      current
    DESCRIPTION
        "The value of vRtrRsvpNbrHelloTimeoutCnt indicates number of times the
         hello timeout timer expired for the neighbor."
    ::= { vRtrRsvpNbrEntry 10 }

vRtrRsvpNbrInstanceMismatchCnt   OBJECT-TYPE
    SYNTAX      Counter32
    MAX-ACCESS  read-only
    STATUS      current
    DESCRIPTION
        "The value of vRtrRsvpNbrInstanceMismatchCnt indicates number of times
         the source and destination instances received in a Hello message did
         not match the destination and source instance for this neighbor."
    ::= { vRtrRsvpNbrEntry 11 }

vRtrRsvpNbrSrefreshTimeRem       OBJECT-TYPE
    SYNTAX      Unsigned32
    UNITS       "seconds"
    MAX-ACCESS  read-only
    STATUS      current
    DESCRIPTION
        "The value of vRtrRsvpNbrSrefreshTimeRem indicates the time remaining
         in the Srefresh timer. An Srefresh message is sent when this timer
         expires."
    ::= { vRtrRsvpNbrEntry 12 }

vRtrRsvpNbrEpochNum              OBJECT-TYPE
    SYNTAX      Unsigned32
    MAX-ACCESS  read-only
    STATUS      current
    DESCRIPTION
        "The value of vRtrRsvpNbrEpochNum indicates the epoch number received
         from the neighbor."
    ::= { vRtrRsvpNbrEntry 13 }

vRtrRsvpNbrMaxMsgId              OBJECT-TYPE
    SYNTAX      Unsigned32
    MAX-ACCESS  read-only
    STATUS      current
    DESCRIPTION
        "The value of vRtrRsvpNbrMaxMsgId indicates the highest message ID
         received from neighbor."
    ::= { vRtrRsvpNbrEntry 14 }

vRtrRsvpNbrOutofOrderMsgs        OBJECT-TYPE
    SYNTAX      Counter32
    MAX-ACCESS  read-only
    STATUS      current
    DESCRIPTION
        "The value of vRtrRsvpNbrOutofOrderMsgs indicates the number of out of
         order messages received from the neighbor."
    ::= { vRtrRsvpNbrEntry 15 }

vRtrRsvpNbrRetransmittedMsgs     OBJECT-TYPE
    SYNTAX      Counter32
    MAX-ACCESS  read-only
    STATUS      current
    DESCRIPTION
        "The value of vRtrRsvpNbrRetransmittedMsgs indicates the number of
         times messages have been retransmitted to the neighbor because the
         neighbor did not acknowledge that it received the message."
    ::= { vRtrRsvpNbrEntry 16 }

vRtrRsvpNbrGrState               OBJECT-TYPE
    SYNTAX      INTEGER {
        none           (0),
        restartInProg  (1),
        recoveryInProg (2),
        cleanup        (3)
    }
    MAX-ACCESS  read-only
    STATUS      current
    DESCRIPTION
        "The value of vRtrRsvpNbrGrState indicates the current state of the
         neighbor after loss of communication.

         none            - phase info not available.
         restartInProg   - indicates restart phase is in progress
         recoveryInProg  - indicates recovery phase is in progress
         cleanup         - indicates cleanup in progress."
    ::= { vRtrRsvpNbrEntry 17 }

vRtrRsvpNbrGrHelperInvkCnt       OBJECT-TYPE
    SYNTAX      Counter32
    MAX-ACCESS  read-only
    STATUS      current
    DESCRIPTION
        "The value of vRtrRsvpNbrGrHelperInvkCnt indicates the number of times
         that GR helper procedure has been invoked."
    ::= { vRtrRsvpNbrEntry 18 }

vRtrRsvpNbrGrHelperTimeRem       OBJECT-TYPE
    SYNTAX      Unsigned32
    UNITS       "seconds"
    MAX-ACCESS  read-only
    STATUS      current
    DESCRIPTION
        "The value of vRtrRsvpNbrGrHelperTimeRem indicates the amount of time
         remaining, in seconds, for the restart phase or recovery phase to
         timeout.  If the timer expires, the RSVP session not recovered will be
         torn down.

         The value of vRtrRsvpNbrGrHelperTimeRem will only be valid when
         vRtrRsvpIfGraceHelper is set to 'true'."
    ::= { vRtrRsvpNbrEntry 19 }

vRtrRsvpNbrGrRestartCap          OBJECT-TYPE
    SYNTAX      TruthValue
    MAX-ACCESS  read-only
    STATUS      current
    DESCRIPTION
        "The value of vRtrRsvpNbrGrRestartCap indicates whether or not the
         neighbor supports graceful restart.

         The value of vRtrRsvpNbrGrRestartCap will only be valid when
         vRtrRsvpIfGraceHelper is set to 'true'."
    ::= { vRtrRsvpNbrEntry 20 }

vRtrRsvpNbrGrRestartTime         OBJECT-TYPE
    SYNTAX      Unsigned32
    UNITS       "milliseconds"
    MAX-ACCESS  read-only
    STATUS      current
    DESCRIPTION
        "The value of vRtrRsvpNbrGrRestartTime indicates the restart timer
         advertised by the neighbor.

         The value of vRtrRsvpNbrGrRestartTime will only be valid when
         vRtrRsvpIfGraceHelper is set to 'true' and when
         vRtrRsvpNbrGrRestartCap has value of 'true'."
    ::= { vRtrRsvpNbrEntry 21 }

vRtrRsvpNbrGrRecoveryTime        OBJECT-TYPE
    SYNTAX      Unsigned32
    UNITS       "milliseconds"
    MAX-ACCESS  read-only
    STATUS      current
    DESCRIPTION
        "The value of vRtrRsvpNbrGrRecoveryTime indicates the recovery timer
         advertised by the neighbor.

         The value of vRtrRsvpNbrGrRecoveryTime will only be valid when
         vRtrRsvpIfGraceHelper is set to 'true' and when
         vRtrRsvpNbrGrRestartCap has value of 'true'."
    ::= { vRtrRsvpNbrEntry 22 }

vRtrRsvpIfDSTETable              OBJECT-TYPE
    SYNTAX      SEQUENCE OF VRtrRsvpIfDSTEEntry
    MAX-ACCESS  not-accessible
    STATUS      current
    DESCRIPTION
        "The vRtrRsvpIfDSTETable is a read-only table that contains objects
         related to Differentiated Services Traffic Engineering (DSTE) feature
         associated with the RSVP protocol running on a virtual router
         interface. Row entries in this table are created by the agent when the
         interface is created. This table always contain eight rows; each row
         corresponds to a TE class."
    ::= { tmnxRsvpObjs 11 }

vRtrRsvpIfDSTEEntry              OBJECT-TYPE
    SYNTAX      VRtrRsvpIfDSTEEntry
    MAX-ACCESS  not-accessible
    STATUS      current
    DESCRIPTION
        "Each row entry represents a vRtrRsvpIfDSTEEntry of the RSVP protocol
         running on a virtual router interface.  Entries in this table cannot
         be created and deleted via SNMP SET operations."
    INDEX       {
        vRtrID,
        vRtrIfIndex,
        vRtrRsvpIfDSTETEClass
    }
    ::= { vRtrRsvpIfDSTETable 1 }

VRtrRsvpIfDSTEEntry              ::= SEQUENCE
{
    vRtrRsvpIfDSTETEClass            TmnxRsvpDSTETeClass,
    vRtrRsvpIfDSTEReservedBw         Counter64,
    vRtrRsvpIfDSTEUnreservedBw       Counter64
}

vRtrRsvpIfDSTETEClass            OBJECT-TYPE
    SYNTAX      TmnxRsvpDSTETeClass
    MAX-ACCESS  not-accessible
    STATUS      current
    DESCRIPTION
        "The value of vRtrRsvpIfDSTETEClass indicates the unique value that
         identifies the traffic engineering (TE) class for this row entry."
    ::= { vRtrRsvpIfDSTEEntry 1 }

vRtrRsvpIfDSTEReservedBw         OBJECT-TYPE
    SYNTAX      Counter64
    UNITS       "kilobps"
    MAX-ACCESS  read-only
    STATUS      current
    DESCRIPTION
        "The value of vRtrRsvpIfDSTEReservedBw indicates the amount of
         bandwidth in kilobits per second (Kbps) that is currently reserved
         by the RSVP sessions on this interface.  A value of zero (0)
         indicates that no bandwidth is reserved."
    ::= { vRtrRsvpIfDSTEEntry 2 }

vRtrRsvpIfDSTEUnreservedBw       OBJECT-TYPE
    SYNTAX      Counter64
    UNITS       "kilobps"
    MAX-ACCESS  read-only
    STATUS      current
    DESCRIPTION
        "The value of vRtrRsvpIfDSTEUnreservedBw indicates the unreserved
         bandwidth for each TE class. "
    ::= { vRtrRsvpIfDSTEEntry 3 }

vRtrRsvpDSTETeClassTable         OBJECT-TYPE
    SYNTAX      SEQUENCE OF VRtrRsvpDSTETeClassEntry
    MAX-ACCESS  not-accessible
    STATUS      current
    DESCRIPTION
        "The vRtrRsvpDSTETeClassTable is a table that contains objects related
         to traffic engineering (TE) classes for Differentiated Services
         Traffic Engineering (DSTE) feature associated with the RSVP protocol
         running in a virtual router. "
    ::= { tmnxRsvpObjs 12 }

vRtrRsvpDSTETeClassEntry         OBJECT-TYPE
    SYNTAX      VRtrRsvpDSTETeClassEntry
    MAX-ACCESS  not-accessible
    STATUS      current
    DESCRIPTION
        "Each row entry represents a TE Class entry within a virtual router.
         Entries in this table cannot be created and deleted via SNMP
         operations, they can be read and modified through SNMP GET and SET
         operations. Row entries are created by the agent when the RSVP
         protocol is created. There are always 8 entries in this table, one for
         each TE class."
    INDEX       {
        vRtrID,
        vRtrRsvpDSTETeClass
    }
    ::= { vRtrRsvpDSTETeClassTable 1 }

VRtrRsvpDSTETeClassEntry         ::= SEQUENCE
{
    vRtrRsvpDSTETeClass              TmnxRsvpDSTETeClass,
    vRtrRsvpDSTETeClassClassType     Integer32,
    vRtrRsvpDSTETeClassPriority      Integer32
}

vRtrRsvpDSTETeClass              OBJECT-TYPE
    SYNTAX      TmnxRsvpDSTETeClass
    MAX-ACCESS  not-accessible
    STATUS      current
    DESCRIPTION
        "The value of vRtrRsvpDSTETeClass indicates the unique value that
         identifies the TE class."
    ::= { vRtrRsvpDSTETeClassEntry 1 }

vRtrRsvpDSTETeClassClassType     OBJECT-TYPE
    SYNTAX      Integer32 (-1..7)
    MAX-ACCESS  read-write
    STATUS      current
    DESCRIPTION
        "The value of vRtrRsvpDSTETeClassClassType specifies the class
         type (CT) associated with the TE class.  Both
         vRtrRsvpDSTETeClassClassType and vRtrRsvpDSTETeClassPriority need
         to be set in the same PDU for a row to be created.  A value of -1
         indicates that the CT for this TE class is invalid and hence the
         TE class is considered as not configured."
    DEFVAL      { -1 }
    ::= { vRtrRsvpDSTETeClassEntry 2 }

vRtrRsvpDSTETeClassPriority      OBJECT-TYPE
    SYNTAX      Integer32 (-1..7)
    MAX-ACCESS  read-write
    STATUS      current
    DESCRIPTION
        "The value of vRtrRsvpDSTETeClassPriority specifies the priority
         associated with the TE class.  Both vRtrRsvpDSTETeClassClassType
         and vRtrRsvpDSTETeClassPriority need to be set in the same PDU for
         a row to be created. A value of -1 indicates that the priority for
         this TE class is invalid and hence the TE class is considered as not
         configured."
    DEFVAL      { -1 }
    ::= { vRtrRsvpDSTETeClassEntry 3 }

vRtrRsvpDSTETable                OBJECT-TYPE
    SYNTAX      SEQUENCE OF VRtrRsvpDSTEEntry
    MAX-ACCESS  not-accessible
    STATUS      current
    DESCRIPTION
        "The vRtrRsvpDSTETable contains objects related to Differentiated
         Services Traffic Engineering (DSTE) feature associated with the RSVP
         protocol running in a virtual router."
    ::= { tmnxRsvpObjs 13 }

vRtrRsvpDSTEEntry                OBJECT-TYPE
    SYNTAX      VRtrRsvpDSTEEntry
    MAX-ACCESS  not-accessible
    STATUS      current
    DESCRIPTION
        "Each row entry represents a vRtrRsvpDSTEEntry of the RSVP protocol
         within a virtual router.  Entries in this table cannot be
         created and deleted via SNMP SET operations.  An entry in this table
         is created when a row is created in vRtrRsvpGeneralTable."
    AUGMENTS    { vRtrRsvpGeneralEntry }
    ::= { vRtrRsvpDSTETable 1 }

VRtrRsvpDSTEEntry                ::= SEQUENCE
{
    vRtrRsvpDSTEAdmCtlModel          INTEGER,
    vRtrRsvpDSTECt0BwPercent         TmnxRsvpDSTEBwPercent,
    vRtrRsvpDSTECt1BwPercent         TmnxRsvpDSTEBwPercent,
    vRtrRsvpDSTECt2BwPercent         TmnxRsvpDSTEBwPercent,
    vRtrRsvpDSTECt3BwPercent         TmnxRsvpDSTEBwPercent,
    vRtrRsvpDSTECt4BwPercent         TmnxRsvpDSTEBwPercent,
    vRtrRsvpDSTECt5BwPercent         TmnxRsvpDSTEBwPercent,
    vRtrRsvpDSTECt6BwPercent         TmnxRsvpDSTEBwPercent,
    vRtrRsvpDSTECt7BwPercent         TmnxRsvpDSTEBwPercent
}

vRtrRsvpDSTEAdmCtlModel          OBJECT-TYPE
    SYNTAX      INTEGER {
        basic (0),
        mam   (1),
        rdm   (2)
    }
    MAX-ACCESS  read-create
    STATUS      current
    DESCRIPTION
        "The value of vRtrRsvpDSTEAdmCtlModel specifies the admission control
         model.

         basic (0) - 'DiffServ' TE is disabled,
         mam   (1) - 'DiffServ' TE is enabled with Maximum Allocation Model,
         rdm   (2) - 'DiffServ' TE is enabled with Russian Dolls Model."
    DEFVAL      { basic }
    ::= { vRtrRsvpDSTEEntry 1 }

vRtrRsvpDSTECt0BwPercent         OBJECT-TYPE
    SYNTAX      TmnxRsvpDSTEBwPercent
    MAX-ACCESS  read-create
    STATUS      current
    DESCRIPTION
        "The value of vRtrRsvpDSTECt0BwPercent specifies the percentage
         of the bandwidth assigned to CT 0. By default this value is
         inherited by all the interfaces unless it is explicitly configured
         for an interface.  When the value of vRtrRsvpDSTEAdmCtlModel is
         changed, vRtrRsvpDSTECt0BwPercent resets the default value
         specific to that admission control model.  The default value is
         100 for the 'basic' model and is 0 for 'mam' and 'rdm' models."
    DEFVAL      { 100 }
    ::= { vRtrRsvpDSTEEntry 2 }

vRtrRsvpDSTECt1BwPercent         OBJECT-TYPE
    SYNTAX      TmnxRsvpDSTEBwPercent
    MAX-ACCESS  read-create
    STATUS      current
    DESCRIPTION
        "The value of vRtrRsvpDSTECt1BwPercent specifies the percentage link
         bandwidth for CT 1.  Whenever the admission control model specified
         by vRtrRsvpDSTEAdmCtlModel changes, vRtrRsvpDSTECt1BwPercent is reset
         to default values for that specific admission control model.
         vRtrRsvpDSTECt1BwPercent resets to 0 for all values of
         vRtrRsvpDSTEAdmCtlModel."
    DEFVAL      { 0 }
    ::= { vRtrRsvpDSTEEntry 3 }

vRtrRsvpDSTECt2BwPercent         OBJECT-TYPE
    SYNTAX      TmnxRsvpDSTEBwPercent
    MAX-ACCESS  read-create
    STATUS      current
    DESCRIPTION
        "The value of vRtrRsvpDSTECt2BwPercent specifies the percentage link
         bandwidth for CT 2.  Whenever the admission control model specified by
         vRtrRsvpDSTEAdmCtlModel changes, vRtrRsvpDSTECt2BwPercent is reset
         to 0."
    DEFVAL      { 0 }
    ::= { vRtrRsvpDSTEEntry 4 }

vRtrRsvpDSTECt3BwPercent         OBJECT-TYPE
    SYNTAX      TmnxRsvpDSTEBwPercent
    MAX-ACCESS  read-create
    STATUS      current
    DESCRIPTION
        "The value of vRtrRsvpDSTECt3BwPercent specifies the percentage link
         bandwidth for CT 3.  Whenever the admission control model specified by
         vRtrRsvpDSTEAdmCtlModel changes, vRtrRsvpDSTECt3BwPercent is reset
         to 0."
    DEFVAL      { 0 }
    ::= { vRtrRsvpDSTEEntry 5 }

vRtrRsvpDSTECt4BwPercent         OBJECT-TYPE
    SYNTAX      TmnxRsvpDSTEBwPercent
    MAX-ACCESS  read-create
    STATUS      current
    DESCRIPTION
        "The value of vRtrRsvpDSTECt4BwPercent specifies the percentage link
         bandwidth for CT 4.  Whenever the admission control model specified by
         vRtrRsvpDSTEAdmCtlModel changes, vRtrRsvpDSTECt4BwPercent is reset
         to 0."
    DEFVAL      { 0 }
    ::= { vRtrRsvpDSTEEntry 6 }

vRtrRsvpDSTECt5BwPercent         OBJECT-TYPE
    SYNTAX      TmnxRsvpDSTEBwPercent
    MAX-ACCESS  read-create
    STATUS      current
    DESCRIPTION
        "The value of vRtrRsvpDSTECt5BwPercent specifies the percentage link
         bandwidth for CT 5.  Whenever the admission control model specified by
         vRtrRsvpDSTEAdmCtlModel changes, vRtrRsvpDSTECt5BwPercent is reset
         to 0."
    DEFVAL      { 0 }
    ::= { vRtrRsvpDSTEEntry 7 }

vRtrRsvpDSTECt6BwPercent         OBJECT-TYPE
    SYNTAX      TmnxRsvpDSTEBwPercent
    MAX-ACCESS  read-create
    STATUS      current
    DESCRIPTION
        "The value of vRtrRsvpDSTECt6BwPercent specifies the percentage link
         bandwidth for CT 6.  Whenever the admission control model specified by
         vRtrRsvpDSTEAdmCtlModel changes, vRtrRsvpDSTECt6BwPercent is reset
         to 0."
    DEFVAL      { 0 }
    ::= { vRtrRsvpDSTEEntry 8 }

vRtrRsvpDSTECt7BwPercent         OBJECT-TYPE
    SYNTAX      TmnxRsvpDSTEBwPercent
    MAX-ACCESS  read-create
    STATUS      current
    DESCRIPTION
        "The value of vRtrRsvpDSTECt7BwPercent specifies the percentage link
         bandwidth for CT 7.  Whenever the admission control model specified by
         vRtrRsvpDSTEAdmCtlModel changes, vRtrRsvpDSTECt7BwPercent is reset to
         0."
    DEFVAL      { 0 }
    ::= { vRtrRsvpDSTEEntry 9 }

vRtrRsvpDSTEFCMappingTable       OBJECT-TYPE
    SYNTAX      SEQUENCE OF VRtrRsvpDSTEFCMappingEntry
    MAX-ACCESS  not-accessible
    STATUS      current
    DESCRIPTION
        "The vRtrRsvpDSTEFCMappingTable has an entry for each Forwarding Class
         (FC) to Class Type (CT) mapping related to DSTE configured on this
         system."
    ::= { tmnxRsvpObjs 14 }

vRtrRsvpDSTEFCMappingEntry       OBJECT-TYPE
    SYNTAX      VRtrRsvpDSTEFCMappingEntry
    MAX-ACCESS  not-accessible
    STATUS      current
    DESCRIPTION
        "Each row entry represents a particular FC name to CT mapping. Entries
         are created/deleted by the user."
    INDEX       {
        vRtrID,
        vRtrRsvpDSTEFCMappingName
    }
    ::= { vRtrRsvpDSTEFCMappingTable 1 }

VRtrRsvpDSTEFCMappingEntry       ::= SEQUENCE
{
    vRtrRsvpDSTEFCMappingName        TNamedItem,
    vRtrRsvpDSTEFCMappingRowStatus   RowStatus,
    vRtrRsvpDSTEFCMappingClassType   TmnxRsvpDSTEClassType
}

vRtrRsvpDSTEFCMappingName        OBJECT-TYPE
    SYNTAX      TNamedItem
    MAX-ACCESS  not-accessible
    STATUS      current
    DESCRIPTION
        "The value of vRtrRsvpDSTEFCMappingName specifies the forwarding class
         for which this mapping is defined."
    ::= { vRtrRsvpDSTEFCMappingEntry 1 }

vRtrRsvpDSTEFCMappingRowStatus   OBJECT-TYPE
    SYNTAX      RowStatus
    MAX-ACCESS  read-create
    STATUS      current
    DESCRIPTION
        "The value of vRtrRsvpDSTEFCMappingRowStatus is used for the creation
         and deletion of forwarding class to class type mappings."
    ::= { vRtrRsvpDSTEFCMappingEntry 2 }

vRtrRsvpDSTEFCMappingClassType   OBJECT-TYPE
    SYNTAX      TmnxRsvpDSTEClassType
    MAX-ACCESS  read-create
    STATUS      current
    DESCRIPTION
        "The value of vRtrRsvpDSTEFCMappingClassType specifies the class type.
         This object MUST be specified at row creation time."
    ::= { vRtrRsvpDSTEFCMappingEntry 3 }

vRtrRsvpGenTEThresholdTable      OBJECT-TYPE
    SYNTAX      SEQUENCE OF VRtrRsvpGenTEThresholdEntry
    MAX-ACCESS  not-accessible
    STATUS      current
    DESCRIPTION
        "The vRtrRsvpGenTEThresholdTable contains objects related to up and
         down threshold levels each expressed as a percentage of available
         bandwidth."
    ::= { tmnxRsvpObjs 15 }

vRtrRsvpGenTEThresholdEntry      OBJECT-TYPE
    SYNTAX      VRtrRsvpGenTEThresholdEntry
    MAX-ACCESS  not-accessible
    STATUS      current
    DESCRIPTION
        "Each row entry represents a vRtrRsvpGenTEThresholdEntry of the RSVP
         protocol within a virtual router. An entry in this table is created
         when a row is created in the vRtrRsvpGeneralTable."
    AUGMENTS    { vRtrRsvpGeneralEntry }
    ::= { vRtrRsvpGenTEThresholdTable 1 }

VRtrRsvpGenTEThresholdEntry      ::= SEQUENCE
{
    vRtrRsvpGenTEThresholdLevelUp1   TmnxRsvpTEThresholdLevel,
    vRtrRsvpGenTEThresholdLevelUp2   TmnxRsvpTEThresholdLevel,
    vRtrRsvpGenTEThresholdLevelUp3   TmnxRsvpTEThresholdLevel,
    vRtrRsvpGenTEThresholdLevelUp4   TmnxRsvpTEThresholdLevel,
    vRtrRsvpGenTEThresholdLevelUp5   TmnxRsvpTEThresholdLevel,
    vRtrRsvpGenTEThresholdLevelUp6   TmnxRsvpTEThresholdLevel,
    vRtrRsvpGenTEThresholdLevelUp7   TmnxRsvpTEThresholdLevel,
    vRtrRsvpGenTEThresholdLevelUp8   TmnxRsvpTEThresholdLevel,
    vRtrRsvpGenTEThresholdLevelUp9   TmnxRsvpTEThresholdLevel,
    vRtrRsvpGenTEThresholdLevelUp10  TmnxRsvpTEThresholdLevel,
    vRtrRsvpGenTEThresholdLevelUp11  TmnxRsvpTEThresholdLevel,
    vRtrRsvpGenTEThresholdLevelUp12  TmnxRsvpTEThresholdLevel,
    vRtrRsvpGenTEThresholdLevelUp13  TmnxRsvpTEThresholdLevel,
    vRtrRsvpGenTEThresholdLevelUp14  TmnxRsvpTEThresholdLevel,
    vRtrRsvpGenTEThresholdLevelUp15  TmnxRsvpTEThresholdLevel,
    vRtrRsvpGenTEThresholdLevelUp16  TmnxRsvpTEThresholdLevel,
    vRtrRsvpGenTEThresholdLevelDn1   TmnxRsvpTEThresholdLevel,
    vRtrRsvpGenTEThresholdLevelDn2   TmnxRsvpTEThresholdLevel,
    vRtrRsvpGenTEThresholdLevelDn3   TmnxRsvpTEThresholdLevel,
    vRtrRsvpGenTEThresholdLevelDn4   TmnxRsvpTEThresholdLevel,
    vRtrRsvpGenTEThresholdLevelDn5   TmnxRsvpTEThresholdLevel,
    vRtrRsvpGenTEThresholdLevelDn6   TmnxRsvpTEThresholdLevel,
    vRtrRsvpGenTEThresholdLevelDn7   TmnxRsvpTEThresholdLevel,
    vRtrRsvpGenTEThresholdLevelDn8   TmnxRsvpTEThresholdLevel,
    vRtrRsvpGenTEThresholdLevelDn9   TmnxRsvpTEThresholdLevel,
    vRtrRsvpGenTEThresholdLevelDn10  TmnxRsvpTEThresholdLevel,
    vRtrRsvpGenTEThresholdLevelDn11  TmnxRsvpTEThresholdLevel,
    vRtrRsvpGenTEThresholdLevelDn12  TmnxRsvpTEThresholdLevel,
    vRtrRsvpGenTEThresholdLevelDn13  TmnxRsvpTEThresholdLevel,
    vRtrRsvpGenTEThresholdLevelDn14  TmnxRsvpTEThresholdLevel,
    vRtrRsvpGenTEThresholdLevelDn15  TmnxRsvpTEThresholdLevel,
    vRtrRsvpGenTEThresholdLevelDn16  TmnxRsvpTEThresholdLevel
}

vRtrRsvpGenTEThresholdLevelUp1   OBJECT-TYPE
    SYNTAX      TmnxRsvpTEThresholdLevel
    MAX-ACCESS  read-create
    STATUS      current
    DESCRIPTION
        "The value of vRtrRsvpGenTEThresholdLevelUp1 specifies up TE threshold
         level 1."
    DEFVAL      { 0 }
    ::= { vRtrRsvpGenTEThresholdEntry 1 }

vRtrRsvpGenTEThresholdLevelUp2   OBJECT-TYPE
    SYNTAX      TmnxRsvpTEThresholdLevel
    MAX-ACCESS  read-create
    STATUS      current
    DESCRIPTION
        "The value of vRtrRsvpGenTEThresholdLevelUp2 specifies up TE threshold
         level 2."
    DEFVAL      { 15 }
    ::= { vRtrRsvpGenTEThresholdEntry 2 }

vRtrRsvpGenTEThresholdLevelUp3   OBJECT-TYPE
    SYNTAX      TmnxRsvpTEThresholdLevel
    MAX-ACCESS  read-create
    STATUS      current
    DESCRIPTION
        "The value of vRtrRsvpGenTEThresholdLevelUp3 specifies up TE threshold
         level 3."
    DEFVAL      { 30 }
    ::= { vRtrRsvpGenTEThresholdEntry 3 }

vRtrRsvpGenTEThresholdLevelUp4   OBJECT-TYPE
    SYNTAX      TmnxRsvpTEThresholdLevel
    MAX-ACCESS  read-create
    STATUS      current
    DESCRIPTION
        "The value of vRtrRsvpGenTEThresholdLevelUp4 specifies up TE threshold
         level 4."
    DEFVAL      { 45 }
    ::= { vRtrRsvpGenTEThresholdEntry 4 }

vRtrRsvpGenTEThresholdLevelUp5   OBJECT-TYPE
    SYNTAX      TmnxRsvpTEThresholdLevel
    MAX-ACCESS  read-create
    STATUS      current
    DESCRIPTION
        "The value of vRtrRsvpGenTEThresholdLevelUp5 specifies up TE threshold
         level 5."
    DEFVAL      { 60 }
    ::= { vRtrRsvpGenTEThresholdEntry 5 }

vRtrRsvpGenTEThresholdLevelUp6   OBJECT-TYPE
    SYNTAX      TmnxRsvpTEThresholdLevel
    MAX-ACCESS  read-create
    STATUS      current
    DESCRIPTION
        "The value of vRtrRsvpGenTEThresholdLevelUp6 specifies up TE threshold
         level 6."
    DEFVAL      { 75 }
    ::= { vRtrRsvpGenTEThresholdEntry 6 }

vRtrRsvpGenTEThresholdLevelUp7   OBJECT-TYPE
    SYNTAX      TmnxRsvpTEThresholdLevel
    MAX-ACCESS  read-create
    STATUS      current
    DESCRIPTION
        "The value of vRtrRsvpGenTEThresholdLevelUp7 specifies up TE threshold
         level 7."
    DEFVAL      { 80 }
    ::= { vRtrRsvpGenTEThresholdEntry 7 }

vRtrRsvpGenTEThresholdLevelUp8   OBJECT-TYPE
    SYNTAX      TmnxRsvpTEThresholdLevel
    MAX-ACCESS  read-create
    STATUS      current
    DESCRIPTION
        "The value of vRtrRsvpGenTEThresholdLevelUp8 specifies up TE threshold
         level 8."
    DEFVAL      { 85 }
    ::= { vRtrRsvpGenTEThresholdEntry 8 }

vRtrRsvpGenTEThresholdLevelUp9   OBJECT-TYPE
    SYNTAX      TmnxRsvpTEThresholdLevel
    MAX-ACCESS  read-create
    STATUS      current
    DESCRIPTION
        "The value of vRtrRsvpGenTEThresholdLevelUp9 specifies up TE threshold
         level 9."
    DEFVAL      { 90 }
    ::= { vRtrRsvpGenTEThresholdEntry 9 }

vRtrRsvpGenTEThresholdLevelUp10  OBJECT-TYPE
    SYNTAX      TmnxRsvpTEThresholdLevel
    MAX-ACCESS  read-create
    STATUS      current
    DESCRIPTION
        "The value of vRtrRsvpGenTEThresholdLevelUp10 specifies up TE threshold
         level 10."
    DEFVAL      { 95 }
    ::= { vRtrRsvpGenTEThresholdEntry 10 }

vRtrRsvpGenTEThresholdLevelUp11  OBJECT-TYPE
    SYNTAX      TmnxRsvpTEThresholdLevel
    MAX-ACCESS  read-create
    STATUS      current
    DESCRIPTION
        "The value of vRtrRsvpGenTEThresholdLevelUp11 specifies up TE threshold
         level 11."
    DEFVAL      { 96 }
    ::= { vRtrRsvpGenTEThresholdEntry 11 }

vRtrRsvpGenTEThresholdLevelUp12  OBJECT-TYPE
    SYNTAX      TmnxRsvpTEThresholdLevel
    MAX-ACCESS  read-create
    STATUS      current
    DESCRIPTION
        "The value of vRtrRsvpGenTEThresholdLevelUp12 specifies up TE threshold
         level 12."
    DEFVAL      { 97 }
    ::= { vRtrRsvpGenTEThresholdEntry 12 }

vRtrRsvpGenTEThresholdLevelUp13  OBJECT-TYPE
    SYNTAX      TmnxRsvpTEThresholdLevel
    MAX-ACCESS  read-create
    STATUS      current
    DESCRIPTION
        "The value of vRtrRsvpGenTEThresholdLevelUp13 specifies up TE threshold
         level 13."
    DEFVAL      { 98 }
    ::= { vRtrRsvpGenTEThresholdEntry 13 }

vRtrRsvpGenTEThresholdLevelUp14  OBJECT-TYPE
    SYNTAX      TmnxRsvpTEThresholdLevel
    MAX-ACCESS  read-create
    STATUS      current
    DESCRIPTION
        "The value of vRtrRsvpGenTEThresholdLevelUp14 specifies up TE threshold
         level 14."
    DEFVAL      { 99 }
    ::= { vRtrRsvpGenTEThresholdEntry 14 }

vRtrRsvpGenTEThresholdLevelUp15  OBJECT-TYPE
    SYNTAX      TmnxRsvpTEThresholdLevel
    MAX-ACCESS  read-create
    STATUS      current
    DESCRIPTION
        "The value of vRtrRsvpGenTEThresholdLevelUp15 specifies up TE threshold
         level 15."
    DEFVAL      { 100 }
    ::= { vRtrRsvpGenTEThresholdEntry 15 }

vRtrRsvpGenTEThresholdLevelUp16  OBJECT-TYPE
    SYNTAX      TmnxRsvpTEThresholdLevel
    MAX-ACCESS  read-create
    STATUS      current
    DESCRIPTION
        "The value of vRtrRsvpGenTEThresholdLevelUp16 specifies up TE threshold
         level 16."
    DEFVAL      { -1 }
    ::= { vRtrRsvpGenTEThresholdEntry 16 }

vRtrRsvpGenTEThresholdLevelDn1   OBJECT-TYPE
    SYNTAX      TmnxRsvpTEThresholdLevel
    MAX-ACCESS  read-create
    STATUS      current
    DESCRIPTION
        "The value of vRtrRsvpGenTEThresholdLevelDn1 specifies down TE
         threshold level 1."
    DEFVAL      { 100 }
    ::= { vRtrRsvpGenTEThresholdEntry 33 }

vRtrRsvpGenTEThresholdLevelDn2   OBJECT-TYPE
    SYNTAX      TmnxRsvpTEThresholdLevel
    MAX-ACCESS  read-create
    STATUS      current
    DESCRIPTION
        "The value of vRtrRsvpGenTEThresholdLevelDn2 specifies down TE
         threshold level 2."
    DEFVAL      { 99 }
    ::= { vRtrRsvpGenTEThresholdEntry 34 }

vRtrRsvpGenTEThresholdLevelDn3   OBJECT-TYPE
    SYNTAX      TmnxRsvpTEThresholdLevel
    MAX-ACCESS  read-create
    STATUS      current
    DESCRIPTION
        "The value of vRtrRsvpGenTEThresholdLevelDn3 specifies down TE
         threshold level 3."
    DEFVAL      { 98 }
    ::= { vRtrRsvpGenTEThresholdEntry 35 }

vRtrRsvpGenTEThresholdLevelDn4   OBJECT-TYPE
    SYNTAX      TmnxRsvpTEThresholdLevel
    MAX-ACCESS  read-create
    STATUS      current
    DESCRIPTION
        "The value of vRtrRsvpGenTEThresholdLevelDn4 specifies down TE
         threshold level 4."
    DEFVAL      { 97 }
    ::= { vRtrRsvpGenTEThresholdEntry 36 }

vRtrRsvpGenTEThresholdLevelDn5   OBJECT-TYPE
    SYNTAX      TmnxRsvpTEThresholdLevel
    MAX-ACCESS  read-create
    STATUS      current
    DESCRIPTION
        "The value of vRtrRsvpGenTEThresholdLevelDn5 specifies down TE
         threshold level 5."
    DEFVAL      { 96 }
    ::= { vRtrRsvpGenTEThresholdEntry 37 }

vRtrRsvpGenTEThresholdLevelDn6   OBJECT-TYPE
    SYNTAX      TmnxRsvpTEThresholdLevel
    MAX-ACCESS  read-create
    STATUS      current
    DESCRIPTION
        "The value of vRtrRsvpGenTEThresholdLevelDn6 specifies down TE
         threshold level 6."
    DEFVAL      { 95 }
    ::= { vRtrRsvpGenTEThresholdEntry 38 }

vRtrRsvpGenTEThresholdLevelDn7   OBJECT-TYPE
    SYNTAX      TmnxRsvpTEThresholdLevel
    MAX-ACCESS  read-create
    STATUS      current
    DESCRIPTION
        "The value of vRtrRsvpGenTEThresholdLevelDn7 specifies down TE
         threshold level 7."
    DEFVAL      { 90 }
    ::= { vRtrRsvpGenTEThresholdEntry 39 }

vRtrRsvpGenTEThresholdLevelDn8   OBJECT-TYPE
    SYNTAX      TmnxRsvpTEThresholdLevel
    MAX-ACCESS  read-create
    STATUS      current
    DESCRIPTION
        "The value of vRtrRsvpGenTEThresholdLevelDn8 specifies down TE
         threshold level 8."
    DEFVAL      { 85 }
    ::= { vRtrRsvpGenTEThresholdEntry 40 }

vRtrRsvpGenTEThresholdLevelDn9   OBJECT-TYPE
    SYNTAX      TmnxRsvpTEThresholdLevel
    MAX-ACCESS  read-create
    STATUS      current
    DESCRIPTION
        "The value of vRtrRsvpGenTEThresholdLevelDn9 specifies down TE
         threshold level 9."
    DEFVAL      { 80 }
    ::= { vRtrRsvpGenTEThresholdEntry 41 }

vRtrRsvpGenTEThresholdLevelDn10  OBJECT-TYPE
    SYNTAX      TmnxRsvpTEThresholdLevel
    MAX-ACCESS  read-create
    STATUS      current
    DESCRIPTION
        "The value of vRtrRsvpGenTEThresholdLevelDn10 specifies down TE
         threshold level 10."
    DEFVAL      { 75 }
    ::= { vRtrRsvpGenTEThresholdEntry 42 }

vRtrRsvpGenTEThresholdLevelDn11  OBJECT-TYPE
    SYNTAX      TmnxRsvpTEThresholdLevel
    MAX-ACCESS  read-create
    STATUS      current
    DESCRIPTION
        "The value of vRtrRsvpGenTEThresholdLevelDn11 specifies down TE
         threshold level 11."
    DEFVAL      { 60 }
    ::= { vRtrRsvpGenTEThresholdEntry 43 }

vRtrRsvpGenTEThresholdLevelDn12  OBJECT-TYPE
    SYNTAX      TmnxRsvpTEThresholdLevel
    MAX-ACCESS  read-create
    STATUS      current
    DESCRIPTION
        "The value of vRtrRsvpGenTEThresholdLevelDn12 specifies down TE
         threshold level 12."
    DEFVAL      { 45 }
    ::= { vRtrRsvpGenTEThresholdEntry 44 }

vRtrRsvpGenTEThresholdLevelDn13  OBJECT-TYPE
    SYNTAX      TmnxRsvpTEThresholdLevel
    MAX-ACCESS  read-create
    STATUS      current
    DESCRIPTION
        "The value of vRtrRsvpGenTEThresholdLevelDn13 specifies down TE
         threshold level 13."
    DEFVAL      { 30 }
    ::= { vRtrRsvpGenTEThresholdEntry 45 }

vRtrRsvpGenTEThresholdLevelDn14  OBJECT-TYPE
    SYNTAX      TmnxRsvpTEThresholdLevel
    MAX-ACCESS  read-create
    STATUS      current
    DESCRIPTION
        "The value of vRtrRsvpGenTEThresholdLevelDn14 specifies down TE
         threshold level 14."
    DEFVAL      { 15 }
    ::= { vRtrRsvpGenTEThresholdEntry 46 }

vRtrRsvpGenTEThresholdLevelDn15  OBJECT-TYPE
    SYNTAX      TmnxRsvpTEThresholdLevel
    MAX-ACCESS  read-create
    STATUS      current
    DESCRIPTION
        "The value of vRtrRsvpGenTEThresholdLevelDn15 specifies down TE
         threshold level 15."
    DEFVAL      { 0 }
    ::= { vRtrRsvpGenTEThresholdEntry 47 }

vRtrRsvpGenTEThresholdLevelDn16  OBJECT-TYPE
    SYNTAX      TmnxRsvpTEThresholdLevel
    MAX-ACCESS  read-create
    STATUS      current
    DESCRIPTION
        "The value of vRtrRsvpGenTEThresholdLevelDn16 specifies down TE
         threshold level 16."
    DEFVAL      { -1 }
    ::= { vRtrRsvpGenTEThresholdEntry 48 }

vRtrRsvpIfTEThresholdTable       OBJECT-TYPE
    SYNTAX      SEQUENCE OF VRtrRsvpIfTEThresholdEntry
    MAX-ACCESS  not-accessible
    STATUS      current
    DESCRIPTION
        "The vRtrRsvpIfTEThresholdTable contains objects related to up and down
         threshold levels per interface each expressed as a percentage of
         available bandwidth."
    ::= { tmnxRsvpObjs 16 }

vRtrRsvpIfTEThresholdEntry       OBJECT-TYPE
    SYNTAX      VRtrRsvpIfTEThresholdEntry
    MAX-ACCESS  not-accessible
    STATUS      current
    DESCRIPTION
        "Each row entry represents a vRtrRsvpIfTEThresholdEntry of the RSVP
         protocol within a virtual router. An entry in this table is created
         when a row is created in the rsvpIfEntry."
    AUGMENTS    { rsvpIfEntry }
    ::= { vRtrRsvpIfTEThresholdTable 1 }

VRtrRsvpIfTEThresholdEntry       ::= SEQUENCE
{
    vRtrRsvpIfTEThresholdLevelUp1    TmnxRsvpTEThresholdLevel,
    vRtrRsvpIfTEThresholdLevelUp2    TmnxRsvpTEThresholdLevel,
    vRtrRsvpIfTEThresholdLevelUp3    TmnxRsvpTEThresholdLevel,
    vRtrRsvpIfTEThresholdLevelUp4    TmnxRsvpTEThresholdLevel,
    vRtrRsvpIfTEThresholdLevelUp5    TmnxRsvpTEThresholdLevel,
    vRtrRsvpIfTEThresholdLevelUp6    TmnxRsvpTEThresholdLevel,
    vRtrRsvpIfTEThresholdLevelUp7    TmnxRsvpTEThresholdLevel,
    vRtrRsvpIfTEThresholdLevelUp8    TmnxRsvpTEThresholdLevel,
    vRtrRsvpIfTEThresholdLevelUp9    TmnxRsvpTEThresholdLevel,
    vRtrRsvpIfTEThresholdLevelUp10   TmnxRsvpTEThresholdLevel,
    vRtrRsvpIfTEThresholdLevelUp11   TmnxRsvpTEThresholdLevel,
    vRtrRsvpIfTEThresholdLevelUp12   TmnxRsvpTEThresholdLevel,
    vRtrRsvpIfTEThresholdLevelUp13   TmnxRsvpTEThresholdLevel,
    vRtrRsvpIfTEThresholdLevelUp14   TmnxRsvpTEThresholdLevel,
    vRtrRsvpIfTEThresholdLevelUp15   TmnxRsvpTEThresholdLevel,
    vRtrRsvpIfTEThresholdLevelUp16   TmnxRsvpTEThresholdLevel,
    vRtrRsvpIfTEThresholdLevelDn1    TmnxRsvpTEThresholdLevel,
    vRtrRsvpIfTEThresholdLevelDn2    TmnxRsvpTEThresholdLevel,
    vRtrRsvpIfTEThresholdLevelDn3    TmnxRsvpTEThresholdLevel,
    vRtrRsvpIfTEThresholdLevelDn4    TmnxRsvpTEThresholdLevel,
    vRtrRsvpIfTEThresholdLevelDn5    TmnxRsvpTEThresholdLevel,
    vRtrRsvpIfTEThresholdLevelDn6    TmnxRsvpTEThresholdLevel,
    vRtrRsvpIfTEThresholdLevelDn7    TmnxRsvpTEThresholdLevel,
    vRtrRsvpIfTEThresholdLevelDn8    TmnxRsvpTEThresholdLevel,
    vRtrRsvpIfTEThresholdLevelDn9    TmnxRsvpTEThresholdLevel,
    vRtrRsvpIfTEThresholdLevelDn10   TmnxRsvpTEThresholdLevel,
    vRtrRsvpIfTEThresholdLevelDn11   TmnxRsvpTEThresholdLevel,
    vRtrRsvpIfTEThresholdLevelDn12   TmnxRsvpTEThresholdLevel,
    vRtrRsvpIfTEThresholdLevelDn13   TmnxRsvpTEThresholdLevel,
    vRtrRsvpIfTEThresholdLevelDn14   TmnxRsvpTEThresholdLevel,
    vRtrRsvpIfTEThresholdLevelDn15   TmnxRsvpTEThresholdLevel,
    vRtrRsvpIfTEThresholdLevelDn16   TmnxRsvpTEThresholdLevel
}

vRtrRsvpIfTEThresholdLevelUp1    OBJECT-TYPE
    SYNTAX      TmnxRsvpTEThresholdLevel
    MAX-ACCESS  read-create
    STATUS      current
    DESCRIPTION
        "The value of vRtrRsvpIfTEThresholdLevelUp1 specifies up TE threshold
         level 1 for the interface."
    DEFVAL      { 0 }
    ::= { vRtrRsvpIfTEThresholdEntry 1 }

vRtrRsvpIfTEThresholdLevelUp2    OBJECT-TYPE
    SYNTAX      TmnxRsvpTEThresholdLevel
    MAX-ACCESS  read-create
    STATUS      current
    DESCRIPTION
        "The value of vRtrRsvpIfTEThresholdLevelUp2 specifies up TE threshold
         level 2 for the interface."
    DEFVAL      { 15 }
    ::= { vRtrRsvpIfTEThresholdEntry 2 }

vRtrRsvpIfTEThresholdLevelUp3    OBJECT-TYPE
    SYNTAX      TmnxRsvpTEThresholdLevel
    MAX-ACCESS  read-create
    STATUS      current
    DESCRIPTION
        "The value of vRtrRsvpIfTEThresholdLevelUp3 specifies up TE threshold
         level 3 for the interface."
    DEFVAL      { 30 }
    ::= { vRtrRsvpIfTEThresholdEntry 3 }

vRtrRsvpIfTEThresholdLevelUp4    OBJECT-TYPE
    SYNTAX      TmnxRsvpTEThresholdLevel
    MAX-ACCESS  read-create
    STATUS      current
    DESCRIPTION
        "The value of vRtrRsvpIfTEThresholdLevelUp4 specifies up TE threshold
         level 4 for the interface."
    DEFVAL      { 45 }
    ::= { vRtrRsvpIfTEThresholdEntry 4 }

vRtrRsvpIfTEThresholdLevelUp5    OBJECT-TYPE
    SYNTAX      TmnxRsvpTEThresholdLevel
    MAX-ACCESS  read-create
    STATUS      current
    DESCRIPTION
        "The value of vRtrRsvpIfTEThresholdLevelUp5 specifies up TE threshold
         level 5 for the interface."
    DEFVAL      { 60 }
    ::= { vRtrRsvpIfTEThresholdEntry 5 }

vRtrRsvpIfTEThresholdLevelUp6    OBJECT-TYPE
    SYNTAX      TmnxRsvpTEThresholdLevel
    MAX-ACCESS  read-create
    STATUS      current
    DESCRIPTION
        "The value of vRtrRsvpIfTEThresholdLevelUp6 specifies up TE threshold
         level 6 for the interface."
    DEFVAL      { 75 }
    ::= { vRtrRsvpIfTEThresholdEntry 6 }

vRtrRsvpIfTEThresholdLevelUp7    OBJECT-TYPE
    SYNTAX      TmnxRsvpTEThresholdLevel
    MAX-ACCESS  read-create
    STATUS      current
    DESCRIPTION
        "The value of vRtrRsvpIfTEThresholdLevelUp7 specifies up TE threshold
         level 7 for the interface."
    DEFVAL      { 80 }
    ::= { vRtrRsvpIfTEThresholdEntry 7 }

vRtrRsvpIfTEThresholdLevelUp8    OBJECT-TYPE
    SYNTAX      TmnxRsvpTEThresholdLevel
    MAX-ACCESS  read-create
    STATUS      current
    DESCRIPTION
        "The value of vRtrRsvpIfTEThresholdLevelUp8 specifies up TE threshold
         level 8 for the interface."
    DEFVAL      { 85 }
    ::= { vRtrRsvpIfTEThresholdEntry 8 }

vRtrRsvpIfTEThresholdLevelUp9    OBJECT-TYPE
    SYNTAX      TmnxRsvpTEThresholdLevel
    MAX-ACCESS  read-create
    STATUS      current
    DESCRIPTION
        "The value of vRtrRsvpIfTEThresholdLevelUp9 specifies up TE threshold
         level 9 for the interface."
    DEFVAL      { 90 }
    ::= { vRtrRsvpIfTEThresholdEntry 9 }

vRtrRsvpIfTEThresholdLevelUp10   OBJECT-TYPE
    SYNTAX      TmnxRsvpTEThresholdLevel
    MAX-ACCESS  read-create
    STATUS      current
    DESCRIPTION
        "The value of vRtrRsvpIfTEThresholdLevelUp10 specifies up TE threshold
         level 10 for the interface."
    DEFVAL      { 95 }
    ::= { vRtrRsvpIfTEThresholdEntry 10 }

vRtrRsvpIfTEThresholdLevelUp11   OBJECT-TYPE
    SYNTAX      TmnxRsvpTEThresholdLevel
    MAX-ACCESS  read-create
    STATUS      current
    DESCRIPTION
        "The value of vRtrRsvpIfTEThresholdLevelUp11 specifies up TE threshold
         level 11 for the interface."
    DEFVAL      { 96 }
    ::= { vRtrRsvpIfTEThresholdEntry 11 }

vRtrRsvpIfTEThresholdLevelUp12   OBJECT-TYPE
    SYNTAX      TmnxRsvpTEThresholdLevel
    MAX-ACCESS  read-create
    STATUS      current
    DESCRIPTION
        "The value of vRtrRsvpIfTEThresholdLevelUp12 specifies up TE threshold
         level 12 bandwidth for the interface."
    DEFVAL      { 97 }
    ::= { vRtrRsvpIfTEThresholdEntry 12 }

vRtrRsvpIfTEThresholdLevelUp13   OBJECT-TYPE
    SYNTAX      TmnxRsvpTEThresholdLevel
    MAX-ACCESS  read-create
    STATUS      current
    DESCRIPTION
        "The value of vRtrRsvpIfTEThresholdLevelUp13 specifies up TE threshold
         level 13 for the interface."
    DEFVAL      { 98 }
    ::= { vRtrRsvpIfTEThresholdEntry 13 }

vRtrRsvpIfTEThresholdLevelUp14   OBJECT-TYPE
    SYNTAX      TmnxRsvpTEThresholdLevel
    MAX-ACCESS  read-create
    STATUS      current
    DESCRIPTION
        "The value of vRtrRsvpIfTEThresholdLevelUp14 specifies up TE threshold
         level 14 for the interface."
    DEFVAL      { 99 }
    ::= { vRtrRsvpIfTEThresholdEntry 14 }

vRtrRsvpIfTEThresholdLevelUp15   OBJECT-TYPE
    SYNTAX      TmnxRsvpTEThresholdLevel
    MAX-ACCESS  read-create
    STATUS      current
    DESCRIPTION
        "The value of vRtrRsvpIfTEThresholdLevelUp15 specifies up TE threshold
         level 15 for the interface."
    DEFVAL      { 100 }
    ::= { vRtrRsvpIfTEThresholdEntry 15 }

vRtrRsvpIfTEThresholdLevelUp16   OBJECT-TYPE
    SYNTAX      TmnxRsvpTEThresholdLevel
    MAX-ACCESS  read-create
    STATUS      current
    DESCRIPTION
        "The value of vRtrRsvpIfTEThresholdLevelUp16 specifies up TE threshold
         level 16 for the interface."
    DEFVAL      { -1 }
    ::= { vRtrRsvpIfTEThresholdEntry 16 }

vRtrRsvpIfTEThresholdLevelDn1    OBJECT-TYPE
    SYNTAX      TmnxRsvpTEThresholdLevel
    MAX-ACCESS  read-create
    STATUS      current
    DESCRIPTION
        "The value of vRtrRsvpIfTEThresholdLevelDn1 specifies down TE threshold
         level 1 for the interface."
    DEFVAL      { 100 }
    ::= { vRtrRsvpIfTEThresholdEntry 33 }

vRtrRsvpIfTEThresholdLevelDn2    OBJECT-TYPE
    SYNTAX      TmnxRsvpTEThresholdLevel
    MAX-ACCESS  read-create
    STATUS      current
    DESCRIPTION
        "The value of vRtrRsvpIfTEThresholdLevelDn2 specifies down TE threshold
         level 2 for the interface."
    DEFVAL      { 99 }
    ::= { vRtrRsvpIfTEThresholdEntry 34 }

vRtrRsvpIfTEThresholdLevelDn3    OBJECT-TYPE
    SYNTAX      TmnxRsvpTEThresholdLevel
    MAX-ACCESS  read-create
    STATUS      current
    DESCRIPTION
        "The value of vRtrRsvpIfTEThresholdLevelDn3 specifies down TE threshold
         level 3 for the interface."
    DEFVAL      { 98 }
    ::= { vRtrRsvpIfTEThresholdEntry 35 }

vRtrRsvpIfTEThresholdLevelDn4    OBJECT-TYPE
    SYNTAX      TmnxRsvpTEThresholdLevel
    MAX-ACCESS  read-create
    STATUS      current
    DESCRIPTION
        "The value of vRtrRsvpIfTEThresholdLevelDn4 specifies down TE threshold
         level 4 for the interface."
    DEFVAL      { 97 }
    ::= { vRtrRsvpIfTEThresholdEntry 36 }

vRtrRsvpIfTEThresholdLevelDn5    OBJECT-TYPE
    SYNTAX      TmnxRsvpTEThresholdLevel
    MAX-ACCESS  read-create
    STATUS      current
    DESCRIPTION
        "The value of vRtrRsvpIfTEThresholdLevelDn5 specifies down TE threshold
         level 5 for the interface."
    DEFVAL      { 96 }
    ::= { vRtrRsvpIfTEThresholdEntry 37 }

vRtrRsvpIfTEThresholdLevelDn6    OBJECT-TYPE
    SYNTAX      TmnxRsvpTEThresholdLevel
    MAX-ACCESS  read-create
    STATUS      current
    DESCRIPTION
        "The value of vRtrRsvpIfTEThresholdLevelDn6 specifies down TE threshold
         level 6 for the interface."
    DEFVAL      { 95 }
    ::= { vRtrRsvpIfTEThresholdEntry 38 }

vRtrRsvpIfTEThresholdLevelDn7    OBJECT-TYPE
    SYNTAX      TmnxRsvpTEThresholdLevel
    MAX-ACCESS  read-create
    STATUS      current
    DESCRIPTION
        "The value of vRtrRsvpIfTEThresholdLevelDn7 specifies down TE threshold
         level 7 for the interface."
    DEFVAL      { 90 }
    ::= { vRtrRsvpIfTEThresholdEntry 39 }

vRtrRsvpIfTEThresholdLevelDn8    OBJECT-TYPE
    SYNTAX      TmnxRsvpTEThresholdLevel
    MAX-ACCESS  read-create
    STATUS      current
    DESCRIPTION
        "The value of vRtrRsvpIfTEThresholdLevelDn8 specifies down TE threshold
         level 8 for the interface."
    DEFVAL      { 85 }
    ::= { vRtrRsvpIfTEThresholdEntry 40 }

vRtrRsvpIfTEThresholdLevelDn9    OBJECT-TYPE
    SYNTAX      TmnxRsvpTEThresholdLevel
    MAX-ACCESS  read-create
    STATUS      current
    DESCRIPTION
        "The value of vRtrRsvpIfTEThresholdLevelDn9 specifies down TE threshold
         level 9 for the interface."
    DEFVAL      { 80 }
    ::= { vRtrRsvpIfTEThresholdEntry 41 }

vRtrRsvpIfTEThresholdLevelDn10   OBJECT-TYPE
    SYNTAX      TmnxRsvpTEThresholdLevel
    MAX-ACCESS  read-create
    STATUS      current
    DESCRIPTION
        "The value of vRtrRsvpIfTEThresholdLevelDn10 specifies down TE
         threshold level 10 for the interface."
    DEFVAL      { 75 }
    ::= { vRtrRsvpIfTEThresholdEntry 42 }

vRtrRsvpIfTEThresholdLevelDn11   OBJECT-TYPE
    SYNTAX      TmnxRsvpTEThresholdLevel
    MAX-ACCESS  read-create
    STATUS      current
    DESCRIPTION
        "The value of vRtrRsvpIfTEThresholdLevelDn11 specifies down TE
         threshold level 11 for the interface."
    DEFVAL      { 60 }
    ::= { vRtrRsvpIfTEThresholdEntry 43 }

vRtrRsvpIfTEThresholdLevelDn12   OBJECT-TYPE
    SYNTAX      TmnxRsvpTEThresholdLevel
    MAX-ACCESS  read-create
    STATUS      current
    DESCRIPTION
        "The value of vRtrRsvpIfTEThresholdLevelDn12 specifies down TE
         threshold level 12 for the interface."
    DEFVAL      { 45 }
    ::= { vRtrRsvpIfTEThresholdEntry 44 }

vRtrRsvpIfTEThresholdLevelDn13   OBJECT-TYPE
    SYNTAX      TmnxRsvpTEThresholdLevel
    MAX-ACCESS  read-create
    STATUS      current
    DESCRIPTION
        "The value of vRtrRsvpIfTEThresholdLevelDn13 specifies down TE
         threshold level 13 for the interface."
    DEFVAL      { 30 }
    ::= { vRtrRsvpIfTEThresholdEntry 45 }

vRtrRsvpIfTEThresholdLevelDn14   OBJECT-TYPE
    SYNTAX      TmnxRsvpTEThresholdLevel
    MAX-ACCESS  read-create
    STATUS      current
    DESCRIPTION
        "The value of vRtrRsvpIfTEThresholdLevelDn14 specifies down TE
         threshold level 14 for the interface."
    DEFVAL      { 15 }
    ::= { vRtrRsvpIfTEThresholdEntry 46 }

vRtrRsvpIfTEThresholdLevelDn15   OBJECT-TYPE
    SYNTAX      TmnxRsvpTEThresholdLevel
    MAX-ACCESS  read-create
    STATUS      current
    DESCRIPTION
        "The value of vRtrRsvpIfTEThresholdLevelDn15 specifies down TE
         threshold level 15 for the interface."
    DEFVAL      { 0 }
    ::= { vRtrRsvpIfTEThresholdEntry 47 }

vRtrRsvpIfTEThresholdLevelDn16   OBJECT-TYPE
    SYNTAX      TmnxRsvpTEThresholdLevel
    MAX-ACCESS  read-create
    STATUS      current
    DESCRIPTION
        "The value of vRtrRsvpIfTEThresholdLevelDn16 specifies down TE
         threshold level 16 for the interface."
    DEFVAL      { -1 }
    ::= { vRtrRsvpIfTEThresholdEntry 48 }

vRtrRsvpGenExtTable              OBJECT-TYPE
    SYNTAX      SEQUENCE OF VRtrRsvpGenExtEntry
    MAX-ACCESS  not-accessible
    STATUS      current
    DESCRIPTION
        "The vRtrRsvpGenExtTable contains objects for general control and
         management of an RSVP protocol instance within a virtual router. This
         table augments the vRtrRsvpGeneralTable."
    ::= { tmnxRsvpObjs 17 }

vRtrRsvpGenExtEntry              OBJECT-TYPE
    SYNTAX      VRtrRsvpGenExtEntry
    MAX-ACCESS  not-accessible
    STATUS      current
    DESCRIPTION
        "Each row entry represents an instance of the MPLS protocol running
         within a virtual router.  Entries in this table cannot be
         created and deleted via SNMP SET operations.  An entry in this table
         is created by the agent when vRtrRsvpStatus in the vRtrConfTable is
         set to 'create'.  The entry is destroyed when vRtrRsvpStatus is set
         to 'delete'"
    AUGMENTS    { vRtrRsvpGeneralEntry }
    ::= { vRtrRsvpGenExtTable 1 }

VRtrRsvpGenExtEntry              ::= SEQUENCE
{
    vRtrRsvpGenExtDBwAccounting      TruthValue,
    vRtrRsvpGenExtDBwMultiplier      Unsigned32,
    vRtrRsvpGenExtDBwSampIntvl       Unsigned32,
    vRtrRsvpGenExtDBwSampMult        Unsigned32,
    vRtrRsvpGenExtDBwUpThdPercent    Unsigned32,
    vRtrRsvpGenExtDBwUpThdBw         Integer32,
    vRtrRsvpGenExtDBwDwnThdPercent   Unsigned32,
    vRtrRsvpGenExtDBwDwnThdBw        Integer32,
    vRtrRsvpGenExtAuthOverBypass     TruthValue
}

vRtrRsvpGenExtDBwAccounting      OBJECT-TYPE
    SYNTAX      TruthValue
    MAX-ACCESS  read-create
    STATUS      current
    DESCRIPTION
        "The value of vRtrRsvpGenExtDBwAccounting specifies whether Dark
         Bandwidth accounting is enabled. When the value of this object is set
         to 'true', Dark Bandwidth accounting is enabled. When the value is set
         to 'false', Dark Bandwidth accounting is disabled."
    DEFVAL      { false }
    ::= { vRtrRsvpGenExtEntry 1 }

vRtrRsvpGenExtDBwMultiplier      OBJECT-TYPE
    SYNTAX      Unsigned32 (0..1000)
    UNITS       "percent"
    MAX-ACCESS  read-create
    STATUS      current
    DESCRIPTION
        "The value of vRtrRsvpGenExtDBwMultiplier specifies the Dark Bandwidth
         Multiplier. Setting the value to 0 percent will lead to no IGP-TE
         updates."
    DEFVAL      { 100 }
    ::= { vRtrRsvpGenExtEntry 2 }

vRtrRsvpGenExtDBwSampIntvl       OBJECT-TYPE
    SYNTAX      Unsigned32 (10..600)
    UNITS       "seconds"
    MAX-ACCESS  read-create
    STATUS      current
    DESCRIPTION
        "The value of vRtrRsvpGenExtDBwSampIntvl specifies the Dark Bandwidth
         sample interval."
    DEFVAL      { 30 }
    ::= { vRtrRsvpGenExtEntry 3 }

vRtrRsvpGenExtDBwSampMult        OBJECT-TYPE
    SYNTAX      Unsigned32 (1..10)
    MAX-ACCESS  read-create
    STATUS      current
    DESCRIPTION
        "The value of vRtrRsvpGenExtDBwSampMult specifies the Dark Bandwidth
         sample interval multiplier."
    DEFVAL      { 3 }
    ::= { vRtrRsvpGenExtEntry 4 }

vRtrRsvpGenExtDBwUpThdPercent    OBJECT-TYPE
    SYNTAX      Unsigned32 (0..100)
    UNITS       "percent"
    MAX-ACCESS  read-create
    STATUS      current
    DESCRIPTION
        "The value of vRtrRsvpGenExtDBwUpThdPercent specifies the threshold
         above which an increase in Maximum Reservable Link Bandwidth/Maximum
         Reservable Bandwidth will trigger an IGP-TE update."
    DEFVAL      { 0 }
    ::= { vRtrRsvpGenExtEntry 5 }

vRtrRsvpGenExtDBwUpThdBw         OBJECT-TYPE
    SYNTAX      Integer32 (-1..1000000)
    UNITS       "megabps"
    MAX-ACCESS  read-create
    STATUS      current
    DESCRIPTION
        "The value of vRtrRsvpGenExtDBwUpThdBw specifies the absolute threshold
         above which an increase in Maximum Reservable Link Bandwidth /Maximum
         Reservable Bandwidth will trigger an IGP-TE update."
    DEFVAL      { -1 }
    ::= { vRtrRsvpGenExtEntry 6 }

vRtrRsvpGenExtDBwDwnThdPercent   OBJECT-TYPE
    SYNTAX      Unsigned32 (0..100)
    UNITS       "percent"
    MAX-ACCESS  read-create
    STATUS      current
    DESCRIPTION
        "The value of vRtrRsvpGenExtDBwDwnThdPercent specifies the threshold
         below which a decrease in Maximum Reservable Link Bandwidth/Maximum
         Reservable Bandwidth will trigger an IGP-TE update."
    DEFVAL      { 0 }
    ::= { vRtrRsvpGenExtEntry 7 }

vRtrRsvpGenExtDBwDwnThdBw        OBJECT-TYPE
    SYNTAX      Integer32 (-1..1000000)
    UNITS       "megabps"
    MAX-ACCESS  read-create
    STATUS      current
    DESCRIPTION
        "The value of vRtrRsvpGenExtDBwDwnThdBw specifies the absolute
         threshold below which a decrease in Maximum Reservable Link Bandwidth
         /Maximum Reservable Bandwidth will trigger an IGP-TE update."
    DEFVAL      { -1 }
    ::= { vRtrRsvpGenExtEntry 8 }

vRtrRsvpGenExtAuthOverBypass     OBJECT-TYPE
    SYNTAX      TruthValue
    MAX-ACCESS  read-create
    STATUS      current
    DESCRIPTION
        "The value of vRtrRsvpGenExtAuthOverBypass specifies whether
         authentication over bypass tunnels is enabled."
    DEFVAL      { false }
    ::= { vRtrRsvpGenExtEntry 9 }

vRtrRsvpIfExtTable               OBJECT-TYPE
    SYNTAX      SEQUENCE OF VRtrRsvpIfExtEntry
    MAX-ACCESS  not-accessible
    STATUS      current
    DESCRIPTION
        "The vRtrRsvpIfExtTable provides an extension to the vRtrRsvpIfTable,
         and augments the rsvpIfTable."
    ::= { tmnxRsvpObjs 18 }

vRtrRsvpIfExtEntry               OBJECT-TYPE
    SYNTAX      VRtrRsvpIfExtEntry
    MAX-ACCESS  not-accessible
    STATUS      current
    DESCRIPTION
        "Each row entry in the vRtrRsvpIfExtTable represents additional columns
         for attributes specific to the Nokia 7x50 SR RSVP implementation."
    AUGMENTS    { rsvpIfEntry }
    ::= { vRtrRsvpIfExtTable 1 }

VRtrRsvpIfExtEntry               ::= SEQUENCE
{
    vRtrRsvpIfExtInheritance         Unsigned32,
    vRtrRsvpIfExtDBwMultiplier       Integer32,
    vRtrRsvpIfExtDBwUpThdPercent     Integer32,
    vRtrRsvpIfExtDBwUpThdBw          Integer32,
    vRtrRsvpIfExtDBwDwnThdPercent    Integer32,
    vRtrRsvpIfExtDBwDwnThdBw         Integer32,
    vRtrRsvpIfExtDBwLastSampleIndex  Unsigned32,
    vRtrRsvpIfExtDBwLastSample       Counter64,
    vRtrRsvpIfExtDBwLatestCalDBw     Counter64,
    vRtrRsvpIfExtAdvMRLB             Counter64,
    vRtrRsvpIfExtDBwLastSampleTime   TimeStamp,
    vRtrRsvpIfExtDBwLatestCalDBwTime TimeStamp,
    vRtrRsvpIfExtLastTedbUpdateTime  TimeStamp
}

vRtrRsvpIfExtInheritance         OBJECT-TYPE
    SYNTAX      Unsigned32
    MAX-ACCESS  read-create
    STATUS      current
    DESCRIPTION
        "A bit within vRtrRsvpIfExtInheritance specifies whether to inherit the
         operational values of the corresponding inherited objects from
         vRtrRsvpGenExtTable or use the administratively set values.

         Non mask bits will always have value of zero, and any attempt to
         change the value will be silently discarded.

         This object is a bit-mask, with the following positions:


         vRtrRsvpIfExtDBwMultiplier                0x1

         When the bit has value of one, then vRtrRsvpIfExtDBwMultiplier
         administrative and operational values are the most recently SET
         values. The mask bit for object vRtrRsvpIfExtDBwMultiplier will be set
         to one when set is performed on it. Any other attempt to set the mask
         bit to one will be silently discarded.

         When the bit is set to zero, then the object's administrative and
         operational value are inherited from the corresponding object in
         vRtrRsvpGenExtTable.

         vRtrRsvpIfExtDBwUpThdPercent              0x2

         When the bit has value of one, then vRtrRsvpIfExtDBwUpThdPercent
         administrative and operational values are the most recently SET
         values. The mask bit for object vRtrRsvpIfExtDBwUpThdPercent will be
         set to one when set is performed on it. Any other attempt to set the
         mask bit to one will be silently discarded.

         When the bit is set to zero, then the object's administrative and
         operational value are inherited from the corresponding object in
         vRtrRsvpGenExtTable.

         vRtrRsvpIfExtDBwDwnThdPercent             0x4

         When the bit has value of one, then vRtrRsvpIfExtDBwDwnThdPercent
         administrative and operational values are the most recently SET
         values. The mask bit for object vRtrRsvpIfExtDBwDwnThdPercent will be
         set to one when set is performed on it. Any other attempt to set the
         mask bit to one will be silently discarded.

         When the bit is set to zero, then the object's administrative and
         operational value are inherited from the corresponding object in
         vRtrRsvpGenExtTable."
    DEFVAL      { 0 }
    ::= { vRtrRsvpIfExtEntry 1 }

vRtrRsvpIfExtDBwMultiplier       OBJECT-TYPE
    SYNTAX      Integer32 (0..1000)
    UNITS       "percent"
    MAX-ACCESS  read-create
    STATUS      current
    DESCRIPTION
        "The value of vRtrRsvpIfExtDBwMultiplier specifies the Dark Bandwidth
         Multiplier per interface. If specified, this value will override  the
         globally defined value of Dark Bandwidth Multiplier specified  by
         vRtrRsvpGenExtDBwMultiplier.

         By default, this will inherit the value of
         vRtrRsvpGenExtDBwMultiplier."
    ::= { vRtrRsvpIfExtEntry 2 }

vRtrRsvpIfExtDBwUpThdPercent     OBJECT-TYPE
    SYNTAX      Integer32 (0..100)
    UNITS       "percent"
    MAX-ACCESS  read-create
    STATUS      current
    DESCRIPTION
        "The value of vRtrRsvpIfExtDBwUpThdPercent specifies the threshold per
         interface, above which an increase in Maximum Reservable Link
         Bandwidth will trigger an IGP-TE update. If specified, this value will
         override the globally defined value specified by
         vRtrRsvpGenExtDBwUpThdPercent.

         By default, this will inherit the value of
         vRtrRsvpGenExtDBwUpThdPercent."
    ::= { vRtrRsvpIfExtEntry 3 }

vRtrRsvpIfExtDBwUpThdBw          OBJECT-TYPE
    SYNTAX      Integer32 (-1..1000000)
    UNITS       "megabps"
    MAX-ACCESS  read-create
    STATUS      current
    DESCRIPTION
        "The value of vRtrRsvpIfExtDBwUpThdBw specifies the absolute threshold
         per inteface, above which an increase in Maximum Reservable Link
         Bandwidth will trigger an IGP-TE update. If specified, this will
         override the globally defined value specified by
         vRtrRsvpGenExtDBwUpThdBw.

         By default, this will inherit the value of vRtrRsvpGenExtDBwUpThdBw."
    DEFVAL      { -1 }
    ::= { vRtrRsvpIfExtEntry 4 }

vRtrRsvpIfExtDBwDwnThdPercent    OBJECT-TYPE
    SYNTAX      Integer32 (0..100)
    UNITS       "percent"
    MAX-ACCESS  read-create
    STATUS      current
    DESCRIPTION
        "The value of vRtrRsvpIfExtDBwDwnThdPercent specifies the threshold per
         interface, below which a decrease in Maximum Reservable Link Bandwidth
         will trigger an IGP-TE update.  If specified, this value will override
         the globally defined value specified by
         vRtrRsvpGenExtDBwDwnThdPercent.

         By default, this will inherit the value of
         vRtrRsvpGenExtDBwDwnThdPercent."
    ::= { vRtrRsvpIfExtEntry 5 }

vRtrRsvpIfExtDBwDwnThdBw         OBJECT-TYPE
    SYNTAX      Integer32 (-1..1000000)
    UNITS       "megabps"
    MAX-ACCESS  read-create
    STATUS      current
    DESCRIPTION
        "The value of vRtrRsvpIfExtDBwDwnThdBw specifies the absolute threshold
         per inteface, below which a decrease in Maximum Reservable Link
         Bandwidth will trigger an IGP-TE update.  If specified, this value
         will override the globally defined value specified by
         vRtrRsvpGenExtDBwDwnThdBw.

         By default, this will inherit the value of vRtrRsvpGenExtDBwDwnThdBw."
    DEFVAL      { -1 }
    ::= { vRtrRsvpIfExtEntry 6 }

vRtrRsvpIfExtDBwLastSampleIndex  OBJECT-TYPE
    SYNTAX      Unsigned32
    MAX-ACCESS  read-only
    STATUS      current
    DESCRIPTION
        "The latest DBw sample index in current sample interval."
    ::= { vRtrRsvpIfExtEntry 7 }

vRtrRsvpIfExtDBwLastSample       OBJECT-TYPE
    SYNTAX      Counter64
    MAX-ACCESS  read-only
    STATUS      current
    DESCRIPTION
        "The total number of SR-MPLS labeled packets transmitted from this
         interface."
    ::= { vRtrRsvpIfExtEntry 8 }

vRtrRsvpIfExtDBwLatestCalDBw     OBJECT-TYPE
    SYNTAX      Counter64
    MAX-ACCESS  read-only
    STATUS      current
    DESCRIPTION
        "The lastest calculated DBw."
    ::= { vRtrRsvpIfExtEntry 9 }

vRtrRsvpIfExtAdvMRLB             OBJECT-TYPE
    SYNTAX      Counter64
    MAX-ACCESS  read-only
    STATUS      current
    DESCRIPTION
        "The advertised maximum reservable link bandwidth"
    ::= { vRtrRsvpIfExtEntry 10 }

vRtrRsvpIfExtDBwLastSampleTime   OBJECT-TYPE
    SYNTAX      TimeStamp
    MAX-ACCESS  read-only
    STATUS      current
    DESCRIPTION
        "Time when last sample DBw was collected"
    ::= { vRtrRsvpIfExtEntry 12 }

vRtrRsvpIfExtDBwLatestCalDBwTime OBJECT-TYPE
    SYNTAX      TimeStamp
    MAX-ACCESS  read-only
    STATUS      current
    DESCRIPTION
        "Time when latest DBw was calculated"
    ::= { vRtrRsvpIfExtEntry 13 }

vRtrRsvpIfExtLastTedbUpdateTime  OBJECT-TYPE
    SYNTAX      TimeStamp
    MAX-ACCESS  read-only
    STATUS      current
    DESCRIPTION
        "Time when last TE-DB update was sent"
    ::= { vRtrRsvpIfExtEntry 14 }

tmnxRsvpConformance              OBJECT IDENTIFIER ::= { tmnxSRConfs 7 }

tmnxRsvpCompliances              OBJECT IDENTIFIER ::= { tmnxRsvpConformance 1 }

tmnxRsvpV3v0Compliance           MODULE-COMPLIANCE
    STATUS      obsolete
    DESCRIPTION
        "The compliance statement for management of extended RSVP capabilities
         on Nokia SROS series systems release 3.0."
    MODULE
        MANDATORY-GROUPS {
            tmnxRsvpGeneralGroup,
            tmnxRsvpIfV3v0Group,
            tmnxRsvpSessionGroup,
            tmnxRsvpNotificationGroup
        }
    ::= { tmnxRsvpCompliances 2 }

tmnxRsvpV5v0Compliance           MODULE-COMPLIANCE
    STATUS      obsolete
    DESCRIPTION
        "The compliance statement for management of extended RSVP capabilities
         on Nokia SROS series systems release 5.0."
    MODULE
        MANDATORY-GROUPS {
            tmnxRsvpGeneralGroup,
            tmnxRsvpSessionGroup,
            tmnxRsvpNotificationGroup,
            tmnxRsvpIfV5v0Group,
            tmnxRsvpSessionV5v0Group
        }
    ::= { tmnxRsvpCompliances 3 }

tmnxRsvpV6v0Compliance           MODULE-COMPLIANCE
    STATUS      obsolete
    DESCRIPTION
        "The compliance statement for management of extended RSVP capabilities
         on Nokia SROS series systems release 6.0."
    MODULE
        MANDATORY-GROUPS {
            tmnxRsvpGeneralGroup,
            tmnxRsvpSessionGroup,
            tmnxRsvpNotificationGroup,
            tmnxRsvpIfV5v0Group,
            tmnxRsvpSessionV5v0Group,
            tmnxRsvpGeneralV6v0Group,
            tmnxRsvpIfV6v0Group,
            tmnxRsvpNbrV6v0Group,
            tmnxRsvpSessionV6v0Group
        }
    ::= { tmnxRsvpCompliances 4 }

tmnxRsvpV6v1Compliance           MODULE-COMPLIANCE
    STATUS      obsolete
    DESCRIPTION
        "The compliance statement for management of extended RSVP capabilities
         on Nokia SROS series systems release 6.1."
    MODULE
        MANDATORY-GROUPS {
            tmnxRsvpGeneralGroup,
            tmnxRsvpSessionGroup,
            tmnxRsvpNotificationGroup,
            tmnxRsvpIfV5v0Group,
            tmnxRsvpSessionV5v0Group,
            tmnxRsvpGeneralV6v0Group,
            tmnxRsvpIfV6v0Group,
            tmnxRsvpNbrV6v0Group,
            tmnxRsvpSessionV6v0Group,
            tmnxRsvpGeneralV6v1Group
        }
    ::= { tmnxRsvpCompliances 5 }

tmnxRsvpV7v0Compliance           MODULE-COMPLIANCE
    STATUS      obsolete
    DESCRIPTION
        "The compliance statement for management of extended RSVP capabilities
         on Nokia SROS series systems release 6.1."
    MODULE
        MANDATORY-GROUPS {
            tmnxRsvpGeneralGroup,
            tmnxRsvpSessionGroup,
            tmnxRsvpNotificationGroup,
            tmnxRsvpIfV5v0Group,
            tmnxRsvpSessionV5v0Group,
            tmnxRsvpGeneralV6v0Group,
            tmnxRsvpIfV6v0Group,
            tmnxRsvpNbrV6v0Group,
            tmnxRsvpSessionV6v0Group,
            tmnxRsvpGeneralV6v1Group,
            tmnxRsvpIfV7v0Group,
            tmnxRsvpDSTEV7v0Group,
            tmnxRsvpGeneralV7v0Group,
            tmnxRsvpSessionV7v0Group
        }
    ::= { tmnxRsvpCompliances 6 }

tmnxRsvpV8v0Compliance           MODULE-COMPLIANCE
    STATUS      obsolete
    DESCRIPTION
        "The compliance statement for management of extended RSVP capabilities
         on Nokia SROS series systems release 8.0."
    MODULE
        MANDATORY-GROUPS {
            tmnxRsvpGeneralGroup,
            tmnxRsvpSessionGroup,
            tmnxRsvpNotificationGroup,
            tmnxRsvpIfV5v0Group,
            tmnxRsvpSessionV5v0Group,
            tmnxRsvpGeneralV6v0Group,
            tmnxRsvpIfV6v0Group,
            tmnxRsvpNbrV6v0Group,
            tmnxRsvpSessionV6v0Group,
            tmnxRsvpGeneralV6v1Group,
            tmnxRsvpIfV7v0Group,
            tmnxRsvpDSTEV7v0Group,
            tmnxRsvpGeneralV7v0Group,
            tmnxRsvpSessionV7v0Group,
            tmnxRsvpGenTEThresholdV8v0Group,
            tmnxRsvpIfTEThresholdV8v0Group,
            tmnxRsvpGeneralV8v0Group,
            tmnxRsvpIfV8v0Group
        }
    ::= { tmnxRsvpCompliances 7 }

tmnxRsvpV9v0Compliance           MODULE-COMPLIANCE
    STATUS      obsolete
    DESCRIPTION
        "The compliance statement for management of extended RSVP capabilities
         on Nokia SROS series systems release 9.0."
    MODULE
        MANDATORY-GROUPS {
            tmnxRsvpGeneralGroup,
            tmnxRsvpSessionGroup,
            tmnxRsvpNotificationGroup,
            tmnxRsvpIfV5v0Group,
            tmnxRsvpSessionV5v0Group,
            tmnxRsvpGeneralV6v0Group,
            tmnxRsvpIfV6v0Group,
            tmnxRsvpNbrV6v0Group,
            tmnxRsvpSessionV6v0Group,
            tmnxRsvpGeneralV6v1Group,
            tmnxRsvpIfV7v0Group,
            tmnxRsvpDSTEV7v0Group,
            tmnxRsvpGeneralV7v0Group,
            tmnxRsvpSessionV7v0Group,
            tmnxRsvpGenTEThresholdV8v0Group,
            tmnxRsvpIfTEThresholdV8v0Group,
            tmnxRsvpGeneralV8v0Group,
            tmnxRsvpIfV8v0Group,
            tmnxRsvpGeneralV9v0Group,
            tmnxRsvpNotificationV9v0Group
        }
    ::= { tmnxRsvpCompliances 8 }

tmnxRsvpV10v0Compliance          MODULE-COMPLIANCE
    STATUS      obsolete
    DESCRIPTION
        "The compliance statement for management of extended RSVP capabilities
         on Nokia SROS series systems release 10.0."
    MODULE
        MANDATORY-GROUPS {
            tmnxRsvpGeneralGroup,
            tmnxRsvpSessionGroup,
            tmnxRsvpNotificationGroup,
            tmnxRsvpIfV5v0Group,
            tmnxRsvpSessionV5v0Group,
            tmnxRsvpGeneralV6v0Group,
            tmnxRsvpIfV6v0Group,
            tmnxRsvpNbrV6v0Group,
            tmnxRsvpSessionV6v0Group,
            tmnxRsvpGeneralV6v1Group,
            tmnxRsvpIfV7v0Group,
            tmnxRsvpDSTEV7v0Group,
            tmnxRsvpGeneralV7v0Group,
            tmnxRsvpSessionV7v0Group,
            tmnxRsvpGenTEThresholdV8v0Group,
            tmnxRsvpIfTEThresholdV8v0Group,
            tmnxRsvpGeneralV8v0Group,
            tmnxRsvpIfV8v0Group,
            tmnxRsvpGeneralV9v0Group,
            tmnxRsvpNotificationV9v0Group,
            tmnxRsvpGeneralV10v0Group,
            tmnxRsvpGeneralV11v0Group
        }
    ::= { tmnxRsvpCompliances 9 }

tmnxRsvpV12v0Compliance          MODULE-COMPLIANCE
    STATUS      obsolete
    DESCRIPTION
        "The compliance statement for management of extended RSVP capabilities
         on Nokia SROS series systems release 12.0."
    MODULE
        MANDATORY-GROUPS {
            tmnxRsvpGeneralGroup,
            tmnxRsvpSessionGroup,
            tmnxRsvpNotificationGroup,
            tmnxRsvpIfV5v0Group,
            tmnxRsvpSessionV5v0Group,
            tmnxRsvpGeneralV6v0Group,
            tmnxRsvpIfV6v0Group,
            tmnxRsvpNbrV6v0Group,
            tmnxRsvpSessionV6v0Group,
            tmnxRsvpGeneralV6v1Group,
            tmnxRsvpIfV7v0Group,
            tmnxRsvpDSTEV7v0Group,
            tmnxRsvpGeneralV7v0Group,
            tmnxRsvpSessionV7v0Group,
            tmnxRsvpGenTEThresholdV8v0Group,
            tmnxRsvpIfTEThresholdV8v0Group,
            tmnxRsvpGeneralV8v0Group,
            tmnxRsvpIfV8v0Group,
            tmnxRsvpGeneralV9v0Group,
            tmnxRsvpNotificationV9v0Group,
            tmnxRsvpGeneralV10v0Group,
            tmnxRsvpGeneralV11v0Group,
            tmnxRsvpGeneralV12v0Group
        }
    ::= { tmnxRsvpCompliances 10 }

tmnxRsvpV14v0Compliance          MODULE-COMPLIANCE
    STATUS      obsolete
    DESCRIPTION
        "The compliance statement for management of extended RSVP capabilities
         on Nokia SROS series systems release 14.0."
    MODULE
        MANDATORY-GROUPS {
            tmnxRsvpGeneralV14v0Group
        }
    ::= { tmnxRsvpCompliances 11 }

tmnxRsvpV15v0Compliance          MODULE-COMPLIANCE
    STATUS      obsolete
    DESCRIPTION
        "The compliance statement for management of extended RSVP capabilities
         on Nokia SROS series systems release 15.0."
    MODULE
        MANDATORY-GROUPS {
            tmnxRsvpGeneralGroup,
            tmnxRsvpSessionGroup,
            tmnxRsvpNotificationGroup,
            tmnxRsvpSessionV5v0Group,
            tmnxRsvpGeneralV6v0Group,
            tmnxRsvpIfV6v0Group,
            tmnxRsvpNbrV6v0Group,
            tmnxRsvpSessionV6v0Group,
            tmnxRsvpGeneralV6v1Group,
            tmnxRsvpIfV7v0Group,
            tmnxRsvpDSTEV7v0Group,
            tmnxRsvpGeneralV7v0Group,
            tmnxRsvpSessionV7v0Group,
            tmnxRsvpGenTEThresholdV8v0Group,
            tmnxRsvpIfTEThresholdV8v0Group,
            tmnxRsvpGeneralV8v0Group,
            tmnxRsvpIfV8v0Group,
            tmnxRsvpGeneralV9v0Group,
            tmnxRsvpNotificationV9v0Group,
            tmnxRsvpGeneralV10v0Group,
            tmnxRsvpGeneralV11v0Group,
            tmnxRsvpGeneralV12v0Group,
            tmnxRsvpGeneralV14v0Group,
            tmnxRsvpIfV15v0Group
        }
    ::= { tmnxRsvpCompliances 12 }

tmnxRsvpV16v0Compliance          MODULE-COMPLIANCE
    STATUS      current
    DESCRIPTION
        "The compliance statement for management of extended RSVP capabilities
         on Nokia SROS series systems release 16.0."
    MODULE
        MANDATORY-GROUPS {
            tmnxRsvpGeneralV16v0Group
        }
    ::= { tmnxRsvpCompliances 13 }

tmnxRsvpV19v0Compliance          MODULE-COMPLIANCE
    STATUS      current
    DESCRIPTION
        "The compliance statement for management of extended RSVP capabilities
         on Nokia SROS series systems release 19.0."
    MODULE
        MANDATORY-GROUPS {
            tmnxRsvpIfReservedBW64Group
        }
    ::= { tmnxRsvpCompliances 14 }

tmnxRsvpV20v0Compliance          MODULE-COMPLIANCE
    STATUS      current
    DESCRIPTION
        "The compliance statement for management of extended RSVP capabilities
         on Nokia SROS series systems release 20.0."
    MODULE
        MANDATORY-GROUPS {
            tmnxRsvpGeneralGroup,
            tmnxRsvpSessionGroup,
            tmnxRsvpNotificationGroup,
            tmnxRsvpSessionV5v0Group,
            tmnxRsvpGeneralV6v0Group,
            tmnxRsvpIfV6v0Group,
            tmnxRsvpNbrV6v0Group,
            tmnxRsvpSessionV6v0Group,
            tmnxRsvpGeneralV6v1Group,
            tmnxRsvpIfV7v0Group,
            tmnxRsvpDSTEV7v0Group,
            tmnxRsvpGeneralV7v0Group,
            tmnxRsvpSessionV7v0Group,
            tmnxRsvpGenTEThresholdV8v0Group,
            tmnxRsvpIfTEThresholdV8v0Group,
            tmnxRsvpGeneralV8v0Group,
            tmnxRsvpGeneralV9v0Group,
            tmnxRsvpNotificationV9v0Group,
            tmnxRsvpGeneralV10v0Group,
            tmnxRsvpGeneralV11v0Group,
            tmnxRsvpGeneralV12v0Group,
            tmnxRsvpGeneralV14v0Group,
            tmnxRsvpIfV20v0Group
        }
    ::= { tmnxRsvpCompliances 15 }

tmnxRsvpV22v0Compliance          MODULE-COMPLIANCE
    STATUS      current
    DESCRIPTION
        "The compliance statement for management of extended RSVP capabilities
         on Nokia SROS series systems release 22.0."
    MODULE
        MANDATORY-GROUPS {
            tmnxRsvpAuthOverBypassGroup
        }
    ::= { tmnxRsvpCompliances 16 }

tmnxRsvpGroups                   OBJECT IDENTIFIER ::= { tmnxRsvpConformance 2 }

tmnxRsvpGeneralGroup             OBJECT-GROUP
    OBJECTS     {
        vRtrRsvpGeneralLastChange,
        vRtrRsvpGeneralAdminState,
        vRtrRsvpGeneralOperState,
        vRtrRsvpGeneralKeepMultiplier,
        vRtrRsvpGeneralRefreshTime,
        vRtrRsvpGeneralMsgPacing,
        vRtrRsvpGeneralMsgPacingMaxBurst,
        vRtrRsvpGeneralMsgPacingPeriod,
        vRtrRsvpGeneralPsbTimeouts,
        vRtrRsvpGeneralRsbTimeouts
    }
    STATUS      current
    DESCRIPTION
        "The group of objects supporting management of extended RSVP general
         capabilities on Nokia SROS series systems."
    ::= { tmnxRsvpGroups 1 }

tmnxRsvpSessionGroup             OBJECT-GROUP
    OBJECTS     {
        vRtrRsvpSessionState,
        vRtrRsvpSessionName,
        vRtrRsvpSessionSetupPriority,
        vRtrRsvpSessionHoldPriority,
        vRtrRsvpSessionFlags,
        vRtrRsvpSessionEndpointAddress,
        vRtrRsvpSessionLspId,
        vRtrRsvpSessionSenderAddress,
        vRtrRsvpSessionType,
        vRtrRsvpSessionLocalProtectAvailable,
        vRtrRsvpSessionLocalProtectInUse,
        vRtrRsvpSessionStyle,
        vRtrRsvpSessionTunnelId,
        vRtrRsvpSessionExtTunnelId,
        vRtrRsvpSessionNextHopIpAddress,
        vRtrRsvpSessionDetourIndex,
        vRtrRsvpSessionDetourPLRId,
        vRtrRsvpSessionDetourAvoidNodeId,
        vRtrRsvpSessionPreviousHop,
        vRtrRsvpSessionFailCode,
        vRtrRsvpSessionFailNodeAddr,
        vRtrRsvpSessionXCIndex,
        vRtrRsvpSessionBypassIndex,
        vRtrRsvpSessionBypassAvoid,
        vRtrRsvpSessionBypassActive,
        vRtrRsvpSessionBypassDnstrmLabel,
        vRtrRsvpSessionTxPaths,
        vRtrRsvpSessionRxPaths,
        vRtrRsvpSessionTxResvs,
        vRtrRsvpSessionRxResvs,
        vRtrRsvpSessionDetourTimeUp,
        vRtrRsvpSessionDetourAge,
        vRtrRsvpSessionBypassTimeUp,
        vRtrRsvpSessionBypassAge,
        vRtrRsvpSessionBypassLspCount
    }
    STATUS      current
    DESCRIPTION
        "The group of objects supporting management of extended RSVP sessions
         on Nokia SROS series systems."
    ::= { tmnxRsvpGroups 3 }

tmnxRsvpNotifyObjsGroup          OBJECT-GROUP
    OBJECTS     {
        vRtrRsvpIfNbrDownReasonCode,
        vRtrRsvpPEFailOverReasonCode
    }
    STATUS      current
    DESCRIPTION
        "The group of objects supporting extended RSVP notifications on Nokia
         SROS series systems."
    ::= { tmnxRsvpGroups 4 }

tmnxRsvpNotificationGroup        NOTIFICATION-GROUP
    NOTIFICATIONS {
        vRtrRsvpStateChange,
        vRtrRsvpIfStateChange,
        vRtrRsvpIfNbrStateUp,
        vRtrRsvpIfNbrStateDown
    }
    STATUS      current
    DESCRIPTION
        "The group of notifications supporting the extended RSVP capabilities
         on Nokia SROS series systems."
    ::= { tmnxRsvpGroups 5 }

tmnxRsvpIfV3v0Group              OBJECT-GROUP
    OBJECTS     {
        vRtrRsvpIfLastEnabledTime,
        vRtrRsvpIfVRtrIfIndex,
        vRtrRsvpIfAggregate,
        vRtrRsvpIfAuthenticationKey,
        vRtrRsvpIfHelloInterval,
        vRtrRsvpIfSubscription,
        vRtrRsvpIfOperState,
        vRtrRsvpIfActiveSessionCount,
        vRtrRsvpIfActiveReservationCount,
        vRtrRsvpIfTotalSessionCount,
        vRtrRsvpIfBandwidth,
        vRtrRsvpIfReservedBandwidth,
        vRtrRsvpIfStatTxPaths,
        vRtrRsvpIfStatTxPathErrors,
        vRtrRsvpIfStatTxPathTears,
        vRtrRsvpIfStatTxResvs,
        vRtrRsvpIfStatTxResvErrors,
        vRtrRsvpIfStatTxResvTears,
        vRtrRsvpIfStatTxResvConfirms,
        vRtrRsvpIfStatTxBundles,
        vRtrRsvpIfStatTxAcks,
        vRtrRsvpIfStatTxHelloReqs,
        vRtrRsvpIfStatTxSRefreshes,
        vRtrRsvpIfStatTxPkts,
        vRtrRsvpIfStatTxErrorPkts,
        vRtrRsvpIfStatTxTotalPkts,
        vRtrRsvpIfStatRxPaths,
        vRtrRsvpIfStatRxPathErrors,
        vRtrRsvpIfStatRxPathTears,
        vRtrRsvpIfStatRxResvs,
        vRtrRsvpIfStatRxResvErrors,
        vRtrRsvpIfStatRxResvTears,
        vRtrRsvpIfStatRxResvConfirms,
        vRtrRsvpIfStatRxBundles,
        vRtrRsvpIfStatRxAcks,
        vRtrRsvpIfStatRxHelloReqs,
        vRtrRsvpIfStatRxSRefreshes,
        vRtrRsvpIfStatRxPkts,
        vRtrRsvpIfStatRxErrorPkts,
        vRtrRsvpIfStatRxTotalPkts,
        vRtrRsvpIfStatHelloTimeout
    }
    STATUS      obsolete
    DESCRIPTION
        "The group of objects supporting management of extended RSVP interfaces
         on Nokia SROS series systems release 3.0."
    ::= { tmnxRsvpGroups 6 }

tmnxRsvpObsoleteV3v0Group        OBJECT-GROUP
    OBJECTS     {
        vRtrRsvpIfKeepMultiplier,
        vRtrRsvpIfRefreshTime
    }
    STATUS      current
    DESCRIPTION
        "The group of objects supporting management of extended RSVP obsoleted
         in Nokia SROS series release 3.0."
    ::= { tmnxRsvpGroups 7 }

tmnxRsvpIfV5v0Group              OBJECT-GROUP
    OBJECTS     {
        vRtrRsvpIfLastEnabledTime,
        vRtrRsvpIfVRtrIfIndex,
        vRtrRsvpIfAggregate,
        vRtrRsvpIfAuthenticationKey,
        vRtrRsvpIfHelloInterval,
        vRtrRsvpIfSubscription,
        vRtrRsvpIfOperState,
        vRtrRsvpIfActiveSessionCount,
        vRtrRsvpIfActiveReservationCount,
        vRtrRsvpIfTotalSessionCount,
        vRtrRsvpIfBandwidth,
        vRtrRsvpIfReservedBandwidth,
        vRtrRsvpIfAuthChallenge,
        vRtrRsvpIfAuthentication,
        vRtrRsvpIfAuthKeyId,
        vRtrRsvpIfAuthRxSeqNum,
        vRtrRsvpIfAuthTxSeqNum,
        vRtrRsvpIfAuthWindowSize,
        vRtrRsvpIfStatTxPaths,
        vRtrRsvpIfStatTxPathErrors,
        vRtrRsvpIfStatTxPathTears,
        vRtrRsvpIfStatTxResvs,
        vRtrRsvpIfStatTxResvErrors,
        vRtrRsvpIfStatTxResvTears,
        vRtrRsvpIfStatTxResvConfirms,
        vRtrRsvpIfStatTxBundles,
        vRtrRsvpIfStatTxAcks,
        vRtrRsvpIfStatTxHelloReqs,
        vRtrRsvpIfStatTxSRefreshes,
        vRtrRsvpIfStatTxPkts,
        vRtrRsvpIfStatTxErrorPkts,
        vRtrRsvpIfStatTxTotalPkts,
        vRtrRsvpIfStatRxPaths,
        vRtrRsvpIfStatRxPathErrors,
        vRtrRsvpIfStatRxPathTears,
        vRtrRsvpIfStatRxResvs,
        vRtrRsvpIfStatRxResvErrors,
        vRtrRsvpIfStatRxResvTears,
        vRtrRsvpIfStatRxResvConfirms,
        vRtrRsvpIfStatRxBundles,
        vRtrRsvpIfStatRxAcks,
        vRtrRsvpIfStatRxHelloReqs,
        vRtrRsvpIfStatRxSRefreshes,
        vRtrRsvpIfStatRxPkts,
        vRtrRsvpIfStatRxErrorPkts,
        vRtrRsvpIfStatRxTotalPkts,
        vRtrRsvpIfStatHelloTimeout,
        vRtrRsvpIfStatTxAuthErrors,
        vRtrRsvpIfStatRxAuthErrors
    }
    STATUS      obsolete
    DESCRIPTION
        "The group of objects supporting management of extended RSVP interfaces
         on a Nokia SROS series systems release 5.0."
    ::= { tmnxRsvpGroups 8 }

tmnxRsvpSessionV5v0Group         OBJECT-GROUP
    OBJECTS     {
        vRtrRsvpSessionTypeName,
        vRtrRsvpProtectedSessionName
    }
    STATUS      current
    DESCRIPTION
        "The group of objects supporting management of extended RSVP sessions
         on Nokia SROS series systems release 5.0."
    ::= { tmnxRsvpGroups 9 }

tmnxRsvpGeneralV6v0Group         OBJECT-GROUP
    OBJECTS     {
        vRtrRsvpGeneralRefreshBypass,
        vRtrRsvpGenRapidRetransmitTime,
        vRtrRsvpGenRapidRetryLimit
    }
    STATUS      current
    DESCRIPTION
        "The group of objects supporting management of extended RSVP general
         capabilities on Nokia SROS series systems release 6.0."
    ::= { tmnxRsvpGroups 10 }

tmnxRsvpIfV6v0Group              OBJECT-GROUP
    OBJECTS     {
        vRtrRsvpIfRefreshReduction,
        vRtrRsvpIfReliableDelivery,
        vRtrRsvpIfBfdEnabled
    }
    STATUS      current
    DESCRIPTION
        "The group of objects supporting management of extended RSVP interfaces
         on Nokia SROS series systems release 6.0."
    ::= { tmnxRsvpGroups 11 }

tmnxRsvpNbrV6v0Group             OBJECT-GROUP
    OBJECTS     {
        vRtrRsvpNbrOperState,
        vRtrRsvpNbrLastOperChange,
        vRtrRsvpNbrFlags,
        vRtrRsvpNbrSrcInstance,
        vRtrRsvpNbrDstInstance,
        vRtrRsvpNbrHelloRefreshTimeRem,
        vRtrRsvpNbrHelloTimeoutTimeRem,
        vRtrRsvpNbrHelloTimeoutCnt,
        vRtrRsvpNbrInstanceMismatchCnt,
        vRtrRsvpNbrSrefreshTimeRem,
        vRtrRsvpNbrEpochNum,
        vRtrRsvpNbrMaxMsgId,
        vRtrRsvpNbrOutofOrderMsgs,
        vRtrRsvpNbrRetransmittedMsgs
    }
    STATUS      current
    DESCRIPTION
        "The group of objects supporting management of RSVP neighbors on Nokia
         SROS series systems release 6.0."
    ::= { tmnxRsvpGroups 12 }

tmnxRsvpSessionV6v0Group         OBJECT-GROUP
    OBJECTS     {
        vRtrRsvpSessionTxSrefreshPaths,
        vRtrRsvpSessionRxSrefreshPaths,
        vRtrRsvpSessionTxSrefreshResvs,
        vRtrRsvpSessionRxSrefreshResvs
    }
    STATUS      current
    DESCRIPTION
        "The group of objects supporting management of RSVP sessions on Nokia
         SROS series systems release 6.0."
    ::= { tmnxRsvpGroups 13 }

tmnxRsvpGeneralV6v1Group         OBJECT-GROUP
    OBJECTS     {
        vRtrRsvpGenGracefulShutdown,
        vRtrRsvpIfGracefulShutdown
    }
    STATUS      current
    DESCRIPTION
        "The group of objects supporting management of extended RSVP general
         capabilities on Nokia SROS series systems release 6.1."
    ::= { tmnxRsvpGroups 14 }

tmnxRsvpIfV7v0Group              OBJECT-GROUP
    OBJECTS     {
        vRtrRsvpIfDSTECt0BwPercent,
        vRtrRsvpIfDSTECt1BwPercent,
        vRtrRsvpIfDSTECt2BwPercent,
        vRtrRsvpIfDSTECt3BwPercent,
        vRtrRsvpIfDSTECt4BwPercent,
        vRtrRsvpIfDSTECt5BwPercent,
        vRtrRsvpIfDSTECt6BwPercent,
        vRtrRsvpIfDSTECt7BwPercent,
        vRtrRsvpIfInheritance,
        vRtrRsvpIfDSTEBC0Bw,
        vRtrRsvpIfDSTEBC1Bw,
        vRtrRsvpIfDSTEBC2Bw,
        vRtrRsvpIfDSTEBC3Bw,
        vRtrRsvpIfDSTEBC4Bw,
        vRtrRsvpIfDSTEBC5Bw,
        vRtrRsvpIfDSTEBC6Bw,
        vRtrRsvpIfDSTEBC7Bw,
        vRtrRsvpIfDSTEReservedBw,
        vRtrRsvpIfDSTEUnreservedBw
    }
    STATUS      current
    DESCRIPTION
        "The group of objects supporting management of extended RSVP interface
         capabilities on Nokia SROS series systems release 7.0."
    ::= { tmnxRsvpGroups 15 }

tmnxRsvpDSTEV7v0Group            OBJECT-GROUP
    OBJECTS     {
        vRtrRsvpDSTETeClassClassType,
        vRtrRsvpDSTETeClassPriority,
        vRtrRsvpDSTEAdmCtlModel,
        vRtrRsvpDSTECt0BwPercent,
        vRtrRsvpDSTECt1BwPercent,
        vRtrRsvpDSTECt2BwPercent,
        vRtrRsvpDSTECt3BwPercent,
        vRtrRsvpDSTECt4BwPercent,
        vRtrRsvpDSTECt5BwPercent,
        vRtrRsvpDSTECt6BwPercent,
        vRtrRsvpDSTECt7BwPercent,
        vRtrRsvpDSTEFCMappingRowStatus,
        vRtrRsvpDSTEFCMappingClassType
    }
    STATUS      current
    DESCRIPTION
        "The group of objects supporting management of 'DiffServ' TE feature
         related to RSVP capabilities on Nokia SROS series systems release 7.0."
    ::= { tmnxRsvpGroups 16 }

tmnxRsvpGeneralV7v0Group         OBJECT-GROUP
    OBJECTS     {
        vRtrRsvpGenPreemptionTimer
    }
    STATUS      current
    DESCRIPTION
        "The group of objects supporting management of extended RSVP general
         capabilities on Nokia SROS series systems release 7.0."
    ::= { tmnxRsvpGroups 17 }

tmnxRsvpSessionV7v0Group         OBJECT-GROUP
    OBJECTS     {
        vRtrRsvpSessionSubGrpId,
        vRtrRsvpSessionSubGrpOrgIdType,
        vRtrRsvpSessionSubGrpOrgIdAddr,
        vRtrRsvpSessionLeafAddrType,
        vRtrRsvpSessionLeafAddr,
        vRtrRsvpSessionP2mpId,
        vRtrRsvpSessionClassType
    }
    STATUS      current
    DESCRIPTION
        "The group of objects supporting management of RSVP sessions on Nokia
         SROS series systems release 7.0."
    ::= { tmnxRsvpGroups 18 }

tmnxRsvpGenTEThresholdV8v0Group  OBJECT-GROUP
    OBJECTS     {
        vRtrRsvpGenTEThresholdLevelUp1,
        vRtrRsvpGenTEThresholdLevelUp2,
        vRtrRsvpGenTEThresholdLevelUp3,
        vRtrRsvpGenTEThresholdLevelUp4,
        vRtrRsvpGenTEThresholdLevelUp5,
        vRtrRsvpGenTEThresholdLevelUp6,
        vRtrRsvpGenTEThresholdLevelUp7,
        vRtrRsvpGenTEThresholdLevelUp8,
        vRtrRsvpGenTEThresholdLevelUp9,
        vRtrRsvpGenTEThresholdLevelUp10,
        vRtrRsvpGenTEThresholdLevelUp11,
        vRtrRsvpGenTEThresholdLevelUp12,
        vRtrRsvpGenTEThresholdLevelUp13,
        vRtrRsvpGenTEThresholdLevelUp14,
        vRtrRsvpGenTEThresholdLevelUp15,
        vRtrRsvpGenTEThresholdLevelUp16,
        vRtrRsvpGenTEThresholdLevelDn1,
        vRtrRsvpGenTEThresholdLevelDn2,
        vRtrRsvpGenTEThresholdLevelDn3,
        vRtrRsvpGenTEThresholdLevelDn4,
        vRtrRsvpGenTEThresholdLevelDn5,
        vRtrRsvpGenTEThresholdLevelDn6,
        vRtrRsvpGenTEThresholdLevelDn7,
        vRtrRsvpGenTEThresholdLevelDn8,
        vRtrRsvpGenTEThresholdLevelDn9,
        vRtrRsvpGenTEThresholdLevelDn10,
        vRtrRsvpGenTEThresholdLevelDn11,
        vRtrRsvpGenTEThresholdLevelDn12,
        vRtrRsvpGenTEThresholdLevelDn13,
        vRtrRsvpGenTEThresholdLevelDn14,
        vRtrRsvpGenTEThresholdLevelDn15,
        vRtrRsvpGenTEThresholdLevelDn16
    }
    STATUS      current
    DESCRIPTION
        "The group of objects supporting management of RSVP TE Threshold on
         Nokia SROS series systems release 8.0."
    ::= { tmnxRsvpGroups 19 }

tmnxRsvpIfTEThresholdV8v0Group   OBJECT-GROUP
    OBJECTS     {
        vRtrRsvpIfTEThresholdLevelUp1,
        vRtrRsvpIfTEThresholdLevelUp2,
        vRtrRsvpIfTEThresholdLevelUp3,
        vRtrRsvpIfTEThresholdLevelUp4,
        vRtrRsvpIfTEThresholdLevelUp5,
        vRtrRsvpIfTEThresholdLevelUp6,
        vRtrRsvpIfTEThresholdLevelUp7,
        vRtrRsvpIfTEThresholdLevelUp8,
        vRtrRsvpIfTEThresholdLevelUp9,
        vRtrRsvpIfTEThresholdLevelUp10,
        vRtrRsvpIfTEThresholdLevelUp11,
        vRtrRsvpIfTEThresholdLevelUp12,
        vRtrRsvpIfTEThresholdLevelUp13,
        vRtrRsvpIfTEThresholdLevelUp14,
        vRtrRsvpIfTEThresholdLevelUp15,
        vRtrRsvpIfTEThresholdLevelUp16,
        vRtrRsvpIfTEThresholdLevelDn1,
        vRtrRsvpIfTEThresholdLevelDn2,
        vRtrRsvpIfTEThresholdLevelDn3,
        vRtrRsvpIfTEThresholdLevelDn4,
        vRtrRsvpIfTEThresholdLevelDn5,
        vRtrRsvpIfTEThresholdLevelDn6,
        vRtrRsvpIfTEThresholdLevelDn7,
        vRtrRsvpIfTEThresholdLevelDn8,
        vRtrRsvpIfTEThresholdLevelDn9,
        vRtrRsvpIfTEThresholdLevelDn10,
        vRtrRsvpIfTEThresholdLevelDn11,
        vRtrRsvpIfTEThresholdLevelDn12,
        vRtrRsvpIfTEThresholdLevelDn13,
        vRtrRsvpIfTEThresholdLevelDn14,
        vRtrRsvpIfTEThresholdLevelDn15,
        vRtrRsvpIfTEThresholdLevelDn16
    }
    STATUS      current
    DESCRIPTION
        "The group of objects supporting management of RSVP TE Threshold per
         interface on Nokia SROS series systems release 8.0."
    ::= { tmnxRsvpGroups 20 }

tmnxRsvpGeneralV8v0Group         OBJECT-GROUP
    OBJECTS     {
        vRtrRsvpGenTEThresholdUpdate,
        vRtrRsvpGenTEUpdateOnCacFail,
        vRtrRsvpGenTEUpdateTimer,
        vRtrRsvpGenImplicitNull
    }
    STATUS      current
    DESCRIPTION
        "The group of objects supporting management of extended RSVP general
         capabilities on Nokia SROS series systems release 8.0."
    ::= { tmnxRsvpGroups 21 }

tmnxRsvpIfV8v0Group              OBJECT-GROUP
    OBJECTS     {
        vRtrRsvpIfImplicitNull,
        vRtrRsvpIfIgpUpdatePending,
        vRtrRsvpIfIgpNextUpdate,
        vRtrRsvpIfMaxResvBandwidth
    }
    STATUS      obsolete
    DESCRIPTION
        "The group of objects supporting management of extended RSVP interface
         capabilities on Nokia SROS series systems release 8.0."
    ::= { tmnxRsvpGroups 22 }

tmnxRsvpGeneralV9v0Group         OBJECT-GROUP
    OBJECTS     {
        vRtrRsvpGenNodeIdInRro
    }
    STATUS      current
    DESCRIPTION
        "The group of objects supporting management of extended RSVP general
         capabilities on Nokia SROS series systems release 9.0."
    ::= { tmnxRsvpGroups 23 }

tmnxRsvpNotificationV9v0Group    NOTIFICATION-GROUP
    NOTIFICATIONS {
        vRtrRsvpPEFailOverStdByToPri,
        vRtrRsvpPEFailOverPriToStdBy
    }
    STATUS      current
    DESCRIPTION
        "The group of notifications supporting the extended RSVP capabilities
         on for release 9.0 Nokia SROS series systems."
    ::= { tmnxRsvpGroups 24 }

tmnxRsvpGeneralV10v0Group        OBJECT-GROUP
    OBJECTS     {
        vRtrRsvpGenP2PMrgPntAbrtTimer,
        vRtrRsvpGenP2MPMrgPntAbrtTimer,
        vRtrRsvpIfGraceHelper,
        vRtrRsvpGeneralGrHlprMaxRcvryTm,
        vRtrRsvpGeneralGrHlprMaxRstrtTm,
        vRtrRsvpNbrGrState,
        vRtrRsvpNbrGrHelperInvkCnt,
        vRtrRsvpNbrGrHelperTimeRem,
        vRtrRsvpNbrGrRestartCap,
        vRtrRsvpNbrGrRestartTime,
        vRtrRsvpNbrGrRecoveryTime,
        vRtrRsvpSessionFrrProperties,
        vRtrRsvpGeneralGrhPsbTimeouts,
        vRtrRsvpGeneralGrhRsbTimeouts
    }
    STATUS      current
    DESCRIPTION
        "The group of objects supporting management of extended RSVP general
         capabilities on Nokia SROS series systems release 10.0."
    ::= { tmnxRsvpGroups 25 }

tmnxRsvpGeneralV11v0Group        OBJECT-GROUP
    OBJECTS     {
        vRtrRsvpSessionExNodeAddrType,
        vRtrRsvpSessionExNodeAddr,
        vRtrRsvpSessionBypassInterArea
    }
    STATUS      current
    DESCRIPTION
        "The group of objects supporting management of extended RSVP general
         capabilities on Nokia SROS series systems release 11.0."
    ::= { tmnxRsvpGroups 26 }

tmnxRsvpGeneralV12v0Group        OBJECT-GROUP
    OBJECTS     {
        vRtrRsvpIfAuthKeyChain,
        vRtrRsvpSessionBypassPathCost,
        vRtrRsvpSessBypLastResigAttempt,
        vRtrRsvpSessBypLastResigReason,
        vRtrRsvpSessBypLastResigStatus,
        vRtrRsvpSBLastResigStatusReason
    }
    STATUS      current
    DESCRIPTION
        "The group of objects supporting management of extended RSVP general
         capabilities on Nokia SROS series systems release 12.0."
    ::= { tmnxRsvpGroups 27 }

tmnxRsvpGeneralV14v0Group        OBJECT-GROUP
    OBJECTS     {
        vRtrRsvpGenEntropyLblCapability,
        vRtrRsvpSessionLspAttributeFlags
    }
    STATUS      current
    DESCRIPTION
        "The group of objects supporting management of extended RSVP general
         capabilities on Nokia SROS series systems release 14.0."
    ::= { tmnxRsvpGroups 28 }

tmnxRsvpIfV15v0Group             OBJECT-GROUP
    OBJECTS     {
        vRtrRsvpIfLastEnabledTime,
        vRtrRsvpIfVRtrIfIndex,
        vRtrRsvpIfAggregate,
        vRtrRsvpIfAuthenticationKey,
        vRtrRsvpIfHelloInterval,
        vRtrRsvpIfSubscription,
        vRtrRsvpIfOperState,
        vRtrRsvpIfActiveSessionCount,
        vRtrRsvpIfActiveReservationCount,
        vRtrRsvpIfTotalSessionCount,
        vRtrRsvpIfBandwidth,
        vRtrRsvpIfReservedBandwidth,
        vRtrRsvpIfAuthentication,
        vRtrRsvpIfAuthKeyId,
        vRtrRsvpIfAuthRxSeqNum,
        vRtrRsvpIfAuthTxSeqNum,
        vRtrRsvpIfAuthWindowSize,
        vRtrRsvpIfStatTxPaths,
        vRtrRsvpIfStatTxPathErrors,
        vRtrRsvpIfStatTxPathTears,
        vRtrRsvpIfStatTxResvs,
        vRtrRsvpIfStatTxResvErrors,
        vRtrRsvpIfStatTxResvTears,
        vRtrRsvpIfStatTxResvConfirms,
        vRtrRsvpIfStatTxBundles,
        vRtrRsvpIfStatTxAcks,
        vRtrRsvpIfStatTxHelloReqs,
        vRtrRsvpIfStatTxSRefreshes,
        vRtrRsvpIfStatTxPkts,
        vRtrRsvpIfStatTxErrorPkts,
        vRtrRsvpIfStatTxTotalPkts,
        vRtrRsvpIfStatRxPaths,
        vRtrRsvpIfStatRxPathErrors,
        vRtrRsvpIfStatRxPathTears,
        vRtrRsvpIfStatRxResvs,
        vRtrRsvpIfStatRxResvErrors,
        vRtrRsvpIfStatRxResvTears,
        vRtrRsvpIfStatRxResvConfirms,
        vRtrRsvpIfStatRxBundles,
        vRtrRsvpIfStatRxAcks,
        vRtrRsvpIfStatRxHelloReqs,
        vRtrRsvpIfStatRxSRefreshes,
        vRtrRsvpIfStatRxPkts,
        vRtrRsvpIfStatRxErrorPkts,
        vRtrRsvpIfStatRxTotalPkts,
        vRtrRsvpIfStatHelloTimeout,
        vRtrRsvpIfStatTxAuthErrors,
        vRtrRsvpIfStatRxAuthErrors
    }
    STATUS      obsolete
    DESCRIPTION
        "The group of objects supporting management of extended RSVP interfaces
         on a Nokia SROS series systems release 15.0."
    ::= { tmnxRsvpGroups 29 }

tmnxRsvpIfObsoleteV15v0Group     OBJECT-GROUP
    OBJECTS     {
        vRtrRsvpIfAuthChallenge
    }
    STATUS      current
    DESCRIPTION
        "The group of obsolete objects for RSVP interfaces on a Nokia SROS
         series systems release 15.0."
    ::= { tmnxRsvpGroups 30 }

tmnxRsvpGeneralV16v0Group        OBJECT-GROUP
    OBJECTS     {
        vRtrRsvpGenExtDBwAccounting,
        vRtrRsvpGenExtDBwMultiplier,
        vRtrRsvpGenExtDBwSampIntvl,
        vRtrRsvpGenExtDBwSampMult,
        vRtrRsvpGenExtDBwUpThdPercent,
        vRtrRsvpGenExtDBwUpThdBw,
        vRtrRsvpGenExtDBwDwnThdPercent,
        vRtrRsvpGenExtDBwDwnThdBw,
        vRtrRsvpIfExtInheritance,
        vRtrRsvpIfExtDBwMultiplier,
        vRtrRsvpIfExtDBwUpThdPercent,
        vRtrRsvpIfExtDBwUpThdBw,
        vRtrRsvpIfExtDBwDwnThdPercent,
        vRtrRsvpIfExtDBwDwnThdBw,
        vRtrRsvpIfExtDBwLastSampleIndex,
        vRtrRsvpIfExtDBwLastSample,
        vRtrRsvpIfExtDBwLatestCalDBw,
        vRtrRsvpIfExtAdvMRLB,
        vRtrRsvpIfExtDBwLastSampleTime,
        vRtrRsvpIfExtDBwLatestCalDBwTime,
        vRtrRsvpIfExtLastTedbUpdateTime
    }
    STATUS      current
    DESCRIPTION
        "The group of objects supporting management of extended RSVP general
         capabilities on Nokia SROS series systems release 16.0."
    ::= { tmnxRsvpGroups 31 }

tmnxRsvpIfReservedBW64Group      OBJECT-GROUP
    OBJECTS     {
        vRtrRsvpIfReservedBandwidth64,
        vRtrRsvpIfMaxReservedBandwidth64
    }
    STATUS      current
    DESCRIPTION
        "The group of objects supporting management of reserved  bandwidth for
         extended RSVP interface capabilities on  Nokia SROS series systems
         release 19.0."
    ::= { tmnxRsvpGroups 32 }

tmnxRsvpIfV20v0Group             OBJECT-GROUP
    OBJECTS     {
        vRtrRsvpIfLastEnabledTime,
        vRtrRsvpIfVRtrIfIndex,
        vRtrRsvpIfAggregate,
        vRtrRsvpIfAuthenticationKey,
        vRtrRsvpIfHelloInterval,
        vRtrRsvpIfSubscription,
        vRtrRsvpIfOperState,
        vRtrRsvpIfActiveSessionCount,
        vRtrRsvpIfActiveReservationCount,
        vRtrRsvpIfTotalSessionCount,
        vRtrRsvpIfBandwidth,
        vRtrRsvpIfAuthentication,
        vRtrRsvpIfAuthKeyId,
        vRtrRsvpIfAuthRxSeqNum,
        vRtrRsvpIfAuthTxSeqNum,
        vRtrRsvpIfAuthWindowSize,
        vRtrRsvpIfStatTxPaths,
        vRtrRsvpIfStatTxPathErrors,
        vRtrRsvpIfStatTxPathTears,
        vRtrRsvpIfStatTxResvs,
        vRtrRsvpIfStatTxResvErrors,
        vRtrRsvpIfStatTxResvTears,
        vRtrRsvpIfStatTxResvConfirms,
        vRtrRsvpIfStatTxBundles,
        vRtrRsvpIfStatTxAcks,
        vRtrRsvpIfStatTxHelloReqs,
        vRtrRsvpIfStatTxSRefreshes,
        vRtrRsvpIfStatTxPkts,
        vRtrRsvpIfStatTxErrorPkts,
        vRtrRsvpIfStatTxTotalPkts,
        vRtrRsvpIfStatRxPaths,
        vRtrRsvpIfStatRxPathErrors,
        vRtrRsvpIfStatRxPathTears,
        vRtrRsvpIfStatRxResvs,
        vRtrRsvpIfStatRxResvErrors,
        vRtrRsvpIfStatRxResvTears,
        vRtrRsvpIfStatRxResvConfirms,
        vRtrRsvpIfStatRxBundles,
        vRtrRsvpIfStatRxAcks,
        vRtrRsvpIfStatRxHelloReqs,
        vRtrRsvpIfStatRxSRefreshes,
        vRtrRsvpIfStatRxPkts,
        vRtrRsvpIfStatRxErrorPkts,
        vRtrRsvpIfStatRxTotalPkts,
        vRtrRsvpIfStatHelloTimeout,
        vRtrRsvpIfStatTxAuthErrors,
        vRtrRsvpIfStatRxAuthErrors,
        vRtrRsvpIfImplicitNull,
        vRtrRsvpIfIgpUpdatePending,
        vRtrRsvpIfIgpNextUpdate
    }
    STATUS      current
    DESCRIPTION
        "The group of objects supporting management of extended RSVP interfaces
         on a Nokia SROS series systems release 20.0."
    ::= { tmnxRsvpGroups 33 }

tmnxRsvpIfObsoletedV20v0Group    OBJECT-GROUP
    OBJECTS     {
        vRtrRsvpIfReservedBandwidth,
        vRtrRsvpIfMaxResvBandwidth
    }
    STATUS      current
    DESCRIPTION
        "The group of obsolete objects for RSVP interfaces on a Nokia SROS
         series systems release 20.0."
    ::= { tmnxRsvpGroups 34 }

tmnxRsvpAuthOverBypassGroup      OBJECT-GROUP
    OBJECTS     {
        vRtrRsvpGenExtAuthOverBypass
    }
    STATUS      current
    DESCRIPTION
        "The group of objects for RSVP authentication over bypass LSP on a
         Nokia SROS series systems."
    ::= { tmnxRsvpGroups 35 }

tmnxRsvpNotifyPrefix             OBJECT IDENTIFIER ::= { tmnxSRNotifyPrefix 7 }

tmnxRsvpNotifications            OBJECT IDENTIFIER ::= { tmnxRsvpNotifyPrefix 0 }

vRtrRsvpStateChange              NOTIFICATION-TYPE
    OBJECTS     {
        vRtrID,
        vRtrRsvpGeneralAdminState,
        vRtrRsvpGeneralOperState
    }
    STATUS      current
    DESCRIPTION
        "This Notification is generated when the RSVP module changes state"
    ::= { tmnxRsvpNotifications 1 }

vRtrRsvpIfStateChange            NOTIFICATION-TYPE
    OBJECTS     {
        ifIndex,
        rsvpIfEnabled,
        vRtrRsvpIfOperState
    }
    STATUS      current
    DESCRIPTION
        "This Notification is generated when a RSVP interface changes state"
    ::= { tmnxRsvpNotifications 2 }

vRtrRsvpIfNbrStateUp             NOTIFICATION-TYPE
    OBJECTS     {
        rsvpNbrProtocol
    }
    STATUS      current
    DESCRIPTION
        "The vRtrRsvpIfNbrStateUp notification is generated when a RSVP
         interface neighbor changes to active state"
    ::= { tmnxRsvpNotifications 3 }

vRtrRsvpIfNbrStateDown           NOTIFICATION-TYPE
    OBJECTS     {
        rsvpNbrProtocol,
        vRtrRsvpIfNbrDownReasonCode
    }
    STATUS      current
    DESCRIPTION
        "The vRtrRsvpIfNbrStateDown notification is generated when a RSVP
         interface neighbor changes to inactive state"
    ::= { tmnxRsvpNotifications 4 }

vRtrRsvpPEFailOverPriToStdBy     NOTIFICATION-TYPE
    OBJECTS     {
        vRtrPimNgMvpnUMHPEStandbyAdrTyp,
        vRtrPimNgMvpnUMHPEStandbyAddr,
        vRtrRsvpPEFailOverReasonCode
    }
    STATUS      current
    DESCRIPTION
        "[CAUSE] The vRtrRsvpPEFailOverPriToStdBy notification is raised when
         primary Provider Edge (PE) has switched over to standby PE. The IP
         address of the primary PE can be extracted from the
         vRtrPimNgMvpnUMHPEAddrType and vRtrPimNgMvpnUMHPEAddr indexes of the
         varbinds in this notification.

         [EFFECT] The tunnel traffic may be affected.

         [RECOVERY] None required."
    ::= { tmnxRsvpNotifications 5 }

vRtrRsvpPEFailOverStdByToPri     NOTIFICATION-TYPE
    OBJECTS     {
        vRtrPimNgMvpnUMHPEStandbyAdrTyp,
        vRtrPimNgMvpnUMHPEStandbyAddr
    }
    STATUS      current
    DESCRIPTION
        "[CAUSE] The vRtrRsvpPEFailOverPriToStdBy notification is raised when
         standby Provider Edge (PE) has switched over to primary PE. The IP
         address of the primary PE can be extracted from the
         vRtrPimNgMvpnUMHPEAddrType and vRtrPimNgMvpnUMHPEAddr indexes of the
         varbinds in this notification.

         [EFFECT] The tunnel traffic may be affected.

         [RECOVERY] None required."
    ::= { tmnxRsvpNotifications 6 }

END
