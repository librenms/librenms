TIMETRA-DHCP-SERVER-MIB DEFINITIONS ::= BEGIN

IMPORTS
    InetAddress, InetAddressPrefixLength,
    InetAddressType
                                                         FROM INET-ADDRESS-MIB
    MODULE-COMPLIANCE, NOTIFICATION-GROUP,
    OBJECT-GROUP
                                                         FROM SNMPv2-CONF
    Counter32, Counter64, Gauge32,
    Integer32, MODULE-IDENTITY,
    NOTIFICATION-TYPE, OBJECT-TYPE,
    Unsigned32
                                                         FROM SNMPv2-SMI
    DateAndTime, DisplayString, MacAddress,
    RowStatus, TEXTUAL-CONVENTION,
    TimeStamp, TruthValue
                                                         FROM SNMPv2-TC
    timetraSRMIBModules, tmnxSRConfs,
    tmnxSRNotifyPrefix, tmnxSRObjs
                                                         FROM TIMETRA-GLOBAL-MIB
    TItemDescription, TNamedItem,
    TNamedItemOrEmpty, TmnxActionType,
    TmnxAdminState, TmnxCreateOrigin,
    TmnxDhcpOptionDisplay,
    TmnxDhcpOptionType,
    TmnxDhcpServerDUIDTypeCode,
    TmnxPppoeUserNameOrEmpty, TmnxVRtrID,
    TmnxVRtrIDOrZero
                                                         FROM TIMETRA-TC-MIB
    vRtrID
                                                         FROM TIMETRA-VRTR-MIB
    ;

timetraDhcpServerMIBModule       MODULE-IDENTITY
    LAST-UPDATED "201703010000Z"
    ORGANIZATION "Nokia"
    CONTACT-INFO
        "Nokia SROS Support
         Web: http://www.nokia.com"
    DESCRIPTION
        "This document is the SNMP MIB module to manage and provision the DHCP
         (Dynamic Host Configuration Protocol) server for the Nokia SROS
         device.

         Copyright 2008-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201703010000Z"
    DESCRIPTION
        "Rev 15.0               1 March 2017 00:00
         15.0 release of the TIMETRA-DHCP-SERVER-MIB."

    REVISION    "201601010000Z"
    DESCRIPTION
        "Rev 14.0               1 Jan 2016 00:00
         14.0 release of the TIMETRA-DHCP-SERVER-MIB."

    REVISION    "201501010000Z"
    DESCRIPTION
        "Rev 13.0               1 Jan 2015 00:00
         13.0 release of the TIMETRA-DHCP-SERVER-MIB."

    REVISION    "201401010000Z"
    DESCRIPTION
        "Rev 12.0               1 Jan 2014 00:00
         12.0 release of the TIMETRA-DHCP-SERVER-MIB."

    REVISION    "201202280000Z"
    DESCRIPTION
        "Rev 10.0               28 Feb 2012 12:00
         10.0 release of the TIMETRA-DHCP-SERVER-MIB."

    REVISION    "201102010000Z"
    DESCRIPTION
        "Rev 9.0                1 Feb 2011 00:00
         9.0 release of the TIMETRA-DHCP-SERVER-MIB."

    REVISION    "200902280000Z"
    DESCRIPTION
        "Rev 7.0                28 Feb 2009 00:00
         7.0 release of the TIMETRA-DHCP-SERVER-MIB."

    REVISION    "200807010000Z"
    DESCRIPTION
        "Rev 6.1                01 Jul 2008 00:00
         6.1 release of the TIMETRA-DHCP-SERVER-MIB."

    REVISION    "200801010000Z"
    DESCRIPTION
        "Rev 0.1                01 Jan 2008 00:00
         Initial version of the TIMETRA-DHCP-SERVER-MIB."

    ::= { timetraSRMIBModules 47 }

TmnxDhcpSvrOperState             ::= TEXTUAL-CONVENTION
    STATUS      current
    DESCRIPTION
        "The TmnxDhcpSvrOperState data type is an enumerated integer
         that describes the values used to identify the operational state of
         a DHCP Server instance.
                unknown
                inService
                outOfService
                transition
                waitPersistence : the DHCP Server instance is waiting for a
                                  persistence action to complete."
    SYNTAX      INTEGER {
        unknown         (1),
        inService       (2),
        outOfService    (3),
        transition      (4),
        waitPersistence (5)
    }

TmnxDhcpSvrClientType            ::= TEXTUAL-CONVENTION
    STATUS      current
    DESCRIPTION
        "Indicates a DHCP Server client type.
         dhcp : CPE is a DHCP client;
         ppp : CPE is a PPP client (IPv4);
         ipoe : CPE is an IPoE client (IPv6);
         ipsec: CPE is an IPSEC tunnel."
    SYNTAX      INTEGER {
        dhcp  (0),
        ppp   (1),
        ipoe  (2),
        ipsec (3)
    }

TmnxDhcpSvrFailCtrlType          ::= TEXTUAL-CONVENTION
    STATUS      current
    DESCRIPTION
        "Indicates a DHCP Server failover control type.
         local         : this system is in control under normal operation;
         remote        : the remote system is in control under normal
                         operation;
         access-driven : the controlling system is decided by the access
                         mechanism."
    SYNTAX      INTEGER {
        local        (1),
        remote       (2),
        accessDriven (3)
    }

TmnxDhcpsFoState                 ::= TEXTUAL-CONVENTION
    STATUS      current
    DESCRIPTION
        "The TmnxDhcpsFoState data type is an enumerated integer that describes
         the values used to identify the failover state of a DHCP Server
         instance.

         unknown
         init            : the DHCP Server instance is preparing
                                  to startup;
         startUp         : the DHCP Server instance is starting up;
         noCommunication : the communication with the partner is lost;
         partnerDown     : the partner is assumed down;
         normal
         shutdown        : the administrative state of the failover
                           facility of this DHCP server instance
                           is 'outOfService', or the administrative
                           state of this DHCP server instance
                           is 'outOfService';
         transition
         preNormal       : sub-state of 'normal', that applies to a pair of
                           servers A and B, while B is recovering after it went down:
             - server A is responding to (instead of dropping) renew and rebind messages
               for remote leases it has allocated during partnerDown;
             - server B is dropping (instead of NACKing) renew and rebind messages for
               yet unknown local leases while resynchronizing with the MCS database."
    SYNTAX      INTEGER {
        unknown         (1),
        init            (2),
        startUp         (3),
        noCommunication (4),
        partnerDown     (5),
        normal          (6),
        shutdown        (7),
        transition      (8),
        preNormal       (9)
    }

TmnxDhcpsFoLeaseFailureReason    ::= TEXTUAL-CONVENTION
    STATUS      current
    DESCRIPTION
        "The TmnxDhcpsFoLeaseFailureReason data type is an enumerated integer
         that describes the values used to identify the reason of a lease
         update failure that occurred in the failover facility of a DHCP Server
         instance.
                foShutdown      : the failover state of this DHCP Server
                                  instance is 'shutdown';
                expired         : the lease received from the peer has expired;
                maxReached      : the maximum number of leases is already
                                  reached; the maximum number of leases is
                                  indicated by the object tmnxDhcpSvrMaxLeases;
                subnetNotFound  : no valid subnet for this lease could be
                                  found;
                rangeNotFound   : no valid include range for this lease could
                                  be found;
                hostConflict    : this DHCP server instance has already leased
                                  this address to another host;
                addressConflict : this DHCP server instance has already leased
                                  another address to this host;
                peerConflict    : the failover peer has leased an address
                                  within a subnet range of which the failover
                                  control is set to 'local' on this local DHCP
                                  server instance;
                persistenceCongested :
                                  the lease received from the peer can not be
                                  persistently stored because the persistence
                                  subsystem is in overload.
                noLeaseHoldTime : tmnxDhcpServerCfgLeaseHoldTime has value '0'
                                  for this DHCP server instance.
                invalidPfxLen   : the prefix of the lease received from the peer
                                  is not inside the range configured in
                                  tmnxDhcpServerPoolMinPrefixLen and
                                  tmnxDhcpServerPoolMaxPrefixLen.
                "
    SYNTAX      INTEGER {
        foShutdown           (1),
        expired              (2),
        maxReached           (3),
        subnetNotFound       (4),
        rangeNotFound        (5),
        hostConflict         (6),
        addressConflict      (7),
        peerConflict         (8),
        persistenceCongested (9),
        noLeaseHoldTime      (10),
        invalidPfxLen        (11)
    }

TmnxDhcpsFoActionType            ::= TEXTUAL-CONVENTION
    STATUS      current
    DESCRIPTION
        "Indicates a DHCP Server failover action type.
         notApplicable   : return value for GETs and GETNEXTs;
         forcePartnerDown: if the failover state of the DHCP server
                           instance is 'noCommunication', force it to
                           transition to 'partnerDown';
         abortStartupWait: abort the startup wait timer."
    SYNTAX      INTEGER {
        notApplicable    (1),
        forcePartnerDown (2),
        abortStartupWait (3)
    }

TmnxDhcpsStickyLeaseActionType   ::= TEXTUAL-CONVENTION
    STATUS      current
    DESCRIPTION
        "Indicates a DHCP Server Sticky Lease action type.
         notApplicable   : return value for GETs and GETNEXTs;
         create          : create a sticky lease."
    SYNTAX      INTEGER {
        notApplicable (1),
        create        (2)
    }

tmnxDhcpServer                   OBJECT IDENTIFIER ::= { tmnxSRObjs 47 }

tmnxDhcpServerObjs               OBJECT IDENTIFIER ::= { tmnxDhcpServer 1 }

tmnxDhcpServerConfigTableLastCh  OBJECT-TYPE
    SYNTAX      TimeStamp
    MAX-ACCESS  read-only
    STATUS      current
    DESCRIPTION
        "The value of the object tmnxDhcpServerConfigTableLastCh indicates the
         value of sysUpTime at the time of the last modification of an entry in
         the tmnxDhcpServerConfigTable."
    ::= { tmnxDhcpServerObjs 1 }

tmnxDhcpServerConfigTable        OBJECT-TYPE
    SYNTAX      SEQUENCE OF TmnxDhcpServerConfigEntry
    MAX-ACCESS  not-accessible
    STATUS      current
    DESCRIPTION
        "The table tmnxDhcpServerConfigTable contains objects to configure the
         DHCP server."
    ::= { tmnxDhcpServerObjs 2 }

tmnxDhcpServerConfigEntry        OBJECT-TYPE
    SYNTAX      TmnxDhcpServerConfigEntry
    MAX-ACCESS  not-accessible
    STATUS      current
    DESCRIPTION
        "Each row represents a DHCP server instance running within a virtual
         router.

         Entries in this table can be created or deleted via SNMP operations."
    INDEX       {
        vRtrID,
        IMPLIED tmnxDhcpServerCfgServerName
    }
    ::= { tmnxDhcpServerConfigTable 1 }

TmnxDhcpServerConfigEntry        ::= SEQUENCE
{
    tmnxDhcpServerCfgServerName      TNamedItem,
    tmnxDhcpServerCfgRowStatus       RowStatus,
    tmnxDhcpServerCfgLastChangeTime  TimeStamp,
    tmnxDhcpServerCfgAdminState      TmnxAdminState,
    tmnxDhcpServerCfgDescription     TItemDescription,
    tmnxDhcpServerCfgUserDatabase    TNamedItemOrEmpty,
    tmnxDhcpServerCfgUseGiAddress    TruthValue,
    tmnxDhcpServerCfgSendForceRenews TruthValue,
    tmnxDhcpServerCfgUseClientPool   TruthValue,
    tmnxDhcpServerCfgOperState       TmnxDhcpSvrOperState,
    tmnxDhcpServerCfgAddrType        InetAddressType,
    tmnxDhcpServerCfgLeaseHoldTime   Unsigned32,
    tmnxDhcpServerCfgUseGiScope      INTEGER,
    tmnxDhcpServerCfgIgnRapidCommit  TruthValue,
    tmnxDhcpServerCfgUserIdent       INTEGER,
    tmnxDhcpServerCfgItfIdMapping    TruthValue,
    tmnxDhcpServerCfgUseCPDelimiter  DisplayString,
    tmnxDhcpServerCfgCreationOrigin  TmnxCreateOrigin,
    tmnxDhcpServerCfgLeaseHoldFor    BITS,
    tmnxDhcpServerCfgAllowLeaseQuery TruthValue,
    tmnxDhcpServerCfgAutoProvisioned TruthValue
}

tmnxDhcpServerCfgServerName      OBJECT-TYPE
    SYNTAX      TNamedItem
    MAX-ACCESS  not-accessible
    STATUS      current
    DESCRIPTION
        "The value of the object tmnxDhcpServerCfgServerName specifies the name
         of this local DHCP server instance.

         This server instance is reachable through the IP address(es) of the
         interface(s) that refer to this DHCP server name in
         TIMETRA-VRTR-MIB::vRtrIfLocalDhcpServerName."
    ::= { tmnxDhcpServerConfigEntry 1 }

tmnxDhcpServerCfgRowStatus       OBJECT-TYPE
    SYNTAX      RowStatus
    MAX-ACCESS  read-create
    STATUS      current
    DESCRIPTION
        "The value of tmnxDhcpServerCfgRowStatus specifies the row status of
         this row."
    ::= { tmnxDhcpServerConfigEntry 2 }

tmnxDhcpServerCfgLastChangeTime  OBJECT-TYPE
    SYNTAX      TimeStamp
    MAX-ACCESS  read-only
    STATUS      current
    DESCRIPTION
        "The value of the object tmnxDhcpServerCfgLastChangeTime indicates the
         sysUpTime at the time of the last modification of this entry."
    ::= { tmnxDhcpServerConfigEntry 3 }

tmnxDhcpServerCfgAdminState      OBJECT-TYPE
    SYNTAX      TmnxAdminState
    MAX-ACCESS  read-create
    STATUS      current
    DESCRIPTION
        "The value of tmnxDhcpServerCfgAdminState specifies the administrative
         state of this local DHCP server instance."
    DEFVAL      { outOfService }
    ::= { tmnxDhcpServerConfigEntry 4 }

tmnxDhcpServerCfgDescription     OBJECT-TYPE
    SYNTAX      TItemDescription
    MAX-ACCESS  read-create
    STATUS      current
    DESCRIPTION
        "The value of the object tmnxDhcpServerCfgDescription specifies a user
         provided description for this DHCP server."
    DEFVAL      { "" }
    ::= { tmnxDhcpServerConfigEntry 5 }

tmnxDhcpServerCfgUserDatabase    OBJECT-TYPE
    SYNTAX      TNamedItemOrEmpty
    MAX-ACCESS  read-create
    STATUS      current
    DESCRIPTION
        "The value of the object tmnxDhcpServerCfgUserDatabase specifies the
         local user database to use for authentication.

         If no authentication is required, the value of this object must be set
         to the empty string, and tmnxDhcpServerCfgUseGiAddress must be set to
         'true(1)' in order for the DHCP server to operate."
    DEFVAL      { "" }
    ::= { tmnxDhcpServerConfigEntry 6 }

tmnxDhcpServerCfgUseGiAddress    OBJECT-TYPE
    SYNTAX      TruthValue
    MAX-ACCESS  read-create
    STATUS      current
    DESCRIPTION
        "The value of the object tmnxDhcpServerCfgUseGiAddress specifies
         whether GI address matching is enabled.

         If tmnxDhcpServerCfgUseGiAddress is set to 'true(1)', then an IP
         address will be provided based on the Gateway IP address from the DHCP
         message, even when authentication fails or when there is no local user
         database configured in tmnxDhcpServerCfgUserDatabase."
    DEFVAL      { false }
    ::= { tmnxDhcpServerConfigEntry 7 }

tmnxDhcpServerCfgSendForceRenews OBJECT-TYPE
    SYNTAX      TruthValue
    MAX-ACCESS  read-create
    STATUS      current
    DESCRIPTION
        "The value of the object tmnxDhcpServerCfgSendForceRenews specifies
         whether the server is allowed to send a DHCP FORCERENEW message to
         DHCP clients.

         If tmnxDhcpServerCfgSendForceRenews is set to 'true(1)', then the
         server will send a DHCP FORCERENEW message to the client when its
         configuration changes in such a way that the clients need to renew
         their lease in order to obtain the new parameters. This will be the
         case when, for example, an option is added to a subnet."
    DEFVAL      { false }
    ::= { tmnxDhcpServerConfigEntry 8 }

tmnxDhcpServerCfgUseClientPool   OBJECT-TYPE
    SYNTAX      TruthValue
    MAX-ACCESS  read-create
    STATUS      current
    DESCRIPTION
        "The value of the object tmnxDhcpServerCfgUseClientPool specifies
         whether the IP address pool selection is based on the relay
         information in the DHCP packet.

         If the value of tmnxDhcpServerCfgUseClientPool is set to 'true (1)',
         the IP address pool selection is determined by the relay information.

         If the value of tmnxDhcpServerCfgUseClientPool is set to 'false (2)',
         or if the DHCP message does not contain the to be used information,
         the pool selection is specified by the value of
         tmnxDhcpServerCfgUseGiAddress.

         When the value of tmnxDhcpServerCfgAddrType is set to 'ipv4 (1), the
         used relay information is the value of the vendor-specific sub-option
         13 of the DHCP option 82.

         When the value of tmnxDhcpServerCfgAddrType is set to 'ipv6 (2), the
         used relay information is the value of the vendor-specific sub-option
         1 for the IA_NA address pool and sub-option 2 for the IA_PD address
         pool."
    DEFVAL      { false }
    ::= { tmnxDhcpServerConfigEntry 9 }

tmnxDhcpServerCfgOperState       OBJECT-TYPE
    SYNTAX      TmnxDhcpSvrOperState
    MAX-ACCESS  read-only
    STATUS      current
    DESCRIPTION
        "The value of tmnxDhcpServerCfgOperState indicates the operational
         state of this local DHCP server instance."
    ::= { tmnxDhcpServerConfigEntry 10 }

tmnxDhcpServerCfgAddrType        OBJECT-TYPE
    SYNTAX      InetAddressType { ipv4 (1), ipv6 (2) }
    MAX-ACCESS  read-create
    STATUS      current
    DESCRIPTION
        "The value of tmnxDhcpServerCfgAddrType specifies the type of addresses
         supported by this local DHCP server instance.

         The value of this object can not be modified after the creation of the
         conceptual row."
    DEFVAL      { ipv4 }
    ::= { tmnxDhcpServerConfigEntry 20 }

tmnxDhcpServerCfgLeaseHoldTime   OBJECT-TYPE
    SYNTAX      Unsigned32 (0..631152000)
    UNITS       "seconds"
    MAX-ACCESS  read-create
    STATUS      current
    DESCRIPTION
        "The value of tmnxDhcpServerCfgLeaseHoldTime specifies the time to
         remember this lease."
    DEFVAL      { 0 }
    ::= { tmnxDhcpServerConfigEntry 21 }

tmnxDhcpServerCfgUseGiScope      OBJECT-TYPE
    SYNTAX      INTEGER {
        subnet (0),
        pool   (1)
    }
    MAX-ACCESS  read-create
    STATUS      current
    DESCRIPTION
        "The value of tmnxDhcpServerCfgUseGiScope specifies whether the GI
         address selects a single subnet or a pool.

         The value of this object is only meaningful when the value of
         tmnxDhcpServerCfgUseGiAddress is set to 'true(1)'."
    DEFVAL      { subnet }
    ::= { tmnxDhcpServerConfigEntry 22 }

tmnxDhcpServerCfgIgnRapidCommit  OBJECT-TYPE
    SYNTAX      TruthValue
    MAX-ACCESS  read-create
    STATUS      current
    DESCRIPTION
        "The value of tmnxDhcpServerCfgIgnRapidCommit specifies whether the
         Rapid Commit Option sent by the DHCPv6 client is processed.

         If the value of this object is set to 'true(1)' and the client has
         included a Rapid Commit option in the Solicit, the server ignores the
         Rapid Commit option and processes the remainder of the message as if
         no Rapid Commit option were present.

         The value of this object is only meaningful when the value of
         tmnxDhcpServerCfgAddrType is set to 'ipv6(2)'."
    REFERENCE
        "RFC 3315 paragraph 17.2.1"
    DEFVAL      { false }
    ::= { tmnxDhcpServerConfigEntry 23 }

tmnxDhcpServerCfgUserIdent       OBJECT-TYPE
    SYNTAX      INTEGER {
        macCircuitId         (1),
        duid                 (2),
        interfaceId          (3),
        interfaceIdLinkLocal (4),
        clientId             (5),
        mac                  (6),
        circuitId            (7),
        remoteId             (8)
    }
    MAX-ACCESS  read-create
    STATUS      current
    DESCRIPTION
        "The value of tmnxDhcpServerCfgUserIdent specifies which method is used
         by the local DHCP server to uniquely identify a user.

         When the value of tmnxDhcpServerCfgAddrType is set to 'ipv4(1)', this
         object can only be set to 'macCircuitId(1)', 'clientId', 'mac',
         'circuitId' or 'remoteId'; the default value is 'macCircuitId'.

         When the value of tmnxDhcpServerCfgAddrType is set to 'ipv6(2)', this
         object can only be set to 'duid', 'interfaceId' or
         'interfaceIdLinkLocal'. The default value is 'duid(2)'."
    ::= { tmnxDhcpServerConfigEntry 24 }

tmnxDhcpServerCfgItfIdMapping    OBJECT-TYPE
    SYNTAX      TruthValue
    MAX-ACCESS  read-create
    STATUS      current
    DESCRIPTION
        "The value of tmnxDhcpServerCfgItfIdMapping specifies whether the
         DHCPv6 server uses a unique /64 prefix per interface-ID options
         combination.

         If the value of this object is set to 'true(1)' and the client
         requests a non-temporary address, the DHCPv6 server leases a /128
         address from the unique /64 prefix belonging to the interface-ID
         option from the relay forward message and, if present, the
         interface-ID option from the encapsulated LDRA relay forward message.

         If the value of this object is set to 'false(2)' each client
         requesting a non-temporary address, gets a /128 lease from a different
         /64 prefix.

         The value of this object is only meaningful when the value of
         tmnxDhcpServerCfgAddrType is set to 'ipv6(2)' and the value of
         iesIfIPv6IpoeBridgedModeEnabled is set to 'true(1)' for all group
         interfaces relaying to this server."
    DEFVAL      { false }
    ::= { tmnxDhcpServerConfigEntry 25 }

tmnxDhcpServerCfgUseCPDelimiter  OBJECT-TYPE
    SYNTAX      DisplayString (SIZE (0..1))
    MAX-ACCESS  read-create
    STATUS      current
    DESCRIPTION
        "A delimiter character to combine primary and secondary pool names."
    DEFVAL      { "" }
    ::= { tmnxDhcpServerConfigEntry 26 }

tmnxDhcpServerCfgCreationOrigin  OBJECT-TYPE
    SYNTAX      TmnxCreateOrigin
    MAX-ACCESS  read-only
    STATUS      current
    DESCRIPTION
        "The value of the object tmnxDhcpServerCfgCreationOrigin indicates the
         mechanism which created this server."
    ::= { tmnxDhcpServerConfigEntry 27 }

tmnxDhcpServerCfgLeaseHoldFor    OBJECT-TYPE
    SYNTAX      BITS {
        solicitedRelease   (0),
        internalLeaseIpsec (1)
    }
    MAX-ACCESS  read-create
    STATUS      current
    DESCRIPTION
        "The value of tmnxDhcpServerCfgLeaseHoldFor specifies behavior details
         while the value of tmnxDhcpServerCfgLeaseHoldTime is not zero.

         By default, sticky leases are only supported for unsolicited releases."
    DEFVAL      { {} }
    ::= { tmnxDhcpServerConfigEntry 28 }

tmnxDhcpServerCfgAllowLeaseQuery OBJECT-TYPE
    SYNTAX      TruthValue
    MAX-ACCESS  read-create
    STATUS      current
    DESCRIPTION
        "The value of tmnxDhcpServerCfgAllowLeaseQuery specifies whether the
         DHCPv6 server will handle Lease Query messages by client id."
    DEFVAL      { false }
    ::= { tmnxDhcpServerConfigEntry 29 }

tmnxDhcpServerCfgAutoProvisioned OBJECT-TYPE
    SYNTAX      TruthValue
    MAX-ACCESS  read-create
    STATUS      current
    DESCRIPTION
        "The value of tmnxDhcpServerCfgAutoProvisioned specifies if the pools
         associated with this server are provisioned automatically rather than
         by means of the tmnxDhcpServerPoolTable, tmnxDhcpServerSubnetTable and
         tmnxDhcpSvrSubnetRangesTable.

         The value of this object can only be modified while the  conceptual
         row is created, and it can not be modified afterwards.

         The value of this object can only be 'true' when the value of
         tmnxDhcpServerCfgAddrType is set to 'ipv6(2).'

         While the value of tmnxDhcpServerCfgAutoProvisioned is equal to
         'true', no further address configuration, for example by means of the
         tables mentioned before, is allowed.

         Address pools can be associated with this server by means of the
         'TIMETRA-NAT-MIB::tmnxNatFwlDomTable'."
    DEFVAL      { false }
    ::= { tmnxDhcpServerConfigEntry 30 }

tmnxDhcpServerPoolTableLastCh    OBJECT-TYPE
    SYNTAX      TimeStamp
    MAX-ACCESS  read-only
    STATUS      current
    DESCRIPTION
        "The value of the object tmnxDhcpServerPoolTableLastCh indicates the
         value of sysUpTime at the time of the last modification of an entry in
         the tmnxDhcpServerPoolTable."
    ::= { tmnxDhcpServerObjs 3 }

tmnxDhcpServerPoolTable          OBJECT-TYPE
    SYNTAX      SEQUENCE OF TmnxDhcpServerPoolEntry
    MAX-ACCESS  not-accessible
    STATUS      current
    DESCRIPTION
        "The table tmnxDhcpServerPoolTable contains objects to configure IP
         address pools.

         Every DHCP server can contain several IP address pools which can each
         contain multiple subnets."
    ::= { tmnxDhcpServerObjs 4 }

tmnxDhcpServerPoolEntry          OBJECT-TYPE
    SYNTAX      TmnxDhcpServerPoolEntry
    MAX-ACCESS  not-accessible
    STATUS      current
    DESCRIPTION
        "Each row represents an IP address pool.

         Entries in this table can be created or deleted via SNMP operations."
    INDEX       {
        vRtrID,
        tmnxDhcpServerCfgServerName,
        tmnxDhcpServerPoolName
    }
    ::= { tmnxDhcpServerPoolTable 1 }

TmnxDhcpServerPoolEntry          ::= SEQUENCE
{
    tmnxDhcpServerPoolName           TNamedItem,
    tmnxDhcpServerPoolRowStatus      RowStatus,
    tmnxDhcpServerPoolLastChangeTime TimeStamp,
    tmnxDhcpServerPoolDescription    TItemDescription,
    tmnxDhcpServerPoolMinLeaseTime   Unsigned32,
    tmnxDhcpServerPoolMaxLeaseTime   Unsigned32,
    tmnxDhcpServerPoolOfferTime      Unsigned32,
    tmnxDhcpServerPoolMinFree        Unsigned32,
    tmnxDhcpServerPoolMinFreeType    INTEGER,
    tmnxDhcpServerPoolDepletedEvent  TruthValue,
    tmnxDhcpServerPoolDlgatedPfxLen  Unsigned32,
    tmnxDhcpServerPoolSubnetBindKey  INTEGER,
    tmnxDhcpServerPoolSubnetBindDly  Unsigned32,
    tmnxDhcpServerPoolNakNonMatch    TruthValue,
    tmnxDhcpServerPoolMinPrefixLen   InetAddressPrefixLength,
    tmnxDhcpServerPoolMaxPrefixLen   InetAddressPrefixLength
}

tmnxDhcpServerPoolName           OBJECT-TYPE
    SYNTAX      TNamedItem
    MAX-ACCESS  not-accessible
    STATUS      current
    DESCRIPTION
        "The value of the object tmnxDhcpServerPoolName specifies the name of
         this IP address pool."
    ::= { tmnxDhcpServerPoolEntry 1 }

tmnxDhcpServerPoolRowStatus      OBJECT-TYPE
    SYNTAX      RowStatus
    MAX-ACCESS  read-create
    STATUS      current
    DESCRIPTION
        "The value of the object tmnxDhcpServerPoolRowStatus specifies the row
         status of this row."
    ::= { tmnxDhcpServerPoolEntry 2 }

tmnxDhcpServerPoolLastChangeTime OBJECT-TYPE
    SYNTAX      TimeStamp
    MAX-ACCESS  read-only
    STATUS      current
    DESCRIPTION
        "The value of the object tmnxDhcpServerPoolLastChangeTime indicates the
         sysUpTime at the time of the last modification of this entry."
    ::= { tmnxDhcpServerPoolEntry 3 }

tmnxDhcpServerPoolDescription    OBJECT-TYPE
    SYNTAX      TItemDescription
    MAX-ACCESS  read-create
    STATUS      current
    DESCRIPTION
        "The value of the object tmnxDhcpServerPoolDescription specifies a user
         provided description for this pool."
    DEFVAL      { "" }
    ::= { tmnxDhcpServerPoolEntry 4 }

tmnxDhcpServerPoolMinLeaseTime   OBJECT-TYPE
    SYNTAX      Unsigned32 (10..315446399)
    UNITS       "seconds"
    MAX-ACCESS  read-create
    STATUS      current
    DESCRIPTION
        "The value of the object tmnxDhcpServerPoolMinLeaseTime specifies the
         minimum lease time.

         The minimum lease time can only be configured to a value that is
         smaller than or equal to the value configured in object
         tmnxDhcpServerPoolMaxLeaseTime."
    DEFVAL      { 600 }
    ::= { tmnxDhcpServerPoolEntry 5 }

tmnxDhcpServerPoolMaxLeaseTime   OBJECT-TYPE
    SYNTAX      Unsigned32 (10..315446399)
    UNITS       "seconds"
    MAX-ACCESS  read-create
    STATUS      current
    DESCRIPTION
        "The value of the object tmnxDhcpServerPoolMaxLeaseTime specifies the
         maximum lease time.

         If there is no lease time configured in DHCP option 51 (in the user
         database, or in the tmnxDhcpSvrPoolOptionTable, or in the
         tmnxDhcpSvrSubnetOptionTable), then this value is encoded in option 51
         of the DHCP reply message.

         The maximum lease time can only be configured to a value that is
         larger than or equal to the value configured in object
         tmnxDhcpServerPoolMinLeaseTime."
    DEFVAL      { 864000 }
    ::= { tmnxDhcpServerPoolEntry 6 }

tmnxDhcpServerPoolOfferTime      OBJECT-TYPE
    SYNTAX      Unsigned32 (10..600)
    UNITS       "seconds"
    MAX-ACCESS  read-create
    STATUS      current
    DESCRIPTION
        "The value of the object tmnxDhcpServerPoolOfferTime specifies the time
         interval during which a DHCP offer is valid."
    DEFVAL      { 60 }
    ::= { tmnxDhcpServerPoolEntry 7 }

tmnxDhcpServerPoolMinFree        OBJECT-TYPE
    SYNTAX      Unsigned32 (0..255)
    MAX-ACCESS  read-create
    STATUS      current
    DESCRIPTION
        "The value of the object tmnxDhcpServerPoolMinFree specifies the
         desired minimum number of free addresses in this pool.

         If the actual number of free addresses in this pool falls below this
         configured minimum, a notification is generated.

         The value zero specifies 'no minimum'."
    DEFVAL      { 1 }
    ::= { tmnxDhcpServerPoolEntry 8 }

tmnxDhcpServerPoolMinFreeType    OBJECT-TYPE
    SYNTAX      INTEGER {
        absolute (0),
        percent  (1)
    }
    MAX-ACCESS  read-create
    STATUS      current
    DESCRIPTION
        "The value of the object tmnxDhcpServerPoolMinFreeType specifies
         whether tmnxDhcpServerPoolMinFree is expressed as an absolute number
         or as a percentage.

         When the value of this object is set to 'percent(1)', the accepted
         range for tmnxDhcpServerPoolMinFree is limited between 0 and 100.

         Default value is 'absolute(0)'."
    DEFVAL      { absolute }
    ::= { tmnxDhcpServerPoolEntry 9 }

tmnxDhcpServerPoolDepletedEvent  OBJECT-TYPE
    SYNTAX      TruthValue
    MAX-ACCESS  read-create
    STATUS      current
    DESCRIPTION
        "The value of the object tmnxDhcpServerPoolDepletedEvent specifies
         whether a notification is generated when this pool is depleted.

         When the value of this object is set to 'true(1)', notification
         tmnxDhcpSvrPoolDepleted is generated."
    DEFVAL      { false }
    ::= { tmnxDhcpServerPoolEntry 10 }

tmnxDhcpServerPoolDlgatedPfxLen  OBJECT-TYPE
    SYNTAX      Unsigned32 (48..127)
    MAX-ACCESS  read-create
    STATUS      current
    DESCRIPTION
        "The value of tmnxDhcpServerPoolDlgatedPfxLen specifies the number of
         bits that can be allocated to a Delegated Prefix for IPv6."
    DEFVAL      { 64 }
    ::= { tmnxDhcpServerPoolEntry 11 }

tmnxDhcpServerPoolSubnetBindKey  OBJECT-TYPE
    SYNTAX      INTEGER {
        none       (0),
        sysIdSvcId (1),
        sysId      (2),
        string     (3)
    }
    MAX-ACCESS  read-create
    STATUS      obsolete
    DESCRIPTION
        "The value of the object tmnxDhcpServerPoolSubnetBindKey specifies the
         key to be used for subnet binding.

         Default value is 'none' (0), disabling the subnet binding.

         The value cannot be changed into 'none' when
         tmnxDhcpServerPoolSubnetBindDly is not set to it's default value."
    DEFVAL      { none }
    ::= { tmnxDhcpServerPoolEntry 12 }

tmnxDhcpServerPoolSubnetBindDly  OBJECT-TYPE
    SYNTAX      Unsigned32 (1..86400)
    UNITS       "seconds"
    MAX-ACCESS  read-create
    STATUS      obsolete
    DESCRIPTION
        "The value of tmnxDhcpServerPoolSubnetBindDly specifies the number of
         seconds before unbinding the subnet from the access node, after the
         last lease in this subnet has been released.

         The value cannot be changed from the default value into something else
         when tmnxDhcpServerPoolSubnetBindKey is set to 'none' (0)."
    DEFVAL      { 300 }
    ::= { tmnxDhcpServerPoolEntry 13 }

tmnxDhcpServerPoolNakNonMatch    OBJECT-TYPE
    SYNTAX      TruthValue
    MAX-ACCESS  read-create
    STATUS      current
    DESCRIPTION
        "The value of the object tmnxDhcpServerPoolNakNonMatch specifies if
         this DHCP server sends a DHCPNAK when it receives a DHCPREQUEST
         message for a subnet that does not match any of the ranges associated
         with this pool.

         If the value of tmnxDhcpServerPoolNakNonMatch is equal to 'false',
         this DHCP server drops such a DHCPREQUEST message.

         A value of 'true' is only allowed where the value of the object
         tmnxDhcpServerCfgAddrType in the conceptual row in the
         tmnxDhcpServerConfigTable associated with this DHCP server, is equal
         to 'ipv4'."
    DEFVAL      { false }
    ::= { tmnxDhcpServerPoolEntry 14 }

tmnxDhcpServerPoolMinPrefixLen   OBJECT-TYPE
    SYNTAX      InetAddressPrefixLength (0 | 48..127)
    MAX-ACCESS  read-create
    STATUS      current
    DESCRIPTION
        "The value of the object tmnxDhcpServerPoolMinPrefixLen specifies the
         minimum prefix length that is accepted.

         A non-zero is only allowed where the value of the object
         tmnxDhcpServerCfgAddrType in the conceptual row in the
         tmnxDhcpServerConfigTable associated with this DHCP server, is equal
         to 'ipv6'; in this case, the default value is equal to 48; otherwise,
         the default value is equal to zero."
    ::= { tmnxDhcpServerPoolEntry 15 }

tmnxDhcpServerPoolMaxPrefixLen   OBJECT-TYPE
    SYNTAX      InetAddressPrefixLength (0 | 48..127)
    MAX-ACCESS  read-create
    STATUS      current
    DESCRIPTION
        "The value of the object tmnxDhcpServerPoolMaxPrefixLen specifies the
         maximum prefix length that is accepted.

         A non-zero is only allowed where the value of the object
         tmnxDhcpServerCfgAddrType in the conceptual row in the
         tmnxDhcpServerConfigTable associated with this DHCP server, is equal
         to 'ipv6'; in this case, the default value is equal to 64; otherwise,
         the default value is equal to zero."
    ::= { tmnxDhcpServerPoolEntry 16 }

tmnxDhcpSvrPoolOptionTableLastCh OBJECT-TYPE
    SYNTAX      TimeStamp
    MAX-ACCESS  read-only
    STATUS      current
    DESCRIPTION
        "The value of the object tmnxDhcpSvrPoolOptionTableLastCh indicates the
         value of sysUpTime at the time of the last modification of an entry in
         the tmnxDhcpSvrPoolOptionTable."
    ::= { tmnxDhcpServerObjs 5 }

tmnxDhcpSvrPoolOptionTable       OBJECT-TYPE
    SYNTAX      SEQUENCE OF TmnxDhcpSvrPoolOptionEntry
    MAX-ACCESS  not-accessible
    STATUS      current
    DESCRIPTION
        "The table tmnxDhcpSvrPoolOptionTable contains objects to configure the
         DHCP options of each IP address pool."
    ::= { tmnxDhcpServerObjs 6 }

tmnxDhcpSvrPoolOptionEntry       OBJECT-TYPE
    SYNTAX      TmnxDhcpSvrPoolOptionEntry
    MAX-ACCESS  not-accessible
    STATUS      current
    DESCRIPTION
        "Each row represents a DHCP option that is encoded in the DHCP reply
         message.

         Options defined here, can be overruled by defining the same option in
         the local user database, or in the tmnxDhcpSvrSubnetOptionTable.

         Entries in this table can be created or deleted via SNMP operations."
    INDEX       {
        vRtrID,
        tmnxDhcpServerCfgServerName,
        tmnxDhcpServerPoolName,
        tmnxDhcpSvrPoolOptionNumber
    }
    ::= { tmnxDhcpSvrPoolOptionTable 1 }

TmnxDhcpSvrPoolOptionEntry       ::= SEQUENCE
{
    tmnxDhcpSvrPoolOptionNumber      Unsigned32,
    tmnxDhcpSvrPoolOptionRowStatus   RowStatus,
    tmnxDhcpSvrPoolOptionLastCh      TimeStamp,
    tmnxDhcpSvrPoolOptionType        TmnxDhcpOptionType,
    tmnxDhcpSvrPoolOptionValue       OCTET STRING,
    tmnxDhcpSvrPoolOptionDisplay     TmnxDhcpOptionDisplay
}

tmnxDhcpSvrPoolOptionNumber      OBJECT-TYPE
    SYNTAX      Unsigned32 (1..65535)
    MAX-ACCESS  not-accessible
    STATUS      current
    DESCRIPTION
        "The value of the object tmnxDhcpSvrPoolOptionNumber specifies the
         number of this DHCP option."
    REFERENCE
        "RFC 2132, RFC 3315, RFC 3633"
    ::= { tmnxDhcpSvrPoolOptionEntry 1 }

tmnxDhcpSvrPoolOptionRowStatus   OBJECT-TYPE
    SYNTAX      RowStatus
    MAX-ACCESS  read-create
    STATUS      current
    DESCRIPTION
        "The value of the object tmnxDhcpSvrPoolOptionRowStatus specifies the
         row status of this row.

         Objects tmnxDhcpSvrPoolOptionType and tmnxDhcpSvrPoolOptionValue must
         be set when creating a new row."
    ::= { tmnxDhcpSvrPoolOptionEntry 2 }

tmnxDhcpSvrPoolOptionLastCh      OBJECT-TYPE
    SYNTAX      TimeStamp
    MAX-ACCESS  read-only
    STATUS      current
    DESCRIPTION
        "The value of the object tmnxDhcpSvrPoolOptionLastCh indicates the
         sysUpTime at the time of the last modification of this entry."
    ::= { tmnxDhcpSvrPoolOptionEntry 3 }

tmnxDhcpSvrPoolOptionType        OBJECT-TYPE
    SYNTAX      TmnxDhcpOptionType
    MAX-ACCESS  read-create
    STATUS      current
    DESCRIPTION
        "The value of the object tmnxDhcpSvrPoolOptionType specifies how the
         value of this option in stored in tmnxDhcpSvrPoolOptionValue.

         The value of this object cannot be set to 'domain (5)' when the value
         of tmnxDhcpServerCfgAddrType is set to 'ipv4(1)'.

         This object is mandatory at creation time."
    ::= { tmnxDhcpSvrPoolOptionEntry 4 }

tmnxDhcpSvrPoolOptionValue       OBJECT-TYPE
    SYNTAX      OCTET STRING (SIZE (0..127))
    MAX-ACCESS  read-create
    STATUS      current
    DESCRIPTION
        "The value of the object tmnxDhcpSvrPoolOptionValue specifies the value
         of this option.

         This object is mandatory at creation time. A zero length value is only
         allowed when the value of tmnxDhcpSvrPoolOptionType is 'hex (3)'."
    ::= { tmnxDhcpSvrPoolOptionEntry 5 }

tmnxDhcpSvrPoolOptionDisplay     OBJECT-TYPE
    SYNTAX      TmnxDhcpOptionDisplay
    MAX-ACCESS  read-only
    STATUS      current
    DESCRIPTION
        "The value of the object tmnxDhcpSvrPoolOptionDisplay indicates a hint
         of how the tmnxDhcpSvrPoolOptionValue can be displayed."
    ::= { tmnxDhcpSvrPoolOptionEntry 6 }

tmnxDhcpServerSubnetTableLastCh  OBJECT-TYPE
    SYNTAX      TimeStamp
    MAX-ACCESS  read-only
    STATUS      current
    DESCRIPTION
        "The value of the object tmnxDhcpServerSubnetTableLastCh indicates the
         value of sysUpTime at the time of the last modification of an entry in
         the tmnxDhcpServerSubnetTable."
    ::= { tmnxDhcpServerObjs 7 }

tmnxDhcpServerSubnetTable        OBJECT-TYPE
    SYNTAX      SEQUENCE OF TmnxDhcpServerSubnetEntry
    MAX-ACCESS  not-accessible
    STATUS      current
    DESCRIPTION
        "The table tmnxDhcpServerSubnetTable contains objects to configure
         subnets."
    ::= { tmnxDhcpServerObjs 8 }

tmnxDhcpServerSubnetEntry        OBJECT-TYPE
    SYNTAX      TmnxDhcpServerSubnetEntry
    MAX-ACCESS  not-accessible
    STATUS      current
    DESCRIPTION
        "Each row represents a subnet. The subnets of a DHCP server instance
         cannot overlap.

         If the local user database defines a pool, then any subnet of that
         pool is used to provide a free IP address.

         If tmnxDhcpServerCfgUseGiAddress is set to 'true(1)', the Gateway IP
         address is used to select the subnet that is used to provide a free IP
         address.

         Entries in this table can be created or deleted via SNMP operations."
    INDEX       {
        vRtrID,
        tmnxDhcpServerCfgServerName,
        tmnxDhcpServerPoolName,
        tmnxDhcpSvrSubnetAddrType,
        tmnxDhcpSvrSubnetAddress,
        tmnxDhcpSvrSubnetPrefixLength
    }
    ::= { tmnxDhcpServerSubnetTable 1 }

TmnxDhcpServerSubnetEntry        ::= SEQUENCE
{
    tmnxDhcpSvrSubnetAddrType        InetAddressType,
    tmnxDhcpSvrSubnetAddress         InetAddress,
    tmnxDhcpSvrSubnetPrefixLength    InetAddressPrefixLength,
    tmnxDhcpSvrSubnetRowStatus       RowStatus,
    tmnxDhcpSvrSubnetLastChangeTime  TimeStamp,
    tmnxDhcpSvrSubnetMinFree         Unsigned32,
    tmnxDhcpSvrSubnetMaxDeclined     Unsigned32,
    tmnxDhcpSvrSubnetMinFreeType     INTEGER,
    tmnxDhcpSvrSubnetRenewTimer      Unsigned32,
    tmnxDhcpSvrSubnetRebindTimer     Unsigned32,
    tmnxDhcpSvrSubnetValidLifetime   Unsigned32,
    tmnxDhcpSvrSubnetPrefLifetime    Unsigned32,
    tmnxDhcpSvrSubnetFailCtrl        TmnxDhcpSvrFailCtrlType,
    tmnxDhcpSvrSubnetPrefixType      BITS,
    tmnxDhcpSvrSubnetDepletedEvent   TruthValue,
    tmnxDhcpSvrSubnetDrain           TruthValue,
    tmnxDhcpSvrSubnetActive          TruthValue
}

tmnxDhcpSvrSubnetAddrType        OBJECT-TYPE
    SYNTAX      InetAddressType
    MAX-ACCESS  not-accessible
    STATUS      current
    DESCRIPTION
        "The value of the object tmnxDhcpSvrSubnetAddrType specifies the
         address type of tmnxDhcpSvrSubnetAddress.

         The only value supported is 'ipv4'."
    ::= { tmnxDhcpServerSubnetEntry 1 }

tmnxDhcpSvrSubnetAddress         OBJECT-TYPE
    SYNTAX      InetAddress (SIZE (4|16))
    MAX-ACCESS  not-accessible
    STATUS      current
    DESCRIPTION
        "The value of the object tmnxDhcpSvrSubnetAddress specifies a subnet.

         The host bits must be zero.

         Only IPv4 addresses are supported."
    ::= { tmnxDhcpServerSubnetEntry 2 }

tmnxDhcpSvrSubnetPrefixLength    OBJECT-TYPE
    SYNTAX      InetAddressPrefixLength (1..128)
    MAX-ACCESS  not-accessible
    STATUS      current
    DESCRIPTION
        "The value of the object tmnxDhcpSvrSubnetPrefixLength specifies the
         length of tmnxDhcpSvrSubnetAddress."
    ::= { tmnxDhcpServerSubnetEntry 3 }

tmnxDhcpSvrSubnetRowStatus       OBJECT-TYPE
    SYNTAX      RowStatus
    MAX-ACCESS  read-create
    STATUS      current
    DESCRIPTION
        "The value of the object tmnxDhcpSvrSubnetRowStatus specifies the row
         status of this row."
    ::= { tmnxDhcpServerSubnetEntry 4 }

tmnxDhcpSvrSubnetLastChangeTime  OBJECT-TYPE
    SYNTAX      TimeStamp
    MAX-ACCESS  read-only
    STATUS      current
    DESCRIPTION
        "The value of the object tmnxDhcpSvrSubnetLastChangeTime indicates the
         sysUpTime at the time of the last modification of this entry."
    ::= { tmnxDhcpServerSubnetEntry 5 }

tmnxDhcpSvrSubnetMinFree         OBJECT-TYPE
    SYNTAX      Unsigned32 (0..255)
    MAX-ACCESS  read-create
    STATUS      current
    DESCRIPTION
        "The value of the object tmnxDhcpSvrSubnetMinFree specifies the desired
         minimum number of free addresses in this subnet.

         The actual number of free addresses in this subnet is indicated in the
         column tmnxDhcpSvrSubnetStatsFree in the augmentation row of the
         tmnxDhcpSvrSubnetStatsTable.

         If the actual number of free addresses in this subnet falls below this
         configured minimum, a notification is generated.

         The value zero specifies 'no minimum'."
    DEFVAL      { 1 }
    ::= { tmnxDhcpServerSubnetEntry 6 }

tmnxDhcpSvrSubnetMaxDeclined     OBJECT-TYPE
    SYNTAX      Unsigned32 (0..4294967295)
    MAX-ACCESS  read-create
    STATUS      current
    DESCRIPTION
        "The value of the object tmnxDhcpSvrSubnetMaxDeclined specifies the
         maximum number of declined IP addresses that are stored. These
         declined IP addresses are removed from the tmnxDhcpSvrFreeAddrTable,
         and are not handed out to the clients.

         When this maximum is reached, and the server receives another DHCP
         DECLINE message from a client, then the oldest declined IP address
         becomes again available for the clients.

         When the value of this object is set to 0, no declined IP addresses
         are removed from the tmnxDhcpSvrFreeAddrTable."
    DEFVAL      { 64 }
    ::= { tmnxDhcpServerSubnetEntry 7 }

tmnxDhcpSvrSubnetMinFreeType     OBJECT-TYPE
    SYNTAX      INTEGER {
        absolute (0),
        percent  (1)
    }
    MAX-ACCESS  read-create
    STATUS      current
    DESCRIPTION
        "The value of the object tmnxDhcpSvrSubnetMinFreeType specifies whether
         tmnxDhcpSvrSubnetMinFree is expressed as an absolute number or as a
         percentage.

         When the value of this object is set to 'percent(1)', the accepted
         range for tmnxDhcpSvrSubnetMinFree is limited between 0 and 100.

         Default value is 'absolute(0)'."
    DEFVAL      { absolute }
    ::= { tmnxDhcpServerSubnetEntry 8 }

tmnxDhcpSvrSubnetRenewTimer      OBJECT-TYPE
    SYNTAX      Unsigned32 (0..604800)
    MAX-ACCESS  read-create
    STATUS      current
    DESCRIPTION
        "The value of tmnxDhcpSvrSubnetRenewTimer specifies the renew-timer
         (T1).

         After T1 has elapsed, the client contacts the server from which the
         addresses in the IA_NA or IA_PD were obtained to extend the lifetimes
         of the addresses or prefixes assigned to the client.

         The value of this object is only meaningful when the value of
         tmnxDhcpSvrSubnetAddrType is set to 'ipv6(2)'."
    DEFVAL      { 1800 }
    ::= { tmnxDhcpServerSubnetEntry 9 }

tmnxDhcpSvrSubnetRebindTimer     OBJECT-TYPE
    SYNTAX      Unsigned32 (0..1209600)
    MAX-ACCESS  read-create
    STATUS      current
    DESCRIPTION
        "The value of tmnxDhcpSvrSubnetRebindTimer specifies the rebind-timer
         (T2).

         After T2 has elapsed, the client contacts any available server to
         extend the lifetimes of the addresses or prefixes assigned to the
         client.

         The value of this object is only meaningful when the value of
         tmnxDhcpSvrSubnetAddrType is set to 'ipv6(2)'."
    DEFVAL      { 2880 }
    ::= { tmnxDhcpServerSubnetEntry 10 }

tmnxDhcpSvrSubnetValidLifetime   OBJECT-TYPE
    SYNTAX      Unsigned32 (300..315446399)
    UNITS       "seconds"
    MAX-ACCESS  read-create
    STATUS      current
    DESCRIPTION
        "The value of tmnxDhcpSvrSubnetValidLifetime specifies
         the valid-lifetime field that this server transmits
         - in the IA Address option, or
         - in the IA_PD Prefix option.

         The value of this object is only meaningful when the value of
         tmnxDhcpSvrSubnetAddrType is set to 'ipv6(2)'."
    DEFVAL      { 86400 }
    ::= { tmnxDhcpServerSubnetEntry 11 }

tmnxDhcpSvrSubnetPrefLifetime    OBJECT-TYPE
    SYNTAX      Unsigned32 (300..315446399)
    UNITS       "seconds"
    MAX-ACCESS  read-create
    STATUS      current
    DESCRIPTION
        "The value of tmnxDhcpSvrSubnetPrefLifetime specifies the value
         of the preferred-lifetime field that this server transmits:
         - in the IA Address option, or
         - in the IA_PD Prefix option.

         When the preferred lifetime expires, any derived addresses are
         deprecated.

         The value of this object is only meaningful when the value of
         tmnxDhcpSvrSubnetAddrType is set to 'ipv6(2)'."
    DEFVAL      { 3600 }
    ::= { tmnxDhcpServerSubnetEntry 12 }

tmnxDhcpSvrSubnetFailCtrl        OBJECT-TYPE
    SYNTAX      TmnxDhcpSvrFailCtrlType
    MAX-ACCESS  read-create
    STATUS      current
    DESCRIPTION
        "The value of the object tmnxDhcpSvrSubnetFailCtrl specifies the type
         of failover control for this subnet.

         This object can be set only at the time the row is created.

         The value of this object is only meaningful when the value of
         tmnxDhcpSvrSubnetAddrType is set to 'ipv6(2)'."
    DEFVAL      { local }
    ::= { tmnxDhcpServerSubnetEntry 13 }

tmnxDhcpSvrSubnetPrefixType      OBJECT-TYPE
    SYNTAX      BITS {
        pd       (0),
        wan-host (1)
    }
    MAX-ACCESS  read-create
    STATUS      current
    DESCRIPTION
        "The value of tmnxDhcpSvrSubnetPrefixType specifies the type of prefix
         contained in tmnxDhcpSvrSubnetAddress.

         This object cannot be modified once the row is created.

         The value of this object is only meaningful when the value of
         tmnxDhcpSvrSubnetAddrType is set to 'ipv6(2)'."
    DEFVAL      { {pd, wan-host} }
    ::= { tmnxDhcpServerSubnetEntry 14 }

tmnxDhcpSvrSubnetDepletedEvent   OBJECT-TYPE
    SYNTAX      TruthValue
    MAX-ACCESS  read-create
    STATUS      current
    DESCRIPTION
        "The value of the object tmnxDhcpSvrSubnetDepletedEvent specifies
         whether a notification is generated when this subnet is depleted.

         When the value of this object is set to 'true(1)', notification
         tmnxDhcpSvrSubnetDepleted is generated.

         The value of this object is only meaningful when the value of
         tmnxDhcpSvrSubnetAddrType is set to 'ipv4(1)'."
    DEFVAL      { false }
    ::= { tmnxDhcpServerSubnetEntry 15 }

tmnxDhcpSvrSubnetDrain           OBJECT-TYPE
    SYNTAX      TruthValue
    MAX-ACCESS  read-create
    STATUS      current
    DESCRIPTION
        "If the value of object tmnxDhcpSvrSubnetDrain is set to 'true (1)'
         then the subnet is draining, which means no new leases can be assigned
         from this subnet and existing leases are cleaned up upon renew/rebind.

         If the value of this object is set to 'false (2)' then the subnet is
         active and new leases can be assigned from it."
    DEFVAL      { false }
    ::= { tmnxDhcpServerSubnetEntry 16 }

tmnxDhcpSvrSubnetActive          OBJECT-TYPE
    SYNTAX      TruthValue
    MAX-ACCESS  read-only
    STATUS      current
    DESCRIPTION
        "The value of object tmnxDhcpSvrSubnetActive indicates if this IPv6
         subnet is currently being served by this system.

         If the value of tmnxDhcpSvrSubnetFailCtrl is equal to 'local' or
         'access-driven', the value of this object is always 'true'. Otherwise,
         the value depends on the failover state, available in tmnxDhcpsFoState
         (if tmnxDhcpsFoAdminState is 'inService') or tmnxDhcpsPoolFoState (if
         tmnxDhcpsPoolFoAdminState is 'inService'): if the value of the
         failover state is 'partnerDown', the value of this object is 'true'."
    ::= { tmnxDhcpServerSubnetEntry 17 }

tmnxDhcpSvrSubnetRangesTblLastCh OBJECT-TYPE
    SYNTAX      TimeStamp
    MAX-ACCESS  read-only
    STATUS      current
    DESCRIPTION
        "The value of the object tmnxDhcpSvrSubnetRangesTblLastCh indicates the
         value of sysUpTime at the time of the last modification of an entry in
         the tmnxDhcpSvrSubnetRangesTable."
    ::= { tmnxDhcpServerObjs 9 }

tmnxDhcpSvrSubnetRangesTable     OBJECT-TYPE
    SYNTAX      SEQUENCE OF TmnxDhcpSvrSubnetRangesEntry
    MAX-ACCESS  not-accessible
    STATUS      current
    DESCRIPTION
        "The table tmnxDhcpSvrSubnetRangesTable contains objects to configure
         address ranges within this subnet."
    ::= { tmnxDhcpServerObjs 10 }

tmnxDhcpSvrSubnetRangesEntry     OBJECT-TYPE
    SYNTAX      TmnxDhcpSvrSubnetRangesEntry
    MAX-ACCESS  not-accessible
    STATUS      current
    DESCRIPTION
        "Each row represents a range of IP addresses that are either included
         in or excluded from the pool of IP addresses in this subnet.

         Include ranges cannot overlap, exclude ranges can overlap.

         Entries in this table can be created or deleted via SNMP operations."
    INDEX       {
        vRtrID,
        tmnxDhcpServerCfgServerName,
        tmnxDhcpServerPoolName,
        tmnxDhcpSvrSubnetAddrType,
        tmnxDhcpSvrSubnetAddress,
        tmnxDhcpSvrSubnetPrefixLength,
        tmnxDhcpSvrSubnetRangeType,
        tmnxDhcpSvrSubnetStartAddrType,
        tmnxDhcpSvrSubnetStartAddress,
        tmnxDhcpSvrSubnetEndAddrType,
        tmnxDhcpSvrSubnetEndAddress
    }
    ::= { tmnxDhcpSvrSubnetRangesTable 1 }

TmnxDhcpSvrSubnetRangesEntry     ::= SEQUENCE
{
    tmnxDhcpSvrSubnetRangeType       INTEGER,
    tmnxDhcpSvrSubnetStartAddrType   InetAddressType,
    tmnxDhcpSvrSubnetStartAddress    InetAddress,
    tmnxDhcpSvrSubnetEndAddrType     InetAddressType,
    tmnxDhcpSvrSubnetEndAddress      InetAddress,
    tmnxDhcpSvrSubnetRangesRowStatus RowStatus,
    tmnxDhcpSvrSubnetRangesLastCh    TimeStamp,
    tmnxDhcpSvrSubnetRangeFailCtrl   TmnxDhcpSvrFailCtrlType
}

tmnxDhcpSvrSubnetRangeType       OBJECT-TYPE
    SYNTAX      INTEGER {
        exclude (0),
        include (1)
    }
    MAX-ACCESS  not-accessible
    STATUS      current
    DESCRIPTION
        "The value of the object tmnxDhcpSvrSubnetRangeType specifies if this
         range will be included in or excluded from the pool of addresses in
         this subnet."
    ::= { tmnxDhcpSvrSubnetRangesEntry 1 }

tmnxDhcpSvrSubnetStartAddrType   OBJECT-TYPE
    SYNTAX      InetAddressType
    MAX-ACCESS  not-accessible
    STATUS      current
    DESCRIPTION
        "The value of the object tmnxDhcpSvrSubnetStartAddrType specifies the
         address type of tmnxDhcpSvrSubnetStartAddress.

         The only value supported is 'ipv4'."
    ::= { tmnxDhcpSvrSubnetRangesEntry 2 }

tmnxDhcpSvrSubnetStartAddress    OBJECT-TYPE
    SYNTAX      InetAddress (SIZE (4|16))
    MAX-ACCESS  not-accessible
    STATUS      current
    DESCRIPTION
        "The value of the object tmnxDhcpSvrSubnetStartAddress specifies the
         start address of this range.

         Only IPv4 addresses are supported."
    ::= { tmnxDhcpSvrSubnetRangesEntry 3 }

tmnxDhcpSvrSubnetEndAddrType     OBJECT-TYPE
    SYNTAX      InetAddressType
    MAX-ACCESS  not-accessible
    STATUS      current
    DESCRIPTION
        "The value of the object tmnxDhcpSvrSubnetEndAddrType specifies the
         address type of tmnxDhcpSvrSubnetEndAddress.

         The only value supported is 'ipv4'."
    ::= { tmnxDhcpSvrSubnetRangesEntry 4 }

tmnxDhcpSvrSubnetEndAddress      OBJECT-TYPE
    SYNTAX      InetAddress (SIZE (4|16))
    MAX-ACCESS  not-accessible
    STATUS      current
    DESCRIPTION
        "The value of the object tmnxDhcpSvrSubnetEndAddress specifies the end
         address of this range.

         A range can only contain 16384 (2^14) IP addresses.

         Only IPv4 addresses are supported."
    ::= { tmnxDhcpSvrSubnetRangesEntry 5 }

tmnxDhcpSvrSubnetRangesRowStatus OBJECT-TYPE
    SYNTAX      RowStatus
    MAX-ACCESS  read-create
    STATUS      current
    DESCRIPTION
        "The value of the object tmnxDhcpSvrSubnetRangesRowStatus specifies the
         row status of this row."
    ::= { tmnxDhcpSvrSubnetRangesEntry 6 }

tmnxDhcpSvrSubnetRangesLastCh    OBJECT-TYPE
    SYNTAX      TimeStamp
    MAX-ACCESS  read-only
    STATUS      current
    DESCRIPTION
        "The value of the object tmnxDhcpSvrSubnetRangesLastCh indicates the
         sysUpTime at the time of the last modification of this entry."
    ::= { tmnxDhcpSvrSubnetRangesEntry 7 }

tmnxDhcpSvrSubnetRangeFailCtrl   OBJECT-TYPE
    SYNTAX      TmnxDhcpSvrFailCtrlType
    MAX-ACCESS  read-create
    STATUS      current
    DESCRIPTION
        "The value of the object tmnxDhcpSvrSubnetRangeFailCtrl specifies the
         type of failover control for this range.

         This object can be set only at the time the row is created."
    DEFVAL      { local }
    ::= { tmnxDhcpSvrSubnetRangesEntry 8 }

tmnxDhcpSvrSubnetOptionTblLastCh OBJECT-TYPE
    SYNTAX      TimeStamp
    MAX-ACCESS  read-only
    STATUS      current
    DESCRIPTION
        "The value of the object tmnxDhcpSvrSubnetOptionTblLastCh indicates the
         value of sysUpTime at the time of the last modification of an entry in
         the tmnxDhcpSvrSubnetOptionTable."
    ::= { tmnxDhcpServerObjs 11 }

tmnxDhcpSvrSubnetOptionTable     OBJECT-TYPE
    SYNTAX      SEQUENCE OF TmnxDhcpSvrSubnetOptionEntry
    MAX-ACCESS  not-accessible
    STATUS      current
    DESCRIPTION
        "The table tmnxDhcpSvrSubnetOptionTable contains objects to configure
         DHCP options."
    ::= { tmnxDhcpServerObjs 12 }

tmnxDhcpSvrSubnetOptionEntry     OBJECT-TYPE
    SYNTAX      TmnxDhcpSvrSubnetOptionEntry
    MAX-ACCESS  not-accessible
    STATUS      current
    DESCRIPTION
        "Each row represents a DHCP option that is encoded in the DHCP reply
         message.

         Options defined here, can be overruled by defining the same option in
         the local user database.

         Entries in this table can be created or deleted via SNMP operations."
    INDEX       {
        vRtrID,
        tmnxDhcpServerCfgServerName,
        tmnxDhcpServerPoolName,
        tmnxDhcpSvrSubnetAddrType,
        tmnxDhcpSvrSubnetAddress,
        tmnxDhcpSvrSubnetPrefixLength,
        tmnxDhcpSvrSubnetOptionNumber
    }
    ::= { tmnxDhcpSvrSubnetOptionTable 1 }

TmnxDhcpSvrSubnetOptionEntry     ::= SEQUENCE
{
    tmnxDhcpSvrSubnetOptionNumber    Unsigned32,
    tmnxDhcpSvrSubnetOptionRowStatus RowStatus,
    tmnxDhcpSvrSubnetOptionLastCh    TimeStamp,
    tmnxDhcpSvrSubnetOptionType      TmnxDhcpOptionType,
    tmnxDhcpSvrSubnetOptionValue     OCTET STRING,
    tmnxDhcpSvrSubnetOptionDisplay   TmnxDhcpOptionDisplay
}

tmnxDhcpSvrSubnetOptionNumber    OBJECT-TYPE
    SYNTAX      Unsigned32 (1..65535)
    MAX-ACCESS  not-accessible
    STATUS      current
    DESCRIPTION
        "The value of the object tmnxDhcpSvrSubnetOptionNumber specifies the
         number of this option."
    REFERENCE
        "RFC 2132"
    ::= { tmnxDhcpSvrSubnetOptionEntry 1 }

tmnxDhcpSvrSubnetOptionRowStatus OBJECT-TYPE
    SYNTAX      RowStatus
    MAX-ACCESS  read-create
    STATUS      current
    DESCRIPTION
        "The value of the object tmnxDhcpSvrSubnetOptionRowStatus specifies the
         row status of this row.

         Objects tmnxDhcpSvrSubnetOptionType and tmnxDhcpSvrSubnetOptionValue
         must be set when creating a new row."
    ::= { tmnxDhcpSvrSubnetOptionEntry 2 }

tmnxDhcpSvrSubnetOptionLastCh    OBJECT-TYPE
    SYNTAX      TimeStamp
    MAX-ACCESS  read-only
    STATUS      current
    DESCRIPTION
        "The value of the object tmnxDhcpSvrSubnetOptionLastCh indicates the
         sysUpTime at the time of the last modification of this entry."
    ::= { tmnxDhcpSvrSubnetOptionEntry 3 }

tmnxDhcpSvrSubnetOptionType      OBJECT-TYPE
    SYNTAX      TmnxDhcpOptionType
    MAX-ACCESS  read-create
    STATUS      current
    DESCRIPTION
        "The value of the object tmnxDhcpSvrSubnetOptionType specifies how the
         value of this option is stored in tmnxDhcpSvrSubnetOptionValue.

         The value of this object cannot be set to 'domain (5)' when the value
         of tmnxDhcpServerCfgAddrType is set to 'ipv4(1)'.

         This object is mandatory at creation time."
    ::= { tmnxDhcpSvrSubnetOptionEntry 4 }

tmnxDhcpSvrSubnetOptionValue     OBJECT-TYPE
    SYNTAX      OCTET STRING (SIZE (0..127))
    MAX-ACCESS  read-create
    STATUS      current
    DESCRIPTION
        "The value of the object tmnxDhcpSvrSubnetOptionValue specifies the
         value of this option.

         This object is mandatory at creation time. A zero length value is only
         allowed when the value of tmnxDhcpSvrSubnetOptionType is 'hex (3)'."
    ::= { tmnxDhcpSvrSubnetOptionEntry 5 }

tmnxDhcpSvrSubnetOptionDisplay   OBJECT-TYPE
    SYNTAX      TmnxDhcpOptionDisplay
    MAX-ACCESS  read-only
    STATUS      current
    DESCRIPTION
        "The value of the object tmnxDhcpSvrSubnetOptionDisplay indicates a
         hint of how the tmnxDhcpSvrSubnetOptionValue can be displayed."
    ::= { tmnxDhcpSvrSubnetOptionEntry 6 }

tmnxDhcpSvrLeaseTable            OBJECT-TYPE
    SYNTAX      SEQUENCE OF TmnxDhcpSvrLeaseEntry
    MAX-ACCESS  not-accessible
    STATUS      current
    DESCRIPTION
        "The table tmnxDhcpSvrLeaseTable contains information about the IP
         addresses handed out to the DHCP clients."
    ::= { tmnxDhcpServerObjs 13 }

tmnxDhcpSvrLeaseEntry            OBJECT-TYPE
    SYNTAX      TmnxDhcpSvrLeaseEntry
    MAX-ACCESS  not-accessible
    STATUS      current
    DESCRIPTION
        "Each row represents a lease.

         Entries in this table cannot be created or deleted via SNMP
         operations."
    INDEX       {
        vRtrID,
        tmnxDhcpServerCfgServerName,
        tmnxDhcpSvrLeaseClientAddrType,
        tmnxDhcpSvrLeaseClientAddress
    }
    ::= { tmnxDhcpSvrLeaseTable 1 }

TmnxDhcpSvrLeaseEntry            ::= SEQUENCE
{
    tmnxDhcpSvrLeaseClientAddrType   InetAddressType,
    tmnxDhcpSvrLeaseClientAddress    InetAddress,
    tmnxDhcpSvrLeaseState            INTEGER,
    tmnxDhcpSvrLeaseStart            DateAndTime,
    tmnxDhcpSvrLeaseLastRenew        DateAndTime,
    tmnxDhcpSvrLeaseRemainLeaseTime  Unsigned32,
    tmnxDhcpSvrLeaseRemPotentExpTime Unsigned32,
    tmnxDhcpSvrLeaseClientHwAddress  MacAddress,
    tmnxDhcpSvrLeaseXid              Unsigned32,
    tmnxDhcpSvrLeaseOption82         OCTET STRING,
    tmnxDhcpSvrLeaseClientType       TmnxDhcpSvrClientType,
    tmnxDhcpSvrLeasePPPoEUserName    TmnxPppoeUserNameOrEmpty,
    tmnxDhcpSvrLeaseOpt82CircId      OCTET STRING,
    tmnxDhcpSvrLeaseFailCtrl         TmnxDhcpSvrFailCtrlType,
    tmnxDhcpSvrLeaseOption60         OCTET STRING,
    tmnxDhcpSvrLeaseClientPrefixLen  InetAddressPrefixLength,
    tmnxDhcpSvrLeaseIAOptionType     INTEGER,
    tmnxDhcpSvrLeaseIAID             Unsigned32,
    tmnxDhcpSvrLeaseDUID             OCTET STRING,
    tmnxDhcpSvrLeaseRemainHoldTime   Unsigned32,
    tmnxDhcpSvrLeaseRelayInterfaceId OCTET STRING,
    tmnxDhcpSvrLeaseLDRAInterfaceId  OCTET STRING,
    tmnxDhcpSvrLeaseLnkLclAddrType   InetAddressType,
    tmnxDhcpSvrLeaseLnkLclAddress    InetAddress,
    tmnxDhcpSvrLeaseIntClientType    INTEGER,
    tmnxDhcpSvrLeaseOpt82RemoteId    OCTET STRING,
    tmnxDhcpSvrLeaseOpt61ClientId    OCTET STRING,
    tmnxDhcpSvrLeaseStickyHostName   TNamedItemOrEmpty
}

tmnxDhcpSvrLeaseClientAddrType   OBJECT-TYPE
    SYNTAX      InetAddressType
    MAX-ACCESS  not-accessible
    STATUS      current
    DESCRIPTION
        "The value of the object tmnxDhcpSvrLeaseClientAddrType indicates the
         address type of tmnxDhcpSvrLeaseClientAddress."
    ::= { tmnxDhcpSvrLeaseEntry 1 }

tmnxDhcpSvrLeaseClientAddress    OBJECT-TYPE
    SYNTAX      InetAddress (SIZE (4|16))
    MAX-ACCESS  not-accessible
    STATUS      current
    DESCRIPTION
        "The value of the object tmnxDhcpSvrLeaseClientAddress specifies the
         client IP address of this lease."
    ::= { tmnxDhcpSvrLeaseEntry 2 }

tmnxDhcpSvrLeaseState            OBJECT-TYPE
    SYNTAX      INTEGER {
        offered           (0),
        stable            (1),
        forceRenewPending (2),
        removePending     (3),
        held              (4),
        internal          (5),
        internalOrphan    (6),
        internalOffered   (7),
        internalHeld      (8),
        sticky            (9)
    }
    MAX-ACCESS  read-only
    STATUS      current
    DESCRIPTION
        "The value of object tmnxDhcpSvrLeaseState indicates the state of this
         lease.

         - 'offered (0)':
                The IP address was offered to the client. The client still
                has to acknowledge the offer by sending a DHCP request.
         - 'stable (1)':
                The IP address is now in use by the client.
         - 'forceRenewPending (2)':
                The IP address is in use by the client, but the server sends
                a DHCP FORCERENEW message to the client, because an option
                has changed in tmnxDhcpSvrPoolOptionTable or in
                tmnxDhcpSvrSubnetOptionTable or in the user database options
                for this client.
         - 'removePending (3)':
                The IP address is in use by the client, but it is no longer
                available in the IP address ranges configured in
                tmnxDhcpSvrSubnetRangesTable. The server sends a FORCERENEW
                message to the client. When the client sends a renewal
                DHCP request message, it will be rejected.
         - 'held (4)':
                The IP address has been used by the client but the lease has
                timed out. The lease is now in the hold list so that the client
                can get the exactly same IP address again upon the next request
                for a lease.
         - 'internal (5)':
                The IP address has been leased via the local pool management
                system and is now in use.
         - 'internalOrphan (6)':
                The IP address has been leased via the local pool management
                system and is now in use. There is however no configured subnet
                to which this lease belongs, because it has been removed or
                because this lease was installed through dual-homing.
         - 'internalOffered (7)':
                The IP address has been offered via the local pool management
                system. The client still has to acknowledge this offer.
         - 'internalHeld (8)':
                The IP address has been used by local pool management system but
                the lease is currently not active. The address is now in the
                hold list so that the local pool management system client can
                get the exactly same IP address again upon the next request
                for a lease.
         - 'sticky (9)':
                The IP address is reserved for the client and will remain
                reserved until the reservation for it is cleared.
                The client will get the exactly same IP address again upon the
                next request for a lease.
                "
    ::= { tmnxDhcpSvrLeaseEntry 3 }

tmnxDhcpSvrLeaseStart            OBJECT-TYPE
    SYNTAX      DateAndTime
    MAX-ACCESS  read-only
    STATUS      current
    DESCRIPTION
        "The value of object tmnxDhcpSvrLeaseStart indicates when this lease
         was created."
    ::= { tmnxDhcpSvrLeaseEntry 4 }

tmnxDhcpSvrLeaseLastRenew        OBJECT-TYPE
    SYNTAX      DateAndTime
    MAX-ACCESS  read-only
    STATUS      current
    DESCRIPTION
        "The value of object tmnxDhcpSvrLeaseLastRenew indicates when the last
         renew was done for this lease."
    ::= { tmnxDhcpSvrLeaseEntry 5 }

tmnxDhcpSvrLeaseRemainLeaseTime  OBJECT-TYPE
    SYNTAX      Unsigned32
    UNITS       "seconds"
    MAX-ACCESS  read-only
    STATUS      current
    DESCRIPTION
        "The value of object tmnxDhcpSvrLeaseRemainLeaseTime indicates the time
         left for this lease."
    ::= { tmnxDhcpSvrLeaseEntry 6 }

tmnxDhcpSvrLeaseRemPotentExpTime OBJECT-TYPE
    SYNTAX      Unsigned32
    UNITS       "seconds"
    MAX-ACCESS  read-only
    STATUS      current
    DESCRIPTION
        "The value of object tmnxDhcpSvrLeaseRemPotentExpTime indicates the
         lease expiration interval for this lease that is negotiated with the
         failover peer."
    REFERENCE
        "draft-ietf-dhc-failover DHCP Failover Protocol section 5.2.1,
         Control of lease time."
    ::= { tmnxDhcpSvrLeaseEntry 7 }

tmnxDhcpSvrLeaseClientHwAddress  OBJECT-TYPE
    SYNTAX      MacAddress
    MAX-ACCESS  read-only
    STATUS      current
    DESCRIPTION
        "The value of object tmnxDhcpSvrLeaseClientHwAddress indicates the MAC
         address of the client."
    ::= { tmnxDhcpSvrLeaseEntry 8 }

tmnxDhcpSvrLeaseXid              OBJECT-TYPE
    SYNTAX      Unsigned32
    MAX-ACCESS  read-only
    STATUS      current
    DESCRIPTION
        "The value of object tmnxDhcpSvrLeaseXid indicates the transaction id
         that the client has sent in its last DHCP message to the server."
    ::= { tmnxDhcpSvrLeaseEntry 9 }

tmnxDhcpSvrLeaseOption82         OBJECT-TYPE
    SYNTAX      OCTET STRING (SIZE (0..257))
    MAX-ACCESS  read-only
    STATUS      current
    DESCRIPTION
        "The value of object tmnxDhcpSvrLeaseOption82 indicates the content of
         option 82 for this DHCP lease state."
    ::= { tmnxDhcpSvrLeaseEntry 10 }

tmnxDhcpSvrLeaseClientType       OBJECT-TYPE
    SYNTAX      TmnxDhcpSvrClientType
    MAX-ACCESS  read-only
    STATUS      current
    DESCRIPTION
        "The value of object tmnxDhcpSvrLeaseClientType indicates the type of
         the client."
    ::= { tmnxDhcpSvrLeaseEntry 11 }

tmnxDhcpSvrLeasePPPoEUserName    OBJECT-TYPE
    SYNTAX      TmnxPppoeUserNameOrEmpty
    MAX-ACCESS  read-only
    STATUS      current
    DESCRIPTION
        "The value of object tmnxDhcpSvrLeasePPPoEUserName indicates the PPP
         user name.

         This object is only relevant if the value of
         tmnxDhcpSvrLeaseClientType is equal to 'ppp'."
    ::= { tmnxDhcpSvrLeaseEntry 12 }

tmnxDhcpSvrLeaseOpt82CircId      OBJECT-TYPE
    SYNTAX      OCTET STRING (SIZE (0..255))
    MAX-ACCESS  read-only
    STATUS      current
    DESCRIPTION
        "The value of object tmnxDhcpSvrLeaseOpt82CircId indicates the Circuit
         ID from the option 82."
    ::= { tmnxDhcpSvrLeaseEntry 13 }

tmnxDhcpSvrLeaseFailCtrl         OBJECT-TYPE
    SYNTAX      TmnxDhcpSvrFailCtrlType
    MAX-ACCESS  read-only
    STATUS      current
    DESCRIPTION
        "The value of object tmnxDhcpSvrLeaseFailCtrl indicates the type of
         failover control for this DHCP lease state."
    ::= { tmnxDhcpSvrLeaseEntry 14 }

tmnxDhcpSvrLeaseOption60         OBJECT-TYPE
    SYNTAX      OCTET STRING (SIZE (0..32))
    MAX-ACCESS  read-only
    STATUS      current
    DESCRIPTION
        "The value of object tmnxDhcpSvrLeaseOption60 indicates the content of
         option 60 for this DHCP lease state.

         The size is limited to the size of
         TIMETRA-LOCAL-USER-DB-MIB::tmnxLocUsrDbDhcpOption60."
    ::= { tmnxDhcpSvrLeaseEntry 15 }

tmnxDhcpSvrLeaseClientPrefixLen  OBJECT-TYPE
    SYNTAX      InetAddressPrefixLength (1..128)
    MAX-ACCESS  read-only
    STATUS      current
    DESCRIPTION
        "The value of object tmnxDhcpSvrLeaseClientPrefixLen indicates the
         length of tmnxDhcpSvrLeaseClientAddress."
    ::= { tmnxDhcpSvrLeaseEntry 16 }

tmnxDhcpSvrLeaseIAOptionType     OBJECT-TYPE
    SYNTAX      INTEGER {
        notApplicable (0),
        iaNa          (1),
        iaPd          (2)
    }
    MAX-ACCESS  read-only
    STATUS      current
    DESCRIPTION
        "The value of object tmnxDhcpSvrLeaseIAOptionType indicates the type of
         the option.

         - 'notApplicable (0)': IA is not applicable to this lease.

         - 'iaNa (1)':
                The IA_NA option type is used to request the assignment of
                non-temporary addresses.

         - 'iaPd (2)':
                The IA_PD option is used to carry a prefix delegation identity
                association, the parameters associated with the IA_PD and the
                prefixes associated with it."
    REFERENCE
        "RFC 3315, RFC 3633"
    ::= { tmnxDhcpSvrLeaseEntry 17 }

tmnxDhcpSvrLeaseIAID             OBJECT-TYPE
    SYNTAX      Unsigned32
    MAX-ACCESS  read-only
    STATUS      current
    DESCRIPTION
        "The value of object tmnxDhcpSvrLeaseIAID indicates the Identity
         Association of the client."
    ::= { tmnxDhcpSvrLeaseEntry 18 }

tmnxDhcpSvrLeaseDUID             OBJECT-TYPE
    SYNTAX      OCTET STRING (SIZE (0..255))
    MAX-ACCESS  read-only
    STATUS      current
    DESCRIPTION
        "The value of object tmnxDhcpSvrLeaseDUID indicates the DHCP Unique
         Identifier associated with the client."
    ::= { tmnxDhcpSvrLeaseEntry 19 }

tmnxDhcpSvrLeaseRemainHoldTime   OBJECT-TYPE
    SYNTAX      Unsigned32
    UNITS       "seconds"
    MAX-ACCESS  read-only
    STATUS      current
    DESCRIPTION
        "The value of object tmnxDhcpSvrLeaseRemainHoldTime indicates the hold
         time left for this lease."
    ::= { tmnxDhcpSvrLeaseEntry 20 }

tmnxDhcpSvrLeaseRelayInterfaceId OBJECT-TYPE
    SYNTAX      OCTET STRING (SIZE (0..255))
    MAX-ACCESS  read-only
    STATUS      current
    DESCRIPTION
        "The value of object tmnxDhcpSvrLeaseRelayInterfaceId indicates the
         value of the Interface-ID Option assigned by the DHCPv6 Relay Agent."
    ::= { tmnxDhcpSvrLeaseEntry 21 }

tmnxDhcpSvrLeaseLDRAInterfaceId  OBJECT-TYPE
    SYNTAX      OCTET STRING (SIZE (0..255))
    MAX-ACCESS  read-only
    STATUS      current
    DESCRIPTION
        "The value of object tmnxDhcpSvrLeaseLDRAInterfaceId indicates the
         value of the Interface-ID Option assigned by the Lightweight DHCPv6
         Relay Agent."
    REFERENCE
        "draft-miles-dhc-dhcpv6-ldra"
    ::= { tmnxDhcpSvrLeaseEntry 22 }

tmnxDhcpSvrLeaseLnkLclAddrType   OBJECT-TYPE
    SYNTAX      InetAddressType
    MAX-ACCESS  read-only
    STATUS      current
    DESCRIPTION
        "The value of object tmnxDhcpSvrLeaseLnkLclAddrType indicates the
         address type of tmnxDhcpSvrLeaseLnkLclAddress."
    ::= { tmnxDhcpSvrLeaseEntry 23 }

tmnxDhcpSvrLeaseLnkLclAddress    OBJECT-TYPE
    SYNTAX      InetAddress (SIZE (0|16))
    MAX-ACCESS  read-only
    STATUS      current
    DESCRIPTION
        "The value of object tmnxDhcpSvrLeaseLnkLclAddress indicates the link
         local IP address of the client."
    ::= { tmnxDhcpSvrLeaseEntry 24 }

tmnxDhcpSvrLeaseIntClientType    OBJECT-TYPE
    SYNTAX      INTEGER {
        notApplicable (0),
        ipoeWan       (1),
        ipoeSlaac     (2),
        ppp           (3),
        pppSlaac      (4),
        ipsec         (5)
    }
    MAX-ACCESS  read-only
    STATUS      current
    DESCRIPTION
        "The value of object tmnxDhcpSvrLeaseIntClientType indicates the type
         of the client if it is an internal client.

         For an external client such as a DHCP host or a PPP host, the value of
         tmnxDhcpSvrLeaseIntClientType is equal to 'notApplicable'.

         An API (Application Program Interface) exists within the system that
         allows applications of this system to create rows in this table that
         do not directly correspond to an external client, and this type of
         client is called 'internal'."
    ::= { tmnxDhcpSvrLeaseEntry 25 }

tmnxDhcpSvrLeaseOpt82RemoteId    OBJECT-TYPE
    SYNTAX      OCTET STRING (SIZE (0..255))
    MAX-ACCESS  read-only
    STATUS      current
    DESCRIPTION
        "The value of object tmnxDhcpSvrLeaseOpt82RemoteId indicates the Remote
         ID from the option 82."
    ::= { tmnxDhcpSvrLeaseEntry 26 }

tmnxDhcpSvrLeaseOpt61ClientId    OBJECT-TYPE
    SYNTAX      OCTET STRING (SIZE (0..255))
    MAX-ACCESS  read-only
    STATUS      current
    DESCRIPTION
        "The value of object tmnxDhcpSvrLeaseOpt61ClientId indicates the Client
         ID from the option 61."
    ::= { tmnxDhcpSvrLeaseEntry 27 }

tmnxDhcpSvrLeaseStickyHostName   OBJECT-TYPE
    SYNTAX      TNamedItemOrEmpty
    MAX-ACCESS  read-only
    STATUS      current
    DESCRIPTION
        "The value of object tmnxDhcpSvrLeaseStickyHostName indicates the name
         of the sticky host configured in tmnxDhcpsStickyLseActHostName."
    ::= { tmnxDhcpSvrLeaseEntry 28 }

tmnxDhcpServerStatsTable         OBJECT-TYPE
    SYNTAX      SEQUENCE OF TmnxDhcpServerStatsEntry
    MAX-ACCESS  not-accessible
    STATUS      current
    DESCRIPTION
        "The tmnxDhcpServerStatsTable contains basic statistics about the DHCP
         server instances."
    ::= { tmnxDhcpServerObjs 14 }

tmnxDhcpServerStatsEntry         OBJECT-TYPE
    SYNTAX      TmnxDhcpServerStatsEntry
    MAX-ACCESS  not-accessible
    STATUS      current
    DESCRIPTION
        "Each row entry contains basic statistics about a particular DHCP
         server instance."
    INDEX       {
        vRtrID,
        IMPLIED tmnxDhcpServerCfgServerName
    }
    ::= { tmnxDhcpServerStatsTable 1 }

TmnxDhcpServerStatsEntry         ::= SEQUENCE
{
    tmnxDhcpSvrStatsRxDiscovers      Counter64,
    tmnxDhcpSvrStatsRxRequests       Counter64,
    tmnxDhcpSvrStatsRxReleases       Counter64,
    tmnxDhcpSvrStatsRxDeclines       Counter64,
    tmnxDhcpSvrStatsRxInforms        Counter64,
    tmnxDhcpSvrStatsTxOffers         Counter64,
    tmnxDhcpSvrStatsTxAcks           Counter64,
    tmnxDhcpSvrStatsTxNaks           Counter64,
    tmnxDhcpSvrStatsTxForceRenews    Counter64,
    tmnxDhcpSvrStatsDropBadPackets   Counter32,
    tmnxDhcpSvrStatsDropInvalidTypes Counter32,
    tmnxDhcpSvrStatsDropNoUsrDbFound Counter32,
    tmnxDhcpSvrStatsDropUnknownHosts Counter32,
    tmnxDhcpSvrStatsDropUserNotAllow Counter32,
    tmnxDhcpSvrStatsDropLseNotReady  Counter32,
    tmnxDhcpSvrStatsDropNoLeaseFound Counter32,
    tmnxDhcpSvrStatsDropNotSrvngPool Counter32,
    tmnxDhcpSvrStatsDropInvalidUsr   Counter32,
    tmnxDhcpSvrStatsDropOverload     Counter32,
    tmnxDhcpSvrStatsDropPersOverload Counter32,
    tmnxDhcpSvrStatsOffersIgnore     Counter32,
    tmnxDhcpSvrStatsDropGenError     Counter32,
    tmnxDhcpSvrStatsDropDestOther    Counter32,
    tmnxDhcpSvrStatsDropAddrUnavail  Counter32,
    tmnxDhcpSvrStatsDropMaxReached   Counter32,
    tmnxDhcpSvrStatsDropSvrDown      Counter32,
    tmnxDhcpSvrStatsDropNoSubnet     Counter32,
    tmnxDhcpSvrStatsLeasesExpired    Counter32,
    tmnxDhcpSvrStatsDropDuplDiffGi   Counter32,
    tmnxDhcpSvrStatsRxIntRequests    Counter64,
    tmnxDhcpSvrStatsRxIntReleases    Counter64,
    tmnxDhcpSvrStatsDropIntWithLudb  Counter32,
    tmnxDhcpSvrStatsDropIntWithFo    Counter32,
    tmnxDhcpSvrStatsDropIntConflicts Counter32,
    tmnxDhcpSvrStatsDropAudit        Counter32,
    tmnxDhcpSvrStatsDropTxFailed     Counter32,
    tmnxDhcpSvrStatsRxIntReqPpp      Counter64,
    tmnxDhcpSvrStatsRxIntReqIpoe     Counter64,
    tmnxDhcpSvrStatsRxIntReqIpsec    Counter64
}

tmnxDhcpSvrStatsRxDiscovers      OBJECT-TYPE
    SYNTAX      Counter64
    MAX-ACCESS  read-only
    STATUS      current
    DESCRIPTION
        "The value of tmnxDhcpSvrStatsRxDiscovers indicates the number of
         DHCPDISCOVER (option 53 with value 1) packets received by the DHCP
         server instance."
    ::= { tmnxDhcpServerStatsEntry 1 }

tmnxDhcpSvrStatsRxRequests       OBJECT-TYPE
    SYNTAX      Counter64
    MAX-ACCESS  read-only
    STATUS      current
    DESCRIPTION
        "The value of tmnxDhcpSvrStatsRxRequests indicates the number of
         DHCPREQUEST (option 53 with value 3) packets received by the DHCP
         server instance."
    ::= { tmnxDhcpServerStatsEntry 2 }

tmnxDhcpSvrStatsRxReleases       OBJECT-TYPE
    SYNTAX      Counter64
    MAX-ACCESS  read-only
    STATUS      current
    DESCRIPTION
        "The value of tmnxDhcpSvrStatsRxReleases indicates the number of
         DHCPRELEASE (option 53 with value 7) packets received by the DHCP
         server instance."
    ::= { tmnxDhcpServerStatsEntry 3 }

tmnxDhcpSvrStatsRxDeclines       OBJECT-TYPE
    SYNTAX      Counter64
    MAX-ACCESS  read-only
    STATUS      current
    DESCRIPTION
        "The value of tmnxDhcpSvrStatsRxDeclines indicates the number of
         DHCPDECLINE (option 53 with value 4) packets received by the DHCP
         server instance."
    ::= { tmnxDhcpServerStatsEntry 4 }

tmnxDhcpSvrStatsRxInforms        OBJECT-TYPE
    SYNTAX      Counter64
    MAX-ACCESS  read-only
    STATUS      current
    DESCRIPTION
        "The value of tmnxDhcpSvrStatsRxInforms indicates the number of
         DHCPINFORM (option 53 with value 8) packets received by the DHCP
         server instance."
    ::= { tmnxDhcpServerStatsEntry 5 }

tmnxDhcpSvrStatsTxOffers         OBJECT-TYPE
    SYNTAX      Counter64
    MAX-ACCESS  read-only
    STATUS      current
    DESCRIPTION
        "The value of tmnxDhcpSvrStatsTxOffers indicates the number of
         DHCPOFFER (option 53 with value 2) packets sent by the DHCP server
         instance."
    ::= { tmnxDhcpServerStatsEntry 6 }

tmnxDhcpSvrStatsTxAcks           OBJECT-TYPE
    SYNTAX      Counter64
    MAX-ACCESS  read-only
    STATUS      current
    DESCRIPTION
        "The value of tmnxDhcpSvrStatsTxAcks indicates the number of DHCPACK
         (option 53 with value 5) packets sent by the DHCP server instance."
    ::= { tmnxDhcpServerStatsEntry 7 }

tmnxDhcpSvrStatsTxNaks           OBJECT-TYPE
    SYNTAX      Counter64
    MAX-ACCESS  read-only
    STATUS      current
    DESCRIPTION
        "The value of tmnxDhcpSvrStatsTxNaks indicates the number of DHCPNAK
         (option 53 with value 6) packets sent by the DHCP server instance."
    ::= { tmnxDhcpServerStatsEntry 8 }

tmnxDhcpSvrStatsTxForceRenews    OBJECT-TYPE
    SYNTAX      Counter64
    MAX-ACCESS  read-only
    STATUS      current
    DESCRIPTION
        "The value of tmnxDhcpSvrStatsTxForceRenews indicates the number of
         DHCPFORCERENEW (option 53 with value 9) packets sent by the DHCP
         server instance."
    ::= { tmnxDhcpServerStatsEntry 9 }

tmnxDhcpSvrStatsDropBadPackets   OBJECT-TYPE
    SYNTAX      Counter32
    MAX-ACCESS  read-only
    STATUS      current
    DESCRIPTION
        "The value of tmnxDhcpSvrStatsDropBadPackets indicates the number of
         DHCP packets received which were corrupt."
    ::= { tmnxDhcpServerStatsEntry 10 }

tmnxDhcpSvrStatsDropInvalidTypes OBJECT-TYPE
    SYNTAX      Counter32
    MAX-ACCESS  read-only
    STATUS      current
    DESCRIPTION
        "The value of tmnxDhcpSvrStatsDropInvalidTypes indicates the number of
         DHCP packets received which had an invalid message type (option 53)."
    ::= { tmnxDhcpServerStatsEntry 11 }

tmnxDhcpSvrStatsDropNoUsrDbFound OBJECT-TYPE
    SYNTAX      Counter32
    MAX-ACCESS  read-only
    STATUS      current
    DESCRIPTION
        "The value of tmnxDhcpSvrStatsDropNoUsrDbFound indicates the number of
         DHCP packets dropped because the value of the object
         tmnxDhcpServerCfgUserDatabase of this server instance is not equal to
         the default value and a local user database with that name could not
         be found."
    ::= { tmnxDhcpServerStatsEntry 12 }

tmnxDhcpSvrStatsDropUnknownHosts OBJECT-TYPE
    SYNTAX      Counter32
    MAX-ACCESS  read-only
    STATUS      current
    DESCRIPTION
        "The value of tmnxDhcpSvrStatsDropUnknownHosts indicates the number of
         DHCP packets dropped from hosts which were not found in the user
         database when tmnxDhcpServerCfgUseGiAddress was disabled."
    ::= { tmnxDhcpServerStatsEntry 13 }

tmnxDhcpSvrStatsDropUserNotAllow OBJECT-TYPE
    SYNTAX      Counter32
    MAX-ACCESS  read-only
    STATUS      current
    DESCRIPTION
        "The value of tmnxDhcpSvrStatsDropUserNotAllow indicates the number of
         DHCP packets dropped from hosts which are found in the user database,
         but which have no address or pool specified, nor has
         tmnxDhcpServerCfgUseGiAddress set to 'true'."
    ::= { tmnxDhcpServerStatsEntry 14 }

tmnxDhcpSvrStatsDropLseNotReady  OBJECT-TYPE
    SYNTAX      Counter32
    MAX-ACCESS  read-only
    STATUS      current
    DESCRIPTION
        "The value of tmnxDhcpSvrStatsDropLseNotReady indicates the number of
         DHCP packets dropped by the server instance before the lease database
         was ready."
    ::= { tmnxDhcpServerStatsEntry 15 }

tmnxDhcpSvrStatsDropNoLeaseFound OBJECT-TYPE
    SYNTAX      Counter32
    MAX-ACCESS  read-only
    STATUS      current
    DESCRIPTION
        "The value of tmnxDhcpSvrStatsDropNoLeaseFound indicates the number of
         DHCP packets dropped by the server instance because no (valid) lease
         was found."
    ::= { tmnxDhcpServerStatsEntry 16 }

tmnxDhcpSvrStatsDropNotSrvngPool OBJECT-TYPE
    SYNTAX      Counter32
    MAX-ACCESS  read-only
    STATUS      current
    DESCRIPTION
        "The value of tmnxDhcpSvrStatsDropNotSrvngPool indicates the number of
         DHCP packets dropped by the server instance because there were no more
         free addresses in the pool."
    ::= { tmnxDhcpServerStatsEntry 17 }

tmnxDhcpSvrStatsDropInvalidUsr   OBJECT-TYPE
    SYNTAX      Counter32
    MAX-ACCESS  read-only
    STATUS      current
    DESCRIPTION
        "The value of tmnxDhcpSvrStatsDropInvalidUsr indicates the number of
         DHCP packets dropped by the server instance because the MAC address of
         the sender or the option 82 didn't match the host lease state."
    ::= { tmnxDhcpServerStatsEntry 18 }

tmnxDhcpSvrStatsDropOverload     OBJECT-TYPE
    SYNTAX      Counter32
    MAX-ACCESS  read-only
    STATUS      current
    DESCRIPTION
        "The value of tmnxDhcpSvrStatsDropOverload indicates the number of DHCP
         packets dropped by the server instance because they were received in
         excess of what the server instance can handle."
    ::= { tmnxDhcpServerStatsEntry 19 }

tmnxDhcpSvrStatsDropPersOverload OBJECT-TYPE
    SYNTAX      Counter32
    MAX-ACCESS  read-only
    STATUS      current
    DESCRIPTION
        "The value of tmnxDhcpSvrStatsDropPersOverload indicates
         the number of DHCP packets dropped by the server instance
         because they were received in excess of what the DHCP persistence
          system can handle. If this occurs, only releases and declines are
          still processed."
    ::= { tmnxDhcpServerStatsEntry 20 }

tmnxDhcpSvrStatsOffersIgnore     OBJECT-TYPE
    SYNTAX      Counter32
    MAX-ACCESS  read-only
    STATUS      current
    DESCRIPTION
        "The value of tmnxDhcpSvrStatsOffersIgnore indicates the number of
         DHCPOFFER (option 52 with value 2) packets sent by the DHCP server
         instance that were ignored by he clients."
    ::= { tmnxDhcpServerStatsEntry 21 }

tmnxDhcpSvrStatsDropGenError     OBJECT-TYPE
    SYNTAX      Counter32
    MAX-ACCESS  read-only
    STATUS      current
    DESCRIPTION
        "The value of tmnxDhcpSvrStatsDropGenError indicates the number of DHCP
         packets dropped by the server instance because of a generic error."
    ::= { tmnxDhcpServerStatsEntry 22 }

tmnxDhcpSvrStatsDropDestOther    OBJECT-TYPE
    SYNTAX      Counter32
    MAX-ACCESS  read-only
    STATUS      current
    DESCRIPTION
        "The value of tmnxDhcpSvrStatsDropDestOther indicates the number of
         DHCP requests dropped by the server instance because the (broadcast)
         request was not destined to this server."
    ::= { tmnxDhcpServerStatsEntry 23 }

tmnxDhcpSvrStatsDropAddrUnavail  OBJECT-TYPE
    SYNTAX      Counter32
    MAX-ACCESS  read-only
    STATUS      current
    DESCRIPTION
        "The value of tmnxDhcpSvrStatsDropAddrUnavail indicates the number of
         DHCP requests dropped by the server instance because the requested
         address is not available."
    ::= { tmnxDhcpServerStatsEntry 24 }

tmnxDhcpSvrStatsDropMaxReached   OBJECT-TYPE
    SYNTAX      Counter32
    MAX-ACCESS  read-only
    STATUS      current
    DESCRIPTION
        "The value of tmnxDhcpSvrStatsDropMaxReached indicates the number of
         DHCP packets dropped by the server instance because the maximum number
         of leases was reached.

          The maximum number of leases is indicated by the value of the object
          tmnxDhcpSvrMaxLeases."
    ::= { tmnxDhcpServerStatsEntry 25 }

tmnxDhcpSvrStatsDropSvrDown      OBJECT-TYPE
    SYNTAX      Counter32
    MAX-ACCESS  read-only
    STATUS      current
    DESCRIPTION
        "The value of tmnxDhcpSvrStatsDropSvrDown indicates the number of DHCP
         packets dropped by the server instance during server instance shutdown
         (while the value of the object tmnxDhcpServerCfgAdminState in the
         corresponding row was set equal to 'outOfService')."
    ::= { tmnxDhcpServerStatsEntry 26 }

tmnxDhcpSvrStatsDropNoSubnet     OBJECT-TYPE
    SYNTAX      Counter32
    MAX-ACCESS  read-only
    STATUS      current
    DESCRIPTION
        "The value of tmnxDhcpSvrStatsDropNoSubnet indicates the number of DHCP
         packets dropped by the server instance for user-db hosts with a fixed
         address because the subnet to which the address belongs is not
         configured."
    ::= { tmnxDhcpServerStatsEntry 27 }

tmnxDhcpSvrStatsLeasesExpired    OBJECT-TYPE
    SYNTAX      Counter32
    MAX-ACCESS  read-only
    STATUS      current
    DESCRIPTION
        "The value of tmnxDhcpSvrStatsLeasesExpired indicates the number of
         DHCP leases that were expired (because no release was received)."
    ::= { tmnxDhcpServerStatsEntry 28 }

tmnxDhcpSvrStatsDropDuplDiffGi   OBJECT-TYPE
    SYNTAX      Counter32
    MAX-ACCESS  read-only
    STATUS      current
    DESCRIPTION
        "The value of tmnxDhcpSvrStatsDropDuplDiffGi indicates the number of
         DHCP requests dropped by the server instance because they were
         received from a different Gateway IP address within a timeframe of 10
         seconds after a previous DHCPREQUEST."
    ::= { tmnxDhcpServerStatsEntry 29 }

tmnxDhcpSvrStatsRxIntRequests    OBJECT-TYPE
    SYNTAX      Counter64
    MAX-ACCESS  read-only
    STATUS      obsolete
    DESCRIPTION
        "The value of tmnxDhcpSvrStatsRxIntRequests indicates the number of
         internal request calls received by the DHCP server instance from the
         local address assignment infrastructure."
    ::= { tmnxDhcpServerStatsEntry 30 }

tmnxDhcpSvrStatsRxIntReleases    OBJECT-TYPE
    SYNTAX      Counter64
    MAX-ACCESS  read-only
    STATUS      current
    DESCRIPTION
        "The value of tmnxDhcpSvrStatsRxIntReleases indicates the number of
         internal release calls received by the DHCP server instance from the
         local address assignment infrastructure."
    ::= { tmnxDhcpServerStatsEntry 31 }

tmnxDhcpSvrStatsDropIntWithLudb  OBJECT-TYPE
    SYNTAX      Counter32
    MAX-ACCESS  read-only
    STATUS      current
    DESCRIPTION
        "The value of tmnxDhcpSvrStatsDropIntWithLudb indicates the number of
         internal calls from the local address assignment infrastructure
         dropped by the DHCP server instance because a local user database is
         attached to the server instance."
    ::= { tmnxDhcpServerStatsEntry 32 }

tmnxDhcpSvrStatsDropIntWithFo    OBJECT-TYPE
    SYNTAX      Counter32
    MAX-ACCESS  read-only
    STATUS      current
    DESCRIPTION
        "The value of tmnxDhcpSvrStatsDropIntWithFo indicates the number of
         internal calls from the local address assignment infrastructure
         dropped by the DHCP server instance because failover is enabled for
         the server instance."
    ::= { tmnxDhcpServerStatsEntry 33 }

tmnxDhcpSvrStatsDropIntConflicts OBJECT-TYPE
    SYNTAX      Counter32
    MAX-ACCESS  read-only
    STATUS      current
    DESCRIPTION
        "The value of tmnxDhcpSvrStatsDropIntConflicts indicates a DHCP host is
         trying to acquire an IP address that was handed through the local
         address assignment infrastructure, or the local address assignment
         infrastructure tries to use an IP address that was handed out to a
         DHCP client."
    ::= { tmnxDhcpServerStatsEntry 34 }

tmnxDhcpSvrStatsDropAudit        OBJECT-TYPE
    SYNTAX      Counter32
    MAX-ACCESS  read-only
    STATUS      current
    DESCRIPTION
        "The value of tmnxDhcpSvrStatsDropAudit indicates the number of DHCP
         requests dropped by the server instance because this server instance
         is busy with the primary audit."
    ::= { tmnxDhcpServerStatsEntry 35 }

tmnxDhcpSvrStatsDropTxFailed     OBJECT-TYPE
    SYNTAX      Counter32
    MAX-ACCESS  read-only
    STATUS      current
    DESCRIPTION
        "The value of tmnxDhcpSvrStatsDropTxFailed indicates the number of DHCP
         responses dropped because this server instance could not transmit it."
    ::= { tmnxDhcpServerStatsEntry 36 }

tmnxDhcpSvrStatsRxIntReqPpp      OBJECT-TYPE
    SYNTAX      Counter64
    MAX-ACCESS  read-only
    STATUS      current
    DESCRIPTION
        "The value of tmnxDhcpSvrStatsRxIntReqPpp indicates the number of
         internal request calls received by the DHCP server instance from the
         local address assignment infrastructure for PPP."
    ::= { tmnxDhcpServerStatsEntry 37 }

tmnxDhcpSvrStatsRxIntReqIpoe     OBJECT-TYPE
    SYNTAX      Counter64
    MAX-ACCESS  read-only
    STATUS      current
    DESCRIPTION
        "The value of tmnxDhcpSvrStatsRxIntReqIpoe indicates the number of
         internal request calls received by the DHCP server instance from the
         local address assignment infrastructure for IPoE."
    ::= { tmnxDhcpServerStatsEntry 38 }

tmnxDhcpSvrStatsRxIntReqIpsec    OBJECT-TYPE
    SYNTAX      Counter64
    MAX-ACCESS  read-only
    STATUS      current
    DESCRIPTION
        "The value of tmnxDhcpSvrStatsRxIntReqIpsec indicates the number of
         internal request calls received by the DHCP server instance from the
         local address assignment infrastructure for IPsec."
    ::= { tmnxDhcpServerStatsEntry 39 }

tmnxDhcpSvrDeclinedAddrTable     OBJECT-TYPE
    SYNTAX      SEQUENCE OF TmnxDhcpSvrDeclinedAddrEntry
    MAX-ACCESS  not-accessible
    STATUS      current
    DESCRIPTION
        "The table tmnxDhcpSvrDeclinedAddrTable contains a list of IP addresses
         which are declined by DHCP clients."
    ::= { tmnxDhcpServerObjs 16 }

tmnxDhcpSvrDeclinedAddrEntry     OBJECT-TYPE
    SYNTAX      TmnxDhcpSvrDeclinedAddrEntry
    MAX-ACCESS  not-accessible
    STATUS      current
    DESCRIPTION
        "Each row represents a declined IP address.

         Entries in this table cannot be created via SNMP operations. Entries
         in this table can be deleted via the TIMETRA-CLEAR-MIB."
    INDEX       {
        vRtrID,
        tmnxDhcpServerCfgServerName,
        tmnxDhcpServerPoolName,
        tmnxDhcpSvrSubnetAddrType,
        tmnxDhcpSvrSubnetAddress,
        tmnxDhcpSvrSubnetPrefixLength,
        tmnxDhcpSvrDeclinedAddrType,
        tmnxDhcpSvrDeclinedAddress
    }
    ::= { tmnxDhcpSvrDeclinedAddrTable 1 }

TmnxDhcpSvrDeclinedAddrEntry     ::= SEQUENCE
{
    tmnxDhcpSvrDeclinedAddrType      InetAddressType,
    tmnxDhcpSvrDeclinedAddress       InetAddress,
    tmnxDhcpSvrDeclinedAddrHwAddress MacAddress,
    tmnxDhcpSvrDeclinedAddrAddedTime DateAndTime,
    tmnxDhcpSvrDeclinedAddrOption82  OCTET STRING,
    tmnxDhcpSvrDeclinedAddrClientType TmnxDhcpSvrClientType,
    tmnxDhcpSvrDeclinedAddrUserName  OCTET STRING,
    tmnxDhcpSvrDeclinedAddrCircId    OCTET STRING
}

tmnxDhcpSvrDeclinedAddrType      OBJECT-TYPE
    SYNTAX      InetAddressType
    MAX-ACCESS  not-accessible
    STATUS      current
    DESCRIPTION
        "The value of the object tmnxDhcpSvrDeclinedAddrType specifies the type
         of tmnxDhcpSvrDeclinedAddress."
    ::= { tmnxDhcpSvrDeclinedAddrEntry 1 }

tmnxDhcpSvrDeclinedAddress       OBJECT-TYPE
    SYNTAX      InetAddress (SIZE (4|16))
    MAX-ACCESS  not-accessible
    STATUS      current
    DESCRIPTION
        "The value of the object tmnxDhcpSvrDeclinedAddress specifies the
         declined IP address."
    ::= { tmnxDhcpSvrDeclinedAddrEntry 2 }

tmnxDhcpSvrDeclinedAddrHwAddress OBJECT-TYPE
    SYNTAX      MacAddress
    MAX-ACCESS  read-only
    STATUS      current
    DESCRIPTION
        "The value of object tmnxDhcpSvrDeclinedAddrHwAddress indicates the MAC
         address of the client."
    ::= { tmnxDhcpSvrDeclinedAddrEntry 3 }

tmnxDhcpSvrDeclinedAddrAddedTime OBJECT-TYPE
    SYNTAX      DateAndTime (SIZE (11))
    MAX-ACCESS  read-only
    STATUS      current
    DESCRIPTION
        "The value of the object tmnxDhcpSvrDeclinedAddrAddedTime indicates the
         creation time of this entry."
    ::= { tmnxDhcpSvrDeclinedAddrEntry 4 }

tmnxDhcpSvrDeclinedAddrOption82  OBJECT-TYPE
    SYNTAX      OCTET STRING (SIZE (0..257))
    MAX-ACCESS  read-only
    STATUS      current
    DESCRIPTION
        "The value of the object tmnxDhcpSvrDeclinedAddrOption82 indicates the
         option82 from the client message."
    ::= { tmnxDhcpSvrDeclinedAddrEntry 5 }

tmnxDhcpSvrDeclinedAddrClientType OBJECT-TYPE
    SYNTAX      TmnxDhcpSvrClientType
    MAX-ACCESS  read-only
    STATUS      current
    DESCRIPTION
        "The value of object tmnxDhcpSvrDeclinedAddrClientType indicates the
         type of the client."
    ::= { tmnxDhcpSvrDeclinedAddrEntry 6 }

tmnxDhcpSvrDeclinedAddrUserName  OBJECT-TYPE
    SYNTAX      OCTET STRING (SIZE (0..253))
    MAX-ACCESS  read-only
    STATUS      current
    DESCRIPTION
        "The value of object tmnxDhcpSvrDeclinedAddrUserName indicates the PPP
         user name.

         This object is only relevant if the value of
         tmnxDhcpSvrDeclinedAddrClientType is equal to 'ppp'."
    ::= { tmnxDhcpSvrDeclinedAddrEntry 7 }

tmnxDhcpSvrDeclinedAddrCircId    OBJECT-TYPE
    SYNTAX      OCTET STRING (SIZE (0..255))
    MAX-ACCESS  read-only
    STATUS      current
    DESCRIPTION
        "The value of object tmnxDhcpSvrDeclinedAddrCircId indicates the
         Circuit ID from the option 82."
    ::= { tmnxDhcpSvrDeclinedAddrEntry 8 }

tmnxDhcpSvrSubnetStatsTable      OBJECT-TYPE
    SYNTAX      SEQUENCE OF TmnxDhcpSvrSubnetStatsEntry
    MAX-ACCESS  not-accessible
    STATUS      current
    DESCRIPTION
        "The tmnxDhcpSvrSubnetStatsTable has an entry for each subnet that
         belongs to the specified DHCP server instance and pool."
    ::= { tmnxDhcpServerObjs 17 }

tmnxDhcpSvrSubnetStatsEntry      OBJECT-TYPE
    SYNTAX      TmnxDhcpSvrSubnetStatsEntry
    MAX-ACCESS  not-accessible
    STATUS      current
    DESCRIPTION
        "Each row entry in the tmnxDhcpSvrSubnetStatsTable represents
         additional columns of operational data for a subnet that belongs to
         the specified DHCP server instance and pool."
    INDEX       {
        vRtrID,
        tmnxDhcpServerCfgServerName,
        tmnxDhcpServerPoolName,
        tmnxDhcpSvrSubnetAddrType,
        tmnxDhcpSvrSubnetAddress,
        tmnxDhcpSvrSubnetPrefixLength
    }
    ::= { tmnxDhcpSvrSubnetStatsTable 1 }

TmnxDhcpSvrSubnetStatsEntry      ::= SEQUENCE
{
    tmnxDhcpSvrSubnetStatsFree       Counter32,
    tmnxDhcpSvrSubnetStatsOffered    Counter32,
    tmnxDhcpSvrSubnetStatsStable     Counter32,
    tmnxDhcpSvrSubnetStatsFRPending  Counter32,
    tmnxDhcpSvrSubnetStatsRemPending Counter32,
    tmnxDhcpSvrSubnetStatsDeclined   Counter32,
    tmnxDhcpSvrSubnetStatsFoFree     Counter32,
    tmnxDhcpSvrSubnetStatsFoOffered  Counter32,
    tmnxDhcpSvrSubnetStatsFoStable   Counter32,
    tmnxDhcpSvrSubnetStatsFoFRPend   Counter32,
    tmnxDhcpSvrSubnetStatsFoRemPend  Counter32,
    tmnxDhcpSvrSubnetStatsFoDeclined Counter32,
    tmnxDhcpSvrSubnetStatsProv       Counter32,
    tmnxDhcpSvrSubnetStatsFoProv     Counter32,
    tmnxDhcpSvrSubnetStatsHasExt     TruthValue,
    tmnxDhcpSvrSubnetStatsExtResetT  TimeStamp,
    tmnxDhcpSvrSubnetStatsStableP    Counter32,
    tmnxDhcpSvrSubnetStatsStablePT   TimeStamp,
    tmnxDhcpSvrSubnetStatsFoStableP  Counter32,
    tmnxDhcpSvrSubnetStatsFoStablePT TimeStamp,
    tmnxDhcpSvrSubnetStatsUsed       Counter32,
    tmnxDhcpSvrSubnetStatsUsedP      Counter32,
    tmnxDhcpSvrSubnetStatsUsedPT     TimeStamp,
    tmnxDhcpSvrSubnetStatsFoUsed     Counter32,
    tmnxDhcpSvrSubnetStatsFoUsedP    Counter32,
    tmnxDhcpSvrSubnetStatsFoUsedPT   TimeStamp,
    tmnxDhcpSvrSubnetStatsFreeP      Counter32,
    tmnxDhcpSvrSubnetStatsFreePT     TimeStamp,
    tmnxDhcpSvrSubnetStatsFoFreeP    Counter32,
    tmnxDhcpSvrSubnetStatsFoFreePT   TimeStamp,
    tmnxDhcpSvrSubnetStatsUsedPct    Integer32,
    tmnxDhcpSvrSubnetStatsUsedPctP   Integer32,
    tmnxDhcpSvrSubnetStatsUsedPctPT  TimeStamp,
    tmnxDhcpSvrSubnetStatsFoUsdPct   Integer32,
    tmnxDhcpSvrSubnetStatsFoUsdPctP  Integer32,
    tmnxDhcpSvrSubnetStatsFoUsdPctPT TimeStamp,
    tmnxDhcpSvrSubnetStatsFreePct    Integer32,
    tmnxDhcpSvrSubnetStatsFreePctP   Integer32,
    tmnxDhcpSvrSubnetStatsFreePctPT  TimeStamp,
    tmnxDhcpSvrSubnetStatsFoFrePct   Integer32,
    tmnxDhcpSvrSubnetStatsFoFrePctP  Integer32,
    tmnxDhcpSvrSubnetStatsFoFrePctPT TimeStamp,
    tmnxDhcpSvrSubnetStatsOfferP     Counter32,
    tmnxDhcpSvrSubnetStatsOfferPT    TimeStamp,
    tmnxDhcpSvrSubnetStatsFoOfferP   Counter32,
    tmnxDhcpSvrSubnetStatsFoOfferPT  TimeStamp
}

tmnxDhcpSvrSubnetStatsFree       OBJECT-TYPE
    SYNTAX      Counter32
    MAX-ACCESS  read-only
    STATUS      current
    DESCRIPTION
        "The value of tmnxDhcpSvrSubnetStatsFree indicates the number of
         addresses in this subnet that are free."
    ::= { tmnxDhcpSvrSubnetStatsEntry 1 }

tmnxDhcpSvrSubnetStatsOffered    OBJECT-TYPE
    SYNTAX      Counter32
    MAX-ACCESS  read-only
    STATUS      current
    DESCRIPTION
        "The value of tmnxDhcpSvrSubnetStatsOffered indicates the number of
         leases in this subnet that are in state 'offered'."
    ::= { tmnxDhcpSvrSubnetStatsEntry 2 }

tmnxDhcpSvrSubnetStatsStable     OBJECT-TYPE
    SYNTAX      Counter32
    MAX-ACCESS  read-only
    STATUS      current
    DESCRIPTION
        "The value of tmnxDhcpSvrSubnetStatsStable indicates the number of
         leases in this subnet that are in state 'stable'."
    ::= { tmnxDhcpSvrSubnetStatsEntry 3 }

tmnxDhcpSvrSubnetStatsFRPending  OBJECT-TYPE
    SYNTAX      Counter32
    MAX-ACCESS  read-only
    STATUS      current
    DESCRIPTION
        "The value of tmnxDhcpSvrSubnetStatsFRPending indicates the number of
         leases in this subnet that are in state 'forceRenewPending'."
    ::= { tmnxDhcpSvrSubnetStatsEntry 4 }

tmnxDhcpSvrSubnetStatsRemPending OBJECT-TYPE
    SYNTAX      Counter32
    MAX-ACCESS  read-only
    STATUS      current
    DESCRIPTION
        "The value of tmnxDhcpSvrSubnetStatsRemPending indicates the number of
         leases in this subnet that are in state 'removePending'."
    ::= { tmnxDhcpSvrSubnetStatsEntry 5 }

tmnxDhcpSvrSubnetStatsDeclined   OBJECT-TYPE
    SYNTAX      Counter32
    MAX-ACCESS  read-only
    STATUS      current
    DESCRIPTION
        "The value of tmnxDhcpSvrSubnetStatsDeclined indicates the number of
         addresses in this subnet that are declined."
    ::= { tmnxDhcpSvrSubnetStatsEntry 6 }

tmnxDhcpSvrSubnetStatsFoFree     OBJECT-TYPE
    SYNTAX      Counter32
    MAX-ACCESS  read-only
    STATUS      current
    DESCRIPTION
        "The value of tmnxDhcpSvrSubnetStatsFoFree indicates the number of
         remote addresses in this subnet that are free.

         The value of this object is only relevant if the value of the object
         tmnxDhcpsFoAdminState of this server is equal to 'inService (2)'."
    ::= { tmnxDhcpSvrSubnetStatsEntry 7 }

tmnxDhcpSvrSubnetStatsFoOffered  OBJECT-TYPE
    SYNTAX      Counter32
    MAX-ACCESS  read-only
    STATUS      current
    DESCRIPTION
        "The value of tmnxDhcpSvrSubnetStatsFoOffered indicates the number of
         remote leases in this subnet that are in state 'offered'.

         The value of this object is only relevant if the value of the object
         tmnxDhcpsFoAdminState of this server is equal to 'inService (2)'."
    ::= { tmnxDhcpSvrSubnetStatsEntry 8 }

tmnxDhcpSvrSubnetStatsFoStable   OBJECT-TYPE
    SYNTAX      Counter32
    MAX-ACCESS  read-only
    STATUS      current
    DESCRIPTION
        "The value of tmnxDhcpSvrSubnetStatsFoStable indicates the number of
         remote leases in this subnet that are in state 'stable'.

         The value of this object is only relevant if the value of the object
         tmnxDhcpsFoAdminState of this server is equal to 'inService (2)'."
    ::= { tmnxDhcpSvrSubnetStatsEntry 9 }

tmnxDhcpSvrSubnetStatsFoFRPend   OBJECT-TYPE
    SYNTAX      Counter32
    MAX-ACCESS  read-only
    STATUS      current
    DESCRIPTION
        "The value of tmnxDhcpSvrSubnetStatsFoFRPend indicates the number of
         remote leases in this subnet that are in state 'forceRenewPending'.

         The value of this object is only relevant if the value of the object
         tmnxDhcpsFoAdminState of this server is equal to 'inService (2)'."
    ::= { tmnxDhcpSvrSubnetStatsEntry 10 }

tmnxDhcpSvrSubnetStatsFoRemPend  OBJECT-TYPE
    SYNTAX      Counter32
    MAX-ACCESS  read-only
    STATUS      current
    DESCRIPTION
        "The value of tmnxDhcpSvrSubnetStatsFoRemPend indicates the number of
         remote leases in this subnet that are in state 'removePending'.

         The value of this object is only relevant if the value of the object
         tmnxDhcpsFoAdminState of this server is equal to 'inService (2)'."
    ::= { tmnxDhcpSvrSubnetStatsEntry 11 }

tmnxDhcpSvrSubnetStatsFoDeclined OBJECT-TYPE
    SYNTAX      Counter32
    MAX-ACCESS  read-only
    STATUS      current
    DESCRIPTION
        "The value of tmnxDhcpSvrSubnetStatsFoDeclined indicates the number of
         remote addresses in this subnet that are declined.

         The value of this object is only relevant if the value of the object
         tmnxDhcpsFoAdminState of this server is equal to 'inService (2)'."
    ::= { tmnxDhcpSvrSubnetStatsEntry 12 }

tmnxDhcpSvrSubnetStatsProv       OBJECT-TYPE
    SYNTAX      Counter32
    MAX-ACCESS  read-only
    STATUS      current
    DESCRIPTION
        "The value of tmnxDhcpSvrSubnetStatsProv indicates the total number of
         local addresses in this subnet that are provisioned."
    ::= { tmnxDhcpSvrSubnetStatsEntry 13 }

tmnxDhcpSvrSubnetStatsFoProv     OBJECT-TYPE
    SYNTAX      Counter32
    MAX-ACCESS  read-only
    STATUS      current
    DESCRIPTION
        "The value of tmnxDhcpSvrSubnetStatsFoProv indicates the total number
         of remote addresses in this subnet that are provisioned.

         The value of this object is only relevant if the value of the object
         tmnxDhcpsFoAdminState of this server is equal to 'inService (2)' and
         the value of the object tmnxDhcpsFoState of this server is equal to
         'partnerDown (5)'."
    ::= { tmnxDhcpSvrSubnetStatsEntry 14 }

tmnxDhcpSvrSubnetStatsHasExt     OBJECT-TYPE
    SYNTAX      TruthValue
    MAX-ACCESS  read-only
    STATUS      current
    DESCRIPTION
        "The value of tmnxDhcpSvrSubnetStatsHasExt indicates whether the
         extended statistics collection for this subnet is enabled."
    ::= { tmnxDhcpSvrSubnetStatsEntry 15 }

tmnxDhcpSvrSubnetStatsExtResetT  OBJECT-TYPE
    SYNTAX      TimeStamp
    MAX-ACCESS  read-only
    STATUS      current
    DESCRIPTION
        "The value of tmnxDhcpSvrSubnetStatsExtResetT indicates the sysUpTime
         at the last reset of the extended statistics."
    ::= { tmnxDhcpSvrSubnetStatsEntry 16 }

tmnxDhcpSvrSubnetStatsStableP    OBJECT-TYPE
    SYNTAX      Counter32
    MAX-ACCESS  read-only
    STATUS      current
    DESCRIPTION
        "The value of tmnxDhcpSvrSubnetStatsStableP indicates the highest value
         of tmnxDhcpSvrSubnetStatsStable since the last reset of the extended
         statistics."
    ::= { tmnxDhcpSvrSubnetStatsEntry 17 }

tmnxDhcpSvrSubnetStatsStablePT   OBJECT-TYPE
    SYNTAX      TimeStamp
    MAX-ACCESS  read-only
    STATUS      current
    DESCRIPTION
        "The value of tmnxDhcpSvrSubnetStatsStablePT indicates the sysUpTime at
         the last change of tmnxDhcpSvrSubnetStatsStableP."
    ::= { tmnxDhcpSvrSubnetStatsEntry 18 }

tmnxDhcpSvrSubnetStatsFoStableP  OBJECT-TYPE
    SYNTAX      Counter32
    MAX-ACCESS  read-only
    STATUS      current
    DESCRIPTION
        "The value of tmnxDhcpSvrSubnetStatsFoStableP indicates the highest
         value of tmnxDhcpSvrSubnetStatsFoStable since the last reset of the
         extended statistics."
    ::= { tmnxDhcpSvrSubnetStatsEntry 19 }

tmnxDhcpSvrSubnetStatsFoStablePT OBJECT-TYPE
    SYNTAX      TimeStamp
    MAX-ACCESS  read-only
    STATUS      current
    DESCRIPTION
        "The value of tmnxDhcpSvrSubnetStatsFoStablePT indicates the sysUpTime
         at the last change of tmnxDhcpSvrSubnetStatsFoStableP."
    ::= { tmnxDhcpSvrSubnetStatsEntry 20 }

tmnxDhcpSvrSubnetStatsUsed       OBJECT-TYPE
    SYNTAX      Counter32
    MAX-ACCESS  read-only
    STATUS      current
    DESCRIPTION
        "The value of tmnxDhcpSvrSubnetStatsUsed indicates the number of leases
         in this subnet that are in use."
    ::= { tmnxDhcpSvrSubnetStatsEntry 21 }

tmnxDhcpSvrSubnetStatsUsedP      OBJECT-TYPE
    SYNTAX      Counter32
    MAX-ACCESS  read-only
    STATUS      current
    DESCRIPTION
        "The value of tmnxDhcpSvrSubnetStatsUsedP indicates the lowest value of
         tmnxDhcpSvrSubnetStatsUsed since the last reset of the extended
         statistics."
    ::= { tmnxDhcpSvrSubnetStatsEntry 22 }

tmnxDhcpSvrSubnetStatsUsedPT     OBJECT-TYPE
    SYNTAX      TimeStamp
    MAX-ACCESS  read-only
    STATUS      current
    DESCRIPTION
        "The value of tmnxDhcpSvrSubnetStatsUsedPT indicates the sysUpTime at
         the last change of tmnxDhcpSvrSubnetStatsUsedP."
    ::= { tmnxDhcpSvrSubnetStatsEntry 23 }

tmnxDhcpSvrSubnetStatsFoUsed     OBJECT-TYPE
    SYNTAX      Counter32
    MAX-ACCESS  read-only
    STATUS      current
    DESCRIPTION
        "The value of tmnxDhcpSvrSubnetStatsFoUsed indicates the number of
         remote leases in this subnet that are in use."
    ::= { tmnxDhcpSvrSubnetStatsEntry 24 }

tmnxDhcpSvrSubnetStatsFoUsedP    OBJECT-TYPE
    SYNTAX      Counter32
    MAX-ACCESS  read-only
    STATUS      current
    DESCRIPTION
        "The value of tmnxDhcpSvrSubnetStatsFoUsedP indicates the lowest value
         of tmnxDhcpSvrSubnetStatsFoUsed since the last reset of the extended
         statistics."
    ::= { tmnxDhcpSvrSubnetStatsEntry 25 }

tmnxDhcpSvrSubnetStatsFoUsedPT   OBJECT-TYPE
    SYNTAX      TimeStamp
    MAX-ACCESS  read-only
    STATUS      current
    DESCRIPTION
        "The value of tmnxDhcpSvrSubnetStatsFoUsedPT indicates the sysUpTime at
         the last change of tmnxDhcpSvrSubnetStatsFoUsedP."
    ::= { tmnxDhcpSvrSubnetStatsEntry 26 }

tmnxDhcpSvrSubnetStatsFreeP      OBJECT-TYPE
    SYNTAX      Counter32
    MAX-ACCESS  read-only
    STATUS      current
    DESCRIPTION
        "The value of tmnxDhcpSvrSubnetStatsFreeP indicates the peak number of
         addresses in this subnet that are free since the last reset of the
         extended statistics."
    ::= { tmnxDhcpSvrSubnetStatsEntry 27 }

tmnxDhcpSvrSubnetStatsFreePT     OBJECT-TYPE
    SYNTAX      TimeStamp
    MAX-ACCESS  read-only
    STATUS      current
    DESCRIPTION
        "The value of tmnxDhcpSvrSubnetStatsFreePT indicates the sysUpTime at
         the last change of tmnxDhcpSvrSubnetStatsFreeP."
    ::= { tmnxDhcpSvrSubnetStatsEntry 28 }

tmnxDhcpSvrSubnetStatsFoFreeP    OBJECT-TYPE
    SYNTAX      Counter32
    MAX-ACCESS  read-only
    STATUS      current
    DESCRIPTION
        "The value of tmnxDhcpSvrSubnetStatsFoFreeP indicates the peak number
         of remote addresses in this subnet that are free since the last reset
         of the extended statistics."
    ::= { tmnxDhcpSvrSubnetStatsEntry 29 }

tmnxDhcpSvrSubnetStatsFoFreePT   OBJECT-TYPE
    SYNTAX      TimeStamp
    MAX-ACCESS  read-only
    STATUS      current
    DESCRIPTION
        "The value of tmnxDhcpSvrSubnetStatsFoFreePT indicates the sysUpTime at
         the last change of tmnxDhcpSvrSubnetStatsFoFreeP."
    ::= { tmnxDhcpSvrSubnetStatsEntry 30 }

tmnxDhcpSvrSubnetStatsUsedPct    OBJECT-TYPE
    SYNTAX      Integer32 (0..100)
    MAX-ACCESS  read-only
    STATUS      current
    DESCRIPTION
        "The value of tmnxDhcpSvrSubnetStatsUsedPct indicates the percentage of
         addresses in this subnet in use."
    ::= { tmnxDhcpSvrSubnetStatsEntry 31 }

tmnxDhcpSvrSubnetStatsUsedPctP   OBJECT-TYPE
    SYNTAX      Integer32 (0..100)
    MAX-ACCESS  read-only
    STATUS      current
    DESCRIPTION
        "The value of tmnxDhcpSvrSubnetStatsUsedPctP indicates the highest
         value of tmnxDhcpSvrSubnetStatsUsedPct since the last reset of the
         extended statistics."
    ::= { tmnxDhcpSvrSubnetStatsEntry 32 }

tmnxDhcpSvrSubnetStatsUsedPctPT  OBJECT-TYPE
    SYNTAX      TimeStamp
    MAX-ACCESS  read-only
    STATUS      current
    DESCRIPTION
        "The value of tmnxDhcpSvrSubnetStatsUsedPctPT indicates the sysUpTime
         at the last change of tmnxDhcpSvrSubnetStatsUsedPctP."
    ::= { tmnxDhcpSvrSubnetStatsEntry 33 }

tmnxDhcpSvrSubnetStatsFoUsdPct   OBJECT-TYPE
    SYNTAX      Integer32 (0..100)
    MAX-ACCESS  read-only
    STATUS      current
    DESCRIPTION
        "The value of tmnxDhcpSvrSubnetStatsFoUsdPct indicates the percentage
         of remote addresses in this subnet that are in use."
    ::= { tmnxDhcpSvrSubnetStatsEntry 34 }

tmnxDhcpSvrSubnetStatsFoUsdPctP  OBJECT-TYPE
    SYNTAX      Integer32 (0..100)
    MAX-ACCESS  read-only
    STATUS      current
    DESCRIPTION
        "The value of tmnxDhcpSvrSubnetStatsFoUsdPctP indicates the highest
         value of tmnxDhcpSvrSubnetStatsFoUsdPct since the last reset of the
         extended statistics."
    ::= { tmnxDhcpSvrSubnetStatsEntry 35 }

tmnxDhcpSvrSubnetStatsFoUsdPctPT OBJECT-TYPE
    SYNTAX      TimeStamp
    MAX-ACCESS  read-only
    STATUS      current
    DESCRIPTION
        "The value of tmnxDhcpSvrSubnetStatsFoUsdPctPT indicates the sysUpTime
         at the last change of tmnxDhcpSvrSubnetStatsFoUsdPctP."
    ::= { tmnxDhcpSvrSubnetStatsEntry 36 }

tmnxDhcpSvrSubnetStatsFreePct    OBJECT-TYPE
    SYNTAX      Integer32 (0..100)
    MAX-ACCESS  read-only
    STATUS      current
    DESCRIPTION
        "The value of tmnxDhcpSvrSubnetStatsFreePct indicates the percentage of
         addresses in this subnet currently unused."
    ::= { tmnxDhcpSvrSubnetStatsEntry 37 }

tmnxDhcpSvrSubnetStatsFreePctP   OBJECT-TYPE
    SYNTAX      Integer32 (0..100)
    MAX-ACCESS  read-only
    STATUS      current
    DESCRIPTION
        "The value of tmnxDhcpSvrSubnetStatsFreePctP indicates the lowest value
         of tmnxDhcpSvrSubnetStatsFreePct since the last reset of the extended
         statistics."
    ::= { tmnxDhcpSvrSubnetStatsEntry 38 }

tmnxDhcpSvrSubnetStatsFreePctPT  OBJECT-TYPE
    SYNTAX      TimeStamp
    MAX-ACCESS  read-only
    STATUS      current
    DESCRIPTION
        "The value of tmnxDhcpSvrSubnetStatsFreePctPT indicates the sysUpTime
         at the last change of tmnxDhcpSvrSubnetStatsFreePctP."
    ::= { tmnxDhcpSvrSubnetStatsEntry 39 }

tmnxDhcpSvrSubnetStatsFoFrePct   OBJECT-TYPE
    SYNTAX      Integer32 (0..100)
    MAX-ACCESS  read-only
    STATUS      current
    DESCRIPTION
        "The value of tmnxDhcpSvrSubnetStatsFoFrePct indicates the percentage
         of remote addresses in this subnet that are currently unused."
    ::= { tmnxDhcpSvrSubnetStatsEntry 40 }

tmnxDhcpSvrSubnetStatsFoFrePctP  OBJECT-TYPE
    SYNTAX      Integer32 (0..100)
    MAX-ACCESS  read-only
    STATUS      current
    DESCRIPTION
        "The value of tmnxDhcpSvrSubnetStatsFoFrePctP indicates the lowest
         value of tmnxDhcpSvrSubnetStatsFoFrePct since the last reset of the
         extended statistics."
    ::= { tmnxDhcpSvrSubnetStatsEntry 41 }

tmnxDhcpSvrSubnetStatsFoFrePctPT OBJECT-TYPE
    SYNTAX      TimeStamp
    MAX-ACCESS  read-only
    STATUS      current
    DESCRIPTION
        "The value of tmnxDhcpSvrSubnetStatsFoFrePctPT indicates the sysUpTime
         at the last change of tmnxDhcpSvrSubnetStatsFoFrePctP."
    ::= { tmnxDhcpSvrSubnetStatsEntry 42 }

tmnxDhcpSvrSubnetStatsOfferP     OBJECT-TYPE
    SYNTAX      Counter32
    MAX-ACCESS  read-only
    STATUS      current
    DESCRIPTION
        "The value of tmnxDhcpSvrSubnetStatsOfferP indicates the highest value
         of tmnxDhcpSvrSubnetStatsOffered since the last reset of the extended
         statistics."
    ::= { tmnxDhcpSvrSubnetStatsEntry 43 }

tmnxDhcpSvrSubnetStatsOfferPT    OBJECT-TYPE
    SYNTAX      TimeStamp
    MAX-ACCESS  read-only
    STATUS      current
    DESCRIPTION
        "The value of tmnxDhcpSvrSubnetStatsOfferPT indicates the sysUpTime at
         the last change of tmnxDhcpSvrSubnetStatsOfferP."
    ::= { tmnxDhcpSvrSubnetStatsEntry 44 }

tmnxDhcpSvrSubnetStatsFoOfferP   OBJECT-TYPE
    SYNTAX      Counter32
    MAX-ACCESS  read-only
    STATUS      current
    DESCRIPTION
        "The value of tmnxDhcpSvrSubnetStatsFoOfferP indicates the highest
         value of tmnxDhcpSvrSubnetStatsFoOffered since the last reset of the
         extended statistics."
    ::= { tmnxDhcpSvrSubnetStatsEntry 45 }

tmnxDhcpSvrSubnetStatsFoOfferPT  OBJECT-TYPE
    SYNTAX      TimeStamp
    MAX-ACCESS  read-only
    STATUS      current
    DESCRIPTION
        "The value of tmnxDhcpSvrSubnetStatsFoOfferPT indicates the sysUpTime
         at the last change of tmnxDhcpSvrSubnetStatsFoOfferP."
    ::= { tmnxDhcpSvrSubnetStatsEntry 46 }

tmnxDhcpsFailoverObjs            OBJECT IDENTIFIER ::= { tmnxDhcpServerObjs 18 }

tmnxDhcpsFoTableLastChanged      OBJECT-TYPE
    SYNTAX      TimeStamp
    MAX-ACCESS  read-only
    STATUS      current
    DESCRIPTION
        "The value of tmnxDhcpsFoTableLastChanged indicates the sysUpTime at
         the time of the last change of an entry in the tmnxDhcpsFoTable.

         If no changes occurred since the last re-initialization of the local
         network management subsystem, then this object contains a zero value."
    ::= { tmnxDhcpsFailoverObjs 1 }

tmnxDhcpsFoTable                 OBJECT-TYPE
    SYNTAX      SEQUENCE OF TmnxDhcpsFoEntry
    MAX-ACCESS  not-accessible
    STATUS      current
    DESCRIPTION
        "The tmnxDhcpsFoTable has an entry for each DHCP server instance."
    ::= { tmnxDhcpsFailoverObjs 2 }

tmnxDhcpsFoEntry                 OBJECT-TYPE
    SYNTAX      TmnxDhcpsFoEntry
    MAX-ACCESS  not-accessible
    STATUS      current
    DESCRIPTION
        "Each row entry represents information related to the failover facility
         of a DHCP server instance.

         Rows are created or removed automatically by the system."
    AUGMENTS    { tmnxDhcpServerConfigEntry }
    ::= { tmnxDhcpsFoTable 1 }

TmnxDhcpsFoEntry                 ::= SEQUENCE
{
    tmnxDhcpsFoLastChanged           TimeStamp,
    tmnxDhcpsFoAdminState            TmnxAdminState,
    tmnxDhcpsFoMaxClientLeadTime     Unsigned32,
    tmnxDhcpsFoOperMaxClientLeadTime Unsigned32,
    tmnxDhcpsFoStartupWaitTime       Unsigned32,
    tmnxDhcpsFoPartnerDownDelay      Unsigned32,
    tmnxDhcpsFoState                 TmnxDhcpsFoState,
    tmnxDhcpsFoTimeLeft              Integer32,
    tmnxDhcpsFoIgnoreMclt            TruthValue
}

tmnxDhcpsFoLastChanged           OBJECT-TYPE
    SYNTAX      TimeStamp
    MAX-ACCESS  read-only
    STATUS      current
    DESCRIPTION
        "The value of tmnxDhcpsFoLastChanged indicates the sysUpTime at the
         time of the last modification of this entry.

         If no changes were made to the entry since the last re-initialization
         of the local network management subsystem, then this object contains a
         zero value."
    ::= { tmnxDhcpsFoEntry 1 }

tmnxDhcpsFoAdminState            OBJECT-TYPE
    SYNTAX      TmnxAdminState
    MAX-ACCESS  read-create
    STATUS      current
    DESCRIPTION
        "The value of tmnxDhcpsFoAdminState specifies the administrative state
         of the failover facility of the DHCP server instance.

         When the value of this object is set to 'inService (2)', it is not
         allowed to remove the corresponding local DHCP server, or to
         create/delete corresponding entries in the following tables:
         tmnxDhcpServerPoolTable, tmnxDhcpServerSubnetTable and
         tmnxDhcpSvrSubnetRangesTable."
    DEFVAL      { outOfService }
    ::= { tmnxDhcpsFoEntry 2 }

tmnxDhcpsFoMaxClientLeadTime     OBJECT-TYPE
    SYNTAX      Unsigned32 (600..86399)
    UNITS       "seconds"
    MAX-ACCESS  read-create
    STATUS      current
    DESCRIPTION
        "The value of the object tmnxDhcpsFoMaxClientLeadTime specifies the
         maximum client lead time (MCLT).

         The MCLT is the maximum amount of time that one server can extend a
         lease for a client's binding beyond the time known by the partner
         server.

         The value of this object can only be set while the value of the object
         tmnxDhcpsFoAdminState is equal to 'outOfService'."
    REFERENCE
        "draft-ietf-dhc-failover DHCP Failover Protocol section 2.2,
         MCLT."
    DEFVAL      { 600 }
    ::= { tmnxDhcpsFoEntry 3 }

tmnxDhcpsFoOperMaxClientLeadTime OBJECT-TYPE
    SYNTAX      Unsigned32 (600..86399)
    UNITS       "seconds"
    MAX-ACCESS  read-only
    STATUS      current
    DESCRIPTION
        "The value of the object tmnxDhcpsFoOperMaxClientLeadTime indicates the
         actual maximum client lead time.

         The value of the object tmnxDhcpsFoOperMaxClientLeadTime is
         initialized to the value of the object tmnxDhcpsFoMaxClientLeadTime.

         Every time the value of the object tmnxDhcpsFoMaxClientLeadTime is
         set, the value of the object tmnxDhcpsFoOperMaxClientLeadTime is
         modified accordingly.

         When the value of the object tmnxDhcpsFoState becomes equal to
         'normal', the actual maximum client lead time becomes equal to the
         maximum of the values of the objects tmnxDhcpsFoOperMaxClientLeadTime
         on this system and on the failover peer.

         When the value of the object tmnxDhcpsFoAdminState becomes equal to
         'outOfService', the value of the object
         tmnxDhcpsFoOperMaxClientLeadTime is reset to the value of the object
         tmnxDhcpsFoMaxClientLeadTime."
    ::= { tmnxDhcpsFoEntry 4 }

tmnxDhcpsFoStartupWaitTime       OBJECT-TYPE
    SYNTAX      Unsigned32 (60..3600)
    UNITS       "seconds"
    MAX-ACCESS  read-create
    STATUS      current
    DESCRIPTION
        "The value of the object tmnxDhcpsFoStartupWaitTime specifies the
         startup wait time.

         The startup wait time is the time that one server attempts to contact
         the partner server. During this time, the server is unresponsive to
         DHCP client requests."
    REFERENCE
        "draft-ietf-dhc-failover DHCP Failover Protocol section 5.9,
         Operating in STARTUP state."
    DEFVAL      { 120 }
    ::= { tmnxDhcpsFoEntry 5 }

tmnxDhcpsFoPartnerDownDelay      OBJECT-TYPE
    SYNTAX      Unsigned32 (0..86399)
    UNITS       "seconds"
    MAX-ACCESS  read-create
    STATUS      current
    DESCRIPTION
        "The value of the object tmnxDhcpsFoPartnerDownDelay specifies the
         minimum safe-time after the beginning of COMMUNICATIONS-INTERRUPTED
         state.

         After the expiry of this time, the server enters the PARTNER-DOWN
         state."
    REFERENCE
        "draft-ietf-dhc-failover DHCP Failover Protocol section 9.4.2,
         Operation while in PARTNER-DOWN state."
    DEFVAL      { 86399 }
    ::= { tmnxDhcpsFoEntry 6 }

tmnxDhcpsFoState                 OBJECT-TYPE
    SYNTAX      TmnxDhcpsFoState
    MAX-ACCESS  read-only
    STATUS      current
    DESCRIPTION
        "The value of tmnxDhcpsFoState indicates the failover state of the DHCP
         server instance."
    ::= { tmnxDhcpsFoEntry 7 }

tmnxDhcpsFoTimeLeft              OBJECT-TYPE
    SYNTAX      Integer32
    UNITS       "seconds"
    MAX-ACCESS  read-only
    STATUS      current
    DESCRIPTION
        "The value of the object tmnxDhcpsFoTimeLeft indicates the time left
         until expiry of one of the timers MCLT, startup wait time or
         partner-down-delay.

         If none of these timers is running, the value of tmnxDhcpsFoTimeLeft
         equals '-1'."
    REFERENCE
        "draft-ietf-dhc-failover DHCP Failover Protocol."
    ::= { tmnxDhcpsFoEntry 8 }

tmnxDhcpsFoIgnoreMclt            OBJECT-TYPE
    SYNTAX      TruthValue
    MAX-ACCESS  read-create
    STATUS      current
    DESCRIPTION
        "The value of tmnxDhcpsFoIgnoreMclt specifies if, after the transition
         COMMUNICATIONS-INTERRUPTED-to-PARTNER-DOWN state, the DHCP server
         instance ignores the safety period with a duration of Maximum Client
         Lead Time; setting the value of this object to 'true' has the effect
         that the DHCP server starts offering IP addresses from the partner's
         scope immediately after this transition, without waiting for existing
         leases allocated by the partner and not known by this system to time
         out.

         Setting the value of this object to 'true' increases the risk that
         duplicate addresses are offered; if the transition to PARTNER-DOWN
         state is likely to be caused by a failure of the partner system rather
         than a communications problem, this risk is reduced."
    DEFVAL      { false }
    ::= { tmnxDhcpsFoEntry 10 }

tmnxDhcpsFoStatsTable            OBJECT-TYPE
    SYNTAX      SEQUENCE OF TmnxDhcpsFoStatsEntry
    MAX-ACCESS  not-accessible
    STATUS      current
    DESCRIPTION
        "The tmnxDhcpsFoStatsTable contains statistics about the DHCP failover
         facility.

         The tmnxDhcpsFoStatsTable has an entry for each DHCP server instance."
    ::= { tmnxDhcpsFailoverObjs 3 }

tmnxDhcpsFoStatsEntry            OBJECT-TYPE
    SYNTAX      TmnxDhcpsFoStatsEntry
    MAX-ACCESS  not-accessible
    STATUS      current
    DESCRIPTION
        "Each row entry contains statistics about the failover facility of a
         specific DHCP Server instance.

         Rows are created or removed automatically by the system."
    AUGMENTS    { tmnxDhcpServerConfigEntry }
    ::= { tmnxDhcpsFoStatsTable 1 }

TmnxDhcpsFoStatsEntry            ::= SEQUENCE
{
    tmnxDhcpsFoStatsLeaseNotFound    Counter32,
    tmnxDhcpsFoStatsDropInvalidPkts  Counter32,
    tmnxDhcpsFoStatsFoShutdown       Counter32,
    tmnxDhcpsFoStatsExpired          Counter32,
    tmnxDhcpsFoStatsMaxReached       Counter32,
    tmnxDhcpsFoStatsSubnetNotFound   Counter32,
    tmnxDhcpsFoStatsRangeNotFound    Counter32,
    tmnxDhcpsFoStatsHostConflict     Counter32,
    tmnxDhcpsFoStatsAddressConflict  Counter32,
    tmnxDhcpsFoStatsPeerConflict     Counter32,
    tmnxDhcpsFoStatsPersistCongest   Counter32,
    tmnxDhcpsFoStatsNoLeaseHoldTime  Counter32,
    tmnxDhcpsFoStatsInvalidPfxLen    Counter32
}

tmnxDhcpsFoStatsLeaseNotFound    OBJECT-TYPE
    SYNTAX      Counter32
    MAX-ACCESS  read-only
    STATUS      current
    DESCRIPTION
        "The value of tmnxDhcpsFoStatsLeaseNotFound indicates how many Binding
         Database Update (BNDUPD) 'remove' packets were dropped because the
         corresponding lease could not be found."
    ::= { tmnxDhcpsFoStatsEntry 1 }

tmnxDhcpsFoStatsDropInvalidPkts  OBJECT-TYPE
    SYNTAX      Counter32
    MAX-ACCESS  read-only
    STATUS      current
    DESCRIPTION
        "The value of tmnxDhcpsFoStatsDropInvalidPkts indicates how many BNDUPD
         packets were dropped because the packet was malformed."
    ::= { tmnxDhcpsFoStatsEntry 2 }

tmnxDhcpsFoStatsFoShutdown       OBJECT-TYPE
    SYNTAX      Counter32
    MAX-ACCESS  read-only
    STATUS      current
    DESCRIPTION
        "The value of tmnxDhcpsFoStatsFoShutdown indicates how many BNDUPD
         packets were dropped because the failover state if the DHCP Server
         instance is 'shutdown'."
    ::= { tmnxDhcpsFoStatsEntry 3 }

tmnxDhcpsFoStatsExpired          OBJECT-TYPE
    SYNTAX      Counter32
    MAX-ACCESS  read-only
    STATUS      current
    DESCRIPTION
        "The value of tmnxDhcpsFoStatsExpired indicates how many BNDUPD 'add'
         packets were dropped because the corresponding lease has expired.

         This may indicate that the clock of the failover peer is not in sync
         with the clock of this system."
    ::= { tmnxDhcpsFoStatsEntry 4 }

tmnxDhcpsFoStatsMaxReached       OBJECT-TYPE
    SYNTAX      Counter32
    MAX-ACCESS  read-only
    STATUS      current
    DESCRIPTION
        "The value of tmnxDhcpsFoStatsMaxReached indicates how many BNDUPD
         'add' packets were dropped because the maximum number of leases was
         reached.

         The maximum number of leases is indicated by the value of the object
         tmnxDhcpSvrMaxLeases."
    ::= { tmnxDhcpsFoStatsEntry 5 }

tmnxDhcpsFoStatsSubnetNotFound   OBJECT-TYPE
    SYNTAX      Counter32
    MAX-ACCESS  read-only
    STATUS      current
    DESCRIPTION
        "The value of tmnxDhcpsFoStatsSubnetNotFound indicates how many BNDUPD
         'add' packets were dropped because a valid subnet could not be found
         for the lease."
    ::= { tmnxDhcpsFoStatsEntry 6 }

tmnxDhcpsFoStatsRangeNotFound    OBJECT-TYPE
    SYNTAX      Counter32
    MAX-ACCESS  read-only
    STATUS      current
    DESCRIPTION
        "The value of tmnxDhcpsFoStatsRangeNotFound indicates how many BNDUPD
         'add' packets were dropped because a valid include range could not be
         found for the lease."
    ::= { tmnxDhcpsFoStatsEntry 7 }

tmnxDhcpsFoStatsHostConflict     OBJECT-TYPE
    SYNTAX      Counter32
    MAX-ACCESS  read-only
    STATUS      current
    DESCRIPTION
        "The value of tmnxDhcpsFoStatsHostConflict indicates how many BNDUPD
         'add' packets were dropped because this DHCP server instance has
         already leased this address to another host."
    ::= { tmnxDhcpsFoStatsEntry 8 }

tmnxDhcpsFoStatsAddressConflict  OBJECT-TYPE
    SYNTAX      Counter32
    MAX-ACCESS  read-only
    STATUS      current
    DESCRIPTION
        "The value of tmnxDhcpsFoStatsAddressConflict indicates how many BNDUPD
         'add' packets were dropped because this DHCP server instance has
         already leased another address to this host."
    ::= { tmnxDhcpsFoStatsEntry 9 }

tmnxDhcpsFoStatsPeerConflict     OBJECT-TYPE
    SYNTAX      Counter32
    MAX-ACCESS  read-only
    STATUS      current
    DESCRIPTION
        "The value of tmnxDhcpsFoStatsPeerConflict indicates how many BNDUPD
         'add' packets were dropped because the failover peer has leased an
         address within a subnet range of which the failover control is set to
         'local' on this local DHCP server instance."
    ::= { tmnxDhcpsFoStatsEntry 10 }

tmnxDhcpsFoStatsPersistCongest   OBJECT-TYPE
    SYNTAX      Counter32
    MAX-ACCESS  read-only
    STATUS      current
    DESCRIPTION
        "The value of tmnxDhcpsFoStatsPersistCongest indicates how many BNDUPD
         packets were dropped because of persistence congestion on this DHCP
         server instance."
    ::= { tmnxDhcpsFoStatsEntry 11 }

tmnxDhcpsFoStatsNoLeaseHoldTime  OBJECT-TYPE
    SYNTAX      Counter32
    MAX-ACCESS  read-only
    STATUS      current
    DESCRIPTION
        "The value of tmnxDhcpsFoStatsNoLeaseHoldTime indicates how many BNDUPD
         packets were dropped because tmnxDhcpServerCfgLeaseHoldTime is zero on
         this DHCP server instance."
    ::= { tmnxDhcpsFoStatsEntry 12 }

tmnxDhcpsFoStatsInvalidPfxLen    OBJECT-TYPE
    SYNTAX      Counter32
    MAX-ACCESS  read-only
    STATUS      current
    DESCRIPTION
        "The value of tmnxDhcpsFoStatsInvalidPfxLen indicates how many BNDUPD
         packets were dropped because the prefix of the lease received from the
         peer is not inside the range configured in
         tmnxDhcpServerPoolMinPrefixLen and tmnxDhcpServerPoolMaxPrefixLen."
    ::= { tmnxDhcpsFoStatsEntry 13 }

tmnxDhcpsFoAction                OBJECT IDENTIFIER ::= { tmnxDhcpsFailoverObjs 4 }

tmnxDhcpsFoActionVRtrId          OBJECT-TYPE
    SYNTAX      TmnxVRtrIDOrZero
    MAX-ACCESS  read-write
    STATUS      current
    DESCRIPTION
        "The value of the object tmnxDhcpsFoActionVRtrId specifies the ID of
         the virtual router instance."
    ::= { tmnxDhcpsFoAction 1 }

tmnxDhcpsFoActionServerName      OBJECT-TYPE
    SYNTAX      TNamedItemOrEmpty
    MAX-ACCESS  read-write
    STATUS      current
    DESCRIPTION
        "The value of the object tmnxDhcpsFoActionServerName specifies the name
         of the local DHCP server instance."
    ::= { tmnxDhcpsFoAction 2 }

tmnxDhcpsFoActionType            OBJECT-TYPE
    SYNTAX      TmnxDhcpsFoActionType
    MAX-ACCESS  read-write
    STATUS      current
    DESCRIPTION
        "The value of the object tmnxDhcpsFoActionType specifies the type of
         action to perform."
    ::= { tmnxDhcpsFoAction 3 }

tmnxDhcpsFoActionGo              OBJECT-TYPE
    SYNTAX      TmnxActionType
    MAX-ACCESS  read-write
    STATUS      current
    DESCRIPTION
        "Setting this object to 'doAction' triggers an attempt to force a
         transition of the failover facility of this DHCP server instance from
         'noCommunication' to 'partnerDown'.

         Reading this object returns the value 'notApplicable'."
    ::= { tmnxDhcpsFoAction 4 }

tmnxDhcpsFoActionSuccessful      OBJECT-TYPE
    SYNTAX      TruthValue
    MAX-ACCESS  read-only
    STATUS      current
    DESCRIPTION
        "The value of the object tmnxDhcpsFoActionSuccessful indicates whether
         the authentication was successful.

         If the value of the object equals 'false', then the value of
         tmnxDhcpsFoActionErrorMsg indicates the reason of the failure."
    ::= { tmnxDhcpsFoAction 5 }

tmnxDhcpsFoActionErrorMsg        OBJECT-TYPE
    SYNTAX      DisplayString (SIZE (0..255))
    MAX-ACCESS  read-only
    STATUS      current
    DESCRIPTION
        "The value of the object tmnxDhcpsFoActionErrorMsg indicates the reason
         of failure, in case the value of the object
         tmnxDhcpsFoActionSuccessful is equal to 'false'.

         If the value of the object tmnxDhcpsFoActionSuccessful is equal to
         'true', this object contains an empty string."
    ::= { tmnxDhcpsFoAction 6 }

tmnxDhcpsFoActionTime            OBJECT-TYPE
    SYNTAX      TimeStamp
    MAX-ACCESS  read-only
    STATUS      current
    DESCRIPTION
        "The value of the object tmnxDhcpsFoActionTime indicates the value of
         sysUpTime at the last time that the object tmnxDhcpsFoActionSuccessful
         was written by the system."
    ::= { tmnxDhcpsFoAction 7 }

tmnxDhcpsFoActionPoolName        OBJECT-TYPE
    SYNTAX      TNamedItemOrEmpty
    MAX-ACCESS  read-write
    STATUS      current
    DESCRIPTION
        "The value of the object tmnxDhcpsFoActionPoolName specifies the name
         of IP address pool within the local DHCP server instance."
    ::= { tmnxDhcpsFoAction 8 }

tmnxDhcpsPoolFoTableLastChanged  OBJECT-TYPE
    SYNTAX      TimeStamp
    MAX-ACCESS  read-only
    STATUS      current
    DESCRIPTION
        "The value of tmnxDhcpsPoolFoTableLastChanged indicates the sysUpTime
         at the time of the last change of an entry in the
         tmnxDhcpsPoolFoTable.

         If no changes occurred since the last re-initialization of the local
         network management subsystem, then this object contains a zero value."
    ::= { tmnxDhcpsFailoverObjs 5 }

tmnxDhcpsPoolFoTable             OBJECT-TYPE
    SYNTAX      SEQUENCE OF TmnxDhcpsPoolFoEntry
    MAX-ACCESS  not-accessible
    STATUS      current
    DESCRIPTION
        "The tmnxDhcpsPoolFoTable has an entry for each IP Address Pool."
    ::= { tmnxDhcpsFailoverObjs 6 }

tmnxDhcpsPoolFoEntry             OBJECT-TYPE
    SYNTAX      TmnxDhcpsPoolFoEntry
    MAX-ACCESS  not-accessible
    STATUS      current
    DESCRIPTION
        "Each row entry represents information related to the failover facility
         of an IP Address Pool.

         Rows are created or removed automatically by the system."
    AUGMENTS    { tmnxDhcpServerPoolEntry }
    ::= { tmnxDhcpsPoolFoTable 1 }

TmnxDhcpsPoolFoEntry             ::= SEQUENCE
{
    tmnxDhcpsPoolFoLastChanged       TimeStamp,
    tmnxDhcpsPoolFoAdminState        TmnxAdminState,
    tmnxDhcpsPoolFoMCLT              Unsigned32,
    tmnxDhcpsPoolFoOperMCLT          Unsigned32,
    tmnxDhcpsPoolFoStartupWaitTime   Unsigned32,
    tmnxDhcpsPoolFoPartnerDownDelay  Unsigned32,
    tmnxDhcpsPoolFoState             TmnxDhcpsFoState,
    tmnxDhcpsPoolFoTimeLeft          Integer32,
    tmnxDhcpsPoolFoIgnoreMclt        TruthValue
}

tmnxDhcpsPoolFoLastChanged       OBJECT-TYPE
    SYNTAX      TimeStamp
    MAX-ACCESS  read-only
    STATUS      current
    DESCRIPTION
        "The value of tmnxDhcpsPoolFoLastChanged indicates the sysUpTime at the
         time of the last modification of this entry.

         If no changes were made to the entry since the last re-initialization
         of the local network management subsystem, then this object contains a
         zero value."
    ::= { tmnxDhcpsPoolFoEntry 1 }

tmnxDhcpsPoolFoAdminState        OBJECT-TYPE
    SYNTAX      TmnxAdminState
    MAX-ACCESS  read-create
    STATUS      current
    DESCRIPTION
        "The value of tmnxDhcpsPoolFoAdminState specifies the administrative
         state of the failover facility of the IP Address Pool instance."
    DEFVAL      { outOfService }
    ::= { tmnxDhcpsPoolFoEntry 2 }

tmnxDhcpsPoolFoMCLT              OBJECT-TYPE
    SYNTAX      Unsigned32 (600..86399)
    UNITS       "seconds"
    MAX-ACCESS  read-create
    STATUS      current
    DESCRIPTION
        "The value of the object tmnxDhcpsPoolFoMCLT specifies the Maximum
         Client Lead Time (MCLT).

         The MCLT is the maximum amount of time that one server can extend a
         lease for a client's binding beyond the time known by the partner
         server.

         The value of this object can only be set while the value of the object
         tmnxDhcpsPoolFoAdminState is equal to 'outOfService'."
    REFERENCE
        "draft-ietf-dhc-failover DHCP Failover Protocol section 2.2,
         MCLT."
    DEFVAL      { 600 }
    ::= { tmnxDhcpsPoolFoEntry 3 }

tmnxDhcpsPoolFoOperMCLT          OBJECT-TYPE
    SYNTAX      Unsigned32 (600..86399)
    UNITS       "seconds"
    MAX-ACCESS  read-only
    STATUS      current
    DESCRIPTION
        "The value of the object tmnxDhcpsPoolFoOperMCLT indicates the actual
         Maximum Client Lead Time.

         The value of the object tmnxDhcpsPoolFoOperMCLT is initialized to the
         value of the object tmnxDhcpsPoolFoMCLT.

         Every time the value of the object tmnxDhcpsPoolFoMCLT is set, the
         value of the object tmnxDhcpsPoolFoOperMCLT is modified accordingly.

         When the value of the object tmnxDhcpsPoolFoState becomes equal to
         'normal', the actual maximum client lead time becomes equal to the
         maximum of the values of the objects tmnxDhcpsPoolFoOperMCLT on this
         system and on the failover peer.

         When the value of the object tmnxDhcpsPoolFoAdminState becomes equal
         to 'outOfService', the value of the object tmnxDhcpsPoolFoOperMCLT is
         reset to the value of the object tmnxDhcpsPoolFoMCLT."
    ::= { tmnxDhcpsPoolFoEntry 4 }

tmnxDhcpsPoolFoStartupWaitTime   OBJECT-TYPE
    SYNTAX      Unsigned32 (60..3600)
    UNITS       "seconds"
    MAX-ACCESS  read-create
    STATUS      current
    DESCRIPTION
        "The value of the object tmnxDhcpsPoolFoStartupWaitTime specifies the
         startup wait time.

         The startup wait time is the time that one IP Address Pool attempts to
         contact the partner IP Address Pool. During this time, the IP Address
         Pool is unresponsive to DHCP client requests."
    REFERENCE
        "draft-ietf-dhc-failover DHCP Failover Protocol section 5.9,
         Operating in STARTUP state."
    DEFVAL      { 120 }
    ::= { tmnxDhcpsPoolFoEntry 5 }

tmnxDhcpsPoolFoPartnerDownDelay  OBJECT-TYPE
    SYNTAX      Unsigned32 (0..86399)
    UNITS       "seconds"
    MAX-ACCESS  read-create
    STATUS      current
    DESCRIPTION
        "The value of the object tmnxDhcpsPoolFoPartnerDownDelay specifies the
         minimum safe-time after the beginning of COMMUNICATIONS-INTERRUPTED
         state.

         After the expiry of this time, the server enters the PARTNER-DOWN
         state."
    REFERENCE
        "draft-ietf-dhc-failover DHCP Failover Protocol section 9.4.2,
         Operation while in PARTNER-DOWN state."
    DEFVAL      { 86399 }
    ::= { tmnxDhcpsPoolFoEntry 6 }

tmnxDhcpsPoolFoState             OBJECT-TYPE
    SYNTAX      TmnxDhcpsFoState
    MAX-ACCESS  read-only
    STATUS      current
    DESCRIPTION
        "The value of tmnxDhcpsPoolFoState indicates the failover state of the
         IP pool instance."
    ::= { tmnxDhcpsPoolFoEntry 7 }

tmnxDhcpsPoolFoTimeLeft          OBJECT-TYPE
    SYNTAX      Integer32
    UNITS       "seconds"
    MAX-ACCESS  read-only
    STATUS      current
    DESCRIPTION
        "The value of the object tmnxDhcpsPoolFoTimeLeft indicates the time
         left until expiry of one of the timers MCLT, startup wait time or
         partner-down-delay.

         If none of these timers is running, the value of
         tmnxDhcpsPoolFoTimeLeft equals '-1'."
    REFERENCE
        "draft-ietf-dhc-failover DHCP Failover Protocol."
    ::= { tmnxDhcpsPoolFoEntry 8 }

tmnxDhcpsPoolFoIgnoreMclt        OBJECT-TYPE
    SYNTAX      TruthValue
    MAX-ACCESS  read-create
    STATUS      current
    DESCRIPTION
        "The value of tmnxDhcpsPoolFoIgnoreMclt specifies if, after the
         transition COMMUNICATIONS-INTERRUPTED-to-PARTNER-DOWN state, the DHCP
         server instance ignores the safety period with a duration of Maximum
         Client Lead Time; setting the value of this object to 'true' has the
         effect that the DHCP server starts offering IP addresses from the
         partner's scope immediately after this transition, without waiting for
         existing leases allocated by the partner and not known by this system
         to time out.

         Setting the value of this object to 'true' increases the risk that
         duplicate addresses are offered; if the transition to PARTNER-DOWN
         state is likely to be caused by a failure of the partner system rather
         than a communications problem, this risk is reduced."
    DEFVAL      { false }
    ::= { tmnxDhcpsPoolFoEntry 10 }

tmnxDhcpsPoolFoStatsTable        OBJECT-TYPE
    SYNTAX      SEQUENCE OF TmnxDhcpsPoolFoStatsEntry
    MAX-ACCESS  not-accessible
    STATUS      current
    DESCRIPTION
        "The tmnxDhcpsPoolFoStatsTable contains statistics about the DHCP
         Address Pool failover facility."
    ::= { tmnxDhcpsFailoverObjs 7 }

tmnxDhcpsPoolFoStatsEntry        OBJECT-TYPE
    SYNTAX      TmnxDhcpsPoolFoStatsEntry
    MAX-ACCESS  not-accessible
    STATUS      current
    DESCRIPTION
        "Each row entry contains statistics about the failover facility of a
         specific DHCP Address Pool instance.

         Rows are created or removed automatically by the system."
    AUGMENTS    { tmnxDhcpServerPoolEntry }
    ::= { tmnxDhcpsPoolFoStatsTable 1 }

TmnxDhcpsPoolFoStatsEntry        ::= SEQUENCE
{
    tmnxDhcpsPoolFoStatsLeaseNFound  Counter32,
    tmnxDhcpsPoolFoStatsDropInvPkts  Counter32,
    tmnxDhcpsPoolFoStatsFoShutdown   Counter32,
    tmnxDhcpsPoolFoStatsExpired      Counter32,
    tmnxDhcpsPoolFoStatsMaxReached   Counter32,
    tmnxDhcpsPoolFoStatsSubnetNFound Counter32,
    tmnxDhcpsPoolFoStatsRangeNFound  Counter32,
    tmnxDhcpsPoolFoStatsHostConflict Counter32,
    tmnxDhcpsPoolFoStatsAddrConflict Counter32,
    tmnxDhcpsPoolFoStatsPeerConflict Counter32,
    tmnxDhcpsPoolFoStatsPersistCong  Counter32,
    tmnxDhcpsPoolFoStatsNoLeaseHoldT Counter32,
    tmnxDhcpsPoolFoStatsInvaldPfxLen Counter32
}

tmnxDhcpsPoolFoStatsLeaseNFound  OBJECT-TYPE
    SYNTAX      Counter32
    MAX-ACCESS  read-only
    STATUS      current
    DESCRIPTION
        "The value of tmnxDhcpsPoolFoStatsLeaseNFound indicates how many
         Binding Database Update (BNDUPD) 'remove' packets were dropped because
         the corresponding lease could not be found."
    ::= { tmnxDhcpsPoolFoStatsEntry 1 }

tmnxDhcpsPoolFoStatsDropInvPkts  OBJECT-TYPE
    SYNTAX      Counter32
    MAX-ACCESS  read-only
    STATUS      current
    DESCRIPTION
        "The value of tmnxDhcpsPoolFoStatsDropInvPkts indicates how many BNDUPD
         packets were dropped because the packet was malformed."
    ::= { tmnxDhcpsPoolFoStatsEntry 2 }

tmnxDhcpsPoolFoStatsFoShutdown   OBJECT-TYPE
    SYNTAX      Counter32
    MAX-ACCESS  read-only
    STATUS      current
    DESCRIPTION
        "The value of tmnxDhcpsPoolFoStatsFoShutdown indicates how many BNDUPD
         packets were dropped because the failover state if the DHCP Server
         instance is 'shutdown'."
    ::= { tmnxDhcpsPoolFoStatsEntry 3 }

tmnxDhcpsPoolFoStatsExpired      OBJECT-TYPE
    SYNTAX      Counter32
    MAX-ACCESS  read-only
    STATUS      current
    DESCRIPTION
        "The value of tmnxDhcpsPoolFoStatsExpired indicates how many BNDUPD
         'add' packets were dropped because the corresponding lease has
         expired.

         This may indicate that the clock of the failover peer is not in sync
         with the clock of this system."
    ::= { tmnxDhcpsPoolFoStatsEntry 4 }

tmnxDhcpsPoolFoStatsMaxReached   OBJECT-TYPE
    SYNTAX      Counter32
    MAX-ACCESS  read-only
    STATUS      current
    DESCRIPTION
        "The value of tmnxDhcpsPoolFoStatsMaxReached indicates how many BNDUPD
         'add' packets were dropped because the maximum number of leases was
         reached.

         The maximum number of leases is indicated by the value of the object
         tmnxDhcpSvrMaxLeases."
    ::= { tmnxDhcpsPoolFoStatsEntry 5 }

tmnxDhcpsPoolFoStatsSubnetNFound OBJECT-TYPE
    SYNTAX      Counter32
    MAX-ACCESS  read-only
    STATUS      current
    DESCRIPTION
        "The value of tmnxDhcpsPoolFoStatsSubnetNFound indicates how many
         BNDUPD 'add' packets were dropped because a valid subnet could not be
         found for the lease."
    ::= { tmnxDhcpsPoolFoStatsEntry 6 }

tmnxDhcpsPoolFoStatsRangeNFound  OBJECT-TYPE
    SYNTAX      Counter32
    MAX-ACCESS  read-only
    STATUS      current
    DESCRIPTION
        "The value of tmnxDhcpsPoolFoStatsRangeNFound indicates how many BNDUPD
         'add' packets were dropped because a valid include range could not be
         found for the lease."
    ::= { tmnxDhcpsPoolFoStatsEntry 7 }

tmnxDhcpsPoolFoStatsHostConflict OBJECT-TYPE
    SYNTAX      Counter32
    MAX-ACCESS  read-only
    STATUS      current
    DESCRIPTION
        "The value of tmnxDhcpsPoolFoStatsHostConflict indicates how many
         BNDUPD 'add' packets were dropped because this DHCP server instance
         has already leased this address to another host."
    ::= { tmnxDhcpsPoolFoStatsEntry 8 }

tmnxDhcpsPoolFoStatsAddrConflict OBJECT-TYPE
    SYNTAX      Counter32
    MAX-ACCESS  read-only
    STATUS      current
    DESCRIPTION
        "The value of tmnxDhcpsPoolFoStatsAddrConflict indicates how many
         BNDUPD 'add' packets were dropped because this DHCP server instance
         has already leased another address to this host."
    ::= { tmnxDhcpsPoolFoStatsEntry 9 }

tmnxDhcpsPoolFoStatsPeerConflict OBJECT-TYPE
    SYNTAX      Counter32
    MAX-ACCESS  read-only
    STATUS      current
    DESCRIPTION
        "The value of tmnxDhcpsPoolFoStatsPeerConflict indicates how many
         BNDUPD 'add' packets were dropped because the failover peer has leased
         an address within a subnet range of which the failover control is set
         to 'local' on this local DHCP Address Pool instance."
    ::= { tmnxDhcpsPoolFoStatsEntry 10 }

tmnxDhcpsPoolFoStatsPersistCong  OBJECT-TYPE
    SYNTAX      Counter32
    MAX-ACCESS  read-only
    STATUS      current
    DESCRIPTION
        "The value of tmnxDhcpsPoolFoStatsPersistCong indicates how many BNDUPD
         packets were dropped because of persistence congestion on this DHCP
         Address Pool instance."
    ::= { tmnxDhcpsPoolFoStatsEntry 11 }

tmnxDhcpsPoolFoStatsNoLeaseHoldT OBJECT-TYPE
    SYNTAX      Counter32
    MAX-ACCESS  read-only
    STATUS      current
    DESCRIPTION
        "The value of tmnxDhcpsPoolFoStatsNoLeaseHoldT indicates how many
         BNDUPD packets were dropped because tmnxDhcpServerCfgLeaseHoldTime is
         zero on this DHCP server instance."
    ::= { tmnxDhcpsPoolFoStatsEntry 12 }

tmnxDhcpsPoolFoStatsInvaldPfxLen OBJECT-TYPE
    SYNTAX      Counter32
    MAX-ACCESS  read-only
    STATUS      current
    DESCRIPTION
        "The value of tmnxDhcpsPoolFoStatsInvaldPfxLen indicates how many
         BNDUPD packets were dropped because the prefix of the lease received
         from the peer is not inside the range configured in
         tmnxDhcpServerPoolMinPrefixLen and tmnxDhcpServerPoolMaxPrefixLen."
    ::= { tmnxDhcpsPoolFoStatsEntry 13 }

tmnxDhcpSvrFreeAddrTable         OBJECT-TYPE
    SYNTAX      SEQUENCE OF TmnxDhcpSvrFreeAddrEntry
    MAX-ACCESS  not-accessible
    STATUS      current
    DESCRIPTION
        "The table tmnxDhcpSvrFreeAddrTable contains a list of free IP
         addresses. These IP addresses are available for DHCP clients."
    ::= { tmnxDhcpServerObjs 19 }

tmnxDhcpSvrFreeAddrEntry         OBJECT-TYPE
    SYNTAX      TmnxDhcpSvrFreeAddrEntry
    MAX-ACCESS  not-accessible
    STATUS      current
    DESCRIPTION
        "Each row represents a free IP address.

         Entries in this table cannot be created via SNMP operations. Entries
         in this table cannot be deleted via the TIMETRA-CLEAR-MIB."
    INDEX       {
        vRtrID,
        tmnxDhcpServerCfgServerName,
        tmnxDhcpServerPoolName,
        tmnxDhcpSvrSubnetAddrType,
        tmnxDhcpSvrSubnetAddress,
        tmnxDhcpSvrSubnetPrefixLength,
        tmnxDhcpSvrFreeAddrType,
        tmnxDhcpSvrFreeAddress
    }
    ::= { tmnxDhcpSvrFreeAddrTable 1 }

TmnxDhcpSvrFreeAddrEntry         ::= SEQUENCE
{
    tmnxDhcpSvrFreeAddrType          InetAddressType,
    tmnxDhcpSvrFreeAddress           InetAddress,
    tmnxDhcpSvrFreeAddrFailCtrl      TmnxDhcpSvrFailCtrlType
}

tmnxDhcpSvrFreeAddrType          OBJECT-TYPE
    SYNTAX      InetAddressType
    MAX-ACCESS  not-accessible
    STATUS      current
    DESCRIPTION
        "The value of the object tmnxDhcpSvrFreeAddrType specifies the type of
         tmnxDhcpSvrFreeAddress."
    ::= { tmnxDhcpSvrFreeAddrEntry 1 }

tmnxDhcpSvrFreeAddress           OBJECT-TYPE
    SYNTAX      InetAddress (SIZE (4|16))
    MAX-ACCESS  not-accessible
    STATUS      current
    DESCRIPTION
        "The value of the object tmnxDhcpSvrFreeAddress specifies the free IP
         address."
    ::= { tmnxDhcpSvrFreeAddrEntry 2 }

tmnxDhcpSvrFreeAddrFailCtrl      OBJECT-TYPE
    SYNTAX      TmnxDhcpSvrFailCtrlType
    MAX-ACCESS  read-only
    STATUS      current
    DESCRIPTION
        "The value of object tmnxDhcpSvrFreeAddrFailCtrl indicates the type of
         failover control for this free IP address."
    ::= { tmnxDhcpSvrFreeAddrEntry 3 }

tmnxDhcpSvrActionTable           OBJECT-TYPE
    SYNTAX      SEQUENCE OF TmnxDhcpSvrActionEntry
    MAX-ACCESS  not-accessible
    STATUS      current
    DESCRIPTION
        "The table tmnxDhcpSvrActionTable allows the operator to request the
         local DHCP server to execute a operational commands."
    ::= { tmnxDhcpServerObjs 20 }

tmnxDhcpSvrActionEntry           OBJECT-TYPE
    SYNTAX      TmnxDhcpSvrActionEntry
    MAX-ACCESS  not-accessible
    STATUS      current
    DESCRIPTION
        "This table contains a row for each DHCP server instance running within
         a virtual router.

         Rows are created and destroyed by the system.

         Each row contains objects that can be written to in order to request
         the DHCP server to execute the corresponding command."
    INDEX       {
        vRtrID,
        IMPLIED tmnxDhcpServerCfgServerName
    }
    ::= { tmnxDhcpSvrActionTable 1 }

TmnxDhcpSvrActionEntry           ::= SEQUENCE
{
    tmnxDhcpSvrActForceRenewAddrType InetAddressType,
    tmnxDhcpSvrActForceRenewAddr     InetAddress
}

tmnxDhcpSvrActForceRenewAddrType OBJECT-TYPE
    SYNTAX      InetAddressType
    MAX-ACCESS  read-write
    STATUS      current
    DESCRIPTION
        "The value of the object tmnxDhcpSvrActForceRenewAddrType specifies the
         type of tmnxDhcpSvrActForceRenewAddr.

         When setting the value of this object, the value of
         tmnxDhcpSvrActForceRenewAddr must be set as well in the same SNMP SET
         PDU.

         The value of this object cannot be set to the value 'unknown(0)'.

         When read, the system will always return the value 'unknown(0)'."
    ::= { tmnxDhcpSvrActionEntry 1 }

tmnxDhcpSvrActForceRenewAddr     OBJECT-TYPE
    SYNTAX      InetAddress (SIZE (0|4|16))
    MAX-ACCESS  read-write
    STATUS      current
    DESCRIPTION
        "The value of the object tmnxDhcpSvrActForceRenewAddr specifies the IP
         address for which a force renew is requested.

         When setting the value of this object, the value of
         tmnxDhcpSvrActForceRenewAddrType must be set as well in the same SNMP
         SET PDU.

         The value of this object cannot be set to the zero-length string.

         When read, the system will always return a zero-length string."
    ::= { tmnxDhcpSvrActionEntry 2 }

tmnxDhcpSvrNumLeases             OBJECT-TYPE
    SYNTAX      Gauge32
    MAX-ACCESS  read-only
    STATUS      current
    DESCRIPTION
        "The value of tmnxDhcpSvrNumLeases indicates the actual number of
         addresses that is currently being leased."
    ::= { tmnxDhcpServerObjs 21 }

tmnxDhcpSvrMaxLeases             OBJECT-TYPE
    SYNTAX      Unsigned32
    MAX-ACCESS  read-only
    STATUS      current
    DESCRIPTION
        "The value of tmnxDhcpSvrMaxLeases indicates the maximum number of
         addresses that can be leased at any given time."
    ::= { tmnxDhcpServerObjs 22 }

tmnxDhcpServerStats6Table        OBJECT-TYPE
    SYNTAX      SEQUENCE OF TmnxDhcpServerStats6Entry
    MAX-ACCESS  not-accessible
    STATUS      current
    DESCRIPTION
        "The tmnxDhcpServerStats6Table contains basic statistics about the
         DHCPv6 server instances."
    ::= { tmnxDhcpServerObjs 23 }

tmnxDhcpServerStats6Entry        OBJECT-TYPE
    SYNTAX      TmnxDhcpServerStats6Entry
    MAX-ACCESS  not-accessible
    STATUS      current
    DESCRIPTION
        "Each row entry contains basic statistics about a particular DHCPv6
         server instance."
    INDEX       {
        vRtrID,
        IMPLIED tmnxDhcpServerCfgServerName
    }
    ::= { tmnxDhcpServerStats6Table 1 }

TmnxDhcpServerStats6Entry        ::= SEQUENCE
{
    tmnxDhcpSvrStats6RxSolicits      Counter64,
    tmnxDhcpSvrStats6TxAdvertises    Counter64,
    tmnxDhcpSvrStats6RxRequests      Counter64,
    tmnxDhcpSvrStats6RxConfirms      Counter64,
    tmnxDhcpSvrStats6RxRenews        Counter64,
    tmnxDhcpSvrStats6RxRebinds       Counter64,
    tmnxDhcpSvrStats6RxDeclines      Counter64,
    tmnxDhcpSvrStats6RxReleases      Counter64,
    tmnxDhcpSvrStats6TxReplies       Counter64,
    tmnxDhcpSvrStats6TxReconfigures  Counter64,
    tmnxDhcpSvrStats6RxInfRequests   Counter64,
    tmnxDhcpSvrStats6DropBadPackets  Counter32,
    tmnxDhcpSvrStats6DropInvldTypes  Counter32,
    tmnxDhcpSvrStats6DropLseNotReady Counter32,
    tmnxDhcpSvrStats6DropNoSrvngPool Counter32,
    tmnxDhcpSvrStats6DropOverload    Counter32,
    tmnxDhcpSvrStats6DropPerOverload Counter32,
    tmnxDhcpSvrStats6OffersIgnore    Counter32,
    tmnxDhcpSvrStats6DropGenError    Counter32,
    tmnxDhcpSvrStats6DropDestOther   Counter32,
    tmnxDhcpSvrStats6DropMaxReached  Counter32,
    tmnxDhcpSvrStats6DropSvrDown     Counter32,
    tmnxDhcpSvrStats6LeasesExpired   Counter32,
    tmnxDhcpSvrStats6DropDuplDiffRly Counter32,
    tmnxDhcpSvrStats6RxIntPppSlaac   Counter64,
    tmnxDhcpSvrStats6RxIntReqIpoeWan Counter64,
    tmnxDhcpSvrStats6RxIntReleases   Counter64,
    tmnxDhcpSvrStats6DropIntWFo      Counter32,
    tmnxDhcpSvrStats6DropIntWConflct Counter32,
    tmnxDhcpSvrStats6DropIntWIfIdMap Counter32,
    tmnxDhcpSvrStats6DropIntWUserId  Counter32,
    tmnxDhcpSvrStats6RxIntIpoeSlaac  Counter64,
    tmnxDhcpSvrStats6DropAudit       Counter64,
    tmnxDhcpSvrStats6RxLeasequeries  Counter64,
    tmnxDhcpSvrStats6TxLqReplies     Counter64,
    tmnxDhcpSvrStats6DropLqNotAllow  Counter32,
    tmnxDhcpSvrStats6RxIntIpsec      Counter64
}

tmnxDhcpSvrStats6RxSolicits      OBJECT-TYPE
    SYNTAX      Counter64
    MAX-ACCESS  read-only
    STATUS      current
    DESCRIPTION
        "The value of tmnxDhcpSvrStats6RxSolicits indicates the number of
         solicit messages received by the DHCP server instance."
    ::= { tmnxDhcpServerStats6Entry 1 }

tmnxDhcpSvrStats6TxAdvertises    OBJECT-TYPE
    SYNTAX      Counter64
    MAX-ACCESS  read-only
    STATUS      current
    DESCRIPTION
        "The value of tmnxDhcpSvrStats6TxAdvertises indicates the number of
         advertise messages sent by the DHCP server instance."
    ::= { tmnxDhcpServerStats6Entry 2 }

tmnxDhcpSvrStats6RxRequests      OBJECT-TYPE
    SYNTAX      Counter64
    MAX-ACCESS  read-only
    STATUS      current
    DESCRIPTION
        "The value of tmnxDhcpSvrStats6RxRequests indicates the number of
         request messages received by the DHCP server instance."
    ::= { tmnxDhcpServerStats6Entry 3 }

tmnxDhcpSvrStats6RxConfirms      OBJECT-TYPE
    SYNTAX      Counter64
    MAX-ACCESS  read-only
    STATUS      current
    DESCRIPTION
        "The value of tmnxDhcpSvrStats6RxConfirms indicates the number of
         confirm messages received by the DHCP server instance."
    ::= { tmnxDhcpServerStats6Entry 4 }

tmnxDhcpSvrStats6RxRenews        OBJECT-TYPE
    SYNTAX      Counter64
    MAX-ACCESS  read-only
    STATUS      current
    DESCRIPTION
        "The value of tmnxDhcpSvrStats6RxRenews indicates the number of renew
         messages received by the DHCP server instance."
    ::= { tmnxDhcpServerStats6Entry 5 }

tmnxDhcpSvrStats6RxRebinds       OBJECT-TYPE
    SYNTAX      Counter64
    MAX-ACCESS  read-only
    STATUS      current
    DESCRIPTION
        "The value of tmnxDhcpSvrStats6RxRebinds indicates the number of rebind
         messages received by the DHCP server instance."
    ::= { tmnxDhcpServerStats6Entry 6 }

tmnxDhcpSvrStats6RxDeclines      OBJECT-TYPE
    SYNTAX      Counter64
    MAX-ACCESS  read-only
    STATUS      current
    DESCRIPTION
        "The value of tmnxDhcpSvrStats6RxDeclines indicates the number of
         decline messages received by the DHCP server instance."
    ::= { tmnxDhcpServerStats6Entry 7 }

tmnxDhcpSvrStats6RxReleases      OBJECT-TYPE
    SYNTAX      Counter64
    MAX-ACCESS  read-only
    STATUS      current
    DESCRIPTION
        "The value of tmnxDhcpSvrStats6RxReleases indicates the number of
         release messages received by the DHCP server instance."
    ::= { tmnxDhcpServerStats6Entry 8 }

tmnxDhcpSvrStats6TxReplies       OBJECT-TYPE
    SYNTAX      Counter64
    MAX-ACCESS  read-only
    STATUS      current
    DESCRIPTION
        "The value of tmnxDhcpSvrStats6TxReplies indicates the number of reply
         messages sent by the DHCP server instance."
    ::= { tmnxDhcpServerStats6Entry 9 }

tmnxDhcpSvrStats6TxReconfigures  OBJECT-TYPE
    SYNTAX      Counter64
    MAX-ACCESS  read-only
    STATUS      current
    DESCRIPTION
        "The value of tmnxDhcpSvrStats6TxReconfigures indicates the number of
         reconfigure messages sent by the DHCP server instance."
    ::= { tmnxDhcpServerStats6Entry 10 }

tmnxDhcpSvrStats6RxInfRequests   OBJECT-TYPE
    SYNTAX      Counter64
    MAX-ACCESS  read-only
    STATUS      current
    DESCRIPTION
        "The value of tmnxDhcpSvrStats6RxInfRequests indicates the number of
         information-request messages received by the DHCP server instance."
    ::= { tmnxDhcpServerStats6Entry 11 }

tmnxDhcpSvrStats6DropBadPackets  OBJECT-TYPE
    SYNTAX      Counter32
    MAX-ACCESS  read-only
    STATUS      current
    DESCRIPTION
        "The value of tmnxDhcpSvrStats6DropBadPackets indicates the number of
         DHCP packets received which were corrupt."
    ::= { tmnxDhcpServerStats6Entry 12 }

tmnxDhcpSvrStats6DropInvldTypes  OBJECT-TYPE
    SYNTAX      Counter32
    MAX-ACCESS  read-only
    STATUS      current
    DESCRIPTION
        "The value of tmnxDhcpSvrStats6DropInvldTypes indicates the number of
         DHCP packets received which had an invalid message type."
    ::= { tmnxDhcpServerStats6Entry 13 }

tmnxDhcpSvrStats6DropLseNotReady OBJECT-TYPE
    SYNTAX      Counter32
    MAX-ACCESS  read-only
    STATUS      current
    DESCRIPTION
        "The value of tmnxDhcpSvrStats6DropLseNotReady indicates the number of
         DHCP packets dropped by the server instance before the lease database
         was ready."
    ::= { tmnxDhcpServerStats6Entry 14 }

tmnxDhcpSvrStats6DropNoSrvngPool OBJECT-TYPE
    SYNTAX      Counter32
    MAX-ACCESS  read-only
    STATUS      current
    DESCRIPTION
        "The value of tmnxDhcpSvrStats6DropNoSrvngPool indicates the number of
         DHCP packets dropped by the server instance because there were no more
         free addresses in the pool."
    ::= { tmnxDhcpServerStats6Entry 15 }

tmnxDhcpSvrStats6DropOverload    OBJECT-TYPE
    SYNTAX      Counter32
    MAX-ACCESS  read-only
    STATUS      current
    DESCRIPTION
        "The value of tmnxDhcpSvrStats6DropOverload indicates the number of
         DHCP packets dropped by the server instance because they were received
         in excess of what the server instance can handle."
    ::= { tmnxDhcpServerStats6Entry 16 }

tmnxDhcpSvrStats6DropPerOverload OBJECT-TYPE
    SYNTAX      Counter32
    MAX-ACCESS  read-only
    STATUS      current
    DESCRIPTION
        "The value of tmnxDhcpSvrStats6DropPerOverload indicates
         the number of DHCP packets dropped by the server instance
         because they were received in excess of what the DHCP persistence
          system can handle. If this occurs, only releases and declines are
          still processed."
    ::= { tmnxDhcpServerStats6Entry 17 }

tmnxDhcpSvrStats6OffersIgnore    OBJECT-TYPE
    SYNTAX      Counter32
    MAX-ACCESS  read-only
    STATUS      current
    DESCRIPTION
        "The value of tmnxDhcpSvrStats6OffersIgnore indicates the number of
         DHCPOFFER (option 52 with value 2) packets sent by the DHCP server
         instance that were ignored by he clients."
    ::= { tmnxDhcpServerStats6Entry 18 }

tmnxDhcpSvrStats6DropGenError    OBJECT-TYPE
    SYNTAX      Counter32
    MAX-ACCESS  read-only
    STATUS      current
    DESCRIPTION
        "The value of tmnxDhcpSvrStats6DropGenError indicates the number of
         DHCP packets dropped by the server instance because of a generic
         error."
    ::= { tmnxDhcpServerStats6Entry 19 }

tmnxDhcpSvrStats6DropDestOther   OBJECT-TYPE
    SYNTAX      Counter32
    MAX-ACCESS  read-only
    STATUS      current
    DESCRIPTION
        "The value of tmnxDhcpSvrStats6DropDestOther indicates the number of
         DHCP requests dropped by the server instance because the (broadcast)
         request was not destined to this server."
    ::= { tmnxDhcpServerStats6Entry 20 }

tmnxDhcpSvrStats6DropMaxReached  OBJECT-TYPE
    SYNTAX      Counter32
    MAX-ACCESS  read-only
    STATUS      current
    DESCRIPTION
        "The value of tmnxDhcpSvrStats6DropMaxReached indicates the number of
         DHCP packets dropped by the server instance because the maximum number
         of leases was reached.

          The maximum number of leases is indicated by the value of the object
          tmnxDhcpSvrMaxLeases."
    ::= { tmnxDhcpServerStats6Entry 21 }

tmnxDhcpSvrStats6DropSvrDown     OBJECT-TYPE
    SYNTAX      Counter32
    MAX-ACCESS  read-only
    STATUS      current
    DESCRIPTION
        "The value of tmnxDhcpSvrStats6DropSvrDown indicates the number of DHCP
         packets dropped by the server instance during server instance shutdown
         (while the value of the object tmnxDhcpServerCfgAdminState in the
         corresponding row was set equal to 'outOfService')."
    ::= { tmnxDhcpServerStats6Entry 22 }

tmnxDhcpSvrStats6LeasesExpired   OBJECT-TYPE
    SYNTAX      Counter32
    MAX-ACCESS  read-only
    STATUS      current
    DESCRIPTION
        "The value of tmnxDhcpSvrStats6LeasesExpired indicates the number of
         DHCP leases that were expired (because no release was received)."
    ::= { tmnxDhcpServerStats6Entry 23 }

tmnxDhcpSvrStats6DropDuplDiffRly OBJECT-TYPE
    SYNTAX      Counter32
    MAX-ACCESS  read-only
    STATUS      current
    DESCRIPTION
        "The value of tmnxDhcpSvrStats6DropDuplDiffRly indicates the number of
         DHCP requests dropped by the server instance because they were
         received from a different Relay IP address within a timeframe of 10
         seconds after a previous DHCPREQUEST."
    ::= { tmnxDhcpServerStats6Entry 24 }

tmnxDhcpSvrStats6RxIntPppSlaac   OBJECT-TYPE
    SYNTAX      Counter64
    MAX-ACCESS  read-only
    STATUS      current
    DESCRIPTION
        "The value of tmnxDhcpSvrStats6RxIntPppSlaac indicates the number of
         internal request calls received by the DHCP server instance from the
         local address assignment infrastructure for PPP SLAAC (stateless
         autoconfiguration)."
    ::= { tmnxDhcpServerStats6Entry 25 }

tmnxDhcpSvrStats6RxIntReqIpoeWan OBJECT-TYPE
    SYNTAX      Counter64
    MAX-ACCESS  read-only
    STATUS      current
    DESCRIPTION
        "The value of tmnxDhcpSvrStats6RxIntReqIpoeWan indicates the number of
         internal request calls received by the DHCP server instance from the
         local address assignment infrastructure for IPoE."
    ::= { tmnxDhcpServerStats6Entry 26 }

tmnxDhcpSvrStats6RxIntReleases   OBJECT-TYPE
    SYNTAX      Counter64
    MAX-ACCESS  read-only
    STATUS      current
    DESCRIPTION
        "The value of tmnxDhcpSvrStats6RxIntReleases indicates the number of
         internal release calls received by the DHCP server instance from the
         local address assignment infrastructure."
    ::= { tmnxDhcpServerStats6Entry 27 }

tmnxDhcpSvrStats6DropIntWFo      OBJECT-TYPE
    SYNTAX      Counter32
    MAX-ACCESS  read-only
    STATUS      current
    DESCRIPTION
        "The value of tmnxDhcpSvrStats6DropIntWFo indicates the number of
         internal calls from the local address assignment infrastructure
         dropped by the DHCP server instance because failover is enabled for
         the server instance."
    ::= { tmnxDhcpServerStats6Entry 28 }

tmnxDhcpSvrStats6DropIntWConflct OBJECT-TYPE
    SYNTAX      Counter32
    MAX-ACCESS  read-only
    STATUS      current
    DESCRIPTION
        "The value of tmnxDhcpSvrStats6DropIntWConflct indicates a DHCP host is
         trying to acquire an IP address that was handed through the local
         address assignment infrastructure, or the local address assignment
         infrastructure tries to use an IP address that was handed out to a
         DHCP client."
    ::= { tmnxDhcpServerStats6Entry 29 }

tmnxDhcpSvrStats6DropIntWIfIdMap OBJECT-TYPE
    SYNTAX      Counter32
    MAX-ACCESS  read-only
    STATUS      current
    DESCRIPTION
        "The value of tmnxDhcpSvrStats6DropIntWIfIdMap indicates the number of
         internal calls from the local address assignment infrastructure
         dropped by the DHCP server instance because interface ID mapping is
         enabled for the server instance."
    ::= { tmnxDhcpServerStats6Entry 30 }

tmnxDhcpSvrStats6DropIntWUserId  OBJECT-TYPE
    SYNTAX      Counter32
    MAX-ACCESS  read-only
    STATUS      current
    DESCRIPTION
        "The value of tmnxDhcpSvrStats6DropIntWUserId indicates the number of
         internal calls from the local address assignment infrastructure
         dropped by the DHCP server instance because tmnxDhcpServerCfgUserIdent
         is not set to duid (2) for the server instance."
    ::= { tmnxDhcpServerStats6Entry 31 }

tmnxDhcpSvrStats6RxIntIpoeSlaac  OBJECT-TYPE
    SYNTAX      Counter64
    MAX-ACCESS  read-only
    STATUS      current
    DESCRIPTION
        "The value of tmnxDhcpSvrStats6RxIntIpoeSlaac indicates the number of
         internal request calls received by the DHCP server instance from the
         local address assignment infrastructure for IPoE SLAAC (stateless
         autoconfiguration)."
    ::= { tmnxDhcpServerStats6Entry 32 }

tmnxDhcpSvrStats6DropAudit       OBJECT-TYPE
    SYNTAX      Counter64
    MAX-ACCESS  read-only
    STATUS      current
    DESCRIPTION
        "The value of tmnxDhcpSvrStats6DropAudit indicates the number of DHCP
         requests dropped by the server instance because this server instance
         is busy with the primary audit."
    ::= { tmnxDhcpServerStats6Entry 33 }

tmnxDhcpSvrStats6RxLeasequeries  OBJECT-TYPE
    SYNTAX      Counter64
    MAX-ACCESS  read-only
    STATUS      current
    DESCRIPTION
        "The value of tmnxDhcpSvrStats6RxLeasequeries indicates the number of
         leasequery messages received by the DHCP server instance."
    ::= { tmnxDhcpServerStats6Entry 34 }

tmnxDhcpSvrStats6TxLqReplies     OBJECT-TYPE
    SYNTAX      Counter64
    MAX-ACCESS  read-only
    STATUS      current
    DESCRIPTION
        "The value of tmnxDhcpSvrStats6TxLqReplies indicates the number of
         leasequery-reply messages sent by the DHCP server instance."
    ::= { tmnxDhcpServerStats6Entry 35 }

tmnxDhcpSvrStats6DropLqNotAllow  OBJECT-TYPE
    SYNTAX      Counter32
    MAX-ACCESS  read-only
    STATUS      current
    DESCRIPTION
        "The value of tmnxDhcpSvrStats6DropLqNotAllow indicates the number of
         DHCP leasequery packets dropped by the server instance because the
         server is configured not to allow leasequery packets."
    ::= { tmnxDhcpServerStats6Entry 36 }

tmnxDhcpSvrStats6RxIntIpsec      OBJECT-TYPE
    SYNTAX      Counter64
    MAX-ACCESS  read-only
    STATUS      current
    DESCRIPTION
        "The value of tmnxDhcpSvrStats6RxIntIpsec indicates the number of
         internal request calls received by the DHCP server instance from the
         local address assignment infrastructure for IPsec."
    ::= { tmnxDhcpServerStats6Entry 37 }

tmnxDhcpSvrSubnetStats6Table     OBJECT-TYPE
    SYNTAX      SEQUENCE OF TmnxDhcpSvrSubnetStats6Entry
    MAX-ACCESS  not-accessible
    STATUS      current
    DESCRIPTION
        "The tmnxDhcpSvrSubnetStats6Table has an entry for each subnet that
         belongs to the specified DHCPv6 server instance and pool."
    ::= { tmnxDhcpServerObjs 24 }

tmnxDhcpSvrSubnetStats6Entry     OBJECT-TYPE
    SYNTAX      TmnxDhcpSvrSubnetStats6Entry
    MAX-ACCESS  not-accessible
    STATUS      current
    DESCRIPTION
        "Each row entry in the tmnxDhcpSvrSubnetStats6Table represents
         additional columns of operational data for a subnet that belongs to
         the specified DHCPv6 server instance and pool."
    INDEX       {
        vRtrID,
        tmnxDhcpServerCfgServerName,
        tmnxDhcpServerPoolName,
        tmnxDhcpSvrSubnetAddrType,
        tmnxDhcpSvrSubnetAddress,
        tmnxDhcpSvrSubnetPrefixLength
    }
    ::= { tmnxDhcpSvrSubnetStats6Table 1 }

TmnxDhcpSvrSubnetStats6Entry     ::= SEQUENCE
{
    tmnxDhcpSvrSubnetStats6Advertise Counter32,
    tmnxDhcpSvrSubnetStats6Stable    Counter32,
    tmnxDhcpSvrSubnetStats6RCPending Counter32,
    tmnxDhcpSvrSubnetStats6RmPending Counter32,
    tmnxDhcpSvrSubnetStats6Declined  Counter32,
    tmnxDhcpSvrSubnetStats6HasExt    TruthValue,
    tmnxDhcpSvrSubnetStats6ExtResetT TimeStamp,
    tmnxDhcpSvrSubnetStats6StableP   Counter32,
    tmnxDhcpSvrSubnetStats6StablePT  TimeStamp,
    tmnxDhcpSvrSubnetStats6ProvBlk   Counter64,
    tmnxDhcpSvrSubnetStats6UsedBlk   Counter64,
    tmnxDhcpSvrSubnetStats6UsedBlkP  Counter64,
    tmnxDhcpSvrSubnetStats6UsedBlkPT TimeStamp,
    tmnxDhcpSvrSubnetStats6FreeBlk   Counter64,
    tmnxDhcpSvrSubnetStats6FreeBlkP  Counter64,
    tmnxDhcpSvrSubnetStats6FreeBlkPT TimeStamp,
    tmnxDhcpSvrSubnetStats6UsedPct   Integer32,
    tmnxDhcpSvrSubnetStats6UsedPctP  Integer32,
    tmnxDhcpSvrSubnetStats6UsedPctPT TimeStamp,
    tmnxDhcpSvrSubnetStats6FreePct   Integer32,
    tmnxDhcpSvrSubnetStats6FreePctP  Integer32,
    tmnxDhcpSvrSubnetStats6FreePctPT TimeStamp,
    tmnxDhcpSvrSubnetStats6AdvertP   Counter32,
    tmnxDhcpSvrSubnetStats6AdvertPT  TimeStamp
}

tmnxDhcpSvrSubnetStats6Advertise OBJECT-TYPE
    SYNTAX      Counter32
    MAX-ACCESS  read-only
    STATUS      current
    DESCRIPTION
        "The value of tmnxDhcpSvrSubnetStats6Advertise indicates the number of
         leases in this subnet that are in state 'advertised'."
    ::= { tmnxDhcpSvrSubnetStats6Entry 1 }

tmnxDhcpSvrSubnetStats6Stable    OBJECT-TYPE
    SYNTAX      Counter32
    MAX-ACCESS  read-only
    STATUS      current
    DESCRIPTION
        "The value of tmnxDhcpSvrSubnetStats6Stable indicates the number of
         leases in this subnet that are in state 'stable'."
    ::= { tmnxDhcpSvrSubnetStats6Entry 2 }

tmnxDhcpSvrSubnetStats6RCPending OBJECT-TYPE
    SYNTAX      Counter32
    MAX-ACCESS  read-only
    STATUS      current
    DESCRIPTION
        "The value of tmnxDhcpSvrSubnetStats6RCPending indicates the number of
         leases in this subnet that are in state 'reconfigurePending'."
    ::= { tmnxDhcpSvrSubnetStats6Entry 3 }

tmnxDhcpSvrSubnetStats6RmPending OBJECT-TYPE
    SYNTAX      Counter32
    MAX-ACCESS  read-only
    STATUS      current
    DESCRIPTION
        "The value of tmnxDhcpSvrSubnetStats6RmPending indicates the number of
         leases in this subnet that are in state 'removePending'."
    ::= { tmnxDhcpSvrSubnetStats6Entry 4 }

tmnxDhcpSvrSubnetStats6Declined  OBJECT-TYPE
    SYNTAX      Counter32
    MAX-ACCESS  read-only
    STATUS      current
    DESCRIPTION
        "The value of tmnxDhcpSvrSubnetStats6Declined indicates the number of
         addresses in this subnet that are declined."
    ::= { tmnxDhcpSvrSubnetStats6Entry 5 }

tmnxDhcpSvrSubnetStats6HasExt    OBJECT-TYPE
    SYNTAX      TruthValue
    MAX-ACCESS  read-only
    STATUS      current
    DESCRIPTION
        "The value of tmnxDhcpSvrSubnetStats6HasExt indicates whether the
         extended statistics collection for this prefix is enabled. These
         extended statistics are only collected when the length of the
         configured subnet is between /32 en /64."
    ::= { tmnxDhcpSvrSubnetStats6Entry 6 }

tmnxDhcpSvrSubnetStats6ExtResetT OBJECT-TYPE
    SYNTAX      TimeStamp
    MAX-ACCESS  read-only
    STATUS      current
    DESCRIPTION
        "The value of tmnxDhcpSvrSubnetStats6ExtResetT indicates the sysUpTime
         at the last reset of the extended statistics."
    ::= { tmnxDhcpSvrSubnetStats6Entry 7 }

tmnxDhcpSvrSubnetStats6StableP   OBJECT-TYPE
    SYNTAX      Counter32
    MAX-ACCESS  read-only
    STATUS      current
    DESCRIPTION
        "The value of tmnxDhcpSvrSubnetStats6StableP indicates the highest
         value of tmnxDhcpSvrSubnetStats6Stable since the last reset of the
         extended statistics."
    ::= { tmnxDhcpSvrSubnetStats6Entry 8 }

tmnxDhcpSvrSubnetStats6StablePT  OBJECT-TYPE
    SYNTAX      TimeStamp
    MAX-ACCESS  read-only
    STATUS      current
    DESCRIPTION
        "The value of tmnxDhcpSvrSubnetStats6StablePT indicates the sysUpTime
         at the last change of tmnxDhcpSvrSubnetStats6StableP."
    ::= { tmnxDhcpSvrSubnetStats6Entry 9 }

tmnxDhcpSvrSubnetStats6ProvBlk   OBJECT-TYPE
    SYNTAX      Counter64
    MAX-ACCESS  read-only
    STATUS      current
    DESCRIPTION
        "The value of tmnxDhcpSvrSubnetStats6ProvBlk indicates the number of
         provisioned /64 blocks."
    ::= { tmnxDhcpSvrSubnetStats6Entry 10 }

tmnxDhcpSvrSubnetStats6UsedBlk   OBJECT-TYPE
    SYNTAX      Counter64
    MAX-ACCESS  read-only
    STATUS      current
    DESCRIPTION
        "The value of tmnxDhcpSvrSubnetStats6UsedBlk indicates the number of
         provisioned but unused /64 blocks."
    ::= { tmnxDhcpSvrSubnetStats6Entry 11 }

tmnxDhcpSvrSubnetStats6UsedBlkP  OBJECT-TYPE
    SYNTAX      Counter64
    MAX-ACCESS  read-only
    STATUS      current
    DESCRIPTION
        "The value of tmnxDhcpSvrSubnetStats6UsedBlkP indicates the lowest
         value of unused /64 blocks since the last reset of the extended
         statistics."
    ::= { tmnxDhcpSvrSubnetStats6Entry 12 }

tmnxDhcpSvrSubnetStats6UsedBlkPT OBJECT-TYPE
    SYNTAX      TimeStamp
    MAX-ACCESS  read-only
    STATUS      current
    DESCRIPTION
        "The value of tmnxDhcpSvrSubnetStats6UsedBlkPT indicates the sysUpTime
         at the last change of tmnxDhcpSvrSubnetStats6UsedBlkP."
    ::= { tmnxDhcpSvrSubnetStats6Entry 13 }

tmnxDhcpSvrSubnetStats6FreeBlk   OBJECT-TYPE
    SYNTAX      Counter64
    MAX-ACCESS  read-only
    STATUS      current
    DESCRIPTION
        "The value of tmnxDhcpSvrSubnetStats6FreeBlk indicates the number of
         provisioned but unused /64 blocks."
    ::= { tmnxDhcpSvrSubnetStats6Entry 14 }

tmnxDhcpSvrSubnetStats6FreeBlkP  OBJECT-TYPE
    SYNTAX      Counter64
    MAX-ACCESS  read-only
    STATUS      current
    DESCRIPTION
        "The value of tmnxDhcpSvrSubnetStats6FreeBlkP indicates the lowest
         value of unused /64 blocks since the last reset of the extended
         statistics."
    ::= { tmnxDhcpSvrSubnetStats6Entry 15 }

tmnxDhcpSvrSubnetStats6FreeBlkPT OBJECT-TYPE
    SYNTAX      TimeStamp
    MAX-ACCESS  read-only
    STATUS      current
    DESCRIPTION
        "The value of tmnxDhcpSvrSubnetStats6FreeBlkPT indicates the sysUpTime
         at the last change of tmnxDhcpSvrSubnetStats6FreeBlkP."
    ::= { tmnxDhcpSvrSubnetStats6Entry 16 }

tmnxDhcpSvrSubnetStats6UsedPct   OBJECT-TYPE
    SYNTAX      Integer32 (0..100)
    MAX-ACCESS  read-only
    STATUS      current
    DESCRIPTION
        "The value of tmnxDhcpSvrSubnetStats6UsedPct indicates the percentage
         of /64 blocks currently in use."
    ::= { tmnxDhcpSvrSubnetStats6Entry 17 }

tmnxDhcpSvrSubnetStats6UsedPctP  OBJECT-TYPE
    SYNTAX      Integer32 (0..100)
    MAX-ACCESS  read-only
    STATUS      current
    DESCRIPTION
        "The value of tmnxDhcpSvrSubnetStats6UsedPctP indicates the highest
         value of tmnxDhcpSvrSubnetStats6UsedPct since the last reset of the
         extended statistics."
    ::= { tmnxDhcpSvrSubnetStats6Entry 18 }

tmnxDhcpSvrSubnetStats6UsedPctPT OBJECT-TYPE
    SYNTAX      TimeStamp
    MAX-ACCESS  read-only
    STATUS      current
    DESCRIPTION
        "The value of tmnxDhcpSvrSubnetStats6UsedPctPT indicates the sysUpTime
         at the last change of tmnxDhcpSvrSubnetStats6UsedPctP."
    ::= { tmnxDhcpSvrSubnetStats6Entry 19 }

tmnxDhcpSvrSubnetStats6FreePct   OBJECT-TYPE
    SYNTAX      Integer32 (0..100)
    MAX-ACCESS  read-only
    STATUS      current
    DESCRIPTION
        "The value of tmnxDhcpSvrSubnetStats6FreePct indicates the percentage
         of /64 blocks currently unused."
    ::= { tmnxDhcpSvrSubnetStats6Entry 20 }

tmnxDhcpSvrSubnetStats6FreePctP  OBJECT-TYPE
    SYNTAX      Integer32 (0..100)
    MAX-ACCESS  read-only
    STATUS      current
    DESCRIPTION
        "The value of tmnxDhcpSvrSubnetStats6FreePctP indicates the lowest
         value of tmnxDhcpSvrSubnetStats6FreePct since the last reset of the
         extended statistics."
    ::= { tmnxDhcpSvrSubnetStats6Entry 21 }

tmnxDhcpSvrSubnetStats6FreePctPT OBJECT-TYPE
    SYNTAX      TimeStamp
    MAX-ACCESS  read-only
    STATUS      current
    DESCRIPTION
        "The value of tmnxDhcpSvrSubnetStats6FreePctPT indicates the sysUpTime
         at the last change of tmnxDhcpSvrSubnetStats6FreePctP."
    ::= { tmnxDhcpSvrSubnetStats6Entry 22 }

tmnxDhcpSvrSubnetStats6AdvertP   OBJECT-TYPE
    SYNTAX      Counter32
    MAX-ACCESS  read-only
    STATUS      current
    DESCRIPTION
        "The value of tmnxDhcpSvrSubnetStats6AdvertP indicates the highest
         value of tmnxDhcpSvrSubnetStats6Advertise since the last reset of the
         extended statistics."
    ::= { tmnxDhcpSvrSubnetStats6Entry 23 }

tmnxDhcpSvrSubnetStats6AdvertPT  OBJECT-TYPE
    SYNTAX      TimeStamp
    MAX-ACCESS  read-only
    STATUS      current
    DESCRIPTION
        "The value of tmnxDhcpSvrSubnetStats6AdvertPT indicates the sysUpTime
         at the last change of tmnxDhcpSvrSubnetStats6AdvertP."
    ::= { tmnxDhcpSvrSubnetStats6Entry 24 }

tmnxDhcpSvrPoolStatsTable        OBJECT-TYPE
    SYNTAX      SEQUENCE OF TmnxDhcpSvrPoolStatsEntry
    MAX-ACCESS  not-accessible
    STATUS      current
    DESCRIPTION
        "The tmnxDhcpSvrPoolStatsTable has an entry for each pool that belongs
         to the specified DHCP server instance."
    ::= { tmnxDhcpServerObjs 25 }

tmnxDhcpSvrPoolStatsEntry        OBJECT-TYPE
    SYNTAX      TmnxDhcpSvrPoolStatsEntry
    MAX-ACCESS  not-accessible
    STATUS      current
    DESCRIPTION
        "Each row entry in the tmnxDhcpSvrPoolStatsTable represents additional
         columns of operational data for a pool that belongs to the specified
         DHCP server instance."
    INDEX       {
        vRtrID,
        tmnxDhcpServerCfgServerName,
        tmnxDhcpServerPoolName
    }
    ::= { tmnxDhcpSvrPoolStatsTable 1 }

TmnxDhcpSvrPoolStatsEntry        ::= SEQUENCE
{
    tmnxDhcpSvrPoolStatsFree         Counter32,
    tmnxDhcpSvrPoolStatsOffered      Counter32,
    tmnxDhcpSvrPoolStatsStable       Counter32,
    tmnxDhcpSvrPoolStatsFRPending    Counter32,
    tmnxDhcpSvrPoolStatsRemPending   Counter32,
    tmnxDhcpSvrPoolStatsDeclined     Counter32,
    tmnxDhcpSvrPoolStatsFoFree       Counter32,
    tmnxDhcpSvrPoolStatsFoOffered    Counter32,
    tmnxDhcpSvrPoolStatsFoStable     Counter32,
    tmnxDhcpSvrPoolStatsFoFRPend     Counter32,
    tmnxDhcpSvrPoolStatsFoRemPend    Counter32,
    tmnxDhcpSvrPoolStatsFoDeclined   Counter32,
    tmnxDhcpSvrPoolStatsProv         Counter32,
    tmnxDhcpSvrPoolStatsFoProv       Counter32,
    tmnxDhcpSvrPoolStatsHasExt       TruthValue,
    tmnxDhcpSvrPoolStatsExtResetT    TimeStamp,
    tmnxDhcpSvrPoolStatsStableP      Counter32,
    tmnxDhcpSvrPoolStatsStablePT     TimeStamp,
    tmnxDhcpSvrPoolStatsFoStableP    Counter32,
    tmnxDhcpSvrPoolStatsFoStablePT   TimeStamp,
    tmnxDhcpSvrPoolStatsUsed         Counter32,
    tmnxDhcpSvrPoolStatsUsedP        Counter32,
    tmnxDhcpSvrPoolStatsUsedPT       TimeStamp,
    tmnxDhcpSvrPoolStatsFoUsed       Counter32,
    tmnxDhcpSvrPoolStatsFoUsedP      Counter32,
    tmnxDhcpSvrPoolStatsFoUsedPT     TimeStamp,
    tmnxDhcpSvrPoolStatsFreeP        Counter32,
    tmnxDhcpSvrPoolStatsFreePT       TimeStamp,
    tmnxDhcpSvrPoolStatsFoFreeP      Counter32,
    tmnxDhcpSvrPoolStatsFoFreePT     TimeStamp,
    tmnxDhcpSvrPoolStatsUsedPct      Integer32,
    tmnxDhcpSvrPoolStatsUsedPctP     Integer32,
    tmnxDhcpSvrPoolStatsUsedPctPT    TimeStamp,
    tmnxDhcpSvrPoolStatsFoUsdPct     Integer32,
    tmnxDhcpSvrPoolStatsFoUsdPctP    Integer32,
    tmnxDhcpSvrPoolStatsFoUsdPctPT   TimeStamp,
    tmnxDhcpSvrPoolStatsFreePct      Integer32,
    tmnxDhcpSvrPoolStatsFreePctP     Integer32,
    tmnxDhcpSvrPoolStatsFreePctPT    TimeStamp,
    tmnxDhcpSvrPoolStatsFoFrePct     Integer32,
    tmnxDhcpSvrPoolStatsFoFrePctP    Integer32,
    tmnxDhcpSvrPoolStatsFoFrePctPT   TimeStamp,
    tmnxDhcpSvrPoolStatsOfferP       Counter32,
    tmnxDhcpSvrPoolStatsOfferPT      TimeStamp,
    tmnxDhcpSvrPoolStatsFoOfferP     Counter32,
    tmnxDhcpSvrPoolStatsFoOfferPT    TimeStamp
}

tmnxDhcpSvrPoolStatsFree         OBJECT-TYPE
    SYNTAX      Counter32
    MAX-ACCESS  read-only
    STATUS      current
    DESCRIPTION
        "The value of tmnxDhcpSvrPoolStatsFree indicates the number of
         addresses in this pool that are free."
    ::= { tmnxDhcpSvrPoolStatsEntry 1 }

tmnxDhcpSvrPoolStatsOffered      OBJECT-TYPE
    SYNTAX      Counter32
    MAX-ACCESS  read-only
    STATUS      current
    DESCRIPTION
        "The value of tmnxDhcpSvrPoolStatsOffered indicates the number of
         leases in this pool that are in state 'offered'."
    ::= { tmnxDhcpSvrPoolStatsEntry 2 }

tmnxDhcpSvrPoolStatsStable       OBJECT-TYPE
    SYNTAX      Counter32
    MAX-ACCESS  read-only
    STATUS      current
    DESCRIPTION
        "The value of tmnxDhcpSvrPoolStatsStable indicates the number of leases
         in this pool that are in state 'stable'."
    ::= { tmnxDhcpSvrPoolStatsEntry 3 }

tmnxDhcpSvrPoolStatsFRPending    OBJECT-TYPE
    SYNTAX      Counter32
    MAX-ACCESS  read-only
    STATUS      current
    DESCRIPTION
        "The value of tmnxDhcpSvrPoolStatsFRPending indicates the number of
         leases in this pool that are in state 'forceRenewPending'."
    ::= { tmnxDhcpSvrPoolStatsEntry 4 }

tmnxDhcpSvrPoolStatsRemPending   OBJECT-TYPE
    SYNTAX      Counter32
    MAX-ACCESS  read-only
    STATUS      current
    DESCRIPTION
        "The value of tmnxDhcpSvrPoolStatsRemPending indicates the number of
         leases in this pool that are in state 'removePending'."
    ::= { tmnxDhcpSvrPoolStatsEntry 5 }

tmnxDhcpSvrPoolStatsDeclined     OBJECT-TYPE
    SYNTAX      Counter32
    MAX-ACCESS  read-only
    STATUS      current
    DESCRIPTION
        "The value of tmnxDhcpSvrPoolStatsDeclined indicates the number of
         addresses in this pool that are declined."
    ::= { tmnxDhcpSvrPoolStatsEntry 6 }

tmnxDhcpSvrPoolStatsFoFree       OBJECT-TYPE
    SYNTAX      Counter32
    MAX-ACCESS  read-only
    STATUS      current
    DESCRIPTION
        "The value of tmnxDhcpSvrPoolStatsFoFree indicates the number of remote
         addresses in this pool that are free.

         The value of this object is only relevant if the value of the object
         tmnxDhcpsFoAdminState of this server is equal to 'inService (2)'."
    ::= { tmnxDhcpSvrPoolStatsEntry 7 }

tmnxDhcpSvrPoolStatsFoOffered    OBJECT-TYPE
    SYNTAX      Counter32
    MAX-ACCESS  read-only
    STATUS      current
    DESCRIPTION
        "The value of tmnxDhcpSvrPoolStatsFoOffered indicates the number of
         remote leases in this pool that are in state 'offered'.

         The value of this object is only relevant if the value of the object
         tmnxDhcpsFoAdminState of this server is equal to 'inService (2)'."
    ::= { tmnxDhcpSvrPoolStatsEntry 8 }

tmnxDhcpSvrPoolStatsFoStable     OBJECT-TYPE
    SYNTAX      Counter32
    MAX-ACCESS  read-only
    STATUS      current
    DESCRIPTION
        "The value of tmnxDhcpSvrPoolStatsFoStable indicates the number of
         remote leases in this pool that are in state 'stable'.

         The value of this object is only relevant if the value of the object
         tmnxDhcpsFoAdminState of this server is equal to 'inService (2)'."
    ::= { tmnxDhcpSvrPoolStatsEntry 9 }

tmnxDhcpSvrPoolStatsFoFRPend     OBJECT-TYPE
    SYNTAX      Counter32
    MAX-ACCESS  read-only
    STATUS      current
    DESCRIPTION
        "The value of tmnxDhcpSvrPoolStatsFoFRPend indicates the number of
         remote leases in this pool that are in state 'forceRenewPending'.

         The value of this object is only relevant if the value of the object
         tmnxDhcpsFoAdminState of this server is equal to 'inService (2)'."
    ::= { tmnxDhcpSvrPoolStatsEntry 10 }

tmnxDhcpSvrPoolStatsFoRemPend    OBJECT-TYPE
    SYNTAX      Counter32
    MAX-ACCESS  read-only
    STATUS      current
    DESCRIPTION
        "The value of tmnxDhcpSvrPoolStatsFoRemPend indicates the number of
         remote leases in this pool that are in state 'removePending'.

         The value of this object is only relevant if the value of the object
         tmnxDhcpsFoAdminState of this server is equal to 'inService (2)'."
    ::= { tmnxDhcpSvrPoolStatsEntry 11 }

tmnxDhcpSvrPoolStatsFoDeclined   OBJECT-TYPE
    SYNTAX      Counter32
    MAX-ACCESS  read-only
    STATUS      current
    DESCRIPTION
        "The value of tmnxDhcpSvrPoolStatsFoDeclined indicates the number of
         remote addresses in this pool that are declined.

         The value of this object is only relevant if the value of the object
         tmnxDhcpsFoAdminState of this server is equal to 'inService (2)'."
    ::= { tmnxDhcpSvrPoolStatsEntry 12 }

tmnxDhcpSvrPoolStatsProv         OBJECT-TYPE
    SYNTAX      Counter32
    MAX-ACCESS  read-only
    STATUS      current
    DESCRIPTION
        "The value of tmnxDhcpSvrPoolStatsProv indicates the total number of
         local addresses in this pool that are provisioned."
    ::= { tmnxDhcpSvrPoolStatsEntry 13 }

tmnxDhcpSvrPoolStatsFoProv       OBJECT-TYPE
    SYNTAX      Counter32
    MAX-ACCESS  read-only
    STATUS      current
    DESCRIPTION
        "The value of tmnxDhcpSvrPoolStatsFoProv indicates the total number of
         remote addresses in this pool that are provisioned.

         The value of this object is only relevant if the value of the object
         tmnxDhcpsFoAdminState of this server is equal to 'inService (2)' and
         the value of the object tmnxDhcpsFoState of this server is equal to
         'partnerDown (5)'."
    ::= { tmnxDhcpSvrPoolStatsEntry 14 }

tmnxDhcpSvrPoolStatsHasExt       OBJECT-TYPE
    SYNTAX      TruthValue
    MAX-ACCESS  read-only
    STATUS      current
    DESCRIPTION
        "The value of tmnxDhcpSvrPoolStatsHasExt indicates whether the extended
         statistics collection for this pool is enabled."
    ::= { tmnxDhcpSvrPoolStatsEntry 15 }

tmnxDhcpSvrPoolStatsExtResetT    OBJECT-TYPE
    SYNTAX      TimeStamp
    MAX-ACCESS  read-only
    STATUS      current
    DESCRIPTION
        "The value of tmnxDhcpSvrPoolStatsExtResetT indicates the sysUpTime at
         the last reset of the extended statistics."
    ::= { tmnxDhcpSvrPoolStatsEntry 16 }

tmnxDhcpSvrPoolStatsStableP      OBJECT-TYPE
    SYNTAX      Counter32
    MAX-ACCESS  read-only
    STATUS      current
    DESCRIPTION
        "The value of tmnxDhcpSvrPoolStatsStableP indicates the highest value
         of tmnxDhcpSvrPoolStatsStable since the last reset of the extended
         statistics."
    ::= { tmnxDhcpSvrPoolStatsEntry 17 }

tmnxDhcpSvrPoolStatsStablePT     OBJECT-TYPE
    SYNTAX      TimeStamp
    MAX-ACCESS  read-only
    STATUS      current
    DESCRIPTION
        "The value of tmnxDhcpSvrPoolStatsStablePT indicates the sysUpTime at
         the last change of tmnxDhcpSvrPoolStatsStableP."
    ::= { tmnxDhcpSvrPoolStatsEntry 18 }

tmnxDhcpSvrPoolStatsFoStableP    OBJECT-TYPE
    SYNTAX      Counter32
    MAX-ACCESS  read-only
    STATUS      current
    DESCRIPTION
        "The value of tmnxDhcpSvrPoolStatsFoStableP indicates the highest value
         of tmnxDhcpSvrPoolStatsFoStable since the last reset of the extended
         statistics."
    ::= { tmnxDhcpSvrPoolStatsEntry 19 }

tmnxDhcpSvrPoolStatsFoStablePT   OBJECT-TYPE
    SYNTAX      TimeStamp
    MAX-ACCESS  read-only
    STATUS      current
    DESCRIPTION
        "The value of tmnxDhcpSvrPoolStatsFoStablePT indicates the sysUpTime at
         the last change of tmnxDhcpSvrPoolStatsFoStableP."
    ::= { tmnxDhcpSvrPoolStatsEntry 20 }

tmnxDhcpSvrPoolStatsUsed         OBJECT-TYPE
    SYNTAX      Counter32
    MAX-ACCESS  read-only
    STATUS      current
    DESCRIPTION
        "The value of tmnxDhcpSvrPoolStatsUsed indicates the number of
         provisioned and used subnets."
    ::= { tmnxDhcpSvrPoolStatsEntry 21 }

tmnxDhcpSvrPoolStatsUsedP        OBJECT-TYPE
    SYNTAX      Counter32
    MAX-ACCESS  read-only
    STATUS      current
    DESCRIPTION
        "The value of tmnxDhcpSvrPoolStatsUsedP indicates the lowest value of
         unused subnets since the last reset of the extended statistics."
    ::= { tmnxDhcpSvrPoolStatsEntry 22 }

tmnxDhcpSvrPoolStatsUsedPT       OBJECT-TYPE
    SYNTAX      TimeStamp
    MAX-ACCESS  read-only
    STATUS      current
    DESCRIPTION
        "The value of tmnxDhcpSvrPoolStatsUsedPT indicates the sysUpTime at the
         last change of tmnxDhcpSvrPoolStatsUsedP."
    ::= { tmnxDhcpSvrPoolStatsEntry 23 }

tmnxDhcpSvrPoolStatsFoUsed       OBJECT-TYPE
    SYNTAX      Counter32
    MAX-ACCESS  read-only
    STATUS      current
    DESCRIPTION
        "The value of tmnxDhcpSvrPoolStatsFoUsed indicates the number of
         provisioned and used remote subnets."
    ::= { tmnxDhcpSvrPoolStatsEntry 24 }

tmnxDhcpSvrPoolStatsFoUsedP      OBJECT-TYPE
    SYNTAX      Counter32
    MAX-ACCESS  read-only
    STATUS      current
    DESCRIPTION
        "The value of tmnxDhcpSvrPoolStatsFoUsedP indicates the lowest value of
         unused subnets since the last reset of the extended statistics."
    ::= { tmnxDhcpSvrPoolStatsEntry 25 }

tmnxDhcpSvrPoolStatsFoUsedPT     OBJECT-TYPE
    SYNTAX      TimeStamp
    MAX-ACCESS  read-only
    STATUS      current
    DESCRIPTION
        "The value of tmnxDhcpSvrPoolStatsFoUsedPT indicates the sysUpTime at
         the last change of tmnxDhcpSvrPoolStatsFoUsedP."
    ::= { tmnxDhcpSvrPoolStatsEntry 26 }

tmnxDhcpSvrPoolStatsFreeP        OBJECT-TYPE
    SYNTAX      Counter32
    MAX-ACCESS  read-only
    STATUS      current
    DESCRIPTION
        "The value of tmnxDhcpSvrPoolStatsFreeP indicates the lowest value of
         unused subnets since the last reset of the extended statistics."
    ::= { tmnxDhcpSvrPoolStatsEntry 27 }

tmnxDhcpSvrPoolStatsFreePT       OBJECT-TYPE
    SYNTAX      TimeStamp
    MAX-ACCESS  read-only
    STATUS      current
    DESCRIPTION
        "The value of tmnxDhcpSvrPoolStatsFreePT indicates the sysUpTime at the
         last change of tmnxDhcpSvrPoolStatsFreeP."
    ::= { tmnxDhcpSvrPoolStatsEntry 28 }

tmnxDhcpSvrPoolStatsFoFreeP      OBJECT-TYPE
    SYNTAX      Counter32
    MAX-ACCESS  read-only
    STATUS      current
    DESCRIPTION
        "The value of tmnxDhcpSvrPoolStatsFoFreeP indicates the lowest value of
         unused subnets since the last reset of the extended statistics."
    ::= { tmnxDhcpSvrPoolStatsEntry 29 }

tmnxDhcpSvrPoolStatsFoFreePT     OBJECT-TYPE
    SYNTAX      TimeStamp
    MAX-ACCESS  read-only
    STATUS      current
    DESCRIPTION
        "The value of tmnxDhcpSvrPoolStatsFoFreePT indicates the sysUpTime at
         the last change of tmnxDhcpSvrPoolStatsFoFreeP."
    ::= { tmnxDhcpSvrPoolStatsEntry 30 }

tmnxDhcpSvrPoolStatsUsedPct      OBJECT-TYPE
    SYNTAX      Integer32 (0..100)
    MAX-ACCESS  read-only
    STATUS      current
    DESCRIPTION
        "The value of tmnxDhcpSvrPoolStatsUsedPct indicates the percentage of
         subnets currently in use."
    ::= { tmnxDhcpSvrPoolStatsEntry 31 }

tmnxDhcpSvrPoolStatsUsedPctP     OBJECT-TYPE
    SYNTAX      Integer32 (0..100)
    MAX-ACCESS  read-only
    STATUS      current
    DESCRIPTION
        "The value of tmnxDhcpSvrPoolStatsUsedPctP indicates the highest value
         of tmnxDhcpSvrPoolStatsUsedPct since the last reset of the extended
         statistics."
    ::= { tmnxDhcpSvrPoolStatsEntry 32 }

tmnxDhcpSvrPoolStatsUsedPctPT    OBJECT-TYPE
    SYNTAX      TimeStamp
    MAX-ACCESS  read-only
    STATUS      current
    DESCRIPTION
        "The value of tmnxDhcpSvrPoolStatsUsedPctPT indicates the sysUpTime at
         the last change of tmnxDhcpSvrPoolStatsUsedPctP."
    ::= { tmnxDhcpSvrPoolStatsEntry 33 }

tmnxDhcpSvrPoolStatsFoUsdPct     OBJECT-TYPE
    SYNTAX      Integer32 (0..100)
    MAX-ACCESS  read-only
    STATUS      current
    DESCRIPTION
        "The value of tmnxDhcpSvrPoolStatsFoUsdPct indicates the percentage of
         remote subnets currently in use."
    ::= { tmnxDhcpSvrPoolStatsEntry 34 }

tmnxDhcpSvrPoolStatsFoUsdPctP    OBJECT-TYPE
    SYNTAX      Integer32 (0..100)
    MAX-ACCESS  read-only
    STATUS      current
    DESCRIPTION
        "The value of tmnxDhcpSvrPoolStatsFoUsdPctP indicates the highest value
         of tmnxDhcpSvrPoolStatsFoUsdPct since the last reset of the extended
         statistics."
    ::= { tmnxDhcpSvrPoolStatsEntry 35 }

tmnxDhcpSvrPoolStatsFoUsdPctPT   OBJECT-TYPE
    SYNTAX      TimeStamp
    MAX-ACCESS  read-only
    STATUS      current
    DESCRIPTION
        "The value of tmnxDhcpSvrPoolStatsFoUsdPctPT indicates the sysUpTime at
         the last change of tmnxDhcpSvrPoolStatsFoUsdPctP."
    ::= { tmnxDhcpSvrPoolStatsEntry 36 }

tmnxDhcpSvrPoolStatsFreePct      OBJECT-TYPE
    SYNTAX      Integer32 (0..100)
    MAX-ACCESS  read-only
    STATUS      current
    DESCRIPTION
        "The value of tmnxDhcpSvrPoolStatsFreePct indicates the percentage of
         subnets currently unused."
    ::= { tmnxDhcpSvrPoolStatsEntry 37 }

tmnxDhcpSvrPoolStatsFreePctP     OBJECT-TYPE
    SYNTAX      Integer32 (0..100)
    MAX-ACCESS  read-only
    STATUS      current
    DESCRIPTION
        "The value of tmnxDhcpSvrPoolStatsFreePctP indicates the lowest value
         of tmnxDhcpSvrPoolStatsFreePct since the last reset of the extended
         statistics."
    ::= { tmnxDhcpSvrPoolStatsEntry 38 }

tmnxDhcpSvrPoolStatsFreePctPT    OBJECT-TYPE
    SYNTAX      TimeStamp
    MAX-ACCESS  read-only
    STATUS      current
    DESCRIPTION
        "The value of tmnxDhcpSvrPoolStatsFreePctPT indicates the sysUpTime at
         the last change of tmnxDhcpSvrPoolStatsFreePctP."
    ::= { tmnxDhcpSvrPoolStatsEntry 39 }

tmnxDhcpSvrPoolStatsFoFrePct     OBJECT-TYPE
    SYNTAX      Integer32 (0..100)
    MAX-ACCESS  read-only
    STATUS      current
    DESCRIPTION
        "The value of tmnxDhcpSvrPoolStatsFoFrePct indicates the percentage of
         remote subnets currently unused."
    ::= { tmnxDhcpSvrPoolStatsEntry 40 }

tmnxDhcpSvrPoolStatsFoFrePctP    OBJECT-TYPE
    SYNTAX      Integer32 (0..100)
    MAX-ACCESS  read-only
    STATUS      current
    DESCRIPTION
        "The value of tmnxDhcpSvrPoolStatsFoFrePctP indicates the lowest value
         of tmnxDhcpSvrPoolStatsFoFrePct since the last reset of the extended
         statistics."
    ::= { tmnxDhcpSvrPoolStatsEntry 41 }

tmnxDhcpSvrPoolStatsFoFrePctPT   OBJECT-TYPE
    SYNTAX      TimeStamp
    MAX-ACCESS  read-only
    STATUS      current
    DESCRIPTION
        "The value of tmnxDhcpSvrPoolStatsFoFrePctPT indicates the sysUpTime at
         the last change of tmnxDhcpSvrPoolStatsFoFrePctP."
    ::= { tmnxDhcpSvrPoolStatsEntry 42 }

tmnxDhcpSvrPoolStatsOfferP       OBJECT-TYPE
    SYNTAX      Counter32
    MAX-ACCESS  read-only
    STATUS      current
    DESCRIPTION
        "The value of tmnxDhcpSvrPoolStatsOfferP indicates the highest value of
         tmnxDhcpSvrPoolStatsOffered since the last reset of the extended
         statistics."
    ::= { tmnxDhcpSvrPoolStatsEntry 43 }

tmnxDhcpSvrPoolStatsOfferPT      OBJECT-TYPE
    SYNTAX      TimeStamp
    MAX-ACCESS  read-only
    STATUS      current
    DESCRIPTION
        "The value of tmnxDhcpSvrPoolStatsOfferPT indicates the sysUpTime at
         the last change of tmnxDhcpSvrPoolStatsOfferP."
    ::= { tmnxDhcpSvrPoolStatsEntry 44 }

tmnxDhcpSvrPoolStatsFoOfferP     OBJECT-TYPE
    SYNTAX      Counter32
    MAX-ACCESS  read-only
    STATUS      current
    DESCRIPTION
        "The value of tmnxDhcpSvrPoolStatsFoOfferP indicates the highest value
         of tmnxDhcpSvrPoolStatsFoOffered since the last reset of the extended
         statistics."
    ::= { tmnxDhcpSvrPoolStatsEntry 45 }

tmnxDhcpSvrPoolStatsFoOfferPT    OBJECT-TYPE
    SYNTAX      TimeStamp
    MAX-ACCESS  read-only
    STATUS      current
    DESCRIPTION
        "The value of tmnxDhcpSvrPoolStatsFoOfferPT indicates the sysUpTime at
         the last change of tmnxDhcpSvrPoolStatsFoOfferP."
    ::= { tmnxDhcpSvrPoolStatsEntry 46 }

tmnxDhcpServerDuidTableLastCh    OBJECT-TYPE
    SYNTAX      TimeStamp
    MAX-ACCESS  read-only
    STATUS      current
    DESCRIPTION
        "The value of the object tmnxDhcpServerDuidTableLastCh indicates the
         value of sysUpTime at the time of the last modification of an entry in
         the tmnxDhcpServerDuidTable."
    ::= { tmnxDhcpServerObjs 26 }

tmnxDhcpServerDuidTable          OBJECT-TYPE
    SYNTAX      SEQUENCE OF TmnxDhcpServerDuidEntry
    MAX-ACCESS  not-accessible
    STATUS      current
    DESCRIPTION
        "The table tmnxDhcpServerDuidTable contains objects to configure the
         DHCPv6 Unique Identifier (DUID)."
    ::= { tmnxDhcpServerObjs 27 }

tmnxDhcpServerDuidEntry          OBJECT-TYPE
    SYNTAX      TmnxDhcpServerDuidEntry
    MAX-ACCESS  not-accessible
    STATUS      current
    DESCRIPTION
        "Each row represents a DHCPv6 server instance running within a virtual
         router.

         Rows are created or removed automatically by the system.

         Changing this value while there are active leases in the server can
         cause renews/releases to fail, only on the following rebind everything
         becomes stable again.

         It is the responsibility of the operator to make sure that the server
         DUID is unique."
    INDEX       {
        vRtrID,
        IMPLIED tmnxDhcpServerCfgServerName
    }
    ::= { tmnxDhcpServerDuidTable 1 }

TmnxDhcpServerDuidEntry          ::= SEQUENCE
{
    tmnxDhcpServerDuidLastChanged    TimeStamp,
    tmnxDhcpServerDuidTypeCode       TmnxDhcpServerDUIDTypeCode,
    tmnxDhcpServerDuidEnNumber       Unsigned32,
    tmnxDhcpServerDuidEnIdData       OCTET STRING,
    tmnxDhcpServerDuidEnIdDataType   TmnxDhcpOptionType
}

tmnxDhcpServerDuidLastChanged    OBJECT-TYPE
    SYNTAX      TimeStamp
    MAX-ACCESS  read-only
    STATUS      current
    DESCRIPTION
        "The value of tmnxDhcpServerDuidLastChanged indicates the sysUpTime at
         the time of the last change of an entry in the
         tmnxDhcpServerDuidTable."
    ::= { tmnxDhcpServerDuidEntry 1 }

tmnxDhcpServerDuidTypeCode       OBJECT-TYPE
    SYNTAX      TmnxDhcpServerDUIDTypeCode
    MAX-ACCESS  read-create
    STATUS      current
    DESCRIPTION
        "The value of tmnxDhcpServerDuidTypeCode specifies the type code of the
         server DUID."
    REFERENCE
        "RFC 3315 paragraph 9.1"
    DEFVAL      { duidLinkLocal }
    ::= { tmnxDhcpServerDuidEntry 2 }

tmnxDhcpServerDuidEnNumber       OBJECT-TYPE
    SYNTAX      Unsigned32
    MAX-ACCESS  read-only
    STATUS      current
    DESCRIPTION
        "The value of tmnxDhcpServerDuidEnNumber indicates the
         enterprise-number. The enterprise-number is the vendor's registered
         Private Enterprise Number as maintained by IANA."
    REFERENCE
        "RFC 3315 paragraph 9.3"
    ::= { tmnxDhcpServerDuidEntry 3 }

tmnxDhcpServerDuidEnIdData       OBJECT-TYPE
    SYNTAX      OCTET STRING (SIZE (0..58))
    MAX-ACCESS  read-create
    STATUS      current
    DESCRIPTION
        "The value tmnxDhcpServerDuidEnIdData specifies the variable length
         identifier following the type code and enterprise-number."
    REFERENCE
        "RFC 3315 paragraph 9.3"
    DEFVAL      { "" }
    ::= { tmnxDhcpServerDuidEntry 4 }

tmnxDhcpServerDuidEnIdDataType   OBJECT-TYPE
    SYNTAX      TmnxDhcpOptionType
    MAX-ACCESS  read-create
    STATUS      current
    DESCRIPTION
        "The value tmnxDhcpServerDuidEnIdDataType specifies the type of
         tmnxDhcpServerDuidEnIdData."
    DEFVAL      { ascii }
    ::= { tmnxDhcpServerDuidEntry 5 }

tmnxDhcpsPoolStats6Table         OBJECT-TYPE
    SYNTAX      SEQUENCE OF TmnxDhcpsPoolStats6Entry
    MAX-ACCESS  not-accessible
    STATUS      current
    DESCRIPTION
        "The tmnxDhcpsPoolStats6Table has an entry for each pool that belongs
         to the specified DHCPv6 server instance."
    ::= { tmnxDhcpServerObjs 28 }

tmnxDhcpsPoolStats6Entry         OBJECT-TYPE
    SYNTAX      TmnxDhcpsPoolStats6Entry
    MAX-ACCESS  not-accessible
    STATUS      current
    DESCRIPTION
        "Each row entry in the tmnxDhcpsPoolStats6Table represents additional
         columns of operational data for a pool that belongs to the specified
         DHCPv6 server instance.

         The value of these columns is only relevant if the value of the object
         tmnxDhcpsFoAdminState of this server is equal to 'inService (2)'."
    INDEX       {
        vRtrID,
        tmnxDhcpServerCfgServerName,
        tmnxDhcpServerPoolName
    }
    ::= { tmnxDhcpsPoolStats6Table 1 }

TmnxDhcpsPoolStats6Entry         ::= SEQUENCE
{
    tmnxDhcpsPoolStats6Stable        Counter32,
    tmnxDhcpsPoolStats6FoStable      Counter32,
    tmnxDhcpsPoolStats6HasExt        TruthValue,
    tmnxDhcpsPoolStats6ExtResetT     TimeStamp,
    tmnxDhcpsPoolStats6StableP       Counter32,
    tmnxDhcpsPoolStats6StablePT      TimeStamp,
    tmnxDhcpsPoolStats6FoStableP     Counter32,
    tmnxDhcpsPoolStats6FoStablePT    TimeStamp,
    tmnxDhcpsPoolStats6ProvBlk       Counter64,
    tmnxDhcpsPoolStats6FoProvBlk     Counter64,
    tmnxDhcpsPoolStats6UsedBlk       Counter64,
    tmnxDhcpsPoolStats6UsedBlkP      Counter64,
    tmnxDhcpsPoolStats6UsedBlkPT     TimeStamp,
    tmnxDhcpsPoolStats6FoUsedBlk     Counter64,
    tmnxDhcpsPoolStats6FoUsedBlkP    Counter64,
    tmnxDhcpsPoolStats6FoUsedBlkPT   TimeStamp,
    tmnxDhcpsPoolStats6FreeBlk       Counter64,
    tmnxDhcpsPoolStats6FreeBlkP      Counter64,
    tmnxDhcpsPoolStats6FreeBlkPT     TimeStamp,
    tmnxDhcpsPoolStats6FoFreeBlk     Counter64,
    tmnxDhcpsPoolStats6FoFreeBlkP    Counter64,
    tmnxDhcpsPoolStats6FoFreeBlkPT   TimeStamp,
    tmnxDhcpsPoolStats6UsedPct       Integer32,
    tmnxDhcpsPoolStats6UsedPctP      Integer32,
    tmnxDhcpsPoolStats6UsedPctPT     TimeStamp,
    tmnxDhcpsPoolStats6FoUsedPct     Integer32,
    tmnxDhcpsPoolStats6FoUsedPctP    Integer32,
    tmnxDhcpsPoolStats6FoUsedPctPT   TimeStamp,
    tmnxDhcpsPoolStats6FreePct       Integer32,
    tmnxDhcpsPoolStats6FreePctP      Integer32,
    tmnxDhcpsPoolStats6FreePctPT     TimeStamp,
    tmnxDhcpsPoolStats6FoFreePct     Integer32,
    tmnxDhcpsPoolStats6FoFreePctP    Integer32,
    tmnxDhcpsPoolStats6FoFreePctPT   TimeStamp,
    tmnxDhcpsPoolStats6Advertise     Counter32,
    tmnxDhcpsPoolStats6AdvertP       Counter32,
    tmnxDhcpsPoolStats6AdvertPT      TimeStamp,
    tmnxDhcpsPoolStats6FoAdvertise   Counter32,
    tmnxDhcpsPoolStats6FoAdvertP     Counter32,
    tmnxDhcpsPoolStats6FoAdvertPT    TimeStamp,
    tmnxDhcpsPoolStats6IntNoPfxWan   Counter32,
    tmnxDhcpsPoolStats6IntNoPfxSlaa  Counter32
}

tmnxDhcpsPoolStats6Stable        OBJECT-TYPE
    SYNTAX      Counter32
    MAX-ACCESS  read-only
    STATUS      current
    DESCRIPTION
        "The value of tmnxDhcpsPoolStats6Stable indicates the number of leases
         in this pool that are in state 'stable'."
    ::= { tmnxDhcpsPoolStats6Entry 1 }

tmnxDhcpsPoolStats6FoStable      OBJECT-TYPE
    SYNTAX      Counter32
    MAX-ACCESS  read-only
    STATUS      current
    DESCRIPTION
        "The value of tmnxDhcpsPoolStats6FoStable indicates the number of
         remote leases in this pool that are in state 'stable'."
    ::= { tmnxDhcpsPoolStats6Entry 2 }

tmnxDhcpsPoolStats6HasExt        OBJECT-TYPE
    SYNTAX      TruthValue
    MAX-ACCESS  read-only
    STATUS      current
    DESCRIPTION
        "The value of tmnxDhcpsPoolStats6HasExt indicates whether the extended
         statistics collection for this prefix is enabled. These extended
         statistics are only collected when the length of the configured subnet
         is between /32 en /64."
    ::= { tmnxDhcpsPoolStats6Entry 3 }

tmnxDhcpsPoolStats6ExtResetT     OBJECT-TYPE
    SYNTAX      TimeStamp
    MAX-ACCESS  read-only
    STATUS      current
    DESCRIPTION
        "The value of tmnxDhcpsPoolStats6ExtResetT indicates the sysUpTime at
         the last reset of the extended statistics."
    ::= { tmnxDhcpsPoolStats6Entry 4 }

tmnxDhcpsPoolStats6StableP       OBJECT-TYPE
    SYNTAX      Counter32
    MAX-ACCESS  read-only
    STATUS      current
    DESCRIPTION
        "The value of tmnxDhcpsPoolStats6StableP indicates the highest value of
         tmnxDhcpsPoolStats6Stable since the last reset of the extended
         statistics."
    ::= { tmnxDhcpsPoolStats6Entry 5 }

tmnxDhcpsPoolStats6StablePT      OBJECT-TYPE
    SYNTAX      TimeStamp
    MAX-ACCESS  read-only
    STATUS      current
    DESCRIPTION
        "The value of tmnxDhcpsPoolStats6StablePT indicates the sysUpTime at
         the last change of tmnxDhcpsPoolStats6StableP."
    ::= { tmnxDhcpsPoolStats6Entry 6 }

tmnxDhcpsPoolStats6FoStableP     OBJECT-TYPE
    SYNTAX      Counter32
    MAX-ACCESS  read-only
    STATUS      current
    DESCRIPTION
        "The value of tmnxDhcpsPoolStats6FoStableP indicates the highest value
         of tmnxDhcpsPoolStats6FoStable since the last reset of the extended
         statistics."
    ::= { tmnxDhcpsPoolStats6Entry 7 }

tmnxDhcpsPoolStats6FoStablePT    OBJECT-TYPE
    SYNTAX      TimeStamp
    MAX-ACCESS  read-only
    STATUS      current
    DESCRIPTION
        "The value of tmnxDhcpsPoolStats6FoStablePT indicates the sysUpTime at
         the last change of tmnxDhcpsPoolStats6FoStableP."
    ::= { tmnxDhcpsPoolStats6Entry 8 }

tmnxDhcpsPoolStats6ProvBlk       OBJECT-TYPE
    SYNTAX      Counter64
    MAX-ACCESS  read-only
    STATUS      current
    DESCRIPTION
        "The value of tmnxDhcpsPoolStats6ProvBlk indicates the number of
         provisioned /64 blocks."
    ::= { tmnxDhcpsPoolStats6Entry 9 }

tmnxDhcpsPoolStats6FoProvBlk     OBJECT-TYPE
    SYNTAX      Counter64
    MAX-ACCESS  read-only
    STATUS      current
    DESCRIPTION
        "The value of tmnxDhcpsPoolStats6FoProvBlk indicates the remote number
         of provisioned /64 blocks."
    ::= { tmnxDhcpsPoolStats6Entry 10 }

tmnxDhcpsPoolStats6UsedBlk       OBJECT-TYPE
    SYNTAX      Counter64
    MAX-ACCESS  read-only
    STATUS      current
    DESCRIPTION
        "The value of tmnxDhcpsPoolStats6UsedBlk indicates the number of
         provisioned but unused /64 blocks."
    ::= { tmnxDhcpsPoolStats6Entry 11 }

tmnxDhcpsPoolStats6UsedBlkP      OBJECT-TYPE
    SYNTAX      Counter64
    MAX-ACCESS  read-only
    STATUS      current
    DESCRIPTION
        "The value of tmnxDhcpsPoolStats6UsedBlkP indicates the lowest value of
         tmnxDhcpsPoolStats6UsedBlk since the last reset of the extended
         statistics."
    ::= { tmnxDhcpsPoolStats6Entry 12 }

tmnxDhcpsPoolStats6UsedBlkPT     OBJECT-TYPE
    SYNTAX      TimeStamp
    MAX-ACCESS  read-only
    STATUS      current
    DESCRIPTION
        "The value of tmnxDhcpsPoolStats6UsedBlkPT indicates the sysUpTime at
         the last change of tmnxDhcpsPoolStats6UsedBlkP."
    ::= { tmnxDhcpsPoolStats6Entry 13 }

tmnxDhcpsPoolStats6FoUsedBlk     OBJECT-TYPE
    SYNTAX      Counter64
    MAX-ACCESS  read-only
    STATUS      current
    DESCRIPTION
        "The value of tmnxDhcpsPoolStats6FoUsedBlk indicates the remote number
         of provisioned but unused /64 blocks."
    ::= { tmnxDhcpsPoolStats6Entry 14 }

tmnxDhcpsPoolStats6FoUsedBlkP    OBJECT-TYPE
    SYNTAX      Counter64
    MAX-ACCESS  read-only
    STATUS      current
    DESCRIPTION
        "The value of tmnxDhcpsPoolStats6FoUsedBlkP indicates the lowest value
         of tmnxDhcpsPoolStats6FoUsedBlk since the last reset of the extended
         statistics."
    ::= { tmnxDhcpsPoolStats6Entry 15 }

tmnxDhcpsPoolStats6FoUsedBlkPT   OBJECT-TYPE
    SYNTAX      TimeStamp
    MAX-ACCESS  read-only
    STATUS      current
    DESCRIPTION
        "The value of tmnxDhcpsPoolStats6FoUsedBlkPT indicates the sysUpTime at
         the last change of tmnxDhcpsPoolStats6FoUsedBlkP."
    ::= { tmnxDhcpsPoolStats6Entry 16 }

tmnxDhcpsPoolStats6FreeBlk       OBJECT-TYPE
    SYNTAX      Counter64
    MAX-ACCESS  read-only
    STATUS      current
    DESCRIPTION
        "The value of tmnxDhcpsPoolStats6FreeBlk indicates the number of
         provisioned but unused /64 blocks."
    ::= { tmnxDhcpsPoolStats6Entry 17 }

tmnxDhcpsPoolStats6FreeBlkP      OBJECT-TYPE
    SYNTAX      Counter64
    MAX-ACCESS  read-only
    STATUS      current
    DESCRIPTION
        "The value of tmnxDhcpsPoolStats6FreeBlkP indicates the lowest value of
         tmnxDhcpsPoolStats6FreeBlk since the last reset of the extended
         statistics."
    ::= { tmnxDhcpsPoolStats6Entry 18 }

tmnxDhcpsPoolStats6FreeBlkPT     OBJECT-TYPE
    SYNTAX      TimeStamp
    MAX-ACCESS  read-only
    STATUS      current
    DESCRIPTION
        "The value of tmnxDhcpsPoolStats6FreeBlkPT indicates the sysUpTime at
         the last change of tmnxDhcpsPoolStats6FreeBlkP."
    ::= { tmnxDhcpsPoolStats6Entry 19 }

tmnxDhcpsPoolStats6FoFreeBlk     OBJECT-TYPE
    SYNTAX      Counter64
    MAX-ACCESS  read-only
    STATUS      current
    DESCRIPTION
        "The value of tmnxDhcpsPoolStats6FoFreeBlk indicates the remote number
         of provisioned but unused /64 blocks."
    ::= { tmnxDhcpsPoolStats6Entry 20 }

tmnxDhcpsPoolStats6FoFreeBlkP    OBJECT-TYPE
    SYNTAX      Counter64
    MAX-ACCESS  read-only
    STATUS      current
    DESCRIPTION
        "The value of tmnxDhcpsPoolStats6FoFreeBlkP indicates the lowest value
         of tmnxDhcpsPoolStats6FoFreeBlk since the last reset of the extended
         statistics."
    ::= { tmnxDhcpsPoolStats6Entry 21 }

tmnxDhcpsPoolStats6FoFreeBlkPT   OBJECT-TYPE
    SYNTAX      TimeStamp
    MAX-ACCESS  read-only
    STATUS      current
    DESCRIPTION
        "The value of tmnxDhcpsPoolStats6FoFreeBlkPT indicates the sysUpTime at
         the last change of tmnxDhcpsPoolStats6FoFreeBlkP."
    ::= { tmnxDhcpsPoolStats6Entry 22 }

tmnxDhcpsPoolStats6UsedPct       OBJECT-TYPE
    SYNTAX      Integer32 (0..100)
    MAX-ACCESS  read-only
    STATUS      current
    DESCRIPTION
        "The value of tmnxDhcpsPoolStats6UsedPct indicates the percentage of
         /64 blocks currently in use."
    ::= { tmnxDhcpsPoolStats6Entry 23 }

tmnxDhcpsPoolStats6UsedPctP      OBJECT-TYPE
    SYNTAX      Integer32 (0..100)
    MAX-ACCESS  read-only
    STATUS      current
    DESCRIPTION
        "The value of tmnxDhcpsPoolStats6UsedPctP indicates the highest value
         of tmnxDhcpsPoolStats6UsedPct since the last reset of the extended
         statistics."
    ::= { tmnxDhcpsPoolStats6Entry 24 }

tmnxDhcpsPoolStats6UsedPctPT     OBJECT-TYPE
    SYNTAX      TimeStamp
    MAX-ACCESS  read-only
    STATUS      current
    DESCRIPTION
        "The value of tmnxDhcpsPoolStats6UsedPctPT indicates the sysUpTime at
         the last change of tmnxDhcpsPoolStats6UsedPctP."
    ::= { tmnxDhcpsPoolStats6Entry 25 }

tmnxDhcpsPoolStats6FoUsedPct     OBJECT-TYPE
    SYNTAX      Integer32 (0..100)
    MAX-ACCESS  read-only
    STATUS      current
    DESCRIPTION
        "The value of tmnxDhcpsPoolStats6FoUsedPct indicates the percentage of
         remote /64 blocks currently in use."
    ::= { tmnxDhcpsPoolStats6Entry 26 }

tmnxDhcpsPoolStats6FoUsedPctP    OBJECT-TYPE
    SYNTAX      Integer32 (0..100)
    MAX-ACCESS  read-only
    STATUS      current
    DESCRIPTION
        "The value of tmnxDhcpsPoolStats6FoUsedPctP indicates the highest value
         of tmnxDhcpsPoolStats6FoUsedPct since the last reset of the extended
         statistics."
    ::= { tmnxDhcpsPoolStats6Entry 27 }

tmnxDhcpsPoolStats6FoUsedPctPT   OBJECT-TYPE
    SYNTAX      TimeStamp
    MAX-ACCESS  read-only
    STATUS      current
    DESCRIPTION
        "The value of tmnxDhcpsPoolStats6FoUsedPctPT indicates the sysUpTime at
         the last change of tmnxDhcpsPoolStats6FoUsedPctP."
    ::= { tmnxDhcpsPoolStats6Entry 28 }

tmnxDhcpsPoolStats6FreePct       OBJECT-TYPE
    SYNTAX      Integer32 (0..100)
    MAX-ACCESS  read-only
    STATUS      current
    DESCRIPTION
        "The value of tmnxDhcpsPoolStats6FreePct indicates the percentage of
         /64 blocks currently unused."
    ::= { tmnxDhcpsPoolStats6Entry 29 }

tmnxDhcpsPoolStats6FreePctP      OBJECT-TYPE
    SYNTAX      Integer32 (0..100)
    MAX-ACCESS  read-only
    STATUS      current
    DESCRIPTION
        "The value of tmnxDhcpsPoolStats6FreePctP indicates the lowest value of
         tmnxDhcpsPoolStats6FreePct since the last reset of the extended
         statistics."
    ::= { tmnxDhcpsPoolStats6Entry 30 }

tmnxDhcpsPoolStats6FreePctPT     OBJECT-TYPE
    SYNTAX      TimeStamp
    MAX-ACCESS  read-only
    STATUS      current
    DESCRIPTION
        "The value of tmnxDhcpsPoolStats6FreePctPT indicates the sysUpTime at
         the last change of tmnxDhcpsPoolStats6FreePctP."
    ::= { tmnxDhcpsPoolStats6Entry 31 }

tmnxDhcpsPoolStats6FoFreePct     OBJECT-TYPE
    SYNTAX      Integer32 (0..100)
    MAX-ACCESS  read-only
    STATUS      current
    DESCRIPTION
        "The value of tmnxDhcpsPoolStats6FoFreePct indicates the percentage of
         remote /64 blocks currently unused."
    ::= { tmnxDhcpsPoolStats6Entry 32 }

tmnxDhcpsPoolStats6FoFreePctP    OBJECT-TYPE
    SYNTAX      Integer32 (0..100)
    MAX-ACCESS  read-only
    STATUS      current
    DESCRIPTION
        "The value of tmnxDhcpsPoolStats6FoFreePctP indicates the lowest value
         of tmnxDhcpsPoolStats6FoFreePct since the last reset of the extended
         statistics."
    ::= { tmnxDhcpsPoolStats6Entry 33 }

tmnxDhcpsPoolStats6FoFreePctPT   OBJECT-TYPE
    SYNTAX      TimeStamp
    MAX-ACCESS  read-only
    STATUS      current
    DESCRIPTION
        "The value of tmnxDhcpsPoolStats6FoFreePctPT indicates the sysUpTime at
         the last change of tmnxDhcpsPoolStats6FoFreePctP."
    ::= { tmnxDhcpsPoolStats6Entry 34 }

tmnxDhcpsPoolStats6Advertise     OBJECT-TYPE
    SYNTAX      Counter32
    MAX-ACCESS  read-only
    STATUS      current
    DESCRIPTION
        "The value of tmnxDhcpsPoolStats6Advertise indicates the number of
         local leases in this pool that are in state 'advertised'."
    ::= { tmnxDhcpsPoolStats6Entry 35 }

tmnxDhcpsPoolStats6AdvertP       OBJECT-TYPE
    SYNTAX      Counter32
    MAX-ACCESS  read-only
    STATUS      current
    DESCRIPTION
        "The value of tmnxDhcpsPoolStats6AdvertP indicates the highest value of
         tmnxDhcpsPoolStats6Advertise since the last reset of the extended
         statistics."
    ::= { tmnxDhcpsPoolStats6Entry 36 }

tmnxDhcpsPoolStats6AdvertPT      OBJECT-TYPE
    SYNTAX      TimeStamp
    MAX-ACCESS  read-only
    STATUS      current
    DESCRIPTION
        "The value of tmnxDhcpsPoolStats6AdvertPT indicates the sysUpTime at
         the last change of tmnxDhcpsPoolStats6AdvertPT."
    ::= { tmnxDhcpsPoolStats6Entry 37 }

tmnxDhcpsPoolStats6FoAdvertise   OBJECT-TYPE
    SYNTAX      Counter32
    MAX-ACCESS  read-only
    STATUS      current
    DESCRIPTION
        "The value of tmnxDhcpsPoolStats6FoAdvertise indicates the number of
         remote leases in this pool that are in state 'advertised'."
    ::= { tmnxDhcpsPoolStats6Entry 38 }

tmnxDhcpsPoolStats6FoAdvertP     OBJECT-TYPE
    SYNTAX      Counter32
    MAX-ACCESS  read-only
    STATUS      current
    DESCRIPTION
        "The value of tmnxDhcpsPoolStats6FoAdvertP indicates the highest value
         of tmnxDhcpsPoolStats6FoAdvertise since the last reset of the extended
         statistics."
    ::= { tmnxDhcpsPoolStats6Entry 39 }

tmnxDhcpsPoolStats6FoAdvertPT    OBJECT-TYPE
    SYNTAX      TimeStamp
    MAX-ACCESS  read-only
    STATUS      current
    DESCRIPTION
        "The value of tmnxDhcpsPoolStats6FoAdvertPT indicates the sysUpTime at
         the last change of tmnxDhcpsPoolStats6FoAdvertP."
    ::= { tmnxDhcpsPoolStats6Entry 40 }

tmnxDhcpsPoolStats6IntNoPfxWan   OBJECT-TYPE
    SYNTAX      Counter32
    MAX-ACCESS  read-only
    STATUS      current
    DESCRIPTION
        "The value of tmnxDhcpsPoolStats6IntNoPfxWan indicates the number of
         times the following event occurred: an internal request for a WAN
         address (IA_NA (Identity association for non-temporary addresses))
         fails because the pool does not have a subnet available where the
         value of tmnxDhcpSvrSubnetPrefixType is equal to 'wan-host'.

         An internal request is triggered by some packet received by this
         system and translated into an internal API (Application Program
         Interface) request to the local DHCP server."
    ::= { tmnxDhcpsPoolStats6Entry 41 }

tmnxDhcpsPoolStats6IntNoPfxSlaa  OBJECT-TYPE
    SYNTAX      Counter32
    MAX-ACCESS  read-only
    STATUS      current
    DESCRIPTION
        "The value of tmnxDhcpsPoolStats6IntNoPfxSlaa indicates the number of
         times the following event occurred: an internal request for a SLAAC
         prefix (IA_PD (Identity Association for Prefix Delegation)) fails
         because the pool does not have a subnet available where the value of
         tmnxDhcpSvrSubnetPrefixType is equal to 'wan-host'.

         An internal request is triggered by some packet received by this
         system and translated into an internal API (Application Program
         Interface) request to the local DHCP server."
    ::= { tmnxDhcpsPoolStats6Entry 42 }

tmnxDhcpSvrSubnetBindingTable    OBJECT-TYPE
    SYNTAX      SEQUENCE OF TmnxDhcpSvrSubnetBindingEntry
    MAX-ACCESS  not-accessible
    STATUS      obsolete
    DESCRIPTION
        "The tmnxDhcpSvrSubnetBindingTable contains subnets that can be bound
         to an access node.

         A conceptual row in this table is created for each row in the
         tmnxDhcpServerSubnetTable that belongs to a pool where the value of
         tmnxDhcpServerPoolSubnetBindKey is different from 'none'"
    ::= { tmnxDhcpServerObjs 29 }

tmnxDhcpSvrSubnetBindingEntry    OBJECT-TYPE
    SYNTAX      TmnxDhcpSvrSubnetBindingEntry
    MAX-ACCESS  not-accessible
    STATUS      obsolete
    DESCRIPTION
        "Each row entry in the tmnxDhcpSvrSubnetBindingTable represents
         additional columns of operational data for a subnet that belongs to
         the specified DHCP server instance and pool and that can be bound to
         an access node."
    INDEX       {
        vRtrID,
        tmnxDhcpServerCfgServerName,
        tmnxDhcpServerPoolName,
        tmnxDhcpSvrSubnetAddrType,
        tmnxDhcpSvrSubnetAddress,
        tmnxDhcpSvrSubnetPrefixLength
    }
    ::= { tmnxDhcpSvrSubnetBindingTable 1 }

TmnxDhcpSvrSubnetBindingEntry    ::= SEQUENCE
{
    tmnxDhcpSvrSubnetBindSystemId    OCTET STRING,
    tmnxDhcpSvrSubnetBindServiceId   OCTET STRING,
    tmnxDhcpSvrSubnetBindString      OCTET STRING,
    tmnxDhcpSvrSubnetBindUnbindTime  Unsigned32,
    tmnxDhcpSvrSubnetBindActive      TruthValue,
    tmnxDhcpSvrSubnetBindState       INTEGER
}

tmnxDhcpSvrSubnetBindSystemId    OBJECT-TYPE
    SYNTAX      OCTET STRING (SIZE (0..255))
    MAX-ACCESS  read-only
    STATUS      obsolete
    DESCRIPTION
        "The value of the object tmnxDhcpSvrSubnetBindSystemId specifies the
         system-id provided by the access node to which this subnet is bound.

         The value of this object comes from the TIMETRA vendor specific
         sub-option 1 in the Option82 coming from the access node.

         This object is only relevant when tmnxDhcpServerPoolSubnetBindKey is
         set to sysIdSvcId (1) or sysId (2)."
    ::= { tmnxDhcpSvrSubnetBindingEntry 1 }

tmnxDhcpSvrSubnetBindServiceId   OBJECT-TYPE
    SYNTAX      OCTET STRING (SIZE (0..255))
    MAX-ACCESS  read-only
    STATUS      obsolete
    DESCRIPTION
        "The value of the object tmnxDhcpSvrSubnetBindServiceId specifies the
         service-id provided by the access node to which this subnet is bound.

         The value of this object comes from the TIMETRA vendor specific
         sub-option 3 in the Option82 coming from the access node.

         This object is only relevant when tmnxDhcpServerPoolSubnetBindKey is
         set to sysIdSvcId (1)."
    ::= { tmnxDhcpSvrSubnetBindingEntry 2 }

tmnxDhcpSvrSubnetBindString      OBJECT-TYPE
    SYNTAX      OCTET STRING (SIZE (0..255))
    MAX-ACCESS  read-only
    STATUS      obsolete
    DESCRIPTION
        "The value of the object tmnxDhcpSvrSubnetBindString specifies a string
         provided by the access node to which this subnet is bound.

         The value of this object comes from the TIMETRA vendor specific
         sub-option 5 in the Option82 coming from the access node.

         This object is only relevant when tmnxDhcpServerPoolSubnetBindKey is
         set to string (3)."
    ::= { tmnxDhcpSvrSubnetBindingEntry 3 }

tmnxDhcpSvrSubnetBindUnbindTime  OBJECT-TYPE
    SYNTAX      Unsigned32
    MAX-ACCESS  read-only
    STATUS      obsolete
    DESCRIPTION
        "The value of the object tmnxDhcpSvrSubnetBindUnbindTime indicates the
         time left before this binding expires.

         This time is only relevant after all lease of this subnet are
         released."
    ::= { tmnxDhcpSvrSubnetBindingEntry 4 }

tmnxDhcpSvrSubnetBindActive      OBJECT-TYPE
    SYNTAX      TruthValue
    MAX-ACCESS  read-only
    STATUS      obsolete
    DESCRIPTION
        "The value of the object tmnxDhcpSvrSubnetBindActive specifies whether
         this subnet has an active binding."
    DEFVAL      { false }
    ::= { tmnxDhcpSvrSubnetBindingEntry 5 }

tmnxDhcpSvrSubnetBindState       OBJECT-TYPE
    SYNTAX      INTEGER {
        notBound  (1),
        offered   (2),
        bound     (3),
        unbinding (4)
    }
    MAX-ACCESS  read-only
    STATUS      obsolete
    DESCRIPTION
        "The value of the object tmnxDhcpSvrSubnetBindState indicates the
         binding state of this subnet.

         'notBound'
             There is no active binding.

         'offered'
             The binding has been made, triggered by a DHCP DISCOVER message.
             It exists for the lifetime of the offered lease in the server,
             or can be made stable in case a REQUEST comes in and the binding
             becomes 'bound'.

         'bound'
             There is a stable lease for this binding.

         'unbinding'
             All clients abandoned the subnet and the binding is preserved for the
             interval of tmnxDhcpServerPoolSubnetBindDly; if during that period
             - a REQUEST comes in and a stable lease is created, then the binding becomes
             bound again;
             - a DISCOVER comes in, the state the state will not change; the timer
             started with tmnxDhcpServerPoolSubnetBindDly will keep running; when it expires,
             the binding will be removed and returns to the unbound state."
    ::= { tmnxDhcpSvrSubnetBindingEntry 6 }

tmnxDhcpSvrSubntBndngTbleLastCh  OBJECT-TYPE
    SYNTAX      TimeStamp
    MAX-ACCESS  read-only
    STATUS      obsolete
    DESCRIPTION
        "The value of the object tmnxDhcpSvrSubntBndngTbleLastCh indicates the
         value of sysUpTime at the time of the last modification of an entry in
         the tmnxDhcpSvrSubnetBindingTable."
    ::= { tmnxDhcpServerObjs 30 }

tmnxDhcpsPlMinFreeTableLastCh    OBJECT-TYPE
    SYNTAX      TimeStamp
    MAX-ACCESS  read-only
    STATUS      current
    DESCRIPTION
        "The value of the object tmnxDhcpsPlMinFreeTableLastCh indicates the
         value of sysUpTime at the time of the last modification of an entry in
         the tmnxDhcpsPlMinFreeTable."
    ::= { tmnxDhcpServerObjs 31 }

tmnxDhcpsPlMinFreeTable          OBJECT-TYPE
    SYNTAX      SEQUENCE OF TmnxDhcpsPlMinFreeEntry
    MAX-ACCESS  not-accessible
    STATUS      current
    DESCRIPTION
        "The table tmnxDhcpsPlMinFreeTable contains objects to configure a
         minimum number of free prefixes with a specified prefix length, per IP
         address pool.

         A conceptual row in this table can only be created for an IPv6 DHCP
         server (where the value of tmnxDhcpServerCfgAddrType is equal to
         'ipv6').

         This table is typically used to control the availability of prefixes
         of the prefix length(s) used for Prefix Delegation, as specified with
         the object tmnxDhcpServerPoolDlgatedPfxLen."
    ::= { tmnxDhcpServerObjs 32 }

tmnxDhcpsPlMinFreeEntry          OBJECT-TYPE
    SYNTAX      TmnxDhcpsPlMinFreeEntry
    MAX-ACCESS  not-accessible
    STATUS      current
    DESCRIPTION
        "Each row represents a category of IPv6 address prefixes with a given
         prefix length.

         Rows in this table can be created or deleted via SNMP operations.

         For the category of prefixes defined by this prefix length, this
         system maintains more detailed statistics, and issues a notification
         when the specified minimum is reached."
    INDEX       {
        vRtrID,
        tmnxDhcpServerCfgServerName,
        tmnxDhcpServerPoolName,
        tmnxDhcpsPlMinFreePrefixLen
    }
    ::= { tmnxDhcpsPlMinFreeTable 1 }

TmnxDhcpsPlMinFreeEntry          ::= SEQUENCE
{
    tmnxDhcpsPlMinFreePrefixLen      InetAddressPrefixLength,
    tmnxDhcpsPlMinFreeRowStatus      RowStatus,
    tmnxDhcpsPlMinFreeLastCh         TimeStamp,
    tmnxDhcpsPlMinFreePercent        Unsigned32,
    tmnxDhcpsPlMinFreeDepletedEvent  TruthValue
}

tmnxDhcpsPlMinFreePrefixLen      OBJECT-TYPE
    SYNTAX      InetAddressPrefixLength (1..128)
    MAX-ACCESS  not-accessible
    STATUS      current
    DESCRIPTION
        "The value of the object tmnxDhcpsPlMinFreePrefixLen specifies the
         length of the prefix."
    ::= { tmnxDhcpsPlMinFreeEntry 1 }

tmnxDhcpsPlMinFreeRowStatus      OBJECT-TYPE
    SYNTAX      RowStatus
    MAX-ACCESS  read-create
    STATUS      current
    DESCRIPTION
        "The value of the object tmnxDhcpsPlMinFreeRowStatus specifies the row
         status of this row."
    ::= { tmnxDhcpsPlMinFreeEntry 2 }

tmnxDhcpsPlMinFreeLastCh         OBJECT-TYPE
    SYNTAX      TimeStamp
    MAX-ACCESS  read-only
    STATUS      current
    DESCRIPTION
        "The value of the object tmnxDhcpsPlMinFreeLastCh indicates the
         sysUpTime at the time of the last modification of this row."
    ::= { tmnxDhcpsPlMinFreeEntry 3 }

tmnxDhcpsPlMinFreePercent        OBJECT-TYPE
    SYNTAX      Unsigned32 (0..100)
    UNITS       "percent"
    MAX-ACCESS  read-create
    STATUS      current
    DESCRIPTION
        "The value of the object tmnxDhcpsPlMinFreePercent specifies the
         desired minimum ratio of free prefixes with the prefix length equal to
         tmnxDhcpsPlMinFreePrefixLen."
    DEFVAL      { 0 }
    ::= { tmnxDhcpsPlMinFreeEntry 4 }

tmnxDhcpsPlMinFreeDepletedEvent  OBJECT-TYPE
    SYNTAX      TruthValue
    MAX-ACCESS  read-create
    STATUS      current
    DESCRIPTION
        "The value of the object tmnxDhcpsPlMinFreeDepletedEvent specifies
         whether a notification is also generated when this pool no more free
         prefixes with a given prefix length.

         When the value of this object is set to 'true(1)', the notification
         tmnxDhcpSvrPoolDepleted is generated."
    DEFVAL      { false }
    ::= { tmnxDhcpsPlMinFreeEntry 5 }

tmnxDhcpsPfxMinFreeTableLastCh   OBJECT-TYPE
    SYNTAX      TimeStamp
    MAX-ACCESS  read-only
    STATUS      current
    DESCRIPTION
        "The value of the object tmnxDhcpsPfxMinFreeTableLastCh indicates the
         value of sysUpTime at the time of the last modification of an entry in
         the tmnxDhcpsPfxMinFreeTable."
    ::= { tmnxDhcpServerObjs 33 }

tmnxDhcpsPfxMinFreeTable         OBJECT-TYPE
    SYNTAX      SEQUENCE OF TmnxDhcpsPfxMinFreeEntry
    MAX-ACCESS  not-accessible
    STATUS      current
    DESCRIPTION
        "The table tmnxDhcpsPfxMinFreeTable contains objects to configure a
         minimum number of free prefixes with a specified prefix length, per
         configured prefix (row in the tmnxDhcpServerSubnetTable of an IPv6
         server).

         A conceptual row in this table can only be created for an IPv6 DHCP
         server (where the value of tmnxDhcpServerCfgAddrType is equal to
         'ipv6').

         This table is typically used to control the availability of prefixes
         of the prefix length(s) used for Prefix Delegation, as specified with
         the object tmnxDhcpServerPoolDlgatedPfxLen."
    ::= { tmnxDhcpServerObjs 34 }

tmnxDhcpsPfxMinFreeEntry         OBJECT-TYPE
    SYNTAX      TmnxDhcpsPfxMinFreeEntry
    MAX-ACCESS  not-accessible
    STATUS      current
    DESCRIPTION
        "Each row represents a category of IPv6 address prefixes with a given
         prefix length.

         Rows in this table can be created or deleted via SNMP operations.

         For the prefix category defined by this prefix length, this system
         maintains more detailed statistics, and issues a notification when the
         specified minimum level of free prefixes is reached."
    INDEX       {
        vRtrID,
        tmnxDhcpServerCfgServerName,
        tmnxDhcpServerPoolName,
        tmnxDhcpSvrSubnetAddrType,
        tmnxDhcpSvrSubnetAddress,
        tmnxDhcpSvrSubnetPrefixLength,
        tmnxDhcpsPfxMinFreePrefixLen
    }
    ::= { tmnxDhcpsPfxMinFreeTable 1 }

TmnxDhcpsPfxMinFreeEntry         ::= SEQUENCE
{
    tmnxDhcpsPfxMinFreePrefixLen     InetAddressPrefixLength,
    tmnxDhcpsPfxMinFreeRowStatus     RowStatus,
    tmnxDhcpsPfxMinFreeLastCh        TimeStamp,
    tmnxDhcpsPfxMinFreePercent       Unsigned32,
    tmnxDhcpsPfxMinFreeNumber        Unsigned32,
    tmnxDhcpsPfxMinFreeDepletedEvent TruthValue
}

tmnxDhcpsPfxMinFreePrefixLen     OBJECT-TYPE
    SYNTAX      InetAddressPrefixLength (1..128)
    MAX-ACCESS  not-accessible
    STATUS      current
    DESCRIPTION
        "The value of the object tmnxDhcpsPfxMinFreePrefixLen specifies the
         length of the prefix."
    ::= { tmnxDhcpsPfxMinFreeEntry 1 }

tmnxDhcpsPfxMinFreeRowStatus     OBJECT-TYPE
    SYNTAX      RowStatus
    MAX-ACCESS  read-create
    STATUS      current
    DESCRIPTION
        "The value of the object tmnxDhcpsPfxMinFreeRowStatus specifies the row
         status of this row."
    ::= { tmnxDhcpsPfxMinFreeEntry 2 }

tmnxDhcpsPfxMinFreeLastCh        OBJECT-TYPE
    SYNTAX      TimeStamp
    MAX-ACCESS  read-only
    STATUS      current
    DESCRIPTION
        "The value of the object tmnxDhcpsPfxMinFreeLastCh indicates the
         sysUpTime at the time of the last modification of this row."
    ::= { tmnxDhcpsPfxMinFreeEntry 3 }

tmnxDhcpsPfxMinFreePercent       OBJECT-TYPE
    SYNTAX      Unsigned32 (0..100)
    UNITS       "percent"
    MAX-ACCESS  read-create
    STATUS      current
    DESCRIPTION
        "The value of the object tmnxDhcpsPfxMinFreePercent specifies the
         desired minimum ratio of free prefixes with the prefix length equal to
         tmnxDhcpsPfxMinFreePrefixLen.

         While the value of tmnxDhcpsPfxMinFreeNumber is not zero, the value of
         tmnxDhcpsPfxMinFreePercent must be zero."
    DEFVAL      { 0 }
    ::= { tmnxDhcpsPfxMinFreeEntry 4 }

tmnxDhcpsPfxMinFreeNumber        OBJECT-TYPE
    SYNTAX      Unsigned32
    MAX-ACCESS  read-create
    STATUS      current
    DESCRIPTION
        "The value of the object tmnxDhcpsPfxMinFreeNumber specifies the
         desired minimum number of free prefixes with the prefix length equal
         to tmnxDhcpsPfxMinFreePrefixLen.

         While the value of tmnxDhcpsPfxMinFreePercent is not zero, the value
         of tmnxDhcpsPfxMinFreeNumber must be zero."
    DEFVAL      { 0 }
    ::= { tmnxDhcpsPfxMinFreeEntry 5 }

tmnxDhcpsPfxMinFreeDepletedEvent OBJECT-TYPE
    SYNTAX      TruthValue
    MAX-ACCESS  read-create
    STATUS      current
    DESCRIPTION
        "The value of the object tmnxDhcpsPfxMinFreeDepletedEvent specifies if
         a notification is also generated when this pool has no more free
         prefixes with a given prefix length.

         When the value of this object is set to 'true(1)', the notification
         tmnxDhcpSvrPoolDepleted is generated."
    DEFVAL      { false }
    ::= { tmnxDhcpsPfxMinFreeEntry 6 }

tmnxDhcpsPlThStats6TableLastCh   OBJECT-TYPE
    SYNTAX      TimeStamp
    MAX-ACCESS  read-only
    STATUS      current
    DESCRIPTION
        "The value of the object tmnxDhcpsPlThStats6TableLastCh indicates the
         value of sysUpTime at the time of the last modification of an entry in
         the tmnxDhcpsPlThStats6Table."
    ::= { tmnxDhcpServerObjs 35 }

tmnxDhcpsPlThStats6Table         OBJECT-TYPE
    SYNTAX      SEQUENCE OF TmnxDhcpsPlThStats6Entry
    MAX-ACCESS  not-accessible
    STATUS      current
    DESCRIPTION
        "The table tmnxDhcpsPlThStats6Table contains the threshold statistics
         for each pool belonging to the specified DHCPv6 instance."
    ::= { tmnxDhcpServerObjs 36 }

tmnxDhcpsPlThStats6Entry         OBJECT-TYPE
    SYNTAX      TmnxDhcpsPlThStats6Entry
    MAX-ACCESS  not-accessible
    STATUS      current
    DESCRIPTION
        "Each row entry in the tmnxDhcpsPlThStats6Entry represents additional
         columns of threshold statistics for a pool that belongs to the
         specified DHCPv6 server instance."
    INDEX       {
        vRtrID,
        tmnxDhcpServerCfgServerName,
        tmnxDhcpServerPoolName,
        tmnxDhcpsPlMinFreePrefixLen
    }
    ::= { tmnxDhcpsPlThStats6Table 1 }

TmnxDhcpsPlThStats6Entry         ::= SEQUENCE
{
    tmnxDhcpsPlThCurrProvBlksHw      Counter64,
    tmnxDhcpsPlThCurrProvBlksLw      Counter64,
    tmnxDhcpsPlThCurrUsedBlksHw      Counter64,
    tmnxDhcpsPlThCurrUsedBlksLw      Counter64,
    tmnxDhcpsPlThCurrFreeBlksHw      Counter64,
    tmnxDhcpsPlThCurrFreeBlksLw      Counter64,
    tmnxDhcpsPlThCurrUsedPct         Counter32,
    tmnxDhcpsPlThCurrUsedPeakBlksHw  Counter64,
    tmnxDhcpsPlThCurrUsedPeakBlksLw  Counter64,
    tmnxDhcpsPlThCurrUsedPeakPct     Counter32,
    tmnxDhcpsPlThCurrUsedPeakTime    Counter32,
    tmnxDhcpsPlThCurrFreePct         Counter32,
    tmnxDhcpsPlThCurrFreeTooLow      TruthValue,
    tmnxDhcpsPlThCurrFreeDepleted    TruthValue,
    tmnxDhcpsPlThLclProvBlksHw       Counter64,
    tmnxDhcpsPlThLclProvBlksLw       Counter64,
    tmnxDhcpsPlThLclUsedBlksHw       Counter64,
    tmnxDhcpsPlThLclUsedBlksLw       Counter64,
    tmnxDhcpsPlThLclFreeBlksHw       Counter64,
    tmnxDhcpsPlThLclFreeBlksLw       Counter64,
    tmnxDhcpsPlThLclUsedPeakBlksHw   Counter64,
    tmnxDhcpsPlThLclUsedPeakBlksLw   Counter64,
    tmnxDhcpsPlThLclUsedPeakPct      Counter32,
    tmnxDhcpsPlThLclUsedPeakTime     Counter32,
    tmnxDhcpsPlThRemProvBlksHw       Counter64,
    tmnxDhcpsPlThRemProvBlksLw       Counter64,
    tmnxDhcpsPlThRemUsedBlksHw       Counter64,
    tmnxDhcpsPlThRemUsedBlksLw       Counter64,
    tmnxDhcpsPlThRemFreeBlksHw       Counter64,
    tmnxDhcpsPlThRemFreeBlksLw       Counter64,
    tmnxDhcpsPlThRemUsedPeakBlksHw   Counter64,
    tmnxDhcpsPlThRemUsedPeakBlksLw   Counter64,
    tmnxDhcpsPlThRemUsedPeakPct      Counter32,
    tmnxDhcpsPlThRemUsedPeakTime     Counter32,
    tmnxDhcpsPlThPeakResetTime       Counter32,
    tmnxDhcpsPlThValidData           TruthValue
}

tmnxDhcpsPlThCurrProvBlksHw      OBJECT-TYPE
    SYNTAX      Counter64
    MAX-ACCESS  read-only
    STATUS      current
    DESCRIPTION
        "The value of the object tmnxDhcpsPlThCurrProvBlksHw indicates the
         higher 64-bits word of the number of provisioned blocks in this pool
         with a prefix length defined by the value of
         tmnxDhcpsPlMinFreePrefixLen.

         The value of this object reflects the part of the address space in
         this pool that is actually in use by this server instance.

         If the value of the object tmnxDhcpsFoAdminState of this server is
         equal to 'inService (2)' and the value of the object tmnxDhcpsFoState
         of this server is equal to 'partnerDown (5)', or the value of the
         object tmnxDhcpsPoolFoAdminState of this pool is equal to 'inService
         (2)' and the value of the object tmnxDhcpsPoolFoState of this pool is
         equal to 'partnerDown (5)', the value of this object is the sum of the
         corresponding local and remote objects. Otherwise the value of this
         object equals the value of corresponding local object only."
    ::= { tmnxDhcpsPlThStats6Entry 1 }

tmnxDhcpsPlThCurrProvBlksLw      OBJECT-TYPE
    SYNTAX      Counter64
    MAX-ACCESS  read-only
    STATUS      current
    DESCRIPTION
        "The value of the object tmnxDhcpsPlThCurrProvBlksLw indicates the
         lower 64-bits word of the number of provisioned blocks in this pool
         with a prefix length defined by the value of
         tmnxDhcpsPlMinFreePrefixLen.

         The value of this object reflects the part of the address space in
         this pool that is actually in use by this server instance.

         If the value of the object tmnxDhcpsFoAdminState of this server is
         equal to 'inService (2)' and the value of the object tmnxDhcpsFoState
         of this server is equal to 'partnerDown (5)', or the value of the
         object tmnxDhcpsPoolFoAdminState of this pool is equal to 'inService
         (2)' and the value of the object tmnxDhcpsPoolFoState of this pool is
         equal to 'partnerDown (5)', the value of this object is the sum of the
         corresponding local and remote objects. Otherwise the value of this
         object equals the value of corresponding local object only."
    ::= { tmnxDhcpsPlThStats6Entry 2 }

tmnxDhcpsPlThCurrUsedBlksHw      OBJECT-TYPE
    SYNTAX      Counter64
    MAX-ACCESS  read-only
    STATUS      current
    DESCRIPTION
        "The value of the object tmnxDhcpsPlThCurrUsedBlksHw indicates the
         higher 64-bits word of the number of used blocks in this pool with a
         prefix length defined by the value of tmnxDhcpsPlMinFreePrefixLen.

         The value of this object reflects the part of the address space in
         this pool that is actually in use by this server instance.

         If the value of the object tmnxDhcpsFoAdminState of this server is
         equal to 'inService (2)' and the value of the object tmnxDhcpsFoState
         of this server is equal to 'partnerDown (5)', or the value of the
         object tmnxDhcpsPoolFoAdminState of this pool is equal to 'inService
         (2)' and the value of the object tmnxDhcpsPoolFoState of this pool is
         equal to 'partnerDown (5)', the value of this object is the sum of the
         corresponding local and remote objects. Otherwise the value of this
         object equals the value of corresponding local object only."
    ::= { tmnxDhcpsPlThStats6Entry 3 }

tmnxDhcpsPlThCurrUsedBlksLw      OBJECT-TYPE
    SYNTAX      Counter64
    MAX-ACCESS  read-only
    STATUS      current
    DESCRIPTION
        "The value of the object tmnxDhcpsPlThCurrUsedBlksLw indicates the
         lower 64-bits word of the number of used blocks in this pool with a
         prefix length defined by the value of tmnxDhcpsPlMinFreePrefixLen.

         The value of this object reflects the part of the address space in
         this pool that is actually in use by this server instance.

         If the value of the object tmnxDhcpsFoAdminState of this server is
         equal to 'inService (2)' and the value of the object tmnxDhcpsFoState
         of this server is equal to 'partnerDown (5)', or the value of the
         object tmnxDhcpsPoolFoAdminState of this pool is equal to 'inService
         (2)' and the value of the object tmnxDhcpsPoolFoState of this pool is
         equal to 'partnerDown (5)', the value of this object is the sum of the
         corresponding local and remote objects. Otherwise the value of this
         object equals the value of corresponding local object only."
    ::= { tmnxDhcpsPlThStats6Entry 4 }

tmnxDhcpsPlThCurrFreeBlksHw      OBJECT-TYPE
    SYNTAX      Counter64
    MAX-ACCESS  read-only
    STATUS      current
    DESCRIPTION
        "The value of the object tmnxDhcpsPlThCurrFreeBlksHw indicates the
         higher 64-bits word of the number of free blocks in this pool with a
         prefix length defined by the value of tmnxDhcpsPlMinFreePrefixLen.

         The value of this object reflects the part of the address space in
         this pool that is actually in use by this server instance.

         If the value of the object tmnxDhcpsFoAdminState of this server is
         equal to 'inService (2)' and the value of the object tmnxDhcpsFoState
         of this server is equal to 'partnerDown (5)', or the value of the
         object tmnxDhcpsPoolFoAdminState of this pool is equal to 'inService
         (2)' and the value of the object tmnxDhcpsPoolFoState of this pool is
         equal to 'partnerDown (5)', the value of this object is the sum of the
         corresponding local and remote objects. Otherwise the value of this
         object equals the value of corresponding local object only."
    ::= { tmnxDhcpsPlThStats6Entry 5 }

tmnxDhcpsPlThCurrFreeBlksLw      OBJECT-TYPE
    SYNTAX      Counter64
    MAX-ACCESS  read-only
    STATUS      current
    DESCRIPTION
        "The value of the object tmnxDhcpsPlThCurrFreeBlksLw indicates the
         lower 64-bits word of the number of used blocks in this pool with a
         prefix length defined by the value of tmnxDhcpsPlMinFreePrefixLen.

         The value of this object reflects the part of the address space in
         this pool that is actually in use by this server instance.

         If the value of the object tmnxDhcpsFoAdminState of this server is
         equal to 'inService (2)' and the value of the object tmnxDhcpsFoState
         of this server is equal to 'partnerDown (5)', or the value of the
         object tmnxDhcpsPoolFoAdminState of this pool is equal to 'inService
         (2)' and the value of the object tmnxDhcpsPoolFoState of this pool is
         equal to 'partnerDown (5)', the value of this object is the sum of the
         corresponding local and remote objects. Otherwise the value of this
         object equals the value of corresponding local object only."
    ::= { tmnxDhcpsPlThStats6Entry 6 }

tmnxDhcpsPlThCurrUsedPct         OBJECT-TYPE
    SYNTAX      Counter32
    MAX-ACCESS  read-only
    STATUS      current
    DESCRIPTION
        "The value of the object tmnxDhcpsPlThCurrUsedPct indicates the
         percentage of used prefixes with the minimum free threshold length in
         the pool compared to the number of provisioned prefixes. This depends
         on the current failover state of the DHCP server or pool."
    ::= { tmnxDhcpsPlThStats6Entry 7 }

tmnxDhcpsPlThCurrUsedPeakBlksHw  OBJECT-TYPE
    SYNTAX      Counter64
    MAX-ACCESS  read-only
    STATUS      current
    DESCRIPTION
        "The value of the object tmnxDhcpsPlThCurrUsedPeakBlksHw indicates the
         higher 64-bits word of the peak value of the number of used blocks in
         the pool with a prefix length defined by the value of
         tmnxDhcpsPlMinFreePrefixLen."
    ::= { tmnxDhcpsPlThStats6Entry 8 }

tmnxDhcpsPlThCurrUsedPeakBlksLw  OBJECT-TYPE
    SYNTAX      Counter64
    MAX-ACCESS  read-only
    STATUS      current
    DESCRIPTION
        "The value of the object tmnxDhcpsPlThCurrUsedPeakBlksLw indicates the
         lower 64-bits word of the peak value of the number of used blocks in
         the pool with a prefix length defined by the value of
         tmnxDhcpsPlMinFreePrefixLen."
    ::= { tmnxDhcpsPlThStats6Entry 9 }

tmnxDhcpsPlThCurrUsedPeakPct     OBJECT-TYPE
    SYNTAX      Counter32
    MAX-ACCESS  read-only
    STATUS      current
    DESCRIPTION
        "The value of the object tmnxDhcpsPlThCurrUsedPeakPct indicates the
         peak value of the number of used prefixes with the minimum free
         threshold length in the pool as a percentage of the provisioned
         prefixes. This depends on the current failover state of the DHCP
         server or pool."
    ::= { tmnxDhcpsPlThStats6Entry 10 }

tmnxDhcpsPlThCurrUsedPeakTime    OBJECT-TYPE
    SYNTAX      Counter32
    MAX-ACCESS  read-only
    STATUS      current
    DESCRIPTION
        "The value of the object tmnxDhcpsPlThCurrUsedPeakTime indicates the
         time at which the peak value of the number of used prefixes in the
         pool was reached."
    ::= { tmnxDhcpsPlThStats6Entry 11 }

tmnxDhcpsPlThCurrFreePct         OBJECT-TYPE
    SYNTAX      Counter32
    MAX-ACCESS  read-only
    STATUS      current
    DESCRIPTION
        "The value of the object tmnxDhcpsPlThCurrFreePct indicates the
         percentage of free prefixes with the minimum free threshold length in
         the pool compared to the number of provisioned prefixes. This depends
         on the current failover state of the DHCP server or pool."
    ::= { tmnxDhcpsPlThStats6Entry 12 }

tmnxDhcpsPlThCurrFreeTooLow      OBJECT-TYPE
    SYNTAX      TruthValue
    MAX-ACCESS  read-only
    STATUS      current
    DESCRIPTION
        "The value of the object tmnxDhcpsPlThCurrFreeTooLow equals '1' if the
         number of free prefixes with the minimum free threshold length
         available in the pool is below the configured number of prefixes with
         the minimum free threshold length. Otherwise the value equals '2'."
    ::= { tmnxDhcpsPlThStats6Entry 13 }

tmnxDhcpsPlThCurrFreeDepleted    OBJECT-TYPE
    SYNTAX      TruthValue
    MAX-ACCESS  read-only
    STATUS      current
    DESCRIPTION
        "The value of the object tmnxDhcpsPlThCurrFreeDepleted equals '1' if
         there are no more prefixes with the minimum free threshold length
         available in the pool. Otherwise the value equals '2'."
    ::= { tmnxDhcpsPlThStats6Entry 14 }

tmnxDhcpsPlThLclProvBlksHw       OBJECT-TYPE
    SYNTAX      Counter64
    MAX-ACCESS  read-only
    STATUS      current
    DESCRIPTION
        "The value of the object tmnxDhcpsPlThLclProvBlksHw indicates the
         higher 64-bits word of the number of provisioned prefixes with the
         minimum free threshold length local in the pool."
    ::= { tmnxDhcpsPlThStats6Entry 15 }

tmnxDhcpsPlThLclProvBlksLw       OBJECT-TYPE
    SYNTAX      Counter64
    MAX-ACCESS  read-only
    STATUS      current
    DESCRIPTION
        "The value of the object tmnxDhcpsPlThLclProvBlksLw indicates the lower
         64-bits word of the number of provisioned prefixes with the minimum
         free threshold length local in the pool."
    ::= { tmnxDhcpsPlThStats6Entry 16 }

tmnxDhcpsPlThLclUsedBlksHw       OBJECT-TYPE
    SYNTAX      Counter64
    MAX-ACCESS  read-only
    STATUS      current
    DESCRIPTION
        "The value of the object tmnxDhcpsPlThLclUsedBlksHw indicates the
         higher 64-bits word of the number of used prefixes with the minimum
         free threshold length local in the pool."
    ::= { tmnxDhcpsPlThStats6Entry 17 }

tmnxDhcpsPlThLclUsedBlksLw       OBJECT-TYPE
    SYNTAX      Counter64
    MAX-ACCESS  read-only
    STATUS      current
    DESCRIPTION
        "The value of the object tmnxDhcpsPlThLclUsedBlksLw indicates the lower
         64-bits word of the number of used prefixes with the minimum free
         threshold length local in the pool."
    ::= { tmnxDhcpsPlThStats6Entry 18 }

tmnxDhcpsPlThLclFreeBlksHw       OBJECT-TYPE
    SYNTAX      Counter64
    MAX-ACCESS  read-only
    STATUS      current
    DESCRIPTION
        "The value of the object tmnxDhcpsPlThLclFreeBlksHw indicates the
         higher 64-bits word of the number of free prefixes with the minimum
         free threshold length local in the pool."
    ::= { tmnxDhcpsPlThStats6Entry 19 }

tmnxDhcpsPlThLclFreeBlksLw       OBJECT-TYPE
    SYNTAX      Counter64
    MAX-ACCESS  read-only
    STATUS      current
    DESCRIPTION
        "The value of the object tmnxDhcpsPlThLclFreeBlksLw indicates the lower
         64-bits word of the number of free prefixes with the minimum free
         threshold length local in the pool."
    ::= { tmnxDhcpsPlThStats6Entry 20 }

tmnxDhcpsPlThLclUsedPeakBlksHw   OBJECT-TYPE
    SYNTAX      Counter64
    MAX-ACCESS  read-only
    STATUS      current
    DESCRIPTION
        "The value of the object tmnxDhcpsPlThLclUsedPeakBlksHw indicates the
         higher 64-bits word of the peak value of the number of used prefixes
         with the minimum free threshold length local in the pool."
    ::= { tmnxDhcpsPlThStats6Entry 21 }

tmnxDhcpsPlThLclUsedPeakBlksLw   OBJECT-TYPE
    SYNTAX      Counter64
    MAX-ACCESS  read-only
    STATUS      current
    DESCRIPTION
        "The value of the object tmnxDhcpsPlThLclUsedPeakBlksLw indicates the
         lower 64-bits word of the peak value of the number of used prefixes
         with the minimum free threshold length local in the pool."
    ::= { tmnxDhcpsPlThStats6Entry 22 }

tmnxDhcpsPlThLclUsedPeakPct      OBJECT-TYPE
    SYNTAX      Counter32
    MAX-ACCESS  read-only
    STATUS      current
    DESCRIPTION
        "The value of the object tmnxDhcpsPlThLclUsedPeakPct indicates the peak
         value of the number of used prefixes with the minimum free threshold
         length local in the pool as a percentage of the provisioned prefixes."
    ::= { tmnxDhcpsPlThStats6Entry 23 }

tmnxDhcpsPlThLclUsedPeakTime     OBJECT-TYPE
    SYNTAX      Counter32
    MAX-ACCESS  read-only
    STATUS      current
    DESCRIPTION
        "The value of the object tmnxDhcpsPlThLclUsedPeakTime indicates the
         time at which the peak value of the number of used prefixes local in
         the pool was reached."
    ::= { tmnxDhcpsPlThStats6Entry 24 }

tmnxDhcpsPlThRemProvBlksHw       OBJECT-TYPE
    SYNTAX      Counter64
    MAX-ACCESS  read-only
    STATUS      current
    DESCRIPTION
        "The value of the object tmnxDhcpsPlThRemProvBlksHw indicates the
         higher 64-bits word of the number of provisioned prefixes with the
         minimum free threshold length remote in the pool."
    ::= { tmnxDhcpsPlThStats6Entry 25 }

tmnxDhcpsPlThRemProvBlksLw       OBJECT-TYPE
    SYNTAX      Counter64
    MAX-ACCESS  read-only
    STATUS      current
    DESCRIPTION
        "The value of the object tmnxDhcpsPlThRemProvBlksLw indicates the lower
         64-bits word of the number of provisioned prefixes with the minimum
         free threshold length remote in the pool."
    ::= { tmnxDhcpsPlThStats6Entry 26 }

tmnxDhcpsPlThRemUsedBlksHw       OBJECT-TYPE
    SYNTAX      Counter64
    MAX-ACCESS  read-only
    STATUS      current
    DESCRIPTION
        "The value of the object tmnxDhcpsPlThRemUsedBlksHw indicates the
         higher 64-bits word of the number of used prefixes with the minimum
         free threshold length remote in the pool."
    ::= { tmnxDhcpsPlThStats6Entry 27 }

tmnxDhcpsPlThRemUsedBlksLw       OBJECT-TYPE
    SYNTAX      Counter64
    MAX-ACCESS  read-only
    STATUS      current
    DESCRIPTION
        "The value of the object tmnxDhcpsPlThRemUsedBlksLw indicates the lower
         64-bits word of the number of used prefixes with the minimum free
         threshold length remote in the pool."
    ::= { tmnxDhcpsPlThStats6Entry 28 }

tmnxDhcpsPlThRemFreeBlksHw       OBJECT-TYPE
    SYNTAX      Counter64
    MAX-ACCESS  read-only
    STATUS      current
    DESCRIPTION
        "The value of the object tmnxDhcpsPlThRemFreeBlksHw indicates the
         higher 64-bits word of the number of free prefixes with the minimum
         free threshold length remote in the pool."
    ::= { tmnxDhcpsPlThStats6Entry 29 }

tmnxDhcpsPlThRemFreeBlksLw       OBJECT-TYPE
    SYNTAX      Counter64
    MAX-ACCESS  read-only
    STATUS      current
    DESCRIPTION
        "The value of the object tmnxDhcpsPlThRemFreeBlksLw indicates the lower
         64-bits word of the number of free prefixes with the minimum free
         threshold length remote in the pool."
    ::= { tmnxDhcpsPlThStats6Entry 30 }

tmnxDhcpsPlThRemUsedPeakBlksHw   OBJECT-TYPE
    SYNTAX      Counter64
    MAX-ACCESS  read-only
    STATUS      current
    DESCRIPTION
        "The value of the object tmnxDhcpsPlThRemUsedPeakBlksHw indicates the
         higher 64-bits word of the peak value of the number of used prefixes
         with the minimum free threshold length remote in the pool."
    ::= { tmnxDhcpsPlThStats6Entry 31 }

tmnxDhcpsPlThRemUsedPeakBlksLw   OBJECT-TYPE
    SYNTAX      Counter64
    MAX-ACCESS  read-only
    STATUS      current
    DESCRIPTION
        "The value of the object tmnxDhcpsPlThRemUsedPeakBlksLw indicates the
         lower 64-bits word of the peak value of the number of used prefixes
         with the minimum free threshold length remote in the pool."
    ::= { tmnxDhcpsPlThStats6Entry 32 }

tmnxDhcpsPlThRemUsedPeakPct      OBJECT-TYPE
    SYNTAX      Counter32
    MAX-ACCESS  read-only
    STATUS      current
    DESCRIPTION
        "The value of the object tmnxDhcpsPlThRemUsedPeakPct indicates the peak
         value of the number of used prefixes with the minimum free threshold
         length remote in the pool as a percentage of the provisioned prefixes."
    ::= { tmnxDhcpsPlThStats6Entry 33 }

tmnxDhcpsPlThRemUsedPeakTime     OBJECT-TYPE
    SYNTAX      Counter32
    MAX-ACCESS  read-only
    STATUS      current
    DESCRIPTION
        "The value of the object tmnxDhcpsPlThRemUsedPeakTime indicates the
         time at which the peak value of the number of used prefixes remote in
         the pool was reached."
    ::= { tmnxDhcpsPlThStats6Entry 34 }

tmnxDhcpsPlThPeakResetTime       OBJECT-TYPE
    SYNTAX      Counter32
    MAX-ACCESS  read-only
    STATUS      current
    DESCRIPTION
        "The value of the object tmnxDhcpsPlThPeakResetTime indicates the time
         at which the peak values have been reset."
    ::= { tmnxDhcpsPlThStats6Entry 35 }

tmnxDhcpsPlThValidData           OBJECT-TYPE
    SYNTAX      TruthValue
    MAX-ACCESS  read-only
    STATUS      current
    DESCRIPTION
        "The value of the object tmnxDhcpsPlThValidData indicates
         the actual status of the threshold statistics data of the pool.
         '1' means that the data is up to date and may be used.
         '2' means that the data is being recalculated in the background
             and isn't stable for further use."
    ::= { tmnxDhcpsPlThStats6Entry 36 }

tmnxDhcpsPfxThStats6TableLastCh  OBJECT-TYPE
    SYNTAX      TimeStamp
    MAX-ACCESS  read-only
    STATUS      current
    DESCRIPTION
        "The value of the object tmnxDhcpsPfxThStats6TableLastCh indicates the
         value of sysUpTime at the time of the last modification of an entry in
         the tmnxDhcpsPfxThStats6Table."
    ::= { tmnxDhcpServerObjs 37 }

tmnxDhcpsPfxThStats6Table        OBJECT-TYPE
    SYNTAX      SEQUENCE OF TmnxDhcpsPfxThStats6Entry
    MAX-ACCESS  not-accessible
    STATUS      current
    DESCRIPTION
        "The table tmnxDhcpsPfxThStats6Table contains the threshold statistics
         for each prefix belonging to the specified DHCPv6 instance."
    ::= { tmnxDhcpServerObjs 38 }

tmnxDhcpsPfxThStats6Entry        OBJECT-TYPE
    SYNTAX      TmnxDhcpsPfxThStats6Entry
    MAX-ACCESS  not-accessible
    STATUS      current
    DESCRIPTION
        "Each row entry in the tmnxDhcpsPfxThStats6Entry represents additional
         columns of threshold statistics for a prefix that belongs to the
         specified DHCPv6 server instance"
    INDEX       {
        vRtrID,
        tmnxDhcpServerCfgServerName,
        tmnxDhcpServerPoolName,
        tmnxDhcpSvrSubnetAddrType,
        tmnxDhcpSvrSubnetAddress,
        tmnxDhcpSvrSubnetPrefixLength,
        tmnxDhcpsPfxMinFreePrefixLen
    }
    ::= { tmnxDhcpsPfxThStats6Table 1 }

TmnxDhcpsPfxThStats6Entry        ::= SEQUENCE
{
    tmnxDhcpsPfxThCurrProvBlksHw     Counter64,
    tmnxDhcpsPfxThCurrProvBlksLw     Counter64,
    tmnxDhcpsPfxThCurrUsedBlksHw     Counter64,
    tmnxDhcpsPfxThCurrUsedBlksLw     Counter64,
    tmnxDhcpsPfxThCurrFreeBlksHw     Counter64,
    tmnxDhcpsPfxThCurrFreeBlksLw     Counter64,
    tmnxDhcpsPfxThCurrUsedPct        Counter32,
    tmnxDhcpsPfxThCurrUsedPeakBlksHw Counter64,
    tmnxDhcpsPfxThCurrUsedPeakBlksLw Counter64,
    tmnxDhcpsPfxThCurrUsedPeakPct    Counter32,
    tmnxDhcpsPfxThCurrUsedPeakTime   Counter32,
    tmnxDhcpsPfxThCurrFreePct        Counter32,
    tmnxDhcpsPfxThCurrFreeTooLow     TruthValue,
    tmnxDhcpsPfxThCurrFreeDepleted   TruthValue,
    tmnxDhcpsPfxThLclProvBlksHw      Counter64,
    tmnxDhcpsPfxThLclProvBlksLw      Counter64,
    tmnxDhcpsPfxThLclUsedBlksHw      Counter64,
    tmnxDhcpsPfxThLclUsedBlksLw      Counter64,
    tmnxDhcpsPfxThLclFreeBlksHw      Counter64,
    tmnxDhcpsPfxThLclFreeBlksLw      Counter64,
    tmnxDhcpsPfxThLclUsedPeakBlksHw  Counter64,
    tmnxDhcpsPfxThLclUsedPeakBlksLw  Counter64,
    tmnxDhcpsPfxThLclUsedPeakPct     Counter32,
    tmnxDhcpsPfxThLclUsedPeakTime    Counter32,
    tmnxDhcpsPfxThRemProvBlksHw      Counter64,
    tmnxDhcpsPfxThRemProvBlksLw      Counter64,
    tmnxDhcpsPfxThRemUsedBlksHw      Counter64,
    tmnxDhcpsPfxThRemUsedBlksLw      Counter64,
    tmnxDhcpsPfxThRemFreeBlksHw      Counter64,
    tmnxDhcpsPfxThRemFreeBlksLw      Counter64,
    tmnxDhcpsPfxThRemUsedPeakBlksHw  Counter64,
    tmnxDhcpsPfxThRemUsedPeakBlksLw  Counter64,
    tmnxDhcpsPfxThRemUsedPeakPct     Counter32,
    tmnxDhcpsPfxThRemUsedPeakTime    Counter32,
    tmnxDhcpsPfxThPeakResetTime      Counter32,
    tmnxDhcpsPfxThValidData          TruthValue
}

tmnxDhcpsPfxThCurrProvBlksHw     OBJECT-TYPE
    SYNTAX      Counter64
    MAX-ACCESS  read-only
    STATUS      current
    DESCRIPTION
        "The value of the object tmnxDhcpsPfxThCurrProvBlksHw indicates the
         higher 64-bits word of the number of provisioned blocks in this
         configured prefix with a prefix length defined by the value of
         tmnxDhcpsPfxMinFreePrefixLen.

         The value of this object reflects the part of the address space in
         this prefix that is actually in use by this server instance.

         If the value of the object tmnxDhcpSvrSubnetFailCtrl of this prefix
         equals 'local (1)' or 'access-driven (3)', the value of this object
         reflects the value of the object tmnxDhcpsPfxThLclProvBlksHw.

         If the value of the object tmnxDhcpSvrSubnetFailCtrl of this prefix
         equals 'remote (2)' and the value of the object tmnxDhcpsFoAdminState
         of this server is equal to 'inService (2)' and the value of the object
         tmnxDhcpsFoState of this server is equal to 'partnerDown (5)', or the
         value of the object tmnxDhcpsPoolFoAdminState of this pool is equal to
         'inService (2)' and the value of the object tmnxDhcpsPoolFoState of
         this pool is equal to 'partnerDown (5)', the value of this object
         reflects the value of the object tmnxDhcpsPfxThRemProvBlksHw.

         Otherwise the value of this object is 0."
    ::= { tmnxDhcpsPfxThStats6Entry 1 }

tmnxDhcpsPfxThCurrProvBlksLw     OBJECT-TYPE
    SYNTAX      Counter64
    MAX-ACCESS  read-only
    STATUS      current
    DESCRIPTION
        "The value of the object tmnxDhcpsPfxThCurrProvBlksLw indicates the
         lower 64-bits word of the number of provisioned blocks in this
         configured prefix with a prefix length defined by the value of
         tmnxDhcpsPfxMinFreePrefixLen.

         The value of this object reflects the part of the address space in
         this prefix that is actually in use by this server instance.

         If the value of the object tmnxDhcpSvrSubnetFailCtrl of this prefix
         equals 'local (1)' or 'access-driven (3)', the value of this object
         reflects the value of the object tmnxDhcpsPfxThLclProvBlksLw.

         If the value of the object tmnxDhcpSvrSubnetFailCtrl of this prefix
         equals 'remote (2)' and the value of the object tmnxDhcpsFoAdminState
         of this server is equal to 'inService (2)' and the value of the object
         tmnxDhcpsFoState of this server is equal to 'partnerDown (5)', or the
         value of the object tmnxDhcpsPoolFoAdminState of this pool is equal to
         'inService (2)' and the value of the object tmnxDhcpsPoolFoState of
         this pool is equal to 'partnerDown (5)', the value of this object
         reflects the value of the object tmnxDhcpsPfxThRemProvBlksLw.

         Otherwise the value of this object is 0."
    ::= { tmnxDhcpsPfxThStats6Entry 2 }

tmnxDhcpsPfxThCurrUsedBlksHw     OBJECT-TYPE
    SYNTAX      Counter64
    MAX-ACCESS  read-only
    STATUS      current
    DESCRIPTION
        "The value of the object tmnxDhcpsPfxThCurrUsedBlksHw indicates the
         higher 64-bits word of the number of used blocks in this configured
         prefix with a prefix length defined by the value of
         tmnxDhcpsPfxMinFreePrefixLen.

         The value of this object reflects the part of the address space in
         this prefix that is actually in use by this server instance.

         If the value of the object tmnxDhcpSvrSubnetFailCtrl of this prefix
         equals 'local (1)' or 'access-driven (3)', the value of this object
         reflects the value of the object tmnxDhcpsPfxThLclUsedBlksHw.

         If the value of the object tmnxDhcpSvrSubnetFailCtrl of this prefix
         equals 'remote (2)' and the value of the object tmnxDhcpsFoAdminState
         of this server is equal to 'inService (2)' and the value of the object
         tmnxDhcpsFoState of this server is equal to 'partnerDown (5)', or the
         value of the object tmnxDhcpsPoolFoAdminState of this pool is equal to
         'inService (2)' and the value of the object tmnxDhcpsPoolFoState of
         this pool is equal to 'partnerDown (5)', the value of this object
         reflects the value of the object tmnxDhcpsPfxThRemUsedBlksHw.

         Otherwise the value of this object is 0."
    ::= { tmnxDhcpsPfxThStats6Entry 3 }

tmnxDhcpsPfxThCurrUsedBlksLw     OBJECT-TYPE
    SYNTAX      Counter64
    MAX-ACCESS  read-only
    STATUS      current
    DESCRIPTION
        "The value of the object tmnxDhcpsPfxThCurrUsedBlksLw indicates the
         lower 64-bits word of the number of used blocks in this configured
         prefix with a prefix length defined by the value of
         tmnxDhcpsPfxMinFreePrefixLen.

         The value of this object reflects the part of the address space in
         this prefix that is actually in use by this server instance.

         If the value of the object tmnxDhcpSvrSubnetFailCtrl of this prefix
         equals 'local (1)' or 'access-driven (3)', the value of this object
         reflects the value of the object tmnxDhcpsPfxThLclUsedBlksLw.

         If the value of the object tmnxDhcpSvrSubnetFailCtrl of this prefix
         equals 'remote (2)' and the value of the object tmnxDhcpsFoAdminState
         of this server is equal to 'inService (2)' and the value of the object
         tmnxDhcpsFoState of this server is equal to 'partnerDown (5)', or the
         value of the object tmnxDhcpsPoolFoAdminState of this pool is equal to
         'inService (2)' and the value of the object tmnxDhcpsPoolFoState of
         this pool is equal to 'partnerDown (5)', the value of this object
         reflects the value of the object tmnxDhcpsPfxThRemUsedBlksLw.

         Otherwise the value of this object is 0."
    ::= { tmnxDhcpsPfxThStats6Entry 4 }

tmnxDhcpsPfxThCurrFreeBlksHw     OBJECT-TYPE
    SYNTAX      Counter64
    MAX-ACCESS  read-only
    STATUS      current
    DESCRIPTION
        "The value of the object tmnxDhcpsPfxThCurrFreeBlksHw indicates the
         higher 64-bits word of the number of free blocks in this configured
         prefix with a prefix length defined by the value of
         tmnxDhcpsPfxMinFreePrefixLen.

         The value of this object reflects the part of the address space in
         this prefix that is actually in use by this server instance.

         If the value of the object tmnxDhcpSvrSubnetFailCtrl of this prefix
         equals 'local (1)' or 'access-driven (3)', the value of this object
         reflects the value of the object tmnxDhcpsPfxThLclFreeBlksHw.

         If the value of the object tmnxDhcpSvrSubnetFailCtrl of this prefix
         equals 'remote (2)' and the value of the object tmnxDhcpsFoAdminState
         of this server is equal to 'inService (2)' and the value of the object
         tmnxDhcpsFoState of this server is equal to 'partnerDown (5)', or the
         value of the object tmnxDhcpsPoolFoAdminState of this pool is equal to
         'inService (2)' and the value of the object tmnxDhcpsPoolFoState of
         this pool is equal to 'partnerDown (5)', the value of this object
         reflects the value of the object tmnxDhcpsPfxThRemFreeBlksHw.

         Otherwise the value of this object is 0."
    ::= { tmnxDhcpsPfxThStats6Entry 5 }

tmnxDhcpsPfxThCurrFreeBlksLw     OBJECT-TYPE
    SYNTAX      Counter64
    MAX-ACCESS  read-only
    STATUS      current
    DESCRIPTION
        "The value of the object tmnxDhcpsPfxThCurrFreeBlksLw indicates the
         lower 64-bits word of the number of free blocks in this configured
         prefix with a prefix length defined by the value of
         tmnxDhcpsPfxMinFreePrefixLen.

         The value of this object reflects the part of the address space in
         this prefix that is actually in use by this server instance.

         If the value of the object tmnxDhcpSvrSubnetFailCtrl of this prefix
         equals 'local (1)' or 'access-driven (3)', the value of this object
         reflects the value of the object tmnxDhcpsPfxThLclFreeBlksLw.

         If the value of the object tmnxDhcpSvrSubnetFailCtrl of this prefix
         equals 'remote (2)' and the value of the object tmnxDhcpsFoAdminState
         of this server is equal to 'inService (2)' and the value of the object
         tmnxDhcpsFoState of this server is equal to 'partnerDown (5)', or the
         value of the object tmnxDhcpsPoolFoAdminState of this pool is equal to
         'inService (2)' and the value of the object tmnxDhcpsPoolFoState of
         this pool is equal to 'partnerDown (5)', the value of this object
         reflects the value of the object tmnxDhcpsPfxThRemFreeBlksLw.

         Otherwise the value of this object is 0."
    ::= { tmnxDhcpsPfxThStats6Entry 6 }

tmnxDhcpsPfxThCurrUsedPct        OBJECT-TYPE
    SYNTAX      Counter32
    MAX-ACCESS  read-only
    STATUS      current
    DESCRIPTION
        "The value of the object tmnxDhcpsPfxThCurrUsedPct indicates the
         percentage of used prefixes with the minimum free threshold length
         compared to the number of provisioned prefixes. This depends on the
         current failover state of the DHCP server or pool."
    ::= { tmnxDhcpsPfxThStats6Entry 7 }

tmnxDhcpsPfxThCurrUsedPeakBlksHw OBJECT-TYPE
    SYNTAX      Counter64
    MAX-ACCESS  read-only
    STATUS      current
    DESCRIPTION
        "The value of the object tmnxDhcpsPfxThCurrUsedPeakBlksHw indicates the
         higher 64-bits word of the peak value of the number of used blocks in
         the configured prefix with a prefix length defined by the value of
         tmnxDhcpsPfxMinFreePrefixLen."
    ::= { tmnxDhcpsPfxThStats6Entry 8 }

tmnxDhcpsPfxThCurrUsedPeakBlksLw OBJECT-TYPE
    SYNTAX      Counter64
    MAX-ACCESS  read-only
    STATUS      current
    DESCRIPTION
        "The value of the object tmnxDhcpsPfxThCurrUsedPeakBlksLw indicates the
         lower 64-bits word of the peak value of the number of used blocks in
         the configured prefix with a prefix length defined by the value of
         tmnxDhcpsPfxMinFreePrefixLen."
    ::= { tmnxDhcpsPfxThStats6Entry 9 }

tmnxDhcpsPfxThCurrUsedPeakPct    OBJECT-TYPE
    SYNTAX      Counter32
    MAX-ACCESS  read-only
    STATUS      current
    DESCRIPTION
        "The value of the object tmnxDhcpsPfxThCurrUsedPeakPct indicates the
         peak value of the number of used prefixes with the minimum free
         threshold length in the configured prefix as a percentage of the
         provisioned prefixes. This depends on the current failover state of
         the DHCP server or pool."
    ::= { tmnxDhcpsPfxThStats6Entry 10 }

tmnxDhcpsPfxThCurrUsedPeakTime   OBJECT-TYPE
    SYNTAX      Counter32
    MAX-ACCESS  read-only
    STATUS      current
    DESCRIPTION
        "The value of the object tmnxDhcpsPfxThCurrUsedPeakTime indicates the
         time at which the peak value of the number of used prefixes was
         reached for the configured prefix."
    ::= { tmnxDhcpsPfxThStats6Entry 11 }

tmnxDhcpsPfxThCurrFreePct        OBJECT-TYPE
    SYNTAX      Counter32
    MAX-ACCESS  read-only
    STATUS      current
    DESCRIPTION
        "The value of the object tmnxDhcpsPfxThCurrFreePct indicates the
         percentage of free prefixes with the minimum free threshold length
         compared to the number of provisioned prefixes. This depends on the
         current failover state of the DHCP server or pool."
    ::= { tmnxDhcpsPfxThStats6Entry 12 }

tmnxDhcpsPfxThCurrFreeTooLow     OBJECT-TYPE
    SYNTAX      TruthValue
    MAX-ACCESS  read-only
    STATUS      current
    DESCRIPTION
        "The value of the object tmnxDhcpsPfxThCurrFreeTooLow equals '1' if the
         number of free prefixes with the minimum free threshold length
         available in the considered prefix is below the configured number of
         prefixes with the minimum free threshold length. Otherwise the value
         equals '2'."
    ::= { tmnxDhcpsPfxThStats6Entry 13 }

tmnxDhcpsPfxThCurrFreeDepleted   OBJECT-TYPE
    SYNTAX      TruthValue
    MAX-ACCESS  read-only
    STATUS      current
    DESCRIPTION
        "The value of the object tmnxDhcpsPfxThCurrFreeDepleted equals '1' if
         there are no more prefixes with the minimum free threshold length
         available in the considered prefix. Otherwise the value equals '2'."
    ::= { tmnxDhcpsPfxThStats6Entry 14 }

tmnxDhcpsPfxThLclProvBlksHw      OBJECT-TYPE
    SYNTAX      Counter64
    MAX-ACCESS  read-only
    STATUS      current
    DESCRIPTION
        "The value of the object tmnxDhcpsPfxThLclProvBlksHw indicates the
         higher 64-bits word of the number of provisioned prefixes with the
         minimum free threshold length if the configured prefix is local,
         otherwise the value is 0."
    ::= { tmnxDhcpsPfxThStats6Entry 15 }

tmnxDhcpsPfxThLclProvBlksLw      OBJECT-TYPE
    SYNTAX      Counter64
    MAX-ACCESS  read-only
    STATUS      current
    DESCRIPTION
        "The value of the object tmnxDhcpsPfxThLclProvBlksLw indicates the
         lower 64-bits word of the number of provisioned prefixes with the
         minimum free threshold length if the configured prefix is local,
         otherwise the value is 0."
    ::= { tmnxDhcpsPfxThStats6Entry 16 }

tmnxDhcpsPfxThLclUsedBlksHw      OBJECT-TYPE
    SYNTAX      Counter64
    MAX-ACCESS  read-only
    STATUS      current
    DESCRIPTION
        "The value of the object tmnxDhcpsPfxThLclUsedBlksHw indicates the
         higher 64-bits word of the number of used prefixes with the minimum
         free threshold length if the configured prefix is local, otherwise the
         value is 0."
    ::= { tmnxDhcpsPfxThStats6Entry 17 }

tmnxDhcpsPfxThLclUsedBlksLw      OBJECT-TYPE
    SYNTAX      Counter64
    MAX-ACCESS  read-only
    STATUS      current
    DESCRIPTION
        "The value of the object tmnxDhcpsPfxThLclUsedBlksLw indicates the
         lower 64-bits word of the number of used prefixes with the minimum
         free threshold length if the configured prefix is local, otherwise the
         value is 0."
    ::= { tmnxDhcpsPfxThStats6Entry 18 }

tmnxDhcpsPfxThLclFreeBlksHw      OBJECT-TYPE
    SYNTAX      Counter64
    MAX-ACCESS  read-only
    STATUS      current
    DESCRIPTION
        "The value of the object tmnxDhcpsPfxThLclFreeBlksHw indicates the
         higher 64-bits word of the number of free prefixes with the minimum
         free threshold length if the configured prefix is local, otherwise the
         value is 0."
    ::= { tmnxDhcpsPfxThStats6Entry 19 }

tmnxDhcpsPfxThLclFreeBlksLw      OBJECT-TYPE
    SYNTAX      Counter64
    MAX-ACCESS  read-only
    STATUS      current
    DESCRIPTION
        "The value of the object tmnxDhcpsPfxThLclFreeBlksLw indicates the
         lower 64-bits word of the number of free prefixes with the minimum
         free threshold length if the configured prefix is local, otherwise the
         value is 0."
    ::= { tmnxDhcpsPfxThStats6Entry 20 }

tmnxDhcpsPfxThLclUsedPeakBlksHw  OBJECT-TYPE
    SYNTAX      Counter64
    MAX-ACCESS  read-only
    STATUS      current
    DESCRIPTION
        "The value of the object tmnxDhcpsPfxThLclUsedPeakBlksHw indicates the
         higher 64-bits word of the peak value of the number of used prefixes
         with the minimum free threshold length for the local configured
         prefix."
    ::= { tmnxDhcpsPfxThStats6Entry 21 }

tmnxDhcpsPfxThLclUsedPeakBlksLw  OBJECT-TYPE
    SYNTAX      Counter64
    MAX-ACCESS  read-only
    STATUS      current
    DESCRIPTION
        "The value of the object tmnxDhcpsPfxThLclUsedPeakBlksLw indicates the
         lower 64-bits word of the peak value of the number of used prefixes
         with the minimum free threshold length for the local configured
         prefix."
    ::= { tmnxDhcpsPfxThStats6Entry 22 }

tmnxDhcpsPfxThLclUsedPeakPct     OBJECT-TYPE
    SYNTAX      Counter32
    MAX-ACCESS  read-only
    STATUS      current
    DESCRIPTION
        "The value of the object tmnxDhcpsPfxThLclUsedPeakPct indicates the
         peak value of the number of used prefixes with the minimum free
         threshold length in the local configured prefix as a percentage of the
         provisioned prefixes."
    ::= { tmnxDhcpsPfxThStats6Entry 23 }

tmnxDhcpsPfxThLclUsedPeakTime    OBJECT-TYPE
    SYNTAX      Counter32
    MAX-ACCESS  read-only
    STATUS      current
    DESCRIPTION
        "The value of the object tmnxDhcpsPfxThLclUsedPeakTime indicates the
         time at which the peak value of the number of used prefixes was
         reached for the local configured prefix."
    ::= { tmnxDhcpsPfxThStats6Entry 24 }

tmnxDhcpsPfxThRemProvBlksHw      OBJECT-TYPE
    SYNTAX      Counter64
    MAX-ACCESS  read-only
    STATUS      current
    DESCRIPTION
        "The value of the object tmnxDhcpsPfxThRemProvBlksHw indicates the
         higher 64-bits word of the number of provisioned prefixes with the
         minimum free threshold length if the configured prefix is remote,
         otherwise the value is 0."
    ::= { tmnxDhcpsPfxThStats6Entry 25 }

tmnxDhcpsPfxThRemProvBlksLw      OBJECT-TYPE
    SYNTAX      Counter64
    MAX-ACCESS  read-only
    STATUS      current
    DESCRIPTION
        "The value of the object tmnxDhcpsPfxThRemProvBlksLw indicates the
         lower 64-bits word of the number of provisioned prefixes with the
         minimum free threshold length if the configured prefix is remote,
         otherwise the value is 0."
    ::= { tmnxDhcpsPfxThStats6Entry 26 }

tmnxDhcpsPfxThRemUsedBlksHw      OBJECT-TYPE
    SYNTAX      Counter64
    MAX-ACCESS  read-only
    STATUS      current
    DESCRIPTION
        "The value of the object tmnxDhcpsPfxThRemUsedBlksHw indicates the
         higher 64-bits word of the number of used prefixes with the minimum
         free threshold length if the configured prefix is remote, otherwise
         the value is 0."
    ::= { tmnxDhcpsPfxThStats6Entry 27 }

tmnxDhcpsPfxThRemUsedBlksLw      OBJECT-TYPE
    SYNTAX      Counter64
    MAX-ACCESS  read-only
    STATUS      current
    DESCRIPTION
        "The value of the object tmnxDhcpsPfxThRemUsedBlksLw indicates the
         lower 64-bits word of the number of used prefixes with the minimum
         free threshold length if the configured prefix is remote, otherwise
         the value is 0."
    ::= { tmnxDhcpsPfxThStats6Entry 28 }

tmnxDhcpsPfxThRemFreeBlksHw      OBJECT-TYPE
    SYNTAX      Counter64
    MAX-ACCESS  read-only
    STATUS      current
    DESCRIPTION
        "The value of the object tmnxDhcpsPfxThRemFreeBlksHw indicates the
         higher 64-bits word of the number of free prefixes with the minimum
         free threshold length if the configured prefix is remote, otherwise
         the value is 0."
    ::= { tmnxDhcpsPfxThStats6Entry 29 }

tmnxDhcpsPfxThRemFreeBlksLw      OBJECT-TYPE
    SYNTAX      Counter64
    MAX-ACCESS  read-only
    STATUS      current
    DESCRIPTION
        "The value of the object tmnxDhcpsPfxThRemFreeBlksLw indicates the
         lower 64-bits word of the number of free prefixes with the minimum
         free threshold length if the configured prefix is remote, otherwise
         the value is 0."
    ::= { tmnxDhcpsPfxThStats6Entry 30 }

tmnxDhcpsPfxThRemUsedPeakBlksHw  OBJECT-TYPE
    SYNTAX      Counter64
    MAX-ACCESS  read-only
    STATUS      current
    DESCRIPTION
        "The value of the object tmnxDhcpsPfxThRemUsedPeakBlksHw indicates the
         higher 64-bits word of the peak value of the number of used prefixes
         with the minimum free threshold length for the remote configured
         prefix."
    ::= { tmnxDhcpsPfxThStats6Entry 31 }

tmnxDhcpsPfxThRemUsedPeakBlksLw  OBJECT-TYPE
    SYNTAX      Counter64
    MAX-ACCESS  read-only
    STATUS      current
    DESCRIPTION
        "The value of the object tmnxDhcpsPfxThRemUsedPeakBlksLw indicates the
         lower 64-bits word of the peak value of the number of used prefixes
         with the minimum free threshold length for the remote configured
         prefix."
    ::= { tmnxDhcpsPfxThStats6Entry 32 }

tmnxDhcpsPfxThRemUsedPeakPct     OBJECT-TYPE
    SYNTAX      Counter32
    MAX-ACCESS  read-only
    STATUS      current
    DESCRIPTION
        "The value of the object tmnxDhcpsPfxThRemUsedPeakPct indicates the
         peak value of the number of used prefixes with the minimum free
         threshold length in the remote configured prefix as a percentage of
         the provisioned prefixes."
    ::= { tmnxDhcpsPfxThStats6Entry 33 }

tmnxDhcpsPfxThRemUsedPeakTime    OBJECT-TYPE
    SYNTAX      Counter32
    MAX-ACCESS  read-only
    STATUS      current
    DESCRIPTION
        "The value of the object tmnxDhcpsPfxThRemUsedPeakTime indicates the
         time at which the peak value of the number of used prefixes was
         reached for the remote configured prefix."
    ::= { tmnxDhcpsPfxThStats6Entry 34 }

tmnxDhcpsPfxThPeakResetTime      OBJECT-TYPE
    SYNTAX      Counter32
    MAX-ACCESS  read-only
    STATUS      current
    DESCRIPTION
        "The value of the object tmnxDhcpsPfxThPeakResetTime indicates the time
         at which the peak values have been reset."
    ::= { tmnxDhcpsPfxThStats6Entry 35 }

tmnxDhcpsPfxThValidData          OBJECT-TYPE
    SYNTAX      TruthValue
    MAX-ACCESS  read-only
    STATUS      current
    DESCRIPTION
        "The value of the object tmnxDhcpsPfxThValidData indicates
         the actual status of the threshold statistics data of the prefix.
         '1' means that the data is up to date and may be used.
         '2' means that the data is being recalculated in the background
             and isn't stable for further use."
    ::= { tmnxDhcpsPfxThStats6Entry 36 }

tmnxDhcps6ExclPfxTableLastCh     OBJECT-TYPE
    SYNTAX      TimeStamp
    MAX-ACCESS  read-only
    STATUS      current
    DESCRIPTION
        "The value of the object tmnxDhcps6ExclPfxTableLastCh indicates the
         value of sysUpTime at the time of the last modification of an entry in
         the tmnxDhcps6ExclPfxTable."
    ::= { tmnxDhcpServerObjs 39 }

tmnxDhcps6ExclPfxTable           OBJECT-TYPE
    SYNTAX      SEQUENCE OF TmnxDhcps6ExclPfxEntry
    MAX-ACCESS  not-accessible
    STATUS      current
    DESCRIPTION
        "The table tmnxDhcps6ExclPfxTable contains IPv6 address prefixes within
         a DHCP server pool that are excluded from the set of address prefixes
         that can actually be offered to DHCP clients.

         This is useful in cases where this system has interfaces with an
         address that is within the scope of a subnet configured by a local
         DHCP server instance of this system, in the tmnxDhcpServerSubnetTable;
         an example of such a case is IPSEC."
    ::= { tmnxDhcpServerObjs 40 }

tmnxDhcps6ExclPfxEntry           OBJECT-TYPE
    SYNTAX      TmnxDhcps6ExclPfxEntry
    MAX-ACCESS  not-accessible
    STATUS      current
    DESCRIPTION
        "Each row represents an IPv6 address prefix that must not be offered to
         any DHCP client (neither partially nor as a whole).

         An exclude prefix can never exclude only a part of a lease; For
         example: if a /63 delegated prefix is assigned, it is not allowed to
         create a /64 exclude prefix that belongs to this prefix.

         Entries in this table can be created or deleted via SNMP operations on
         the tmnxDhcps6ExclPfxRowStatus object."
    INDEX       {
        vRtrID,
        tmnxDhcpServerCfgServerName,
        tmnxDhcpServerPoolName,
        tmnxDhcps6ExclPfxAddrType,
        tmnxDhcps6ExclPfx,
        tmnxDhcps6ExclPfxLength
    }
    ::= { tmnxDhcps6ExclPfxTable 1 }

TmnxDhcps6ExclPfxEntry           ::= SEQUENCE
{
    tmnxDhcps6ExclPfxAddrType        InetAddressType,
    tmnxDhcps6ExclPfx                InetAddress,
    tmnxDhcps6ExclPfxLength          InetAddressPrefixLength,
    tmnxDhcps6ExclPfxRowStatus       RowStatus,
    tmnxDhcps6ExclPfxLastChangeTime  TimeStamp
}

tmnxDhcps6ExclPfxAddrType        OBJECT-TYPE
    SYNTAX      InetAddressType
    MAX-ACCESS  not-accessible
    STATUS      current
    DESCRIPTION
        "The value of the object tmnxDhcps6ExclPfxAddrType specifies the
         address type of tmnxDhcps6ExclPfx.

         The only value supported is 'ipv6'."
    ::= { tmnxDhcps6ExclPfxEntry 1 }

tmnxDhcps6ExclPfx                OBJECT-TYPE
    SYNTAX      InetAddress (SIZE (16))
    MAX-ACCESS  not-accessible
    STATUS      current
    DESCRIPTION
        "The value of the object tmnxDhcps6ExclPfx specifies an address prefix.

         The host bits must be zero.

         Only IPv6 prefixes are supported."
    ::= { tmnxDhcps6ExclPfxEntry 2 }

tmnxDhcps6ExclPfxLength          OBJECT-TYPE
    SYNTAX      InetAddressPrefixLength (1..128)
    MAX-ACCESS  not-accessible
    STATUS      current
    DESCRIPTION
        "The value of the object tmnxDhcps6ExclPfxLength specifies the address
         prefix length."
    ::= { tmnxDhcps6ExclPfxEntry 3 }

tmnxDhcps6ExclPfxRowStatus       OBJECT-TYPE
    SYNTAX      RowStatus
    MAX-ACCESS  read-create
    STATUS      current
    DESCRIPTION
        "The value of the object tmnxDhcps6ExclPfxRowStatus specifies the row
         status of this row."
    ::= { tmnxDhcps6ExclPfxEntry 4 }

tmnxDhcps6ExclPfxLastChangeTime  OBJECT-TYPE
    SYNTAX      TimeStamp
    MAX-ACCESS  read-only
    STATUS      current
    DESCRIPTION
        "The value of the object tmnxDhcps6ExclPfxLastChangeTime indicates the
         sysUpTime at the time of the last modification of this entry."
    ::= { tmnxDhcps6ExclPfxEntry 5 }

tmnxDhcpsStickyLeaseAction       OBJECT IDENTIFIER ::= { tmnxDhcpServerObjs 41 }

tmnxDhcpsStickyLseActVRtrId      OBJECT-TYPE
    SYNTAX      TmnxVRtrIDOrZero
    MAX-ACCESS  read-write
    STATUS      current
    DESCRIPTION
        "The value of object tmnxDhcpsStickyLseActVRtrId specifies the ID of
         the virtual router instance."
    ::= { tmnxDhcpsStickyLeaseAction 1 }

tmnxDhcpsStickyLseActServerName  OBJECT-TYPE
    SYNTAX      TNamedItemOrEmpty
    MAX-ACCESS  read-write
    STATUS      current
    DESCRIPTION
        "The value of object tmnxDhcpsStickyLseActServerName specifies the name
         of the local DHCP server instance."
    ::= { tmnxDhcpsStickyLeaseAction 2 }

tmnxDhcpsStickyLseActPoolName    OBJECT-TYPE
    SYNTAX      TNamedItemOrEmpty
    MAX-ACCESS  read-write
    STATUS      current
    DESCRIPTION
        "The value of object tmnxDhcpsStickyLseActPoolName specifies the name
         of IP address pool within the local DHCP server instance."
    ::= { tmnxDhcpsStickyLeaseAction 3 }

tmnxDhcpsStickyLseActHostName    OBJECT-TYPE
    SYNTAX      TNamedItemOrEmpty
    MAX-ACCESS  read-write
    STATUS      current
    DESCRIPTION
        "The value of object tmnxDhcpsStickyLseActHostName specifies the name
         of the host for which an entry is created in table
         tmnxDhcpsStickyLeaseTable.

         The value of this object must also be specified when setting
         tmnxDhcpsStickyLseActActionGo."
    ::= { tmnxDhcpsStickyLeaseAction 4 }

tmnxDhcpsStickyLseActActionType  OBJECT-TYPE
    SYNTAX      TmnxDhcpsStickyLeaseActionType
    MAX-ACCESS  read-write
    STATUS      current
    DESCRIPTION
        "The value of object tmnxDhcpsStickyLseActActionType specifies the type
         of action to perform."
    ::= { tmnxDhcpsStickyLeaseAction 5 }

tmnxDhcpsStickyLseActActionGo    OBJECT-TYPE
    SYNTAX      TmnxActionType
    MAX-ACCESS  read-write
    STATUS      current
    DESCRIPTION
        "Setting this object to 'doAction' triggers an attempt to perform the
         action specified in tmnxDhcpsStickyLseActActionType.

         Reading this object returns the value 'notApplicable'."
    ::= { tmnxDhcpsStickyLeaseAction 6 }

tmnxDhcpsStickyLseActResultCode  OBJECT-TYPE
    SYNTAX      INTEGER {
        success          (0),
        wrongServerType  (1),
        serverUnknown    (2),
        serverShutdown   (3),
        userDbAttached   (4),
        failoverEnabled  (5),
        notReady         (6),
        poolUnknown      (7),
        hostExists       (8),
        wrongPool        (9),
        addrNotAvailable (10),
        maxLseReached    (11),
        poolDepleted     (12),
        leaseConflict    (13)
    }
    MAX-ACCESS  read-only
    STATUS      current
    DESCRIPTION
        "The value of object tmnxDhcpsStickyLseActResultCode indicates the
         result of the last performed action."
    ::= { tmnxDhcpsStickyLeaseAction 7 }

tmnxDhcpsStickyLseActErrorMsg    OBJECT-TYPE
    SYNTAX      DisplayString (SIZE (0..255))
    MAX-ACCESS  read-only
    STATUS      current
    DESCRIPTION
        "The value of object tmnxDhcpsStickyLseActErrorMsg indicates the reason
         of failure, in case the value of the object
         tmnxDhcpsStickyLseActResultCode is not 'success(0)'."
    ::= { tmnxDhcpsStickyLeaseAction 8 }

tmnxDhcpsStickyLseActActionTime  OBJECT-TYPE
    SYNTAX      TimeStamp
    MAX-ACCESS  read-only
    STATUS      current
    DESCRIPTION
        "The value of object tmnxDhcpsStickyLseActActionTime indicates the
         value of sysUpTime at the last time that the object
         tmnxDhcpsStickyLseActResultCode was written by the system."
    ::= { tmnxDhcpsStickyLeaseAction 9 }

tmnxDhcpsStickyLseActMacAddress  OBJECT-TYPE
    SYNTAX      MacAddress
    MAX-ACCESS  read-write
    STATUS      current
    DESCRIPTION
        "The value of object tmnxDhcpsStickyLseActMacAddress specifies the MAC
         address for this host."
    ::= { tmnxDhcpsStickyLeaseAction 10 }

tmnxDhcpsStickyLseActCircuitId   OBJECT-TYPE
    SYNTAX      OCTET STRING (SIZE (0..253))
    MAX-ACCESS  read-write
    STATUS      current
    DESCRIPTION
        "The value of object tmnxDhcpsStickyLseActCircuitId specifies the
         circuit Id for this host."
    ::= { tmnxDhcpsStickyLeaseAction 11 }

tmnxDhcpsStickyLseActClientId    OBJECT-TYPE
    SYNTAX      OCTET STRING (SIZE (0..255))
    MAX-ACCESS  read-write
    STATUS      current
    DESCRIPTION
        "The value of object tmnxDhcpsStickyLseActClientId specifies the client
         Id for this host."
    ::= { tmnxDhcpsStickyLeaseAction 12 }

tmnxDhcpsStickyLseActAddressType OBJECT-TYPE
    SYNTAX      InetAddressType
    MAX-ACCESS  read-write
    STATUS      current
    DESCRIPTION
        "The value of object tmnxDhcpsStickyLseActAddressType specifies the
         address type of tmnxDhcpsStickyLseActAddress."
    ::= { tmnxDhcpsStickyLeaseAction 13 }

tmnxDhcpsStickyLseActAddress     OBJECT-TYPE
    SYNTAX      InetAddress (SIZE (0|4|16))
    MAX-ACCESS  read-write
    STATUS      current
    DESCRIPTION
        "The value of object tmnxDhcpsStickyLseActAddress specifies the request
         IP address for this Sticky Lease.

         If tmnxDhcpsStickyLseActActionType is set to 'create(2)' and
         tmnxDhcpsStickyLseActAddress is not specified in the SNMP SET PDU, the
         system selects an IP address. The value of this object will be that
         selected IP address on the SNMP read operation."
    ::= { tmnxDhcpsStickyLeaseAction 14 }

tmnxDhcpsStickyLeaseTable        OBJECT-TYPE
    SYNTAX      SEQUENCE OF TmnxDhcpsStickyLeaseEntry
    MAX-ACCESS  not-accessible
    STATUS      current
    DESCRIPTION
        "The table tmnxDhcpsStickyLeaseTable contains information about Sticky
         Leases."
    ::= { tmnxDhcpServerObjs 42 }

tmnxDhcpsStickyLeaseEntry        OBJECT-TYPE
    SYNTAX      TmnxDhcpsStickyLeaseEntry
    MAX-ACCESS  not-accessible
    STATUS      current
    DESCRIPTION
        "Each row represents a Sticky Lease.

         Entries in this table cannot be created or deleted via SNMP
         operations."
    INDEX       {
        vRtrID,
        tmnxDhcpServerCfgServerName,
        IMPLIED tmnxDhcpsStickyLeaseHostName
    }
    ::= { tmnxDhcpsStickyLeaseTable 1 }

TmnxDhcpsStickyLeaseEntry        ::= SEQUENCE
{
    tmnxDhcpsStickyLeaseHostName     TNamedItem,
    tmnxDhcpsStickyLeaseAddressType  InetAddressType,
    tmnxDhcpsStickyLeaseAddress      InetAddress
}

tmnxDhcpsStickyLeaseHostName     OBJECT-TYPE
    SYNTAX      TNamedItem
    MAX-ACCESS  not-accessible
    STATUS      current
    DESCRIPTION
        "The value of object tmnxDhcpsStickyLeaseHostName indicates the name of
         the host."
    ::= { tmnxDhcpsStickyLeaseEntry 1 }

tmnxDhcpsStickyLeaseAddressType  OBJECT-TYPE
    SYNTAX      InetAddressType
    MAX-ACCESS  read-only
    STATUS      current
    DESCRIPTION
        "The value of object tmnxDhcpsStickyLeaseAddressType indicates the
         address type of tmnxDhcpsStickyLeaseAddress."
    ::= { tmnxDhcpsStickyLeaseEntry 2 }

tmnxDhcpsStickyLeaseAddress      OBJECT-TYPE
    SYNTAX      InetAddress (SIZE (4|16))
    MAX-ACCESS  read-only
    STATUS      current
    DESCRIPTION
        "The value of object tmnxDhcpsStickyLeaseAddress indicates the client
         IP address of this lease."
    ::= { tmnxDhcpsStickyLeaseEntry 3 }

tmnxDhcpsDefTableLastCh          OBJECT-TYPE
    SYNTAX      TimeStamp
    MAX-ACCESS  read-only
    STATUS      current
    DESCRIPTION
        "The value of the object tmnxDhcpsDefTableLastCh indicates the value of
         sysUpTime at the time of the last modification of an entry in the
         tmnxDhcpsDefTable."
    ::= { tmnxDhcpServerObjs 43 }

tmnxDhcpsDefTable                OBJECT-TYPE
    SYNTAX      SEQUENCE OF TmnxDhcpsDefEntry
    MAX-ACCESS  not-accessible
    STATUS      current
    DESCRIPTION
        "The table tmnxDhcpsDefTable is a means to configure default values per
         DHCP server."
    ::= { tmnxDhcpServerObjs 44 }

tmnxDhcpsDefEntry                OBJECT-TYPE
    SYNTAX      TmnxDhcpsDefEntry
    MAX-ACCESS  not-accessible
    STATUS      current
    DESCRIPTION
        "Each row represents a set of default values for a DHCP server instance
         running within a virtual router.

         Rows in this table are created automatically by the system, one row
         for each row in the tmnxDhcpServerConfigTable where the value of the
         object tmnxDhcpServerCfgAutoProvisioned is equal to 'true'."
    INDEX       {
        vRtrID,
        IMPLIED tmnxDhcpServerCfgServerName
    }
    ::= { tmnxDhcpsDefTable 1 }

TmnxDhcpsDefEntry                ::= SEQUENCE
{
    tmnxDhcpsDefLastChangeTime       TimeStamp,
    tmnxDhcpsDefRenewTimer           Unsigned32,
    tmnxDhcpsDefRebindTimer          Unsigned32,
    tmnxDhcpsDefValidLifetime        Unsigned32,
    tmnxDhcpsDefPrefLifetime         Unsigned32
}

tmnxDhcpsDefLastChangeTime       OBJECT-TYPE
    SYNTAX      TimeStamp
    MAX-ACCESS  read-only
    STATUS      current
    DESCRIPTION
        "The value of the object tmnxDhcpsDefLastChangeTime indicates the
         sysUpTime at the time of the last modification of this entry."
    ::= { tmnxDhcpsDefEntry 1 }

tmnxDhcpsDefRenewTimer           OBJECT-TYPE
    SYNTAX      Unsigned32 (0..604800)
    MAX-ACCESS  read-create
    STATUS      current
    DESCRIPTION
        "The value of tmnxDhcpsDefRenewTimer specifies the renew-timer (T1).

         After T1 has elapsed, the client contacts the server from which the
         addresses in the IA_NA or IA_PD were obtained to extend the lifetimes
         of the addresses or prefixes assigned to the client."
    DEFVAL      { 1800 }
    ::= { tmnxDhcpsDefEntry 2 }

tmnxDhcpsDefRebindTimer          OBJECT-TYPE
    SYNTAX      Unsigned32 (0..1209600)
    MAX-ACCESS  read-create
    STATUS      current
    DESCRIPTION
        "The value of tmnxDhcpsDefRebindTimer specifies the rebind-timer (T2).

         After T2 has elapsed, the client contacts any available server to
         extend the lifetimes of the addresses or prefixes assigned to the
         client."
    DEFVAL      { 2880 }
    ::= { tmnxDhcpsDefEntry 3 }

tmnxDhcpsDefValidLifetime        OBJECT-TYPE
    SYNTAX      Unsigned32 (300..315446399)
    UNITS       "seconds"
    MAX-ACCESS  read-create
    STATUS      current
    DESCRIPTION
        "The value of tmnxDhcpsDefValidLifetime specifies
         the valid-lifetime field that this server transmits
         - in the IA Address option, or
         - in the IA_PD Prefix option."
    DEFVAL      { 86400 }
    ::= { tmnxDhcpsDefEntry 4 }

tmnxDhcpsDefPrefLifetime         OBJECT-TYPE
    SYNTAX      Unsigned32 (300..315446399)
    UNITS       "seconds"
    MAX-ACCESS  read-create
    STATUS      current
    DESCRIPTION
        "The value of tmnxDhcpsDefPrefLifetime specifies the value
         of the preferred-lifetime field that this server transmits:
         - in the IA Address option, or
         - in the IA_PD Prefix option.

         When the preferred lifetime expires, any derived addresses are
         deprecated."
    DEFVAL      { 3600 }
    ::= { tmnxDhcpsDefEntry 5 }

tmnxDhcpsDefOptionTableLastCh    OBJECT-TYPE
    SYNTAX      TimeStamp
    MAX-ACCESS  read-only
    STATUS      current
    DESCRIPTION
        "The value of the object tmnxDhcpsDefOptionTableLastCh indicates the
         value of sysUpTime at the time of the last modification of an entry in
         the tmnxDhcpsDefOptionTable."
    ::= { tmnxDhcpServerObjs 45 }

tmnxDhcpsDefOptionTable          OBJECT-TYPE
    SYNTAX      SEQUENCE OF TmnxDhcpsDefOptionEntry
    MAX-ACCESS  not-accessible
    STATUS      current
    DESCRIPTION
        "The table tmnxDhcpsDefOptionTable contains objects to configure the
         default DHCP options of an auto-provisioned local DHCP server."
    ::= { tmnxDhcpServerObjs 46 }

tmnxDhcpsDefOptionEntry          OBJECT-TYPE
    SYNTAX      TmnxDhcpsDefOptionEntry
    MAX-ACCESS  not-accessible
    STATUS      current
    DESCRIPTION
        "Each row represents a DHCP option that is encoded in the DHCP reply
         message.

         Entries in this table can be created or deleted via SNMP operations.

         The combination of vRtrID and tmnxDhcpServerCfgServerName values must
         correspond to a conceptual row in the tmnxDhcpsDefTable."
    INDEX       {
        vRtrID,
        tmnxDhcpServerCfgServerName,
        tmnxDhcpsDefOptionNumber
    }
    ::= { tmnxDhcpsDefOptionTable 1 }

TmnxDhcpsDefOptionEntry          ::= SEQUENCE
{
    tmnxDhcpsDefOptionNumber         Unsigned32,
    tmnxDhcpsDefOptionRowStatus      RowStatus,
    tmnxDhcpsDefOptionLastCh         TimeStamp,
    tmnxDhcpsDefOptionType           TmnxDhcpOptionType,
    tmnxDhcpsDefOptionValue          OCTET STRING,
    tmnxDhcpsDefOptionDisplay        TmnxDhcpOptionDisplay
}

tmnxDhcpsDefOptionNumber         OBJECT-TYPE
    SYNTAX      Unsigned32 (1..65535)
    MAX-ACCESS  not-accessible
    STATUS      current
    DESCRIPTION
        "The value of the object tmnxDhcpsDefOptionNumber specifies the number
         of this DHCP option."
    REFERENCE
        "RFC 2132, RFC 3315, RFC 3633"
    ::= { tmnxDhcpsDefOptionEntry 1 }

tmnxDhcpsDefOptionRowStatus      OBJECT-TYPE
    SYNTAX      RowStatus
    MAX-ACCESS  read-create
    STATUS      current
    DESCRIPTION
        "The value of the object tmnxDhcpsDefOptionRowStatus specifies the row
         status of this row.

         Objects tmnxDhcpsDefOptionType and tmnxDhcpsDefOptionValue must be set
         when creating a new row."
    ::= { tmnxDhcpsDefOptionEntry 2 }

tmnxDhcpsDefOptionLastCh         OBJECT-TYPE
    SYNTAX      TimeStamp
    MAX-ACCESS  read-only
    STATUS      current
    DESCRIPTION
        "The value of the object tmnxDhcpsDefOptionLastCh indicates the
         sysUpTime at the time of the last modification of this entry."
    ::= { tmnxDhcpsDefOptionEntry 3 }

tmnxDhcpsDefOptionType           OBJECT-TYPE
    SYNTAX      TmnxDhcpOptionType
    MAX-ACCESS  read-create
    STATUS      current
    DESCRIPTION
        "The value of the object tmnxDhcpsDefOptionType specifies how the value
         of this option in stored in tmnxDhcpsDefOptionValue.

         The value of this object cannot be set to 'domain (5)' when the value
         of tmnxDhcpServerCfgAddrType is set to 'ipv4(1)'.

         This object is mandatory at creation time."
    ::= { tmnxDhcpsDefOptionEntry 4 }

tmnxDhcpsDefOptionValue          OBJECT-TYPE
    SYNTAX      OCTET STRING (SIZE (0..127))
    MAX-ACCESS  read-create
    STATUS      current
    DESCRIPTION
        "The value of the object tmnxDhcpsDefOptionValue specifies the value of
         this option.

         This object is mandatory at creation time. A zero length value is only
         allowed when the value of tmnxDhcpsDefOptionType is 'hex (3)'."
    ::= { tmnxDhcpsDefOptionEntry 5 }

tmnxDhcpsDefOptionDisplay        OBJECT-TYPE
    SYNTAX      TmnxDhcpOptionDisplay
    MAX-ACCESS  read-only
    STATUS      current
    DESCRIPTION
        "The value of the object tmnxDhcpsDefOptionDisplay indicates a hint of
         how the tmnxDhcpsDefOptionValue can be displayed."
    ::= { tmnxDhcpsDefOptionEntry 6 }

tmnxDhcpServerNotificationObjs   OBJECT IDENTIFIER ::= { tmnxDhcpServer 2 }

tmnxDhcpSvrNotifDescription      OBJECT-TYPE
    SYNTAX      DisplayString
    MAX-ACCESS  accessible-for-notify
    STATUS      current
    DESCRIPTION
        "The object tmnxDhcpSvrNotifDescription is a printable character string
         which contains information about the problem that occurred."
    ::= { tmnxDhcpServerNotificationObjs 1 }

tmnxDhcpSvrNotifUnknownPoolName  OBJECT-TYPE
    SYNTAX      TNamedItem
    MAX-ACCESS  accessible-for-notify
    STATUS      current
    DESCRIPTION
        "The object tmnxDhcpSvrNotifUnknownPoolName indicates the pppoe pool
         name which is not defined in the system."
    ::= { tmnxDhcpServerNotificationObjs 2 }

tmnxDhcpSvrNotifServerName       OBJECT-TYPE
    SYNTAX      TNamedItem
    MAX-ACCESS  accessible-for-notify
    STATUS      current
    DESCRIPTION
        "The value of the object tmnxDhcpSvrNotifServerName indicates the name
         of this local DHCP server instance."
    ::= { tmnxDhcpServerNotificationObjs 3 }

tmnxDhcpSvrNotifLeaseClientAddrType OBJECT-TYPE
    SYNTAX      InetAddressType
    MAX-ACCESS  accessible-for-notify
    STATUS      current
    DESCRIPTION
        "The value of the object tmnxDhcpSvrNotifLeaseClientAddrType indicates
         the address type of tmnxDhcpSvrNotifLeaseClientAddr."
    ::= { tmnxDhcpServerNotificationObjs 4 }

tmnxDhcpSvrNotifLeaseClientAddr  OBJECT-TYPE
    SYNTAX      InetAddress (SIZE (4|16))
    MAX-ACCESS  accessible-for-notify
    STATUS      current
    DESCRIPTION
        "The value of the object tmnxDhcpSvrNotifLeaseClientAddr indicates the
         client IP address of this lease."
    ::= { tmnxDhcpServerNotificationObjs 5 }

tmnxDhcpSvrNotifUserDatabaseName OBJECT-TYPE
    SYNTAX      TNamedItem
    MAX-ACCESS  accessible-for-notify
    STATUS      current
    DESCRIPTION
        "The value of the object tmnxDhcpSvrNotifUserDatabaseName indicates the
         name of this local user database."
    ::= { tmnxDhcpServerNotificationObjs 6 }

tmnxDhcpSvrNotifHostName         OBJECT-TYPE
    SYNTAX      DisplayString (SIZE (1..32))
    MAX-ACCESS  accessible-for-notify
    STATUS      current
    DESCRIPTION
        "The value of the object tmnxDhcpSvrNotifHostName indicates the name of
         this host or set of hosts."
    ::= { tmnxDhcpServerNotificationObjs 7 }

tmnxDhcpSvrNotifHostType         OBJECT-TYPE
    SYNTAX      INTEGER {
        unknown (0),
        dhcp    (1),
        pppoe   (2)
    }
    MAX-ACCESS  accessible-for-notify
    STATUS      current
    DESCRIPTION
        "The value of the object tmnxDhcpSvrNotifHostType indicates the type of
         the host."
    ::= { tmnxDhcpServerNotificationObjs 8 }

tmnxDhcpSvrNotifVRtrID           OBJECT-TYPE
    SYNTAX      TmnxVRtrID
    MAX-ACCESS  accessible-for-notify
    STATUS      current
    DESCRIPTION
        "The  unique value which identifies this virtual router in the Tmnx
         system. "
    ::= { tmnxDhcpServerNotificationObjs 9 }

tmnxDhcpSvrNotifMsgHwAddress     OBJECT-TYPE
    SYNTAX      MacAddress
    MAX-ACCESS  accessible-for-notify
    STATUS      current
    DESCRIPTION
        "The value of object tmnxDhcpSvrNotifMsgHwAddress indicates the MAC
         address from the received DHCP message."
    ::= { tmnxDhcpServerNotificationObjs 10 }

tmnxDhcpSvrNotifMsgOption82      OBJECT-TYPE
    SYNTAX      OCTET STRING
    MAX-ACCESS  accessible-for-notify
    STATUS      current
    DESCRIPTION
        "The value of object tmnxDhcpSvrNotifMsgOption82 indicates the content
         of option 82 from the received DHCP message."
    ::= { tmnxDhcpServerNotificationObjs 11 }

tmnxDhcpSvrNotifMsgSizeLimit     OBJECT-TYPE
    SYNTAX      Unsigned32
    MAX-ACCESS  accessible-for-notify
    STATUS      current
    DESCRIPTION
        "The value of the object tmnxDhcpSvrNotifMsgSizeLimit indicates the
         minimum of either the maximum DHCP message size or the size provided
         by the client in the option maximum DHCP message size."
    ::= { tmnxDhcpServerNotificationObjs 12 }

tmnxDhcpsFoLeaseFailureReason    OBJECT-TYPE
    SYNTAX      TmnxDhcpsFoLeaseFailureReason
    MAX-ACCESS  accessible-for-notify
    STATUS      current
    DESCRIPTION
        "The value of the object tmnxDhcpsFoLeaseFailureReason indicates the
         reason of a lease update failure that occurred in the failover
         facility of a DHCP Server instance."
    ::= { tmnxDhcpServerNotificationObjs 13 }

tmnxDhcpSvrNotifPoolFree         OBJECT-TYPE
    SYNTAX      Unsigned32
    MAX-ACCESS  accessible-for-notify
    STATUS      current
    DESCRIPTION
        "The value of the object tmnxDhcpSvrNotifPoolFree indicates the actual
         number of free addresses in the pool."
    ::= { tmnxDhcpServerNotificationObjs 14 }

tmnxDhcpSvrNotifLeaseClientAddrLen OBJECT-TYPE
    SYNTAX      Unsigned32
    MAX-ACCESS  accessible-for-notify
    STATUS      current
    DESCRIPTION
        "The value of the object tmnxDhcpSvrNotifLeaseClientAddrLen indicates
         the prefix length of tmnxDhcpSvrNotifLeaseClientAddr."
    ::= { tmnxDhcpServerNotificationObjs 15 }

tmnxDhcpSvrNotifClientDUID       OBJECT-TYPE
    SYNTAX      OCTET STRING (SIZE (0..130))
    MAX-ACCESS  accessible-for-notify
    STATUS      current
    DESCRIPTION
        "The value of object tmnxDhcpSvrNotifClientDUID indicates the content
         of option 0x01 from the received DHCPv6 message."
    ::= { tmnxDhcpServerNotificationObjs 16 }

tmnxDhcpSvrNotifLinkAddr         OBJECT-TYPE
    SYNTAX      InetAddress (SIZE (4|16))
    MAX-ACCESS  accessible-for-notify
    STATUS      current
    DESCRIPTION
        "The value of tmnxDhcpSvrNotifLinkAddr indicates the link address from
         the RELAY-FORWARD message."
    ::= { tmnxDhcpServerNotificationObjs 17 }

tmnxDhcpSvrNotifPrimaryPool      OBJECT-TYPE
    SYNTAX      TNamedItemOrEmpty
    MAX-ACCESS  accessible-for-notify
    STATUS      current
    DESCRIPTION
        "The value of tmnxDhcpSvrNotifPrimaryPool indicates the primary pool
         name from the RELAY-FORWARD message."
    ::= { tmnxDhcpServerNotificationObjs 18 }

tmnxDhcpSvrNotifSecondaryPool    OBJECT-TYPE
    SYNTAX      TNamedItemOrEmpty
    MAX-ACCESS  accessible-for-notify
    STATUS      current
    DESCRIPTION
        "The value of tmnxDhcpSvrNotifSecondaryPool indicates the secondary
         pool name from the RELAY-FORWARD message."
    ::= { tmnxDhcpServerNotificationObjs 19 }

tmnxDhcpSvrNotifSystemId         OBJECT-TYPE
    SYNTAX      OCTET STRING (SIZE (0..255))
    MAX-ACCESS  accessible-for-notify
    STATUS      current
    DESCRIPTION
        "The value of the object tmnxDhcpSvrNotifSystemId indicates a system-id
         provided by an access node to which this subnet is bound."
    ::= { tmnxDhcpServerNotificationObjs 20 }

tmnxDhcpSvrNotifServiceId        OBJECT-TYPE
    SYNTAX      OCTET STRING (SIZE (0..255))
    MAX-ACCESS  accessible-for-notify
    STATUS      current
    DESCRIPTION
        "The value of the object tmnxDhcpSvrNotifServiceId indicates a
         service-id provided by an access node."
    ::= { tmnxDhcpServerNotificationObjs 21 }

tmnxDhcpSvrNotifString           OBJECT-TYPE
    SYNTAX      DisplayString (SIZE (0..255))
    MAX-ACCESS  accessible-for-notify
    STATUS      current
    DESCRIPTION
        "The value of the object tmnxDhcpSvrNotifString is a string."
    ::= { tmnxDhcpServerNotificationObjs 22 }

tmnxDhcpSvrNotifPoolName         OBJECT-TYPE
    SYNTAX      TNamedItem
    MAX-ACCESS  accessible-for-notify
    STATUS      current
    DESCRIPTION
        "The object tmnxDhcpSvrNotifPoolName indicates the pppoe pool name in
         the system."
    ::= { tmnxDhcpServerNotificationObjs 23 }

tmnxDhcpSvrNotifSubnetAddrType   OBJECT-TYPE
    SYNTAX      InetAddressType
    MAX-ACCESS  accessible-for-notify
    STATUS      current
    DESCRIPTION
        "The value of the object tmnxDhcpSvrNotifSubnetAddrType indicates the
         address type of the address that follows."
    ::= { tmnxDhcpServerNotificationObjs 24 }

tmnxDhcpSvrNotifSubnetPfx        OBJECT-TYPE
    SYNTAX      InetAddress (SIZE (4|16))
    MAX-ACCESS  accessible-for-notify
    STATUS      current
    DESCRIPTION
        "The value of the object tmnxDhcpSvrNotifSubnetPfx specifies a subnet."
    ::= { tmnxDhcpServerNotificationObjs 25 }

tmnxDhcpSvrNotifSubnetPfxlen     OBJECT-TYPE
    SYNTAX      InetAddressPrefixLength (1..128)
    MAX-ACCESS  accessible-for-notify
    STATUS      current
    DESCRIPTION
        "The value of the object tmnxDhcpSvrNotifSubnetPfxlen specifies the
         length of tmnxDhcpSvrNotifSubnetPfx."
    ::= { tmnxDhcpServerNotificationObjs 26 }

tmnxDhcpSvrNotifUnbindTime       OBJECT-TYPE
    SYNTAX      Unsigned32
    MAX-ACCESS  accessible-for-notify
    STATUS      current
    DESCRIPTION
        "The value of the object tmnxDhcpSvrNotifUnbindTime indicates the time
         left before this binding expires."
    ::= { tmnxDhcpServerNotificationObjs 27 }

tmnxDhcpSvrNotifGwIpAddrType     OBJECT-TYPE
    SYNTAX      InetAddressType
    MAX-ACCESS  accessible-for-notify
    STATUS      current
    DESCRIPTION
        "The value of the object tmnxDhcpSvrNotifGwIpAddrType specifies the
         address type of tmnxDhcpSvrNotifGatewayIpAddr.

         The only value supported is 'ipv4'."
    ::= { tmnxDhcpServerNotificationObjs 28 }

tmnxDhcpSvrNotifGatewayIpAddr    OBJECT-TYPE
    SYNTAX      InetAddress (SIZE (0|4))
    MAX-ACCESS  accessible-for-notify
    STATUS      current
    DESCRIPTION
        "The value of tmnxDhcpSvrNotifGatewayIpAddr indicates the gateway
         address from the RELAY-FORWARD message."
    ::= { tmnxDhcpServerNotificationObjs 29 }

tmnxDhcpServerConformance        OBJECT IDENTIFIER ::= { tmnxSRConfs 47 }

tmnxDhcpServerCompliances        OBJECT IDENTIFIER ::= { tmnxDhcpServerConformance 1 }

tmnxDhcpServerCompliance         MODULE-COMPLIANCE
    STATUS      obsolete
    DESCRIPTION
        "The compliance statement for management of DHCP Server on Nokia SROS
         series systems."
    MODULE
        MANDATORY-GROUPS {
            tmnxDhcpServerGroup,
            tmnxDhcpLeaseGroup,
            tmnxDhcpStatsGroup,
            tmnxDhcpAddrListGroup,
            tmnxDhcpToolsGroup,
            tmnxDhcpSvrNotifGroup,
            tmnxDhcpsFailoverGroup,
            tmnxDhcpSvrFoNotifGroup
        }
    ::= { tmnxDhcpServerCompliances 1 }

tmnxDhcpServerV6v1Compliance     MODULE-COMPLIANCE
    STATUS      obsolete
    DESCRIPTION
        "The compliance statement for management of DHCP Server on Nokia SROS
         series systems."
    MODULE
        MANDATORY-GROUPS {
            tmnxDhcpServerV6v1Group,
            tmnxDhcpLeaseGroup,
            tmnxDhcpStatsV6v1Group,
            tmnxDhcpAddrListGroup,
            tmnxDhcpToolsGroup,
            tmnxDhcpSvrNotifGroup,
            tmnxDhcpsFailoverGroup,
            tmnxDhcpSvrFoNotifGroup
        }
    ::= { tmnxDhcpServerCompliances 2 }

tmnxDhcpServerV8v0Compliance     MODULE-COMPLIANCE
    STATUS      obsolete
    DESCRIPTION
        "The compliance statement for management of DHCP Server on Nokia SROS
         series systems release 8.0."
    MODULE
        MANDATORY-GROUPS {
            tmnxDhcpServerV8v0Group,
            tmnxDhcpLeaseGroup,
            tmnxDhcpStatsV8v0Group,
            tmnxDhcpAddrListGroup,
            tmnxDhcpToolsGroup,
            tmnxDhcpSvrNotifGroup,
            tmnxDhcpsFailoverGroup,
            tmnxDhcpSvrFoNotifGroup
        }
    ::= { tmnxDhcpServerCompliances 3 }

tmnxDhcpServerV9v0Compliance     MODULE-COMPLIANCE
    STATUS      obsolete
    DESCRIPTION
        "The compliance statement for management of DHCP Server on Nokia SROS
         series systems release 9.0."
    MODULE
        MANDATORY-GROUPS {
            tmnxDhcpServerV8v0Group,
            tmnxDhcpServerV9v0Group,
            tmnxDhcpLeaseGroup,
            tmnxDhcpStatsV8v0Group,
            tmnxDhcpStatsV9v0Group,
            tmnxDhcpAddrListGroup,
            tmnxDhcpToolsGroup,
            tmnxDhcpSvrNotifGroup,
            tmnxDhcpsFailoverGroup,
            tmnxDhcpSvrFoNotifGroup
        }
    ::= { tmnxDhcpServerCompliances 4 }

tmnxDhcpServerV10v0Compliance    MODULE-COMPLIANCE
    STATUS      obsolete
    DESCRIPTION
        "The compliance statement for management of DHCP Server on Nokia SROS
         series systems release 10.0."
    MODULE
        MANDATORY-GROUPS {
            tmnxDhcpServerV8v0Group,
            tmnxDhcpServerV9v0Group,
            tmnxDhcpServerV10v0Group,
            tmnxDhcpLeaseGroup,
            tmnxDhcpStatsV8v0Group,
            tmnxDhcpStatsV9v0Group,
            tmnxDhcpAddrListGroup,
            tmnxDhcpToolsGroup,
            tmnxDhcpSvrNotifGroup,
            tmnxDhcpSvrNotifV10v0Group,
            tmnxDhcpsFailoverGroup,
            tmnxDhcpSvrFoNotifGroup
        }
    ::= { tmnxDhcpServerCompliances 5 }

tmnxDhcpServerV11v0Compliance    MODULE-COMPLIANCE
    STATUS      obsolete
    DESCRIPTION
        "The compliance statement for management of DHCP Server on Nokia SROS
         series systems release 11.0."
    MODULE
        MANDATORY-GROUPS {
            tmnxDhcpServerV8v0Group,
            tmnxDhcpServerV9v0Group,
            tmnxDhcpServerV10v0Group,
            tmnxDhcpServerV11v0Group,
            tmnxDhcpServerDuidGroup,
            tmnxDhcpLeaseGroup,
            tmnxDhcpStatsV8v0Group,
            tmnxDhcpStatsV9v0Group,
            tmnxDhcpAddrListGroup,
            tmnxDhcpToolsGroup,
            tmnxDhcpSvrNotifGroup,
            tmnxDhcpSvrNotifV10v0Group,
            tmnxDhcpSvrNotifV11v0Group,
            tmnxDhcpsFailoverGroup,
            tmnxDhcpsFailoverV11v0Group,
            tmnxDhcpSvrFoNotifGroup,
            tmnxDhcpStatsV11v0Group
        }
    ::= { tmnxDhcpServerCompliances 6 }

tmnxDhcpServerV12v0Compliance    MODULE-COMPLIANCE
    STATUS      obsolete
    DESCRIPTION
        "The compliance statement for management of DHCP Server on Nokia SROS
         series systems release 12.0."
    MODULE
        MANDATORY-GROUPS {
            tmnxDhcpServerV8v0Group,
            tmnxDhcpServerV9v0Group,
            tmnxDhcpServerV10v0Group,
            tmnxDhcpServerV12v0Group,
            tmnxDhcpServerDuidGroup,
            tmnxDhcpLeaseGroup,
            tmnxDhcpLeaseV12v0Group,
            tmnxDhcpStatsV8v0Group,
            tmnxDhcpStatsV9v0Group,
            tmnxDhcpAddrListGroup,
            tmnxDhcpToolsGroup,
            tmnxDhcpSvrNotifGroup,
            tmnxDhcpSvrNotifV10v0Group,
            tmnxDhcpSvrNotifV12v0Group,
            tmnxDhcpsFailoverGroup,
            tmnxDhcpsFailoverV10v0Group,
            tmnxDhcpsFailoverV11v0Group,
            tmnxDhcpSvrFoNotifGroup,
            tmnxDhcpStatsV11v0Group
        }
    ::= { tmnxDhcpServerCompliances 7 }

tmnxDhcpServerV13v0Compliance    MODULE-COMPLIANCE
    STATUS      obsolete
    DESCRIPTION
        "The compliance statement for management of DHCP Server on Nokia SROS
         series systems release 13.0."
    MODULE
        MANDATORY-GROUPS {
            tmnxDhcpServerV8v0Group,
            tmnxDhcpServerV9v0Group,
            tmnxDhcpServerV10v0Group,
            tmnxDhcpServerV12v0Group,
            tmnxDhcpServerV13v0Group,
            tmnxDhcpServerDuidGroup,
            tmnxDhcpLeaseGroup,
            tmnxDhcpLeaseV12v0Group,
            tmnxDhcpStatsV8v0Group,
            tmnxDhcpStatsV9v0Group,
            tmnxDhcpStatsV13v0Group,
            tmnxDhcpAddrListGroup,
            tmnxDhcpToolsGroup,
            tmnxDhcpSvrNotifGroup,
            tmnxDhcpSvrNotifV10v0Group,
            tmnxDhcpSvrNotifV12v0Group,
            tmnxDhcpSvrNotifV13v0Group,
            tmnxDhcpsFailoverGroup,
            tmnxDhcpsFailoverV10v0Group,
            tmnxDhcpsFailoverV11v0Group,
            tmnxDhcpsFailoverV12v0Group,
            tmnxDhcpSvrFoNotifGroup,
            tmnxDhcpStatsV11v0Group
        }
    ::= { tmnxDhcpServerCompliances 8 }

tmnxDhcpServerV14v0Compliance    MODULE-COMPLIANCE
    STATUS      obsolete
    DESCRIPTION
        "The compliance statement for management of DHCP Server on Nokia SROS
         series since systems release 14.0."
    MODULE
        MANDATORY-GROUPS {
            tmnxDhcpServerStickyLseGroup,
            tmnxDhcpsPrefixLenExtensionGroup
        }
    ::= { tmnxDhcpServerCompliances 9 }

tmnxDhcpServerV15v0Compliance    MODULE-COMPLIANCE
    STATUS      obsolete
    DESCRIPTION
        "The compliance statement for management of DHCP Server on Nokia SROS
         series systems release 15.0."
    MODULE
        MANDATORY-GROUPS {
            tmnxDhcpServerV8v0Group,
            tmnxDhcpServerV9v0Group,
            tmnxDhcpServerV10v0Group,
            tmnxDhcpServerV12v0Group,
            tmnxDhcpServerV13v0Group,
            tmnxDhcpServerDuidGroup,
            tmnxDhcpLeaseGroup,
            tmnxDhcpLeaseV12v0Group,
            tmnxDhcpStatsV8v0Group,
            tmnxDhcpStatsV9v0Group,
            tmnxDhcpStatsV13v0Group,
            tmnxDhcpAddrListGroup,
            tmnxDhcpToolsGroup,
            tmnxDhcpSvrNotifGroup,
            tmnxDhcpSvrNotifV10v0Group,
            tmnxDhcpSvrNotifV12v0Group,
            tmnxDhcpSvrNotifV13v0Group,
            tmnxDhcpsFailoverGroup,
            tmnxDhcpsFailoverV10v0Group,
            tmnxDhcpsFailoverV11v0Group,
            tmnxDhcpsFailoverV12v0Group,
            tmnxDhcpSvrFoNotifGroup,
            tmnxDhcpStatsV11v0Group,
            tmnxDhcpServerStickyLseGroup,
            tmnxDhcpsPrefixLenExtensionGroup,
            tmnxDhcpsAutoProvisionGroup
        }
    ::= { tmnxDhcpServerCompliances 10 }

tmnxDhcpServerV16v0Compliance    MODULE-COMPLIANCE
    STATUS      current
    DESCRIPTION
        "The compliance statement for management of DHCP Server on Nokia SROS
         series systems release 16.0."
    MODULE
        MANDATORY-GROUPS {
            tmnxDhcpServerV8v0Group,
            tmnxDhcpServerV9v0Group,
            tmnxDhcpServerV10v0Group,
            tmnxDhcpServerV12v0Group,
            tmnxDhcpServerV13v0Group,
            tmnxDhcpServerV16v0Group,
            tmnxDhcpServerDuidGroup,
            tmnxDhcpLeaseGroup,
            tmnxDhcpLeaseV12v0Group,
            tmnxDhcpStatsV8v0Group,
            tmnxDhcpStatsV9v0Group,
            tmnxDhcpStatsV13v0Group,
            tmnxDhcpAddrListGroup,
            tmnxDhcpToolsGroup,
            tmnxDhcpSvrNotifGroup,
            tmnxDhcpSvrNotifV10v0Group,
            tmnxDhcpSvrNotifV12v0Group,
            tmnxDhcpSvrNotifV13v0Group,
            tmnxDhcpsFailoverGroup,
            tmnxDhcpsFailoverV10v0Group,
            tmnxDhcpsFailoverV11v0Group,
            tmnxDhcpsFailoverV12v0Group,
            tmnxDhcpSvrFoNotifGroup,
            tmnxDhcpServerStickyLseGroup,
            tmnxDhcpsPrefixLenExtensionGroup,
            tmnxDhcpsAutoProvisionGroup,
            tmnxDhcpStatsV16v0Group,
            tmnxDhcpIntReqStatsGroup
        }
    ::= { tmnxDhcpServerCompliances 11 }

tmnxDhcpServerGroups             OBJECT IDENTIFIER ::= { tmnxDhcpServerConformance 2 }

tmnxDhcpServerGroup              OBJECT-GROUP
    OBJECTS     {
        tmnxDhcpServerConfigTableLastCh,
        tmnxDhcpServerCfgRowStatus,
        tmnxDhcpServerCfgLastChangeTime,
        tmnxDhcpServerCfgAdminState,
        tmnxDhcpServerCfgDescription,
        tmnxDhcpServerCfgUserDatabase,
        tmnxDhcpServerCfgUseGiAddress,
        tmnxDhcpServerCfgSendForceRenews,
        tmnxDhcpServerCfgOperState,
        tmnxDhcpServerPoolTableLastCh,
        tmnxDhcpServerPoolRowStatus,
        tmnxDhcpServerPoolLastChangeTime,
        tmnxDhcpServerPoolDescription,
        tmnxDhcpServerPoolMinLeaseTime,
        tmnxDhcpServerPoolMaxLeaseTime,
        tmnxDhcpServerPoolOfferTime,
        tmnxDhcpSvrPoolOptionTableLastCh,
        tmnxDhcpSvrPoolOptionRowStatus,
        tmnxDhcpSvrPoolOptionLastCh,
        tmnxDhcpSvrPoolOptionType,
        tmnxDhcpSvrPoolOptionValue,
        tmnxDhcpServerSubnetTableLastCh,
        tmnxDhcpSvrSubnetRowStatus,
        tmnxDhcpSvrSubnetLastChangeTime,
        tmnxDhcpSvrSubnetMinFree,
        tmnxDhcpSvrSubnetMaxDeclined,
        tmnxDhcpSvrSubnetRangesTblLastCh,
        tmnxDhcpSvrSubnetRangesRowStatus,
        tmnxDhcpSvrSubnetRangesLastCh,
        tmnxDhcpSvrSubnetOptionTblLastCh,
        tmnxDhcpSvrSubnetOptionRowStatus,
        tmnxDhcpSvrSubnetOptionLastCh,
        tmnxDhcpSvrSubnetOptionType,
        tmnxDhcpSvrSubnetOptionValue
    }
    STATUS      obsolete
    DESCRIPTION
        "The group of objects supporting DHCP server capability on Nokia SROS
         series systems."
    ::= { tmnxDhcpServerGroups 1 }

tmnxDhcpLeaseGroup               OBJECT-GROUP
    OBJECTS     {
        tmnxDhcpSvrLeaseState,
        tmnxDhcpSvrLeaseStart,
        tmnxDhcpSvrLeaseLastRenew,
        tmnxDhcpSvrLeaseRemainLeaseTime,
        tmnxDhcpSvrLeaseRemPotentExpTime,
        tmnxDhcpSvrLeaseClientHwAddress,
        tmnxDhcpSvrLeaseXid,
        tmnxDhcpSvrLeaseOption82,
        tmnxDhcpSvrLeaseClientType,
        tmnxDhcpSvrLeasePPPoEUserName,
        tmnxDhcpSvrLeaseOpt82CircId,
        tmnxDhcpSvrLeaseOption60,
        tmnxDhcpSvrNumLeases,
        tmnxDhcpSvrMaxLeases
    }
    STATUS      current
    DESCRIPTION
        "The group of objects providing DHCP lease information on Nokia SROS
         series systems."
    ::= { tmnxDhcpServerGroups 2 }

tmnxDhcpStatsGroup               OBJECT-GROUP
    OBJECTS     {
        tmnxDhcpSvrStatsRxDiscovers,
        tmnxDhcpSvrStatsRxRequests,
        tmnxDhcpSvrStatsRxReleases,
        tmnxDhcpSvrStatsRxDeclines,
        tmnxDhcpSvrStatsRxInforms,
        tmnxDhcpSvrStatsTxOffers,
        tmnxDhcpSvrStatsTxAcks,
        tmnxDhcpSvrStatsTxNaks,
        tmnxDhcpSvrStatsTxForceRenews,
        tmnxDhcpSvrStatsDropBadPackets,
        tmnxDhcpSvrStatsDropInvalidTypes,
        tmnxDhcpSvrStatsDropNoUsrDbFound,
        tmnxDhcpSvrStatsDropUnknownHosts,
        tmnxDhcpSvrStatsDropUserNotAllow,
        tmnxDhcpSvrStatsDropLseNotReady,
        tmnxDhcpSvrStatsDropNoLeaseFound,
        tmnxDhcpSvrStatsDropNotSrvngPool,
        tmnxDhcpSvrStatsDropInvalidUsr,
        tmnxDhcpSvrStatsDropOverload,
        tmnxDhcpSvrStatsDropPersOverload,
        tmnxDhcpSvrStatsOffersIgnore,
        tmnxDhcpSvrStatsDropGenError,
        tmnxDhcpSvrStatsDropDestOther,
        tmnxDhcpSvrStatsDropAddrUnavail,
        tmnxDhcpSvrStatsDropMaxReached,
        tmnxDhcpSvrStatsDropSvrDown,
        tmnxDhcpSvrStatsDropNoSubnet,
        tmnxDhcpSvrStatsLeasesExpired,
        tmnxDhcpSvrSubnetStatsFree,
        tmnxDhcpSvrSubnetStatsOffered,
        tmnxDhcpSvrSubnetStatsStable,
        tmnxDhcpSvrSubnetStatsFRPending,
        tmnxDhcpSvrSubnetStatsRemPending,
        tmnxDhcpSvrSubnetStatsDeclined
    }
    STATUS      obsolete
    DESCRIPTION
        "The group of objects providing DHCP statistics on Nokia SROS series
         systems."
    ::= { tmnxDhcpServerGroups 3 }

tmnxDhcpAddrListGroup            OBJECT-GROUP
    OBJECTS     {
        tmnxDhcpSvrDeclinedAddrAddedTime,
        tmnxDhcpSvrDeclinedAddrHwAddress,
        tmnxDhcpSvrDeclinedAddrOption82,
        tmnxDhcpSvrDeclinedAddrClientType,
        tmnxDhcpSvrDeclinedAddrUserName,
        tmnxDhcpSvrDeclinedAddrCircId
    }
    STATUS      current
    DESCRIPTION
        "The group of objects providing information for DHCP on Nokia SROS
         series systems."
    ::= { tmnxDhcpServerGroups 4 }

tmnxDhcpToolsGroup               OBJECT-GROUP
    OBJECTS     {
        tmnxDhcpSvrActForceRenewAddrType,
        tmnxDhcpSvrActForceRenewAddr
    }
    STATUS      current
    DESCRIPTION
        "The group of objects supporting DHCP server capability on Nokia SROS
         series systems."
    ::= { tmnxDhcpServerGroups 5 }

tmnxDhcpsFailoverGroup           OBJECT-GROUP
    OBJECTS     {
        tmnxDhcpsFoTableLastChanged,
        tmnxDhcpsFoLastChanged,
        tmnxDhcpsFoAdminState,
        tmnxDhcpsFoMaxClientLeadTime,
        tmnxDhcpsFoOperMaxClientLeadTime,
        tmnxDhcpsFoStartupWaitTime,
        tmnxDhcpsFoPartnerDownDelay,
        tmnxDhcpsFoState,
        tmnxDhcpsFoTimeLeft,
        tmnxDhcpSvrSubnetRangeFailCtrl,
        tmnxDhcpSvrLeaseFailCtrl,
        tmnxDhcpSvrFreeAddrFailCtrl,
        tmnxDhcpSvrSubnetStatsFoFree,
        tmnxDhcpSvrSubnetStatsFoOffered,
        tmnxDhcpSvrSubnetStatsFoStable,
        tmnxDhcpSvrSubnetStatsFoFRPend,
        tmnxDhcpSvrSubnetStatsFoRemPend,
        tmnxDhcpSvrSubnetStatsFoDeclined,
        tmnxDhcpsFoStatsLeaseNotFound,
        tmnxDhcpsFoStatsDropInvalidPkts,
        tmnxDhcpsFoStatsFoShutdown,
        tmnxDhcpsFoStatsExpired,
        tmnxDhcpsFoStatsMaxReached,
        tmnxDhcpsFoStatsSubnetNotFound,
        tmnxDhcpsFoStatsRangeNotFound,
        tmnxDhcpsFoStatsHostConflict,
        tmnxDhcpsFoStatsAddressConflict,
        tmnxDhcpsFoStatsPeerConflict,
        tmnxDhcpsFoActionVRtrId,
        tmnxDhcpsFoActionServerName,
        tmnxDhcpsFoActionType,
        tmnxDhcpsFoActionGo,
        tmnxDhcpsFoActionSuccessful,
        tmnxDhcpsFoActionErrorMsg,
        tmnxDhcpsFoActionTime
    }
    STATUS      current
    DESCRIPTION
        "The group of objects supporting DHCP server failover capability on
         Nokia SROS series systems."
    ::= { tmnxDhcpServerGroups 6 }

tmnxDhcpsNotifyObjsGroup         OBJECT-GROUP
    OBJECTS     {
        tmnxDhcpSvrNotifDescription,
        tmnxDhcpSvrNotifUnknownPoolName,
        tmnxDhcpSvrNotifServerName,
        tmnxDhcpSvrNotifLeaseClientAddrType,
        tmnxDhcpSvrNotifLeaseClientAddr,
        tmnxDhcpSvrNotifUserDatabaseName,
        tmnxDhcpSvrNotifHostName,
        tmnxDhcpSvrNotifHostType,
        tmnxDhcpSvrNotifVRtrID,
        tmnxDhcpSvrNotifMsgHwAddress,
        tmnxDhcpSvrNotifMsgOption82,
        tmnxDhcpSvrNotifMsgSizeLimit,
        tmnxDhcpsFoLeaseFailureReason,
        tmnxDhcpSvrNotifPoolFree
    }
    STATUS      current
    DESCRIPTION
        "The group of objects supporting DHCP server notifications on Nokia
         SROS series systems."
    ::= { tmnxDhcpServerGroups 7 }

tmnxDhcpServerV6v1Group          OBJECT-GROUP
    OBJECTS     {
        tmnxDhcpServerConfigTableLastCh,
        tmnxDhcpServerCfgRowStatus,
        tmnxDhcpServerCfgLastChangeTime,
        tmnxDhcpServerCfgAdminState,
        tmnxDhcpServerCfgDescription,
        tmnxDhcpServerCfgUserDatabase,
        tmnxDhcpServerCfgUseGiAddress,
        tmnxDhcpServerCfgSendForceRenews,
        tmnxDhcpServerCfgUseClientPool,
        tmnxDhcpServerCfgOperState,
        tmnxDhcpServerPoolTableLastCh,
        tmnxDhcpServerPoolRowStatus,
        tmnxDhcpServerPoolLastChangeTime,
        tmnxDhcpServerPoolDescription,
        tmnxDhcpServerPoolMinLeaseTime,
        tmnxDhcpServerPoolMaxLeaseTime,
        tmnxDhcpServerPoolOfferTime,
        tmnxDhcpSvrPoolOptionTableLastCh,
        tmnxDhcpSvrPoolOptionRowStatus,
        tmnxDhcpSvrPoolOptionLastCh,
        tmnxDhcpSvrPoolOptionType,
        tmnxDhcpSvrPoolOptionValue,
        tmnxDhcpServerSubnetTableLastCh,
        tmnxDhcpSvrSubnetRowStatus,
        tmnxDhcpSvrSubnetLastChangeTime,
        tmnxDhcpSvrSubnetMinFree,
        tmnxDhcpSvrSubnetMaxDeclined,
        tmnxDhcpSvrSubnetRangesTblLastCh,
        tmnxDhcpSvrSubnetRangesRowStatus,
        tmnxDhcpSvrSubnetRangesLastCh,
        tmnxDhcpSvrSubnetOptionTblLastCh,
        tmnxDhcpSvrSubnetOptionRowStatus,
        tmnxDhcpSvrSubnetOptionLastCh,
        tmnxDhcpSvrSubnetOptionType,
        tmnxDhcpSvrSubnetOptionValue
    }
    STATUS      obsolete
    DESCRIPTION
        "The group of objects supporting DHCP server capability on Nokia SROS
         series systems release 6.1."
    ::= { tmnxDhcpServerGroups 8 }

tmnxDhcpStatsV6v1Group           OBJECT-GROUP
    OBJECTS     {
        tmnxDhcpSvrStatsRxDiscovers,
        tmnxDhcpSvrStatsRxRequests,
        tmnxDhcpSvrStatsRxReleases,
        tmnxDhcpSvrStatsRxDeclines,
        tmnxDhcpSvrStatsRxInforms,
        tmnxDhcpSvrStatsTxOffers,
        tmnxDhcpSvrStatsTxAcks,
        tmnxDhcpSvrStatsTxNaks,
        tmnxDhcpSvrStatsTxForceRenews,
        tmnxDhcpSvrStatsDropBadPackets,
        tmnxDhcpSvrStatsDropInvalidTypes,
        tmnxDhcpSvrStatsDropNoUsrDbFound,
        tmnxDhcpSvrStatsDropUnknownHosts,
        tmnxDhcpSvrStatsDropUserNotAllow,
        tmnxDhcpSvrStatsDropLseNotReady,
        tmnxDhcpSvrStatsDropNoLeaseFound,
        tmnxDhcpSvrStatsDropNotSrvngPool,
        tmnxDhcpSvrStatsDropInvalidUsr,
        tmnxDhcpSvrStatsDropOverload,
        tmnxDhcpSvrStatsDropPersOverload,
        tmnxDhcpSvrStatsOffersIgnore,
        tmnxDhcpSvrStatsDropGenError,
        tmnxDhcpSvrStatsDropDestOther,
        tmnxDhcpSvrStatsDropAddrUnavail,
        tmnxDhcpSvrStatsDropMaxReached,
        tmnxDhcpSvrStatsDropSvrDown,
        tmnxDhcpSvrStatsDropNoSubnet,
        tmnxDhcpSvrStatsLeasesExpired,
        tmnxDhcpSvrStatsDropDuplDiffGi,
        tmnxDhcpSvrSubnetStatsFree,
        tmnxDhcpSvrSubnetStatsOffered,
        tmnxDhcpSvrSubnetStatsStable,
        tmnxDhcpSvrSubnetStatsFRPending,
        tmnxDhcpSvrSubnetStatsRemPending,
        tmnxDhcpSvrSubnetStatsDeclined
    }
    STATUS      obsolete
    DESCRIPTION
        "The group of objects providing DHCP statistics on Nokia SROS series
         systems release 6.1."
    ::= { tmnxDhcpServerGroups 9 }

tmnxDhcpServerV8v0Group          OBJECT-GROUP
    OBJECTS     {
        tmnxDhcpServerConfigTableLastCh,
        tmnxDhcpServerCfgRowStatus,
        tmnxDhcpServerCfgLastChangeTime,
        tmnxDhcpServerCfgAdminState,
        tmnxDhcpServerCfgDescription,
        tmnxDhcpServerCfgUserDatabase,
        tmnxDhcpServerCfgUseGiAddress,
        tmnxDhcpServerCfgSendForceRenews,
        tmnxDhcpServerCfgUseClientPool,
        tmnxDhcpServerCfgOperState,
        tmnxDhcpServerPoolTableLastCh,
        tmnxDhcpServerPoolRowStatus,
        tmnxDhcpServerPoolLastChangeTime,
        tmnxDhcpServerPoolDescription,
        tmnxDhcpServerPoolMinLeaseTime,
        tmnxDhcpServerPoolMaxLeaseTime,
        tmnxDhcpServerPoolOfferTime,
        tmnxDhcpSvrPoolOptionTableLastCh,
        tmnxDhcpSvrPoolOptionRowStatus,
        tmnxDhcpSvrPoolOptionLastCh,
        tmnxDhcpSvrPoolOptionType,
        tmnxDhcpSvrPoolOptionValue,
        tmnxDhcpServerSubnetTableLastCh,
        tmnxDhcpSvrSubnetRowStatus,
        tmnxDhcpSvrSubnetLastChangeTime,
        tmnxDhcpSvrSubnetMinFree,
        tmnxDhcpSvrSubnetMaxDeclined,
        tmnxDhcpSvrSubnetRangesTblLastCh,
        tmnxDhcpSvrSubnetRangesRowStatus,
        tmnxDhcpSvrSubnetRangesLastCh,
        tmnxDhcpSvrSubnetOptionTblLastCh,
        tmnxDhcpSvrSubnetOptionRowStatus,
        tmnxDhcpSvrSubnetOptionLastCh,
        tmnxDhcpSvrSubnetOptionType,
        tmnxDhcpSvrSubnetOptionValue,
        tmnxDhcpSvrSubnetMinFreeType,
        tmnxDhcpServerPoolMinFree,
        tmnxDhcpServerPoolMinFreeType
    }
    STATUS      current
    DESCRIPTION
        "The group of objects supporting DHCP server capability on Nokia SROS
         series systems release 8.0."
    ::= { tmnxDhcpServerGroups 10 }

tmnxDhcpStatsV8v0Group           OBJECT-GROUP
    OBJECTS     {
        tmnxDhcpSvrStatsRxDiscovers,
        tmnxDhcpSvrStatsRxRequests,
        tmnxDhcpSvrStatsRxReleases,
        tmnxDhcpSvrStatsRxDeclines,
        tmnxDhcpSvrStatsRxInforms,
        tmnxDhcpSvrStatsTxOffers,
        tmnxDhcpSvrStatsTxAcks,
        tmnxDhcpSvrStatsTxNaks,
        tmnxDhcpSvrStatsTxForceRenews,
        tmnxDhcpSvrStatsDropBadPackets,
        tmnxDhcpSvrStatsDropInvalidTypes,
        tmnxDhcpSvrStatsDropNoUsrDbFound,
        tmnxDhcpSvrStatsDropUnknownHosts,
        tmnxDhcpSvrStatsDropUserNotAllow,
        tmnxDhcpSvrStatsDropLseNotReady,
        tmnxDhcpSvrStatsDropNoLeaseFound,
        tmnxDhcpSvrStatsDropNotSrvngPool,
        tmnxDhcpSvrStatsDropInvalidUsr,
        tmnxDhcpSvrStatsDropOverload,
        tmnxDhcpSvrStatsDropPersOverload,
        tmnxDhcpSvrStatsOffersIgnore,
        tmnxDhcpSvrStatsDropGenError,
        tmnxDhcpSvrStatsDropDestOther,
        tmnxDhcpSvrStatsDropAddrUnavail,
        tmnxDhcpSvrStatsDropMaxReached,
        tmnxDhcpSvrStatsDropSvrDown,
        tmnxDhcpSvrStatsDropNoSubnet,
        tmnxDhcpSvrStatsLeasesExpired,
        tmnxDhcpSvrStatsDropDuplDiffGi,
        tmnxDhcpSvrSubnetStatsFree,
        tmnxDhcpSvrSubnetStatsOffered,
        tmnxDhcpSvrSubnetStatsStable,
        tmnxDhcpSvrSubnetStatsFRPending,
        tmnxDhcpSvrSubnetStatsRemPending,
        tmnxDhcpSvrSubnetStatsDeclined,
        tmnxDhcpSvrSubnetStatsProv,
        tmnxDhcpSvrSubnetStatsFoProv
    }
    STATUS      current
    DESCRIPTION
        "The group of objects providing DHCP statistics on Nokia SROS series
         systems release 8.0."
    ::= { tmnxDhcpServerGroups 11 }

tmnxDhcpServerV9v0Group          OBJECT-GROUP
    OBJECTS     {
        tmnxDhcpServerCfgAddrType,
        tmnxDhcpServerCfgLeaseHoldTime,
        tmnxDhcpServerCfgUseGiScope,
        tmnxDhcpSvrSubnetRenewTimer,
        tmnxDhcpSvrSubnetRebindTimer,
        tmnxDhcpSvrSubnetValidLifetime,
        tmnxDhcpSvrSubnetPrefLifetime,
        tmnxDhcpSvrLeaseClientPrefixLen,
        tmnxDhcpSvrLeaseIAOptionType,
        tmnxDhcpSvrLeaseIAID,
        tmnxDhcpSvrLeaseDUID,
        tmnxDhcpSvrLeaseRemainHoldTime
    }
    STATUS      current
    DESCRIPTION
        "The group of objects supporting DHCP server capability on Nokia SROS
         series systems added in release 9.0."
    ::= { tmnxDhcpServerGroups 12 }

tmnxDhcpStatsV9v0Group           OBJECT-GROUP
    OBJECTS     {
        tmnxDhcpSvrStats6RxSolicits,
        tmnxDhcpSvrStats6TxAdvertises,
        tmnxDhcpSvrStats6RxRequests,
        tmnxDhcpSvrStats6RxConfirms,
        tmnxDhcpSvrStats6RxRenews,
        tmnxDhcpSvrStats6RxRebinds,
        tmnxDhcpSvrStats6RxDeclines,
        tmnxDhcpSvrStats6RxReleases,
        tmnxDhcpSvrStats6TxReplies,
        tmnxDhcpSvrStats6TxReconfigures,
        tmnxDhcpSvrStats6RxInfRequests,
        tmnxDhcpSvrStats6DropBadPackets,
        tmnxDhcpSvrStats6DropInvldTypes,
        tmnxDhcpSvrStats6DropLseNotReady,
        tmnxDhcpSvrStats6DropNoSrvngPool,
        tmnxDhcpSvrStats6DropOverload,
        tmnxDhcpSvrStats6DropPerOverload,
        tmnxDhcpSvrStats6OffersIgnore,
        tmnxDhcpSvrStats6DropGenError,
        tmnxDhcpSvrStats6DropDestOther,
        tmnxDhcpSvrStats6DropMaxReached,
        tmnxDhcpSvrStats6DropSvrDown,
        tmnxDhcpSvrStats6LeasesExpired,
        tmnxDhcpSvrSubnetStats6Advertise,
        tmnxDhcpSvrSubnetStats6Stable,
        tmnxDhcpSvrSubnetStats6RCPending,
        tmnxDhcpSvrSubnetStats6RmPending,
        tmnxDhcpSvrSubnetStats6Declined
    }
    STATUS      current
    DESCRIPTION
        "The group of objects providing DHCP statistics on Nokia SROS series
         systems since release 9.0."
    ::= { tmnxDhcpServerGroups 13 }

tmnxDhcpsNotifyObjsV9v0Group     OBJECT-GROUP
    OBJECTS     {
        tmnxDhcpSvrNotifLeaseClientAddrLen,
        tmnxDhcpSvrNotifClientDUID
    }
    STATUS      current
    DESCRIPTION
        "The group of objects supporting DHCP server notifications on Nokia
         SROS series systems since release 9.0."
    ::= { tmnxDhcpServerGroups 14 }

tmnxDhcpServerV10v0Group         OBJECT-GROUP
    OBJECTS     {
        tmnxDhcpServerPoolDepletedEvent,
        tmnxDhcpSvrSubnetDepletedEvent,
        tmnxDhcpSvrSubnetFailCtrl,
        tmnxDhcpServerCfgIgnRapidCommit,
        tmnxDhcpServerCfgUserIdent,
        tmnxDhcpServerCfgItfIdMapping,
        tmnxDhcpSvrLeaseRelayInterfaceId,
        tmnxDhcpSvrLeaseLDRAInterfaceId,
        tmnxDhcpSvrLeaseLnkLclAddrType,
        tmnxDhcpSvrLeaseLnkLclAddress,
        tmnxDhcpSvrSubnetPrefixType,
        tmnxDhcpSvrStats6DropDuplDiffRly
    }
    STATUS      current
    DESCRIPTION
        "The group of objects supporting DHCP server capability on Nokia SROS
         series systems added in release 10.0."
    ::= { tmnxDhcpServerGroups 15 }

tmnxDhcpServerV11v0Group         OBJECT-GROUP
    OBJECTS     {
        tmnxDhcpSvrSubnetDrain,
        tmnxDhcpServerCfgUseCPDelimiter,
        tmnxDhcpServerPoolDlgatedPfxLen,
        tmnxDhcpServerCfgCreationOrigin,
        tmnxDhcpServerPoolSubnetBindKey,
        tmnxDhcpServerPoolSubnetBindDly,
        tmnxDhcpSvrSubnetBindSystemId,
        tmnxDhcpSvrSubnetBindServiceId,
        tmnxDhcpSvrSubnetBindString,
        tmnxDhcpSvrSubnetBindUnbindTime,
        tmnxDhcpSvrSubnetBindState,
        tmnxDhcpSvrSubntBndngTbleLastCh
    }
    STATUS      obsolete
    DESCRIPTION
        "The group of objects supporting DHCP server capability on Nokia SROS
         series systems added in release 11.0."
    ::= { tmnxDhcpServerGroups 16 }

tmnxDhcpStatsV11v0Group          OBJECT-GROUP
    OBJECTS     {
        tmnxDhcpSvrPoolStatsFree,
        tmnxDhcpSvrPoolStatsOffered,
        tmnxDhcpSvrPoolStatsStable,
        tmnxDhcpSvrPoolStatsFRPending,
        tmnxDhcpSvrPoolStatsRemPending,
        tmnxDhcpSvrPoolStatsDeclined,
        tmnxDhcpSvrPoolStatsFoFree,
        tmnxDhcpSvrPoolStatsFoOffered,
        tmnxDhcpSvrPoolStatsFoStable,
        tmnxDhcpSvrPoolStatsFoFRPend,
        tmnxDhcpSvrPoolStatsFoRemPend,
        tmnxDhcpSvrPoolStatsFoDeclined,
        tmnxDhcpSvrPoolStatsProv,
        tmnxDhcpSvrPoolStatsFoProv,
        tmnxDhcpSvrPoolStatsHasExt,
        tmnxDhcpSvrPoolStatsExtResetT,
        tmnxDhcpSvrPoolStatsStableP,
        tmnxDhcpSvrPoolStatsStablePT,
        tmnxDhcpSvrPoolStatsFoStableP,
        tmnxDhcpSvrPoolStatsFoStablePT,
        tmnxDhcpSvrPoolStatsUsed,
        tmnxDhcpSvrPoolStatsUsedP,
        tmnxDhcpSvrPoolStatsUsedPT,
        tmnxDhcpSvrPoolStatsFoUsed,
        tmnxDhcpSvrPoolStatsFoUsedP,
        tmnxDhcpSvrPoolStatsFoUsedPT,
        tmnxDhcpSvrPoolStatsFree,
        tmnxDhcpSvrPoolStatsFreeP,
        tmnxDhcpSvrPoolStatsFreePT,
        tmnxDhcpSvrPoolStatsFoFree,
        tmnxDhcpSvrPoolStatsFoFreeP,
        tmnxDhcpSvrPoolStatsFoFreePT,
        tmnxDhcpSvrPoolStatsUsedPct,
        tmnxDhcpSvrPoolStatsUsedPctP,
        tmnxDhcpSvrPoolStatsUsedPctPT,
        tmnxDhcpSvrPoolStatsFoUsdPct,
        tmnxDhcpSvrPoolStatsFoUsdPctP,
        tmnxDhcpSvrPoolStatsFoUsdPctPT,
        tmnxDhcpSvrPoolStatsFreePct,
        tmnxDhcpSvrPoolStatsFreePctP,
        tmnxDhcpSvrPoolStatsFreePctPT,
        tmnxDhcpSvrPoolStatsFoFrePct,
        tmnxDhcpSvrPoolStatsFoFrePctP,
        tmnxDhcpSvrPoolStatsFoFrePctPT,
        tmnxDhcpSvrPoolStatsOfferP,
        tmnxDhcpSvrPoolStatsOfferPT,
        tmnxDhcpSvrPoolStatsFoOfferP,
        tmnxDhcpSvrPoolStatsFoOfferPT,
        tmnxDhcpSvrStatsRxIntRequests,
        tmnxDhcpSvrStatsRxIntReleases,
        tmnxDhcpSvrStatsDropIntWithLudb,
        tmnxDhcpSvrStatsDropIntWithFo,
        tmnxDhcpSvrStatsDropIntConflicts,
        tmnxDhcpSvrStatsDropTxFailed,
        tmnxDhcpSvrSubnetStats6HasExt,
        tmnxDhcpSvrSubnetStats6ExtResetT,
        tmnxDhcpSvrSubnetStats6StableP,
        tmnxDhcpSvrSubnetStats6StablePT,
        tmnxDhcpSvrSubnetStats6ProvBlk,
        tmnxDhcpSvrSubnetStats6UsedBlk,
        tmnxDhcpSvrSubnetStats6UsedBlkP,
        tmnxDhcpSvrSubnetStats6UsedBlkPT,
        tmnxDhcpSvrSubnetStats6FreeBlk,
        tmnxDhcpSvrSubnetStats6FreeBlkP,
        tmnxDhcpSvrSubnetStats6FreeBlkPT,
        tmnxDhcpSvrSubnetStats6UsedPct,
        tmnxDhcpSvrSubnetStats6UsedPctP,
        tmnxDhcpSvrSubnetStats6UsedPctPT,
        tmnxDhcpSvrSubnetStats6FreePct,
        tmnxDhcpSvrSubnetStats6FreePctP,
        tmnxDhcpSvrSubnetStats6FreePctPT,
        tmnxDhcpSvrSubnetStats6AdvertP,
        tmnxDhcpSvrSubnetStats6AdvertPT,
        tmnxDhcpsPoolStats6Stable,
        tmnxDhcpsPoolStats6FoStable,
        tmnxDhcpsPoolStats6HasExt,
        tmnxDhcpsPoolStats6ExtResetT,
        tmnxDhcpsPoolStats6StableP,
        tmnxDhcpsPoolStats6StablePT,
        tmnxDhcpsPoolStats6FoStableP,
        tmnxDhcpsPoolStats6FoStablePT,
        tmnxDhcpsPoolStats6ProvBlk,
        tmnxDhcpsPoolStats6FoProvBlk,
        tmnxDhcpsPoolStats6UsedBlk,
        tmnxDhcpsPoolStats6UsedBlkP,
        tmnxDhcpsPoolStats6UsedBlkPT,
        tmnxDhcpsPoolStats6FoUsedBlk,
        tmnxDhcpsPoolStats6FoUsedBlkP,
        tmnxDhcpsPoolStats6FoUsedBlkPT,
        tmnxDhcpsPoolStats6FreeBlk,
        tmnxDhcpsPoolStats6FreeBlkP,
        tmnxDhcpsPoolStats6FreeBlkPT,
        tmnxDhcpsPoolStats6FoFreeBlk,
        tmnxDhcpsPoolStats6FoFreeBlkP,
        tmnxDhcpsPoolStats6FoFreeBlkPT,
        tmnxDhcpsPoolStats6UsedPct,
        tmnxDhcpsPoolStats6UsedPctP,
        tmnxDhcpsPoolStats6UsedPctPT,
        tmnxDhcpsPoolStats6FoUsedPct,
        tmnxDhcpsPoolStats6FoUsedPctP,
        tmnxDhcpsPoolStats6FoUsedPctPT,
        tmnxDhcpsPoolStats6FreePct,
        tmnxDhcpsPoolStats6FreePctP,
        tmnxDhcpsPoolStats6FreePctPT,
        tmnxDhcpsPoolStats6FoFreePct,
        tmnxDhcpsPoolStats6FoFreePctP,
        tmnxDhcpsPoolStats6FoFreePctPT,
        tmnxDhcpsPoolStats6Advertise,
        tmnxDhcpsPoolStats6AdvertP,
        tmnxDhcpsPoolStats6AdvertPT,
        tmnxDhcpsPoolStats6FoAdvertise,
        tmnxDhcpsPoolStats6FoAdvertP,
        tmnxDhcpsPoolStats6FoAdvertPT,
        tmnxDhcpsPoolStats6IntNoPfxWan,
        tmnxDhcpsPoolStats6IntNoPfxSlaa,
        tmnxDhcpSvrSubnetStatsHasExt,
        tmnxDhcpSvrSubnetStatsExtResetT,
        tmnxDhcpSvrSubnetStatsStableP,
        tmnxDhcpSvrSubnetStatsStablePT,
        tmnxDhcpSvrSubnetStatsFoStableP,
        tmnxDhcpSvrSubnetStatsFoStablePT,
        tmnxDhcpSvrSubnetStatsUsed,
        tmnxDhcpSvrSubnetStatsUsedP,
        tmnxDhcpSvrSubnetStatsUsedPT,
        tmnxDhcpSvrSubnetStatsFoUsed,
        tmnxDhcpSvrSubnetStatsFoUsedP,
        tmnxDhcpSvrSubnetStatsFoUsedPT,
        tmnxDhcpSvrSubnetStatsFreeP,
        tmnxDhcpSvrSubnetStatsFreePT,
        tmnxDhcpSvrSubnetStatsFoFreeP,
        tmnxDhcpSvrSubnetStatsFoFreePT,
        tmnxDhcpSvrSubnetStatsUsedPct,
        tmnxDhcpSvrSubnetStatsUsedPctP,
        tmnxDhcpSvrSubnetStatsUsedPctPT,
        tmnxDhcpSvrSubnetStatsFoUsdPct,
        tmnxDhcpSvrSubnetStatsFoUsdPctP,
        tmnxDhcpSvrSubnetStatsFoUsdPctPT,
        tmnxDhcpSvrSubnetStatsFreePct,
        tmnxDhcpSvrSubnetStatsFreePctP,
        tmnxDhcpSvrSubnetStatsFreePctPT,
        tmnxDhcpSvrSubnetStatsFoFrePct,
        tmnxDhcpSvrSubnetStatsFoFrePctP,
        tmnxDhcpSvrSubnetStatsFoFrePctPT,
        tmnxDhcpSvrSubnetStatsOfferP,
        tmnxDhcpSvrSubnetStatsOfferPT,
        tmnxDhcpSvrSubnetStatsFoOfferP,
        tmnxDhcpSvrSubnetStatsFoOfferPT
    }
    STATUS      obsolete
    DESCRIPTION
        "The group of objects providing DHCP statistics on Nokia SROS series
         systems since release 11.0."
    ::= { tmnxDhcpServerGroups 17 }

tmnxDhcpsFailoverV11v0Group      OBJECT-GROUP
    OBJECTS     {
        tmnxDhcpsFoIgnoreMclt,
        tmnxDhcpsPoolFoTableLastChanged,
        tmnxDhcpsPoolFoLastChanged,
        tmnxDhcpsPoolFoAdminState,
        tmnxDhcpsPoolFoMCLT,
        tmnxDhcpsPoolFoOperMCLT,
        tmnxDhcpsPoolFoStartupWaitTime,
        tmnxDhcpsPoolFoPartnerDownDelay,
        tmnxDhcpsPoolFoState,
        tmnxDhcpsPoolFoTimeLeft,
        tmnxDhcpsPoolFoIgnoreMclt,
        tmnxDhcpsPoolFoStatsLeaseNFound,
        tmnxDhcpsPoolFoStatsDropInvPkts,
        tmnxDhcpsPoolFoStatsFoShutdown,
        tmnxDhcpsPoolFoStatsExpired,
        tmnxDhcpsPoolFoStatsMaxReached,
        tmnxDhcpsPoolFoStatsSubnetNFound,
        tmnxDhcpsPoolFoStatsRangeNFound,
        tmnxDhcpsPoolFoStatsHostConflict,
        tmnxDhcpsPoolFoStatsAddrConflict,
        tmnxDhcpsPoolFoStatsPeerConflict,
        tmnxDhcpsPoolFoStatsPersistCong,
        tmnxDhcpsFoActionPoolName
    }
    STATUS      current
    DESCRIPTION
        "The group of objects supporting DHCP server failover capability on
         Nokia SROS series systems in release 11.0."
    ::= { tmnxDhcpServerGroups 18 }

tmnxDhcpServerDuidGroup          OBJECT-GROUP
    OBJECTS     {
        tmnxDhcpServerDuidTableLastCh,
        tmnxDhcpServerDuidLastChanged,
        tmnxDhcpServerDuidTypeCode,
        tmnxDhcpServerDuidEnNumber,
        tmnxDhcpServerDuidEnIdData,
        tmnxDhcpServerDuidEnIdDataType
    }
    STATUS      current
    DESCRIPTION
        "The group of objects supporting DHCP Unique Identifier (DUID)
         capability on Nokia SROS series systems."
    ::= { tmnxDhcpServerGroups 19 }

tmnxDhcpsNotifyObjsV11v0Group    OBJECT-GROUP
    OBJECTS     {
        tmnxDhcpSvrNotifLinkAddr,
        tmnxDhcpSvrNotifPrimaryPool,
        tmnxDhcpSvrNotifSecondaryPool,
        tmnxDhcpSvrNotifSystemId,
        tmnxDhcpSvrNotifServiceId,
        tmnxDhcpSvrNotifString,
        tmnxDhcpSvrNotifPoolName,
        tmnxDhcpSvrNotifSubnetAddrType,
        tmnxDhcpSvrNotifSubnetPfx,
        tmnxDhcpSvrNotifSubnetPfxlen,
        tmnxDhcpSvrNotifUnbindTime
    }
    STATUS      current
    DESCRIPTION
        "The group of objects supporting DHCP server notifications added in
         Nokia SROS release 11.0."
    ::= { tmnxDhcpServerGroups 20 }

tmnxDhcpServerV12v0Group         OBJECT-GROUP
    OBJECTS     {
        tmnxDhcpSvrSubnetDrain,
        tmnxDhcpServerCfgUseCPDelimiter,
        tmnxDhcpServerPoolDlgatedPfxLen,
        tmnxDhcpServerCfgCreationOrigin,
        tmnxDhcpSvrStats6RxIntPppSlaac,
        tmnxDhcpSvrStats6RxIntReqIpoeWan,
        tmnxDhcpSvrStats6RxIntReleases,
        tmnxDhcpSvrStats6DropIntWFo,
        tmnxDhcpSvrStats6DropIntWConflct,
        tmnxDhcpSvrStats6DropIntWIfIdMap,
        tmnxDhcpSvrStats6DropIntWUserId,
        tmnxDhcpSvrStats6RxIntIpoeSlaac,
        tmnxDhcpSvrStatsDropAudit,
        tmnxDhcpSvrStats6DropAudit
    }
    STATUS      current
    DESCRIPTION
        "The group of objects supporting DHCP server capability on Nokia SROS
         series systems (added) in release 12.0."
    ::= { tmnxDhcpServerGroups 21 }

tmnxDhcpsFailoverV10v0Group      OBJECT-GROUP
    OBJECTS     {
        tmnxDhcpsFoStatsPersistCongest
    }
    STATUS      current
    DESCRIPTION
        "The group of objects supporting DHCP server failover capability on
         Nokia SROS series systems in release 10.0."
    ::= { tmnxDhcpServerGroups 22 }

tmnxDhcpLeaseV12v0Group          OBJECT-GROUP
    OBJECTS     {
        tmnxDhcpSvrLeaseIntClientType
    }
    STATUS      current
    DESCRIPTION
        "The group of objects providing DHCP lease information added in release
         12.0 of Nokia SROS series systems."
    ::= { tmnxDhcpServerGroups 23 }

tmnxDhcpServerV13v0Group         OBJECT-GROUP
    OBJECTS     {
        tmnxDhcpServerCfgLeaseHoldFor,
        tmnxDhcpServerCfgAllowLeaseQuery,
        tmnxDhcpServerPoolNakNonMatch,
        tmnxDhcpsPlMinFreePercent,
        tmnxDhcpsPlMinFreeDepletedEvent,
        tmnxDhcpsPlMinFreeLastCh,
        tmnxDhcpsPlMinFreeRowStatus,
        tmnxDhcpsPlMinFreeTableLastCh,
        tmnxDhcpsPfxMinFreeRowStatus,
        tmnxDhcpsPfxMinFreeLastCh,
        tmnxDhcpsPfxMinFreePercent,
        tmnxDhcpsPfxMinFreeNumber,
        tmnxDhcpsPfxMinFreeDepletedEvent,
        tmnxDhcpsPfxMinFreeTableLastCh,
        tmnxDhcpSvrSubnetActive,
        tmnxDhcpSvrLeaseOpt82RemoteId,
        tmnxDhcpSvrLeaseOpt61ClientId,
        tmnxDhcps6ExclPfxTableLastCh,
        tmnxDhcps6ExclPfxRowStatus,
        tmnxDhcps6ExclPfxLastChangeTime
    }
    STATUS      current
    DESCRIPTION
        "The group of objects supporting DHCP server capability on Nokia SROS
         series systems added in release 13.0."
    ::= { tmnxDhcpServerGroups 24 }

tmnxDhcpStatsV13v0Group          OBJECT-GROUP
    OBJECTS     {
        tmnxDhcpsPlThStats6TableLastCh,
        tmnxDhcpsPlThCurrProvBlksHw,
        tmnxDhcpsPlThCurrProvBlksLw,
        tmnxDhcpsPlThCurrUsedBlksHw,
        tmnxDhcpsPlThCurrUsedBlksLw,
        tmnxDhcpsPlThCurrFreeBlksHw,
        tmnxDhcpsPlThCurrFreeBlksLw,
        tmnxDhcpsPlThCurrUsedPct,
        tmnxDhcpsPlThCurrUsedPeakBlksHw,
        tmnxDhcpsPlThCurrUsedPeakBlksLw,
        tmnxDhcpsPlThCurrUsedPeakPct,
        tmnxDhcpsPlThCurrUsedPeakTime,
        tmnxDhcpsPlThCurrFreePct,
        tmnxDhcpsPlThCurrFreeTooLow,
        tmnxDhcpsPlThCurrFreeDepleted,
        tmnxDhcpsPlThLclProvBlksHw,
        tmnxDhcpsPlThLclProvBlksLw,
        tmnxDhcpsPlThLclUsedBlksHw,
        tmnxDhcpsPlThLclUsedBlksLw,
        tmnxDhcpsPlThLclFreeBlksHw,
        tmnxDhcpsPlThLclFreeBlksLw,
        tmnxDhcpsPlThLclUsedPeakBlksHw,
        tmnxDhcpsPlThLclUsedPeakBlksLw,
        tmnxDhcpsPlThLclUsedPeakPct,
        tmnxDhcpsPlThLclUsedPeakTime,
        tmnxDhcpsPlThRemProvBlksHw,
        tmnxDhcpsPlThRemProvBlksLw,
        tmnxDhcpsPlThRemUsedBlksHw,
        tmnxDhcpsPlThRemUsedBlksLw,
        tmnxDhcpsPlThRemFreeBlksHw,
        tmnxDhcpsPlThRemFreeBlksLw,
        tmnxDhcpsPlThRemUsedPeakBlksHw,
        tmnxDhcpsPlThRemUsedPeakBlksLw,
        tmnxDhcpsPlThRemUsedPeakPct,
        tmnxDhcpsPlThRemUsedPeakTime,
        tmnxDhcpsPlThPeakResetTime,
        tmnxDhcpsPlThValidData,
        tmnxDhcpsPfxThStats6TableLastCh,
        tmnxDhcpsPfxThCurrProvBlksHw,
        tmnxDhcpsPfxThCurrProvBlksLw,
        tmnxDhcpsPfxThCurrUsedBlksHw,
        tmnxDhcpsPfxThCurrUsedBlksLw,
        tmnxDhcpsPfxThCurrFreeBlksHw,
        tmnxDhcpsPfxThCurrFreeBlksLw,
        tmnxDhcpsPfxThCurrUsedPct,
        tmnxDhcpsPfxThCurrUsedPeakBlksHw,
        tmnxDhcpsPfxThCurrUsedPeakBlksLw,
        tmnxDhcpsPfxThCurrUsedPeakPct,
        tmnxDhcpsPfxThCurrUsedPeakTime,
        tmnxDhcpsPfxThCurrFreePct,
        tmnxDhcpsPfxThCurrFreeTooLow,
        tmnxDhcpsPfxThCurrFreeDepleted,
        tmnxDhcpsPfxThLclProvBlksHw,
        tmnxDhcpsPfxThLclProvBlksLw,
        tmnxDhcpsPfxThLclUsedBlksHw,
        tmnxDhcpsPfxThLclUsedBlksLw,
        tmnxDhcpsPfxThLclFreeBlksHw,
        tmnxDhcpsPfxThLclFreeBlksLw,
        tmnxDhcpsPfxThLclUsedPeakBlksHw,
        tmnxDhcpsPfxThLclUsedPeakBlksLw,
        tmnxDhcpsPfxThLclUsedPeakPct,
        tmnxDhcpsPfxThLclUsedPeakTime,
        tmnxDhcpsPfxThRemProvBlksHw,
        tmnxDhcpsPfxThRemProvBlksLw,
        tmnxDhcpsPfxThRemUsedBlksHw,
        tmnxDhcpsPfxThRemUsedBlksLw,
        tmnxDhcpsPfxThRemFreeBlksHw,
        tmnxDhcpsPfxThRemFreeBlksLw,
        tmnxDhcpsPfxThRemUsedPeakBlksHw,
        tmnxDhcpsPfxThRemUsedPeakBlksLw,
        tmnxDhcpsPfxThRemUsedPeakPct,
        tmnxDhcpsPfxThRemUsedPeakTime,
        tmnxDhcpsPfxThPeakResetTime,
        tmnxDhcpsPfxThValidData,
        tmnxDhcpSvrStats6RxLeasequeries,
        tmnxDhcpSvrStats6TxLqReplies,
        tmnxDhcpSvrStats6DropLqNotAllow
    }
    STATUS      current
    DESCRIPTION
        "The group of objects providing DHCP statistics on Nokia SROS series
         systems since release 13.0."
    ::= { tmnxDhcpServerGroups 25 }

tmnxDhcpServerStickyLseGroup     OBJECT-GROUP
    OBJECTS     {
        tmnxDhcpsStickyLseActVRtrId,
        tmnxDhcpsStickyLseActServerName,
        tmnxDhcpsStickyLseActPoolName,
        tmnxDhcpsStickyLseActHostName,
        tmnxDhcpsStickyLseActActionType,
        tmnxDhcpsStickyLseActActionGo,
        tmnxDhcpsStickyLseActResultCode,
        tmnxDhcpsStickyLseActErrorMsg,
        tmnxDhcpsStickyLseActActionTime,
        tmnxDhcpsStickyLseActMacAddress,
        tmnxDhcpsStickyLseActCircuitId,
        tmnxDhcpsStickyLseActClientId,
        tmnxDhcpsStickyLseActAddressType,
        tmnxDhcpsStickyLseActAddress,
        tmnxDhcpsStickyLeaseAddressType,
        tmnxDhcpsStickyLeaseAddress,
        tmnxDhcpSvrLeaseStickyHostName
    }
    STATUS      current
    DESCRIPTION
        "The group of objects supporting DHCP server Sticky Lease capability on
         Nokia SROS series systems added in release 14.0."
    ::= { tmnxDhcpServerGroups 26 }

tmnxDhcpsPrefixLenExtensionGroup OBJECT-GROUP
    OBJECTS     {
        tmnxDhcpServerPoolMinPrefixLen,
        tmnxDhcpServerPoolMaxPrefixLen,
        tmnxDhcpsFoStatsInvalidPfxLen,
        tmnxDhcpsPoolFoStatsInvaldPfxLen
    }
    STATUS      current
    DESCRIPTION
        "The group of objects supporting the DHCP server IPv6 prefix length
         range extension Sticky Lease capability on Nokia SROS series systems."
    ::= { tmnxDhcpServerGroups 27 }

tmnxDhcpsFailoverV12v0Group      OBJECT-GROUP
    OBJECTS     {
        tmnxDhcpsFoStatsNoLeaseHoldTime,
        tmnxDhcpsPoolFoStatsNoLeaseHoldT
    }
    STATUS      current
    DESCRIPTION
        "The group of objects supporting DHCP server failover capability on
         Nokia SROS series systems since release 12.0."
    ::= { tmnxDhcpServerGroups 28 }

tmnxDhcpsAutoProvisionGroup      OBJECT-GROUP
    OBJECTS     {
        tmnxDhcpServerCfgAutoProvisioned,
        tmnxDhcpsDefTableLastCh,
        tmnxDhcpsDefLastChangeTime,
        tmnxDhcpsDefRenewTimer,
        tmnxDhcpsDefRebindTimer,
        tmnxDhcpsDefValidLifetime,
        tmnxDhcpsDefPrefLifetime,
        tmnxDhcpsDefOptionTableLastCh,
        tmnxDhcpsDefOptionRowStatus,
        tmnxDhcpsDefOptionLastCh,
        tmnxDhcpsDefOptionType,
        tmnxDhcpsDefOptionValue
    }
    STATUS      current
    DESCRIPTION
        "The group of objects supporting DHCP server automatic provisioning
         capability on Nokia SROS series systems."
    ::= { tmnxDhcpServerGroups 29 }

tmnxDhcpStatsV16v0Group          OBJECT-GROUP
    OBJECTS     {
        tmnxDhcpSvrPoolStatsFree,
        tmnxDhcpSvrPoolStatsOffered,
        tmnxDhcpSvrPoolStatsStable,
        tmnxDhcpSvrPoolStatsFRPending,
        tmnxDhcpSvrPoolStatsRemPending,
        tmnxDhcpSvrPoolStatsDeclined,
        tmnxDhcpSvrPoolStatsFoFree,
        tmnxDhcpSvrPoolStatsFoOffered,
        tmnxDhcpSvrPoolStatsFoStable,
        tmnxDhcpSvrPoolStatsFoFRPend,
        tmnxDhcpSvrPoolStatsFoRemPend,
        tmnxDhcpSvrPoolStatsFoDeclined,
        tmnxDhcpSvrPoolStatsProv,
        tmnxDhcpSvrPoolStatsFoProv,
        tmnxDhcpSvrPoolStatsHasExt,
        tmnxDhcpSvrPoolStatsExtResetT,
        tmnxDhcpSvrPoolStatsStableP,
        tmnxDhcpSvrPoolStatsStablePT,
        tmnxDhcpSvrPoolStatsFoStableP,
        tmnxDhcpSvrPoolStatsFoStablePT,
        tmnxDhcpSvrPoolStatsUsed,
        tmnxDhcpSvrPoolStatsUsedP,
        tmnxDhcpSvrPoolStatsUsedPT,
        tmnxDhcpSvrPoolStatsFoUsed,
        tmnxDhcpSvrPoolStatsFoUsedP,
        tmnxDhcpSvrPoolStatsFoUsedPT,
        tmnxDhcpSvrPoolStatsFree,
        tmnxDhcpSvrPoolStatsFreeP,
        tmnxDhcpSvrPoolStatsFreePT,
        tmnxDhcpSvrPoolStatsFoFree,
        tmnxDhcpSvrPoolStatsFoFreeP,
        tmnxDhcpSvrPoolStatsFoFreePT,
        tmnxDhcpSvrPoolStatsUsedPct,
        tmnxDhcpSvrPoolStatsUsedPctP,
        tmnxDhcpSvrPoolStatsUsedPctPT,
        tmnxDhcpSvrPoolStatsFoUsdPct,
        tmnxDhcpSvrPoolStatsFoUsdPctP,
        tmnxDhcpSvrPoolStatsFoUsdPctPT,
        tmnxDhcpSvrPoolStatsFreePct,
        tmnxDhcpSvrPoolStatsFreePctP,
        tmnxDhcpSvrPoolStatsFreePctPT,
        tmnxDhcpSvrPoolStatsFoFrePct,
        tmnxDhcpSvrPoolStatsFoFrePctP,
        tmnxDhcpSvrPoolStatsFoFrePctPT,
        tmnxDhcpSvrPoolStatsOfferP,
        tmnxDhcpSvrPoolStatsOfferPT,
        tmnxDhcpSvrPoolStatsFoOfferP,
        tmnxDhcpSvrPoolStatsFoOfferPT,
        tmnxDhcpSvrStatsRxIntReleases,
        tmnxDhcpSvrStatsDropIntWithLudb,
        tmnxDhcpSvrStatsDropIntWithFo,
        tmnxDhcpSvrStatsDropIntConflicts,
        tmnxDhcpSvrStatsDropTxFailed,
        tmnxDhcpSvrSubnetStats6HasExt,
        tmnxDhcpSvrSubnetStats6ExtResetT,
        tmnxDhcpSvrSubnetStats6StableP,
        tmnxDhcpSvrSubnetStats6StablePT,
        tmnxDhcpSvrSubnetStats6ProvBlk,
        tmnxDhcpSvrSubnetStats6UsedBlk,
        tmnxDhcpSvrSubnetStats6UsedBlkP,
        tmnxDhcpSvrSubnetStats6UsedBlkPT,
        tmnxDhcpSvrSubnetStats6FreeBlk,
        tmnxDhcpSvrSubnetStats6FreeBlkP,
        tmnxDhcpSvrSubnetStats6FreeBlkPT,
        tmnxDhcpSvrSubnetStats6UsedPct,
        tmnxDhcpSvrSubnetStats6UsedPctP,
        tmnxDhcpSvrSubnetStats6UsedPctPT,
        tmnxDhcpSvrSubnetStats6FreePct,
        tmnxDhcpSvrSubnetStats6FreePctP,
        tmnxDhcpSvrSubnetStats6FreePctPT,
        tmnxDhcpSvrSubnetStats6AdvertP,
        tmnxDhcpSvrSubnetStats6AdvertPT,
        tmnxDhcpsPoolStats6Stable,
        tmnxDhcpsPoolStats6FoStable,
        tmnxDhcpsPoolStats6HasExt,
        tmnxDhcpsPoolStats6ExtResetT,
        tmnxDhcpsPoolStats6StableP,
        tmnxDhcpsPoolStats6StablePT,
        tmnxDhcpsPoolStats6FoStableP,
        tmnxDhcpsPoolStats6FoStablePT,
        tmnxDhcpsPoolStats6ProvBlk,
        tmnxDhcpsPoolStats6FoProvBlk,
        tmnxDhcpsPoolStats6UsedBlk,
        tmnxDhcpsPoolStats6UsedBlkP,
        tmnxDhcpsPoolStats6UsedBlkPT,
        tmnxDhcpsPoolStats6FoUsedBlk,
        tmnxDhcpsPoolStats6FoUsedBlkP,
        tmnxDhcpsPoolStats6FoUsedBlkPT,
        tmnxDhcpsPoolStats6FreeBlk,
        tmnxDhcpsPoolStats6FreeBlkP,
        tmnxDhcpsPoolStats6FreeBlkPT,
        tmnxDhcpsPoolStats6FoFreeBlk,
        tmnxDhcpsPoolStats6FoFreeBlkP,
        tmnxDhcpsPoolStats6FoFreeBlkPT,
        tmnxDhcpsPoolStats6UsedPct,
        tmnxDhcpsPoolStats6UsedPctP,
        tmnxDhcpsPoolStats6UsedPctPT,
        tmnxDhcpsPoolStats6FoUsedPct,
        tmnxDhcpsPoolStats6FoUsedPctP,
        tmnxDhcpsPoolStats6FoUsedPctPT,
        tmnxDhcpsPoolStats6FreePct,
        tmnxDhcpsPoolStats6FreePctP,
        tmnxDhcpsPoolStats6FreePctPT,
        tmnxDhcpsPoolStats6FoFreePct,
        tmnxDhcpsPoolStats6FoFreePctP,
        tmnxDhcpsPoolStats6FoFreePctPT,
        tmnxDhcpsPoolStats6Advertise,
        tmnxDhcpsPoolStats6AdvertP,
        tmnxDhcpsPoolStats6AdvertPT,
        tmnxDhcpsPoolStats6FoAdvertise,
        tmnxDhcpsPoolStats6FoAdvertP,
        tmnxDhcpsPoolStats6FoAdvertPT,
        tmnxDhcpsPoolStats6IntNoPfxWan,
        tmnxDhcpsPoolStats6IntNoPfxSlaa,
        tmnxDhcpSvrSubnetStatsHasExt,
        tmnxDhcpSvrSubnetStatsExtResetT,
        tmnxDhcpSvrSubnetStatsStableP,
        tmnxDhcpSvrSubnetStatsStablePT,
        tmnxDhcpSvrSubnetStatsFoStableP,
        tmnxDhcpSvrSubnetStatsFoStablePT,
        tmnxDhcpSvrSubnetStatsUsed,
        tmnxDhcpSvrSubnetStatsUsedP,
        tmnxDhcpSvrSubnetStatsUsedPT,
        tmnxDhcpSvrSubnetStatsFoUsed,
        tmnxDhcpSvrSubnetStatsFoUsedP,
        tmnxDhcpSvrSubnetStatsFoUsedPT,
        tmnxDhcpSvrSubnetStatsFreeP,
        tmnxDhcpSvrSubnetStatsFreePT,
        tmnxDhcpSvrSubnetStatsFoFreeP,
        tmnxDhcpSvrSubnetStatsFoFreePT,
        tmnxDhcpSvrSubnetStatsUsedPct,
        tmnxDhcpSvrSubnetStatsUsedPctP,
        tmnxDhcpSvrSubnetStatsUsedPctPT,
        tmnxDhcpSvrSubnetStatsFoUsdPct,
        tmnxDhcpSvrSubnetStatsFoUsdPctP,
        tmnxDhcpSvrSubnetStatsFoUsdPctPT,
        tmnxDhcpSvrSubnetStatsFreePct,
        tmnxDhcpSvrSubnetStatsFreePctP,
        tmnxDhcpSvrSubnetStatsFreePctPT,
        tmnxDhcpSvrSubnetStatsFoFrePct,
        tmnxDhcpSvrSubnetStatsFoFrePctP,
        tmnxDhcpSvrSubnetStatsFoFrePctPT,
        tmnxDhcpSvrSubnetStatsOfferP,
        tmnxDhcpSvrSubnetStatsOfferPT,
        tmnxDhcpSvrSubnetStatsFoOfferP,
        tmnxDhcpSvrSubnetStatsFoOfferPT
    }
    STATUS      current
    DESCRIPTION
        "The group of objects providing DHCP statistics on Nokia SROS series
         systems since release 11.0."
    ::= { tmnxDhcpServerGroups 30 }

tmnxDhcpIntReqStatsGroup         OBJECT-GROUP
    OBJECTS     {
        tmnxDhcpSvrStatsRxIntReqPpp,
        tmnxDhcpSvrStatsRxIntReqIpoe,
        tmnxDhcpSvrStatsRxIntReqIpsec,
        tmnxDhcpSvrStats6RxIntIpsec
    }
    STATUS      current
    DESCRIPTION
        "The group of objects providing DHCP statistics on Nokia SROS series
         systems for internal requests."
    ::= { tmnxDhcpServerGroups 31 }

tmnxDhcpServerV16v0Group         OBJECT-GROUP
    OBJECTS     {
        tmnxDhcpSvrPoolOptionDisplay,
        tmnxDhcpSvrSubnetOptionDisplay,
        tmnxDhcpsDefOptionDisplay
    }
    STATUS      current
    DESCRIPTION
        "The group of objects supporting DHCP server capability on Nokia SROS
         series systems added in release 16.0."
    ::= { tmnxDhcpServerGroups 32 }

tmnxDhcpsNotifyObjsV20v0Group    OBJECT-GROUP
    OBJECTS     {
        tmnxDhcpSvrNotifGwIpAddrType,
        tmnxDhcpSvrNotifGatewayIpAddr
    }
    STATUS      current
    DESCRIPTION
        "The group of objects supporting DHCP server notifications added in
         Nokia SROS release 20.0."
    ::= { tmnxDhcpServerGroups 33 }

tmnxDhcpsObsoletedNotifyGroup    NOTIFICATION-GROUP
    NOTIFICATIONS {
        tmnxDhcpSvrSubnetBindingCreate,
        tmnxDhcpSvrSubnetBindingDelete,
        tmnxDhcpSvrSubnetBindingFailed,
        tmnxDhcpSvrSubnetBindingUnbind,
        tmnxDhcpSvrSubnetFailCtrlError
    }
    STATUS      current
    DESCRIPTION
        "The group of obsoleted DHCP Server notifications of Nokia SROS series
         systems."
    ::= { tmnxDhcpServerGroups 99 }

tmnxDhcpsObsoleteGroup           OBJECT-GROUP
    OBJECTS     {
        tmnxDhcpServerPoolSubnetBindDly,
        tmnxDhcpServerPoolSubnetBindKey,
        tmnxDhcpSvrSubnetBindSystemId,
        tmnxDhcpSvrSubnetBindServiceId,
        tmnxDhcpSvrSubnetBindString,
        tmnxDhcpSvrSubnetBindUnbindTime,
        tmnxDhcpSvrSubnetBindState,
        tmnxDhcpSvrSubntBndngTbleLastCh,
        tmnxDhcpSvrSubnetBindActive,
        tmnxDhcpSvrStatsRxIntRequests
    }
    STATUS      current
    DESCRIPTION
        "The group of obsoleted objects in this MIB."
    ::= { tmnxDhcpServerGroups 100 }

tmnxDhcpServerNotifGroups        OBJECT IDENTIFIER ::= { tmnxDhcpServerConformance 3 }

tmnxDhcpSvrNotifGroup            NOTIFICATION-GROUP
    NOTIFICATIONS {
        tmnxDhcpSvrSubnetMinFreeExc,
        tmnxDhcpSvrHostConflict,
        tmnxDhcpSvrPoolUnknown,
        tmnxDhcpSvrLeaseNotOwner,
        tmnxDhcpSvrDeclineStaticAddr,
        tmnxDhcpSvrMsgTooLong,
        tmnxDhcpSvrUserDbUnknown,
        tmnxDhcpSvrMaxLeasesReached,
        tmnxDhcpSvrNoSubnetFixAddr,
        tmnxDhcpSvrLeaseDefaultTimers,
        tmnxDhcpSvrPoolMinFreeExc
    }
    STATUS      current
    DESCRIPTION
        "The group of objects supporting traps for the DHCP server capability
         on Nokia SROS series systems."
    ::= { tmnxDhcpServerNotifGroups 1 }

tmnxDhcpSvrFoNotifGroup          NOTIFICATION-GROUP
    NOTIFICATIONS {
        tmnxDhcpsFoStateChange,
        tmnxDhcpsFoLeaseUpdateFailed
    }
    STATUS      current
    DESCRIPTION
        "The group of objects supporting traps for the failover facility of a
         DHCP server instance on Nokia SROS series systems."
    ::= { tmnxDhcpServerNotifGroups 2 }

tmnxDhcpSvrNotifV10v0Group       NOTIFICATION-GROUP
    NOTIFICATIONS {
        tmnxDhcpSvrSubnetDepleted,
        tmnxDhcpSvrPoolDepleted
    }
    STATUS      current
    DESCRIPTION
        "The group of objects supporting traps for the DHCP server capability
         on Nokia SROS series systems since release 10.0."
    ::= { tmnxDhcpServerNotifGroups 3 }

tmnxDhcpSvrNotifV11v0Group       NOTIFICATION-GROUP
    NOTIFICATIONS {
        tmnxDhcpSvrIntLseConflict,
        tmnxDhcpSvrLeaseModify,
        tmnxDhcpSvrLeaseCreate,
        tmnxDhcpSvrLeaseDelete,
        tmnxDhcpSvrNoContFreeBlocks,
        tmnxDhcpSvrSubnetBindingFailed,
        tmnxDhcpSvrSubnetFailCtrlError,
        tmnxDhcpsPoolFoStateChange,
        tmnxDhcpsPoolFoLeaseUpdateFailed,
        tmnxDhcpSvrSubnetBindingCreate,
        tmnxDhcpSvrSubnetBindingUnbind,
        tmnxDhcpSvrSubnetBindingDelete
    }
    STATUS      obsolete
    DESCRIPTION
        "The group of objects supporting traps for the DHCP server capability
         on Nokia SROS series systems since release 11.0."
    ::= { tmnxDhcpServerNotifGroups 4 }

tmnxDhcpSvrNotifV12v0Group       NOTIFICATION-GROUP
    NOTIFICATIONS {
        tmnxDhcpSvrIntLseConflict,
        tmnxDhcpSvrLeaseModify,
        tmnxDhcpSvrLeaseCreate,
        tmnxDhcpSvrLeaseDelete,
        tmnxDhcpSvrNoContFreeBlocks,
        tmnxDhcpsPoolFoStateChange,
        tmnxDhcpsPoolFoLeaseUpdateFailed
    }
    STATUS      current
    DESCRIPTION
        "The group of objects supporting traps for the DHCP server capability
         on Nokia SROS series systems since release 11.0."
    ::= { tmnxDhcpServerNotifGroups 5 }

tmnxDhcpSvrNotifV13v0Group       NOTIFICATION-GROUP
    NOTIFICATIONS {
        tmnxDhcpSvrPlThTooLowV6,
        tmnxDhcpSvrPlThDepletedV6,
        tmnxDhcpSvrPfxThTooLowV6,
        tmnxDhcpSvrPfxThDepletedV6,
        tmnxDhcpsLeaseOfferedExpired,
        tmnxDhcpsAddrAllocationFailure,
        tmnxDhcpsPacketDropped
    }
    STATUS      current
    DESCRIPTION
        "The group of objects supporting traps for the DHCP server capability
         on Nokia SROS series systems since release 13.0."
    ::= { tmnxDhcpServerNotifGroups 6 }

tmnxDhcpServerNotifyPrefix       OBJECT IDENTIFIER ::= { tmnxSRNotifyPrefix 47 }

tmnxDhcpServerNotifications      OBJECT IDENTIFIER ::= { tmnxDhcpServerNotifyPrefix 0 }

tmnxDhcpSvrSubnetMinFreeExc      NOTIFICATION-TYPE
    OBJECTS     {
        tmnxDhcpSvrSubnetStatsFree,
        tmnxDhcpSvrSubnetMinFree,
        tmnxDhcpSvrSubnetMinFreeType
    }
    STATUS      current
    DESCRIPTION
        "The tmnxDhcpSvrSubnetMinFreeExc notification is generated when the
         actual number of free addresses in a subnet falls below the desired
         minimum number.

         This notification is only generated for DHCP server instances with the
         value of tmnxDhcpServerCfgAddrType set to 'ipv4(1)'."
    ::= { tmnxDhcpServerNotifications 1 }

tmnxDhcpSvrHostConflict          NOTIFICATION-TYPE
    OBJECTS     {
        tmnxDhcpSvrNotifVRtrID,
        tmnxDhcpSvrNotifServerName,
        tmnxDhcpSvrNotifLeaseClientAddrType,
        tmnxDhcpSvrNotifLeaseClientAddr,
        tmnxDhcpSvrNotifUserDatabaseName,
        tmnxDhcpSvrNotifHostType,
        tmnxDhcpSvrNotifHostName,
        tmnxDhcpSvrNotifDescription,
        tmnxDhcpSvrNotifMsgHwAddress
    }
    STATUS      current
    DESCRIPTION
        "The tmnxDhcpSvrHostConflict notification can be generated for hosts
         configured with a fixed IP address in the local user database.

         If such a host requests an IP address and the system detects that this
         IP address has already been handed out to another (dynamic) host, then
         the tmnxDhcpSvrHostConflict notification is generated.

         This notification is only generated for DHCP server instances with the
         value of tmnxDhcpServerCfgAddrType set to 'ipv4(1)'."
    ::= { tmnxDhcpServerNotifications 2 }

tmnxDhcpSvrPoolUnknown           NOTIFICATION-TYPE
    OBJECTS     {
        tmnxDhcpSvrNotifVRtrID,
        tmnxDhcpSvrNotifServerName,
        tmnxDhcpSvrNotifUnknownPoolName,
        tmnxDhcpSvrNotifDescription,
        tmnxDhcpSvrNotifMsgHwAddress,
        tmnxDhcpSvrNotifClientDUID
    }
    STATUS      current
    DESCRIPTION
        "The tmnxDhcpSvrPoolUnknown notification is generated when the lookup
         in the local user database for a host returns a poolname which is not
         defined within the local DHCP server or the DHCP message contains an
         unknown pool name.

         This notification is generated for DHCP server instances with the
         value of tmnxDhcpServerCfgAddrType set to 'ipv4(1)' or 'ipv6(2)'."
    ::= { tmnxDhcpServerNotifications 3 }

tmnxDhcpSvrLeaseNotOwner         NOTIFICATION-TYPE
    OBJECTS     {
        tmnxDhcpSvrNotifVRtrID,
        tmnxDhcpSvrNotifServerName,
        tmnxDhcpSvrNotifLeaseClientAddrType,
        tmnxDhcpSvrNotifLeaseClientAddr,
        tmnxDhcpSvrNotifMsgHwAddress,
        tmnxDhcpSvrNotifMsgOption82,
        tmnxDhcpSvrNotifDescription,
        tmnxDhcpSvrNotifLeaseClientAddrLen,
        tmnxDhcpSvrNotifClientDUID
    }
    STATUS      current
    DESCRIPTION
        "The tmnxDhcpSvrLeaseNotOwner notification is generated when a DHCP
         message is received from a DHCP client that does not own the lease
         indicated by the IP address from the message.

         This notification is generated for DHCP server instances with the
         value of tmnxDhcpServerCfgAddrType set to 'ipv4(1)' or 'ipv6(2)'."
    ::= { tmnxDhcpServerNotifications 4 }

tmnxDhcpSvrDeclineStaticAddr     NOTIFICATION-TYPE
    OBJECTS     {
        tmnxDhcpSvrNotifVRtrID,
        tmnxDhcpSvrNotifServerName,
        tmnxDhcpSvrNotifLeaseClientAddrType,
        tmnxDhcpSvrNotifLeaseClientAddr,
        tmnxDhcpSvrNotifMsgHwAddress,
        tmnxDhcpSvrNotifMsgOption82
    }
    STATUS      current
    DESCRIPTION
        "The tmnxDhcpSvrDeclineStaticAddr notification is generated when a DHCP
         decline message is received from a DHCP client that has a static IP
         address assigned.

         This notification is only generated for DHCP server instances with the
         value of tmnxDhcpServerCfgAddrType set to 'ipv4(1)'."
    ::= { tmnxDhcpServerNotifications 5 }

tmnxDhcpSvrMsgTooLong            NOTIFICATION-TYPE
    OBJECTS     {
        tmnxDhcpSvrNotifVRtrID,
        tmnxDhcpSvrNotifServerName,
        tmnxDhcpSvrNotifMsgHwAddress,
        tmnxDhcpSvrNotifMsgOption82,
        tmnxDhcpSvrNotifMsgSizeLimit,
        tmnxDhcpSvrNotifClientDUID
    }
    STATUS      current
    DESCRIPTION
        "The tmnxDhcpSvrMsgTooLong notification is generated when a DHCP
         message is built, but the message size either exceeds the maximum DHCP
         message size or the size provided by the client in the option maximum
         DHCP message size. A reason can be that too many options are defined
         on host, pool and subnet levels.

         This notification is only generated for DHCP server instances with the
         value of tmnxDhcpServerCfgAddrType set to 'ipv4(1)'."
    ::= { tmnxDhcpServerNotifications 6 }

tmnxDhcpsFoStateChange           NOTIFICATION-TYPE
    OBJECTS     {
        tmnxDhcpsFoState
    }
    STATUS      current
    DESCRIPTION
        "The tmnxDhcpsFoStateChange notification is generated when the failover
         state of the DHCP server instance changes.

         This notification is generated for DHCP server instances with the
         value of tmnxDhcpServerCfgAddrType set to 'ipv4(1)' or 'ipv6(2)'."
    ::= { tmnxDhcpServerNotifications 7 }

tmnxDhcpsFoLeaseUpdateFailed     NOTIFICATION-TYPE
    OBJECTS     {
        tmnxDhcpSvrNotifVRtrID,
        tmnxDhcpSvrNotifServerName,
        tmnxDhcpSvrNotifLeaseClientAddrType,
        tmnxDhcpSvrNotifLeaseClientAddr,
        tmnxDhcpsFoLeaseFailureReason,
        tmnxDhcpSvrNotifMsgHwAddress,
        tmnxDhcpSvrNotifClientDUID
    }
    STATUS      current
    DESCRIPTION
        "The tmnxDhcpsFoLeaseUpdateFailed notification is generated when a
         Binding Database Update (BNDUPD) packet received from the failover
         peer, cannot be processed successfully.

         This notification is only generated for DHCP server instances with the
         value of tmnxDhcpServerCfgAddrType set to 'ipv4(1)' or 'ipv6(2)'."
    ::= { tmnxDhcpServerNotifications 8 }

tmnxDhcpSvrUserDbUnknown         NOTIFICATION-TYPE
    OBJECTS     {
        tmnxDhcpServerCfgUserDatabase,
        tmnxDhcpSvrNotifMsgHwAddress
    }
    STATUS      current
    DESCRIPTION
        "The tmnxDhcpSvrUserDbUnknown notification is generated when the local
         DHCP server instance drops a DHCP message because a local user
         database with the name specified for this server instance could not be
         found.

         This notification is only generated for DHCP server instances with the
         value of tmnxDhcpServerCfgAddrType set to 'ipv4(1)'."
    ::= { tmnxDhcpServerNotifications 9 }

tmnxDhcpSvrMaxLeasesReached      NOTIFICATION-TYPE
    OBJECTS     {
        tmnxDhcpSvrMaxLeases,
        tmnxDhcpSvrNotifMsgHwAddress,
        tmnxDhcpSvrNotifClientDUID
    }
    STATUS      current
    DESCRIPTION
        "The tmnxDhcpSvrMaxLeasesReached notification is generated when any
         local DHCP server instance drops a DHCP message because the maximum
         number of leases was reached.

         This notification is generated for DHCP server instances with the
         value of tmnxDhcpServerCfgAddrType set to 'ipv4(1)' or 'ipv6(2)'."
    ::= { tmnxDhcpServerNotifications 10 }

tmnxDhcpSvrNoSubnetFixAddr       NOTIFICATION-TYPE
    OBJECTS     {
        tmnxDhcpSvrNotifVRtrID,
        tmnxDhcpSvrNotifServerName,
        tmnxDhcpSvrNotifUserDatabaseName,
        tmnxDhcpSvrNotifHostType,
        tmnxDhcpSvrNotifHostName,
        tmnxDhcpSvrNotifLeaseClientAddrType,
        tmnxDhcpSvrNotifLeaseClientAddr,
        tmnxDhcpSvrNotifMsgHwAddress
    }
    STATUS      current
    DESCRIPTION
        "The tmnxDhcpSvrNoSubnetFixAddr notification can be generated for hosts
         configured with a fixed IP address in the local user database.

         If such a host requests an IP address and the system cannot find a
         matching subnet in this server instance for this IP address, then the
         tmnxDhcpSvrNoSubnetFixAddr notification is generated, and the request
         is dropped.

         This notification is only generated for DHCP server instances with the
         value of tmnxDhcpServerCfgAddrType set to 'ipv4(1)'."
    ::= { tmnxDhcpServerNotifications 11 }

tmnxDhcpSvrLeaseDefaultTimers    NOTIFICATION-TYPE
    OBJECTS     {
        tmnxDhcpSvrNotifVRtrID,
        tmnxDhcpSvrNotifServerName,
        tmnxDhcpSvrNotifLeaseClientAddrType,
        tmnxDhcpSvrNotifLeaseClientAddr,
        tmnxDhcpSvrNotifDescription,
        tmnxDhcpSvrNotifLeaseClientAddrLen,
        tmnxDhcpSvrNotifMsgHwAddress,
        tmnxDhcpSvrNotifClientDUID
    }
    STATUS      current
    DESCRIPTION
        "The tmnxDhcpSvrLeaseDefaultTimers notification is generated when, for
         a particular DHCP client, the system has reverted to default lease
         timer values, because the configuration of the lease timers was
         inconsistent.

         The lease renew time T1 and lease rebind time T2 have been reverted to
         the default values of 1/2 and 2/3 of the lease time.

         This notification is generated for DHCP server instances with the
         value of tmnxDhcpServerCfgAddrType set to 'ipv4(1)' or 'ipv6(2)'."
    ::= { tmnxDhcpServerNotifications 12 }

tmnxDhcpSvrPoolMinFreeExc        NOTIFICATION-TYPE
    OBJECTS     {
        tmnxDhcpSvrNotifPoolFree,
        tmnxDhcpServerPoolMinFree,
        tmnxDhcpServerPoolMinFreeType
    }
    STATUS      current
    DESCRIPTION
        "The tmnxDhcpSvrPoolMinFreeExc notification is generated when the
         actual number of free addresses in a pool falls below the desired
         minimum number.

         This notification is only generated for DHCP server instances with the
         value of tmnxDhcpServerCfgAddrType set to 'ipv4(1)'."
    ::= { tmnxDhcpServerNotifications 13 }

tmnxDhcpSvrSubnetDepleted        NOTIFICATION-TYPE
    OBJECTS     {
        tmnxDhcpSvrSubnetRowStatus
    }
    STATUS      current
    DESCRIPTION
        "The tmnxDhcpSvrSubnetDepleted notification is generated when the
         actual number of free addresses becomes zero.

         This notification is only generated for DHCP server instances with the
         value of tmnxDhcpServerCfgAddrType set to 'ipv4(1)'."
    ::= { tmnxDhcpServerNotifications 14 }

tmnxDhcpSvrPoolDepleted          NOTIFICATION-TYPE
    OBJECTS     {
        tmnxDhcpServerPoolRowStatus
    }
    STATUS      current
    DESCRIPTION
        "The tmnxDhcpSvrPoolDepleted notification is generated when the actual
         number of free addresses becomes zero.

         This notification is only generated for DHCP server instances with the
         value of tmnxDhcpServerCfgAddrType set to 'ipv4(1)'."
    ::= { tmnxDhcpServerNotifications 15 }

tmnxDhcpSvrIntLseConflict        NOTIFICATION-TYPE
    OBJECTS     {
        tmnxDhcpSvrNotifVRtrID,
        tmnxDhcpSvrNotifServerName,
        tmnxDhcpSvrNotifLeaseClientAddrType,
        tmnxDhcpSvrNotifLeaseClientAddr,
        tmnxDhcpSvrNotifDescription,
        tmnxDhcpSvrNotifMsgHwAddress,
        tmnxDhcpSvrNotifClientDUID
    }
    STATUS      current
    DESCRIPTION
        "The tmnxDhcpSvrIntLseConflict notification is generated for DHCP hosts
         trying to acquire an IP address that was handed through the local
         address assignment infrastructure, or the local address assignment
         infrastructure tries to use an IP address that was handed out to a
         DHCP client.

         This notification is generated for DHCP server instances with the
         value of tmnxDhcpServerCfgAddrType set to 'ipv4(1)' or 'ipv6(2)'."
    ::= { tmnxDhcpServerNotifications 16 }

tmnxDhcpSvrLeaseModify           NOTIFICATION-TYPE
    OBJECTS     {
        tmnxDhcpSvrLeaseStart,
        tmnxDhcpSvrNotifMsgHwAddress,
        tmnxDhcpSvrNotifClientDUID
    }
    STATUS      current
    DESCRIPTION
        "The tmnxDhcpSvrLeaseModify notification is generated when a DHCP host
         is modified.

         This notification is generated for DHCP server instances with the
         value of tmnxDhcpServerCfgAddrType set to 'ipv4(1)' or 'ipv6(2)'."
    ::= { tmnxDhcpServerNotifications 17 }

tmnxDhcpSvrLeaseCreate           NOTIFICATION-TYPE
    OBJECTS     {
        tmnxDhcpSvrLeaseStart,
        tmnxDhcpSvrNotifMsgHwAddress,
        tmnxDhcpSvrNotifClientDUID
    }
    STATUS      current
    DESCRIPTION
        "The tmnxDhcpSvrLeaseCreate notification is generated when a DHCP host
         is created.

         This notification is generated for DHCP server instances with the
         value of tmnxDhcpServerCfgAddrType set to 'ipv4(1)' or 'ipv6(2)'."
    ::= { tmnxDhcpServerNotifications 18 }

tmnxDhcpSvrLeaseDelete           NOTIFICATION-TYPE
    OBJECTS     {
        tmnxDhcpSvrLeaseStart,
        tmnxDhcpSvrNotifMsgHwAddress,
        tmnxDhcpSvrNotifClientDUID
    }
    STATUS      current
    DESCRIPTION
        "The tmnxDhcpSvrLeaseDelete notification is generated when a DHCP host
         is deleted.

         This notification is generated for DHCP server instances with the
         value of tmnxDhcpServerCfgAddrType set to 'ipv4(1)' or 'ipv6(2)'."
    ::= { tmnxDhcpServerNotifications 19 }

tmnxDhcpSvrNoContFreeBlocks      NOTIFICATION-TYPE
    OBJECTS     {
        tmnxDhcpServerCfgUseGiAddress,
        tmnxDhcpServerCfgUseClientPool,
        tmnxDhcpSvrNotifLinkAddr,
        tmnxDhcpSvrNotifPrimaryPool,
        tmnxDhcpSvrNotifSecondaryPool,
        tmnxDhcpSvrNotifClientDUID,
        tmnxDhcpSvrNotifString
    }
    STATUS      current
    DESCRIPTION
        "The tmnxDhcpSvrNoContFreeBlocks notification is generated when a lease
         cannot be created because not enough contiguous blocks are found for
         the requested delegated prefix size.

         This notification is only generated for DHCP server instances with the
         value of tmnxDhcpServerCfgAddrType set to 'ipv6(2)'.

         More detailed information about the failure is indicated in the
         tmnxDhcpSvrNotifString object."
    ::= { tmnxDhcpServerNotifications 20 }

tmnxDhcpSvrSubnetBindingFailed   NOTIFICATION-TYPE
    OBJECTS     {
        tmnxDhcpServerPoolSubnetBindKey,
        tmnxDhcpSvrNotifSystemId,
        tmnxDhcpSvrNotifServiceId,
        tmnxDhcpSvrNotifString
    }
    STATUS      obsolete
    DESCRIPTION
        "The tmnxDhcpSvrSubnetBindingFailed notification is obsolete."
    ::= { tmnxDhcpServerNotifications 23 }

tmnxDhcpsPoolFoStateChange       NOTIFICATION-TYPE
    OBJECTS     {
        tmnxDhcpsPoolFoState
    }
    STATUS      current
    DESCRIPTION
        "The tmnxDhcpsPoolFoStateChange notification is generated when the
         failover state of the DHCP server instance pool changes.

         This notification is generated for DHCP server instances with the
         value of tmnxDhcpServerCfgAddrType set to 'ipv4(1)' or 'ipv6(2)'."
    ::= { tmnxDhcpServerNotifications 24 }

tmnxDhcpsPoolFoLeaseUpdateFailed NOTIFICATION-TYPE
    OBJECTS     {
        tmnxDhcpsPoolFoLastChanged,
        tmnxDhcpSvrNotifLeaseClientAddrType,
        tmnxDhcpSvrNotifLeaseClientAddr,
        tmnxDhcpsFoLeaseFailureReason,
        tmnxDhcpSvrNotifMsgHwAddress,
        tmnxDhcpSvrNotifClientDUID
    }
    STATUS      current
    DESCRIPTION
        "The tmnxDhcpsPoolFoLeaseUpdateFailed notification is generated when a
         Binding Database Update (BNDUPD) packet received from the failover
         peer, cannot be processed successfully.

         This notification is only generated for DHCP server instances with the
         value of tmnxDhcpServerCfgAddrType set to 'ipv4(1)' or 'ipv6(2)'."
    ::= { tmnxDhcpServerNotifications 25 }

tmnxDhcpSvrSubnetBindingCreate   NOTIFICATION-TYPE
    OBJECTS     {
        tmnxDhcpSvrNotifVRtrID,
        tmnxDhcpSvrNotifServerName,
        tmnxDhcpSvrNotifPoolName,
        tmnxDhcpSvrNotifSubnetAddrType,
        tmnxDhcpSvrNotifSubnetPfx,
        tmnxDhcpSvrNotifSubnetPfxlen,
        tmnxDhcpSvrNotifSystemId,
        tmnxDhcpSvrNotifServiceId,
        tmnxDhcpSvrNotifString
    }
    STATUS      obsolete
    DESCRIPTION
        "The tmnxDhcpSvrSubnetBindingCreate notification is obsolete."
    ::= { tmnxDhcpServerNotifications 26 }

tmnxDhcpSvrSubnetBindingUnbind   NOTIFICATION-TYPE
    OBJECTS     {
        tmnxDhcpSvrNotifVRtrID,
        tmnxDhcpSvrNotifServerName,
        tmnxDhcpSvrNotifPoolName,
        tmnxDhcpSvrNotifSubnetAddrType,
        tmnxDhcpSvrNotifSubnetPfx,
        tmnxDhcpSvrNotifSubnetPfxlen,
        tmnxDhcpSvrNotifSystemId,
        tmnxDhcpSvrNotifServiceId,
        tmnxDhcpSvrNotifString,
        tmnxDhcpSvrNotifUnbindTime
    }
    STATUS      obsolete
    DESCRIPTION
        "The tmnxDhcpSvrSubnetBindingUnbind notification is obsolete."
    ::= { tmnxDhcpServerNotifications 27 }

tmnxDhcpSvrSubnetBindingDelete   NOTIFICATION-TYPE
    OBJECTS     {
        tmnxDhcpSvrNotifVRtrID,
        tmnxDhcpSvrNotifServerName,
        tmnxDhcpSvrNotifPoolName,
        tmnxDhcpSvrNotifSubnetAddrType,
        tmnxDhcpSvrNotifSubnetPfx,
        tmnxDhcpSvrNotifSubnetPfxlen,
        tmnxDhcpSvrNotifSystemId,
        tmnxDhcpSvrNotifServiceId,
        tmnxDhcpSvrNotifString
    }
    STATUS      obsolete
    DESCRIPTION
        "The tmnxDhcpSvrSubnetBindingDelete notification is obsolete."
    ::= { tmnxDhcpServerNotifications 28 }

tmnxDhcpSvrSubnetFailCtrlError   NOTIFICATION-TYPE
    OBJECTS     {
        tmnxDhcpSvrSubnetRowStatus
    }
    STATUS      obsolete
    DESCRIPTION
        "The tmnxDhcpSvrSubnetFailCtrlError notification is obsolete."
    ::= { tmnxDhcpServerNotifications 29 }

tmnxDhcpSvrPlThTooLowV6          NOTIFICATION-TYPE
    OBJECTS     {
        tmnxDhcpsPlThCurrFreeTooLow,
        tmnxDhcpsPlThCurrFreeBlksHw,
        tmnxDhcpsPlThCurrFreeBlksLw,
        tmnxDhcpsPlMinFreePercent
    }
    STATUS      current
    DESCRIPTION
        "The tmnxDhcpSvrPlThTooLowV6 notification is generated when the number
         of free prefixes with the minimum free threshold length available in
         the pool is below the configured number of prefixes with the minimum
         free threshold length.

         [CAUSE] The tmnxDhcpSvrPlThTooLowV6 notification is generated when the
         actual number of free prefixes with minimum free threshold length
         available in the pool is becoming too low.

         [EFFECT] Only a limited number of free prefixes with minimum free
         threshold length are available in the pool.

         [RECOVERY]
         The operator may create additional prefixes in the pool
         to prevent a shortage of available prefixes with minimum
         free threshold length.  Alternatively, examination of
         the leases in the pool may reveal that the distribution
         is not appropriate."
    ::= { tmnxDhcpServerNotifications 30 }

tmnxDhcpSvrPlThDepletedV6        NOTIFICATION-TYPE
    OBJECTS     {
        tmnxDhcpsPlThCurrFreeDepleted
    }
    STATUS      current
    DESCRIPTION
        "The tmnxDhcpSvrPlThDepletedV6 notification is generated when there are
         no more prefixes with the minimum free threshold length available in
         the pool.

         [CAUSE] The tmnxDhcpSvrPlThDepletedV6 notification is generated when
         the actual number of free prefixes with minimum free threshold length
         available in the pool becomes zero.

         [EFFECT] No more free prefixes with minimum free threshold length are
         available in the pool.

         [RECOVERY] The operator may create additional prefixes in the pool.
         Alternatively, examination of the leases in the pool may reveal that
         the distribution is not appropriate."
    ::= { tmnxDhcpServerNotifications 31 }

tmnxDhcpSvrPfxThTooLowV6         NOTIFICATION-TYPE
    OBJECTS     {
        tmnxDhcpsPfxThCurrFreeTooLow,
        tmnxDhcpsPfxThCurrFreeBlksHw,
        tmnxDhcpsPfxThCurrFreeBlksLw,
        tmnxDhcpsPfxMinFreePercent,
        tmnxDhcpsPfxMinFreeNumber
    }
    STATUS      current
    DESCRIPTION
        "The tmnxDhcpSvrPfxThTooLowV6 notification is generated when the number
         of free prefixes with the minimum free threshold length available in
         the considered prefix is below the configured number of prefixes with
         the minimum free threshold length.

         [CAUSE] The tmnxDhcpSvrPfxThTooLowV6 notification is generated when
         the actual number of free prefixes with minimum free threshold length
         available in the considered prefix is becoming too low.

         [EFFECT] Only a limited number of free prefixes with minimum free
         threshold length are available in the considered prefix.

         [RECOVERY] The operator may create additional prefixes in the
         considered prefix to prevent a shortage of available prefixes with
         minimum free threshold length. Alternatively, examination of the
         leases in the prefix may reveal that the distribution is not
         appropriate."
    ::= { tmnxDhcpServerNotifications 32 }

tmnxDhcpSvrPfxThDepletedV6       NOTIFICATION-TYPE
    OBJECTS     {
        tmnxDhcpsPfxThCurrFreeDepleted
    }
    STATUS      current
    DESCRIPTION
        "The tmnxDhcpSvrPfxThDepletedV6 notification is generated when there
         are no more free prefixes with the minimum free threshold length
         available in the considered prefix.

         [CAUSE] The tmnxDhcpSvrPfxThDepletedV6 notification is generated when
         the actual number of free prefixes with minimum free threshold length
         available in the considered prefix becomes zero.

         [EFFECT] No more prefixes with minimum free threshold length are
         available in considered prefix.

         [RECOVERY] The operator may create additional prefixes in the
         considered prefix. Alternatively, examination of the leases in the
         pool may reveal that the distribution is not appropriate."
    ::= { tmnxDhcpServerNotifications 33 }

tmnxDhcpsLeaseOfferedExpired     NOTIFICATION-TYPE
    OBJECTS     {
        tmnxDhcpSvrLeaseStart,
        tmnxDhcpSvrNotifMsgHwAddress,
        tmnxDhcpSvrNotifClientDUID
    }
    STATUS      current
    DESCRIPTION
        "The tmnxDhcpsLeaseOfferedExpired notification is generated when an
         offered DHCP lease expires in the 'offered' state.

         This notification is generated for DHCP server instances with the
         value of tmnxDhcpServerCfgAddrType set to 'ipv4(1)' or 'ipv6(2)'

         [CAUSE] The tmnxDhcpsLeaseOfferedExpired notification is generated
         when a DHCP lease that this system had offered to a client, expires
         while it is still in the 'offered' state, because this system did not
         receive a DHCP request message from the client.

         [EFFECT] The client does not get a lease this time. The client will
         have to try again if it needs a lease from this system.

         [RECOVERY] The recovery action, if any, will depend on the reason of
         the expiry."
    ::= { tmnxDhcpServerNotifications 34 }

tmnxDhcpsAddrAllocationFailure   NOTIFICATION-TYPE
    OBJECTS     {
        tmnxDhcpSvrNotifVRtrID,
        tmnxDhcpSvrNotifServerName,
        tmnxDhcpSvrNotifMsgHwAddress,
        tmnxDhcpSvrNotifString,
        tmnxDhcpSvrNotifGwIpAddrType,
        tmnxDhcpSvrNotifGatewayIpAddr,
        tmnxDhcpSvrNotifPrimaryPool,
        tmnxDhcpSvrNotifSecondaryPool
    }
    STATUS      current
    DESCRIPTION
        "The tmnxDhcpsAddrAllocationFailure notification is generated when a
         DHCP server instance could not allocate an address for a client.

         This notification is generated for DHCP server instances with the
         value of tmnxDhcpServerCfgAddrType set to 'ipv4(1)'.

         The tmnxDhcpSvrNotifMsgHwAddress object indicates the MAC address of
         the client.

         The tmnxDhcpSvrNotifString object indicates the reason.

         [CAUSE] The tmnxDhcpsAddrAllocationFailure notification is generated
         when a DHCP server instance could not allocate an address for a
         client.

         The reason could be that the DHCP server instance could not find a
         free address, or it could be a configuration issue.

         [EFFECT] The client does not get an IP address lease this time. The
         client will have to try again if it needs a lease from this system.

         [RECOVERY] The recovery action, if any, will depend on the reason."
    ::= { tmnxDhcpServerNotifications 35 }

tmnxDhcpsPacketDropped           NOTIFICATION-TYPE
    OBJECTS     {
        tmnxDhcpSvrNotifVRtrID,
        tmnxDhcpSvrNotifServerName,
        tmnxDhcpSvrNotifMsgHwAddress,
        tmnxDhcpSvrNotifClientDUID,
        tmnxDhcpSvrNotifString
    }
    STATUS      current
    DESCRIPTION
        "The tmnxDhcpsPacketDropped notification is generated when a DHCP
         server instance dropped a DHCP packet it received.

         This notification is generated for DHCP server instances with the
         value of tmnxDhcpServerCfgAddrType set to 'ipv4(1)' or 'ipv6(2)'

         The tmnxDhcpSvrNotifMsgHwAddress object indicates the MAC address of
         the client; the tmnxDhcpSvrNotifClientDUID object indicates the DUID
         of the client; either of these objects, or both, may be empty.

         The tmnxDhcpSvrNotifString object indicates the reason.

         [CAUSE] The tmnxDhcpsPacketDropped notification is generated when a
         DHCP server instance dropped a DHCP packet it received.

         [EFFECT] Some client request fails. The client will have to try again.

         [RECOVERY] The recovery action, if any, will depend on the reason."
    ::= { tmnxDhcpServerNotifications 36 }

END
