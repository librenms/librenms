ALCATEL-IND1-TIMETRA-SERV-MIB DEFINITIONS ::= BEGIN

IMPORTS
    MODULE-IDENTITY, OBJECT-TYPE,
    NOTIFICATION-TYPE, Gauge32,
    Integer32, Unsigned32, IpAddress,
    TimeTicks, Counter64, Counter32             FROM SNMPv2-SMI

    MODULE-COMPLIANCE, OBJECT-GROUP,
    NOTIFICATION-GROUP                          FROM SNMPv2-CONF

    TEXTUAL-CONVENTION, DisplayString,
    RowStatus, MacAddress, TimeStamp,
    TruthValue, RowPointer, DateAndTime         FROM SNMPv2-TC

    InterfaceIndex, InterfaceIndexOrZero        FROM IF-MIB

    InetAddressPrefixLength,
    InetAddressType, InetAddress                FROM INET-ADDRESS-MIB

    ServiceAdminStatus, ServiceOperStatus,
    TmnxPortID, TmnxEncapVal,
    TmnxServId, TmnxCustId, TNamedItem,
    TmnxVRtrIDOrZero, QTag,
    SdpBindId, TNamedItemOrEmpty,
    TPortSchedulerPIR,
    TmnxActionType,
    TCIRRate, TPIRRate,
    TmnxEnabledDisabled,
    TPolicyStatementNameOrEmpty,
    TmnxAncpStringOrZero, 
    TmnxVPNRouteDistinguisher,
    TmnxManagedRouteStatus                      FROM ALCATEL-IND1-TIMETRA-TC-MIB

    timetraSRMIBModules, tmnxSRObjs,
    tmnxSRNotifyPrefix, tmnxSRConfs             FROM ALCATEL-IND1-TIMETRA-GLOBAL-MIB

    tVirtualSchedulerName, tSchedulerPolicyName FROM ALCATEL-IND1-TIMETRA-QOS-MIB

    TFilterID                                   FROM ALCATEL-IND1-TIMETRA-FILTER-MIB;

timetraServicesMIBModule   MODULE-IDENTITY
    LAST-UPDATED "201911270000Z"
    ORGANIZATION "ALE USA Inc."
    CONTACT-INFO
     "Please consult with Customer Service to ensure the most appropriate
      version of this document is used with the products in question:

                      Alcatel-Lucent Enterprise
                        26801 West Agoura Road
                     Agoura Hills, CA  91301-5122
                       United States Of America

     Telephone:          +1 800 995 2696

     Electronic Mail:    ebg_global_supportcenter@al-enterprise.com
     World Wide Web:     https://www.al-enterprise.com"

    DESCRIPTION
        "This  document  is the SNMP MIB module to manage and provision
        the various services of the Alcatel 7x50 SR system.

        Reproduction of this document is authorized  on  the  condition
        that the foregoing copyright notice is included.

        This   SNMP   MIB  module  (Specification)  embodies  Alcatel's
        proprietary  intellectual  property.  Alcatel retains all title
        and ownership in the Specification, including any revisions.

        Alcatel  grants  all interested parties a non-exclusive license
        to  use and distribute an unmodified copy of this Specification
        in  connection with management of Alcatel products, and without
        fee,  provided  this copyright notice and license appear on all
        copies.

        This  Specification  is  supplied `as is', and Alcatel makes no
        warranty,  either express or implied, as to the use, operation,
        condition, or performance of the Specification.

                   Copyright (C) ALE USA Inc. 2014-2019
                   Copyright (C) 2003-2013 Alcatel-Lucent
                       ALL RIGHTS RESERVED WORLDWIDE"

--
--  Revision History
--
    REVISION        "201911270000Z"
    DESCRIPTION     "Updated the latest contact and Copyright information for ALE USA Inc."

    REVISION        "0801010000Z"
    DESCRIPTION     "Rev 6.0                01 Jan 2008 00:00
                     6.0 release of the TIMETRA-SERV-MIB."

    REVISION        "0701010000Z"
    DESCRIPTION     "Rev 5.0                01 Jan 2007 00:00
                     5.0 release of the TIMETRA-SERV-MIB."

    REVISION        "0602280000Z"
    DESCRIPTION     "Rev 4.0                28 Feb 2006 00:00
                     4.0 release of the TIMETRA-SERV-MIB."

    REVISION        "0508310000Z"
    DESCRIPTION     "Rev 3.0                31 Aug 2005 00:00
                     3.0 release of the TIMETRA-SERV-MIB."

    REVISION        "0501240000Z"
    DESCRIPTION     "Rev 2.1                24 Jan 2005 00:00
                     2.1 release of the TIMETRA-SERV-MIB."

    REVISION        "0401150000Z"
    DESCRIPTION     "Rev 2.0                15 Jan 2004 00:00
                     2.0 release of the TIMETRA-SERV-MIB."

    REVISION        "0308150000Z"
    DESCRIPTION     "Rev 1.2                15 Aug 2003 00:00
                     1.2 release of the TIMETRA-SERV-MIB."

    REVISION        "0301200000Z"
    DESCRIPTION     "Rev 1.0                20 Jan 2003 00:00
                     1.0 Release of the TIMETRA-SERV-MIB."

    REVISION        "0008140000Z"
    DESCRIPTION     "Rev 0.1                14 Aug 2000 00:00
                     Initial version of the TIMETRA-SERV-MIB."
    ::= { timetraSRMIBModules 4 }

-- --------------------------------------------------------------------
--      ALCATEL-IND1-TIMETRA-SERV-MIB organisation
-- --------------------------------------------------------------------
tmnxServObjs            OBJECT IDENTIFIER ::= { tmnxSRObjs 4 }
    tmnxCustObjs            OBJECT IDENTIFIER ::= { tmnxServObjs 1 }
    tmnxSvcObjs             OBJECT IDENTIFIER ::= { tmnxServObjs 2 }
    tmnxTstpNotifyObjs      OBJECT IDENTIFIER ::= { tmnxServObjs 5 }
    tmnxSvcNotifyObjs       OBJECT IDENTIFIER ::= { tmnxServObjs 6 }

tmnxServConformance     OBJECT IDENTIFIER ::= { tmnxSRConfs 4 }
    tmnxCustConformance     OBJECT IDENTIFIER ::= { tmnxServConformance 1 }
    tmnxSvcConformance      OBJECT IDENTIFIER ::= { tmnxServConformance 2 }
    tmnxTstpConformance     OBJECT IDENTIFIER ::= { tmnxServConformance 5 }

tmnxServNotifications   OBJECT IDENTIFIER ::= { tmnxSRNotifyPrefix 4 }
    custTrapsPrefix         OBJECT IDENTIFIER ::= { tmnxServNotifications 1 }
        custTraps               OBJECT IDENTIFIER ::= { custTrapsPrefix 0 }
    svcTrapsPrefix          OBJECT IDENTIFIER ::= { tmnxServNotifications 2 }
        svcTraps                OBJECT IDENTIFIER ::= { svcTrapsPrefix 0 }
    tstpTrapsPrefix         OBJECT IDENTIFIER ::= { tmnxServNotifications 5 }
        tstpTraps               OBJECT IDENTIFIER ::= { tstpTrapsPrefix 0 }

-- --------------------------------------------------------------------
--      ALCATEL-IND1-TIMETRA-SERV-MIB Textual Conventions
-- --------------------------------------------------------------------
ServObjName ::= TEXTUAL-CONVENTION
    DISPLAY-HINT    "255a"
    STATUS          current
    DESCRIPTION     "ASCII string used to name various service
                     objects."
    SYNTAX          OCTET STRING (SIZE (0..32))

ServObjDesc ::= TEXTUAL-CONVENTION
    DISPLAY-HINT    "255a"
    STATUS          current
    DESCRIPTION     "ASCII string used to describe various service
                     objects."
    SYNTAX          OCTET STRING (SIZE (0..80))

ServObjLongDesc ::= TEXTUAL-CONVENTION
    DISPLAY-HINT    "255a"
    STATUS          current
    DESCRIPTION     "Long ASCII string used to describe various service
                     objects."
    SYNTAX          OCTET STRING (SIZE (0..160))

ServType ::= TEXTUAL-CONVENTION
    STATUS          current
    DESCRIPTION     "This textual convention is used to specify the
                     type of a given service."
    SYNTAX          INTEGER {
                        unknown (0), -- Unknown service type
                        epipe   (1), -- Ethernet pipe
                        p3pipe  (2), -- POS pipe
                        tls     (3), -- Virtual private LAN service
                        vprn    (4), -- Virtual private routed network
                        ies     (5), -- Internet enhanced service
                        mirror  (6), -- Mirror service
                        apipe   (7), -- ATM pipe service
                        fpipe   (8), -- FR pipe service
                        ipipe   (9), -- IP interworking pipe service
                        cpipe   (10) -- Circuit Emulation pipe service
                    }

VpnId ::= TEXTUAL-CONVENTION
    STATUS          current
    DESCRIPTION     "A number used to identify a VPN. In general
                     each service corresponds to a single VPN, but
                     under some circumstances a VPN may be composed
                     of multiple services."
    SYNTAX          Unsigned32 (0|1..2147483647)

SdpId ::= TEXTUAL-CONVENTION
    STATUS          current
    DESCRIPTION     "A 16-bit number used to identify a Service
                     Distribution Point. This ID must be unique only
                     within the ESR where it is defined. The value 0
                     is used as the null ID."
    SYNTAX          Unsigned32 (0|1..17407)

SdpTemplateId ::= TEXTUAL-CONVENTION
    STATUS          current
    DESCRIPTION     "A number used to uniquely identify a template 
                     for the creation of a Service Distribution Point.
                     The value 0 is used as the null ID."
    SYNTAX          Unsigned32 (0|1..2147483647)

PWTemplateId ::= TEXTUAL-CONVENTION
    STATUS          current
    DESCRIPTION     "A number used to uniquely identify an pseudowire (PW)
                     template for the creation of a Service Distribution
                     Point. The value 0 is used as the null ID."
    SYNTAX          Unsigned32 (0|1..2147483647)

SdpBindTlsBpduTranslation ::= TEXTUAL-CONVENTION
    STATUS          current
    DESCRIPTION     "This textual convention is used to specify whether
                     received L2 Protocol Tunnel pdu's are translated
                     before being sent out on a port or sap."
    SYNTAX          INTEGER {
                        auto     (1),
                        disabled (2),
                        pvst     (3),
                        stp      (4),
                        cdp      (5), -- Not supported
                        vtp      (6)  -- Not supported
                    }

TlsLimitMacMoveLevel ::= TEXTUAL-CONVENTION
    STATUS          current
    DESCRIPTION     "This textual convention is used to specify the hierarchy
                     in which spoke-SDPs are blocked when a MAC-move limit is
                     exceeded. When a MAC is moving among multiple SAPs or
                     spoke-SDPs, the SAP bind or spoke-SDP bind with the
                     lower level is blocked first. (tertiary is the lowest)"
    SYNTAX          INTEGER {
                        primary   (1),
                        secondary (2),
                        tertiary  (3)
                    }

TlsLimitMacMove  ::= TEXTUAL-CONVENTION
    STATUS          current
    DESCRIPTION     "This textual convention is used to specify the behavior
                     when the re-learn rate specified by svcTlsMacMoveMaxRate
                     is exceeded.

                     A value of 'blockable' specifies that the agent will
                     monitor the MAC relearn rate on a SAP or SDP Bind and
                     it will block it when the re-learn rate specified by
                     svcTlsMacMoveMaxRate is exceeded. A value of 'nonBlockable'
                     specifies that the  SAP or SDP Bind will not be blocked,
                     and another blockable SAP or SDP Bind will be blocked
                     instead."
    SYNTAX          INTEGER {
                        blockable    (1),
                        nonBlockable (2)
                    }

SdpBindVcType  ::= TEXTUAL-CONVENTION
    STATUS          current
    DESCRIPTION     "This textual convention is used to specify the type of
                     virtual circuit (VC) associated with the SDP binding.
                     The value 'vpls' is no longer supported."
    SYNTAX          INTEGER {
                        undef      (1),
                        ether      (2),
                        --vpls     (3) obsolete
                        vlan       (4),
                        mirror     (5),
                        atmSdu     (6),
                        atmCell    (7),
                        atmVcc     (8),
                        atmVpc     (9),
                        frDlci     (10),
                        ipipe      (11),
                        satopE1    (12),
                        satopT1    (13),
                        satopE3    (14),
                        satopT3    (15),
                        cesopsn    (16),
                        cesopsnCas (17)
                    }

StpExceptionCondition ::= TEXTUAL-CONVENTION
    STATUS          current
    DESCRIPTION     "This textual convention is used to specify an
                     STP exception condition encountered on an
                     interface
                     - none : no exception condition found.
                     - oneWayCommuniation : The neighbor RSTP peer on this link
                                            is not able to detect our presence.
                     - downstreamLoopDetected : A loop is detected on this
                       link."
    SYNTAX          INTEGER {
                        none                   (1),
                        oneWayCommuniation     (2),
                        downstreamLoopDetected (3)
                    }

LspIdList ::= TEXTUAL-CONVENTION
    STATUS          current
    DESCRIPTION     "Each group of four octets in this string specify
                     a 32-bit LSP ID, which corresponds to the
                     vRtrMplsLspIndex of the given MPLS LSP. The LSP
                     IDs are stored in network byte order; i.e. octet
                     N corresponds to the most significant 8 bits of
                     the LSP ID, and octet N+3 correspond to the least
                     significant 8 bits. The list is terminated by the
                     null LSP ID. The LSP IDs in this list are not
                     required to be sorted in any specific order. The
                     list is large enough to hold up to 16 LSP IDs,
                     plus the null terminator."
    SYNTAX          OCTET STRING (SIZE (0..68))

BridgeId ::= TEXTUAL-CONVENTION
    STATUS          current
    DESCRIPTION     "The Bridge-Identifier used by the Spanning Tree
                     Protocol to uniquely identify a bridge. The first
                     two octets represent the bridge priority (in big
                     endian format) while the remaining six octets
                     represent the main MAC address of the bridge."
    SYNTAX          OCTET STRING (SIZE (8))

TSapIngQueueId ::= TEXTUAL-CONVENTION
    STATUS          current
    DESCRIPTION     "The value used to uniquely identify a SAP ingress queue.
                     The actual valid values are those defined in the given
                     SAP ingress QoS policy."
    SYNTAX          Unsigned32 (1..32)

TSapEgrQueueId ::= TEXTUAL-CONVENTION
    STATUS          current
    DESCRIPTION     "The value used to uniquely identify a SAP egress queue.
                     The actual valid values are those defined in the given
                     SAP egress QoS policy."
    SYNTAX          Unsigned32 (1..8)

TStpPortState ::= TEXTUAL-CONVENTION
    STATUS          current
    DESCRIPTION     "The value used to specify the port state as defined
                     by application of the Spanning Tree Protocol. This
                     state controls what action a port takes on reception
                     of a frame."
    SYNTAX          INTEGER {
                        disabled   (1),
                        blocking   (2),
                        listening  (3),
                        learning   (4),
                        forwarding (5),
                        broken     (6),
                        discarding (7)
                    }

StpPortRole ::= TEXTUAL-CONVENTION
    STATUS          current
    DESCRIPTION     "the stp portrole defined by the Rapid Spanning Tree
                     Protocol."

    SYNTAX          INTEGER {
                        master     (0),
                        root       (1),
                        designated (2),
                        alternate  (3),
                        backup     (4),
                        disabled   (5)
                    }

StpProtocol ::= TEXTUAL-CONVENTION
    STATUS          current
    DESCRIPTION     "indicates all possible version of the stp protocol."
    SYNTAX          INTEGER {
                        notApplicable (0),
                        stp           (1),
                        rstp          (2),
                        mstp          (3)
                    }

MfibLocation ::= TEXTUAL-CONVENTION
    STATUS          current
    DESCRIPTION     "MfibLocation represents the type of local 'interface':
                     -'sap': sap interface
                     -'sdp': mesh-sdp or spoke-sdp interface."
    SYNTAX          INTEGER {
                        sap (1),
                        sdp (2)
                    }

MfibGrpSrcFwdOrBlk ::= TEXTUAL-CONVENTION
    STATUS          current
    DESCRIPTION     "MfibGrpSrcFwdOrBlk describes whether traffic for the
                     related source-group is to be forwarded or blocked."
    SYNTAX          INTEGER {
                        forward (1),
                        block   (2)
                    }

MvplsPruneState ::= TEXTUAL-CONVENTION
    STATUS          current
    DESCRIPTION     "Managed VPLS (mVPLS): state of a SAP or spoke-SDP in a
                     user VPLS (uVPLS).
                     - notApplicable :
                       the SAP or spoke SDP of a uVPLS is not managed by a SAP
                       or spoke SDP of a mVPLS.
                     - notPruned:
                       the SAP or spoke SDP of a uVPLS is managed by a mVPLS,
                       but the link is not pruned.
                     -pruned
                       the SAP or spoke SDP of a uVPLS is managed by a mVPLS,
                       but the link is pruned as a result of an STP decision
                       taken in the STP instance running in the mVPLS."
    SYNTAX          INTEGER {
                        notApplicable (1),
                        notPruned     (2),
                        pruned        (3)
                    }

TQosQueueAttribute ::= TEXTUAL-CONVENTION
    STATUS          current
    DESCRIPTION     "Indicates attributes of a QoS queue"
    SYNTAX          BITS {
                        cbs          (0),
                        cir          (1),
                        cirAdaptRule (2),
                        mbs          (3),
                        pir          (4),
                        pirAdaptRule (5),
                        hiPrioOnly   (6),
                        avgOverhead  (7) --egress only
                    }

TVirtSchedAttribute ::= TEXTUAL-CONVENTION
    STATUS          current
    DESCRIPTION     "Indicates attributes of a virtual scheduler"
    SYNTAX          BITS {
                        cir       (0),
                        pir       (1),
                        summedCir (2)
                    }

MstiInstanceId ::= TEXTUAL-CONVENTION
    STATUS          current
    DESCRIPTION     "indicates all possible multiple spanning tree instances,
                     not including the CIST."
    SYNTAX          Unsigned32 (1..4094)

MstiInstanceIdOrZero ::= TEXTUAL-CONVENTION
    STATUS          current
    DESCRIPTION     "indicates all possible multiple spanning tree instances,
                     including the CIST (for which case the value '0' is 
                     reserved)."
    SYNTAX          Unsigned32 (0..4094)

DhcpLseStateInfoOrigin ::= TEXTUAL-CONVENTION
    STATUS          current
    DESCRIPTION     "Indicates the originator of the provided information."
    SYNTAX          INTEGER {
                        none            (0),
                        dhcp            (1),
                        radius          (2),
                        retailerRadius  (3),
                        retailerDhcp    (4),
                        default         (5) -- The default subId, specified in
                                            -- sapSubMgmtDefSubIdent, is used.
                    }

IAIDType ::= TEXTUAL-CONVENTION
    STATUS          current
    DESCRIPTION     "Indicates the type of the addresses that are associated
                     with the Identity Association ID (IAID)"
    SYNTAX          INTEGER {
                        undefined     (0),
                        temporary     (1), -- IAID for temporary addresses,
                                           -- as defined in RFC 3041
                        non-temporary (2), -- IAID for non-temporary addresses
                        prefix        (3)  -- IAID for prefixes
                    }

TdmOptionsSigPkts ::= TEXTUAL-CONVENTION
    STATUS          current
    DESCRIPTION     "Encodes support for the cpipe circuit emulation (CE)
                     application signaling packets:
                     - 'noSigPkts' :
                       for a cpipe that does not use signalling packets.
                     - 'dataPkts' :
                       for a cpipe carrying TDM data packets and expecting CE
                       application signalling packets in a separate cpipe.
                     - 'sigPkts' :
                       for a cpipe carrying CE application signalling packets
                       with the data packets in a separate cpipe.
                     - 'dataAndSigPkts' :
                       for a cpipe carrying TDM data and CE application
                       signalling on the same cpipe."

    SYNTAX          INTEGER {
                        noSigPkts      (0),
                        dataPkts       (1),
                        sigPkts        (2),
                        dataAndSigPkts (3)
                    }

TdmOptionsCasTrunkFraming ::= TEXTUAL-CONVENTION
    STATUS          current
    DESCRIPTION     "Encodes the CEM SAPs CAS trunk framing type:
                     - 'noCas' :
                       for all CEM SAPs except 'nxDS0WithCas'.
                     - 'e1Trunk' :
                       for a 'nxDS0WithCas' SAP with E1 trunk.
                     - 't1EsfTrunk' :
                       for a 'nxDS0WithCas' SAP with T1 ESF trunk.
                     - 't1SfTrunk' :
                       for a 'nxDS0WithCas' SAP with T1 SF trunk."
    SYNTAX          INTEGER {
                        noCas      (0),
                        e1Trunk    (1),
                        t1EsfTrunk (2),
                        t1SfTrunk  (3)
                    }

CemSapReportAlarm ::= TEXTUAL-CONVENTION
    STATUS      current
    DESCRIPTION
        "The CemSapReportAlarm data type indicates the type of CEM SAP alarm:
         strayPkts     - receiving stray packets.
         malformedPkts - detecting malformed packets.
         pktLoss       - experiencing packet loss.
         bfrOverrun    - experiencing jitter buffer overrun.
         bfrUnderrun   - experiencing jitter buffer underrun.
         rmtPktLoss    - remote packet loss indication.
         rmtFault      - remote TDM fault indication.
         rmtRdi        - remote RDI indication."
    SYNTAX          BITS {
                        notUsed       (0),
                        strayPkts     (1),
                        malformedPkts (2),
                        pktLoss       (3),
                        bfrOverrun    (4),
                        bfrUnderrun   (5),
                        rmtPktLoss    (6),
                        rmtFault      (7),
                        rmtRdi        (8)
                    }
 
CemSapEcid ::= TEXTUAL-CONVENTION
    STATUS          current
    DESCRIPTION     "The Emulated Circuit Identifier (ECID) is a 20 bit
                     unsigned binary field containing an identifier for the
                     circuit being emulated.  ECIDs have local significance
                     only and are associated with a specific MAC address.
                     Therefore the SAP can have a different ECID for each
                     direction."
    SYNTAX          Unsigned32 (0..1048575)
                     
SdpBFHundredthsOfPercent ::= TEXTUAL-CONVENTION
    STATUS      current
    DESCRIPTION
        "The percentage of total SDP bandwidth reserved for SDP bindings 
         with two decimal places accuracy."
    SYNTAX      Integer32 (1..10000)

SdpBindBandwidth ::= TEXTUAL-CONVENTION
    STATUS       current
    DESCRIPTION
        "The required SDP binding bandwidth, in kbps."
    SYNTAX       Unsigned32 (0..100000000)


L2ptProtocols ::= TEXTUAL-CONVENTION
    STATUS      current
    DESCRIPTION
        "The L2ptProtocols indicates which L2 protocols should have their tunnels
         terminated when 'L2ptTermination' is enabled.
         stp           - spanning tree protocols stp/mstp/pvst/rstp
         cdp           - cisco discovery protocol
         vtp           - virtual trunk protocol
         dtp           - dynamic trunking protocol     
         pagp          - port aggregation protocol
         udld          - unidirectional link detection"

    SYNTAX          BITS {
                        stp       (0),
                        cdp       (1),
                        vtp       (2),
                        dtp       (3),
                        pagp      (4),
                        udld      (5)
                    }

SvcISID ::= TEXTUAL-CONVENTION
    STATUS      current
    DESCRIPTION
        "The SvcISID specifies a 24 bit (0..16777215) service instance
        identifier for the service. As part of the Provider Backbone Bridging
        frames, it is used at the destination PE as a demultiplexor field.

        The value of -1 is used to indicate the value of this object is
        un-specified."
    SYNTAX          Integer32 (-1 | 0..16777215)

L2RouteOrigin ::= TEXTUAL-CONVENTION
    STATUS      current
    DESCRIPTION
        "The L2RouteOrigin indicates the source from which an L2 route
         was learned."
    SYNTAX          INTEGER {
                        manual    (1),
                        bgp-l2vpn (2),
                        radius    (3)
                    }

ConfigStatus ::= TEXTUAL-CONVENTION
    STATUS      current
    DESCRIPTION
        "The ConfigStatus indicates the status of the configuration for
         the purpose of notifications."
    SYNTAX          INTEGER {
                        created  (1),
                        modified (2),
                        deleted  (3)
                    }

-- --------------------------------------------------------------------
-- Objects in the ALCATEL-IND1-TIMETRA-SERV-MIB
-- --------------------------------------------------------------------
-- --------------------------------------------------------------------
-- Customer related objects
-- --------------------------------------------------------------------
custNumEntries OBJECT-TYPE
    SYNTAX          Integer32
    MAX-ACCESS      read-only
    STATUS          current
    DESCRIPTION     "The value of the object custNumEntries indicates the
                     current number of customer records configured in this
                     device."
    ::= { tmnxCustObjs 1 }

custNextFreeId OBJECT-TYPE
    SYNTAX          TmnxCustId
    MAX-ACCESS      read-only
    STATUS          current
    DESCRIPTION     "The value of the object custNextFreeId indicates the next
                     available value for custId, the index for the
                     custInfoTable."
    ::= { tmnxCustObjs 2 }

-- ------------------------------------
-- Customer Table
-- ------------------------------------
custInfoTable OBJECT-TYPE
    SYNTAX          SEQUENCE OF CustInfoEntry
    MAX-ACCESS      not-accessible
    STATUS          current
    DESCRIPTION     "A table that contains customer information. There
                     is an entry in this table corresponding to the
                     default customer. This entry cannot be edited or
                     deleted, and it is used as the default customer
                     for newly created services."
    ::= { tmnxCustObjs 3 }

custInfoEntry OBJECT-TYPE
    SYNTAX          CustInfoEntry
    MAX-ACCESS      not-accessible
    STATUS          current
    DESCRIPTION     "Information about a specific customer."
    INDEX           { custId }
    ::= { custInfoTable 1 }

CustInfoEntry ::=
    SEQUENCE {
        custId              TmnxCustId,
        custRowStatus       RowStatus,
        custDescription     ServObjDesc,
        custContact         ServObjDesc,
        custPhone           ServObjDesc,
        custLastMgmtChange  TimeStamp
    }

custId OBJECT-TYPE
    SYNTAX          TmnxCustId
    MAX-ACCESS      read-only
    STATUS          current
    DESCRIPTION     "Customer identifier. This ID must be unique
                     within a service domain."
    ::= { custInfoEntry 1 }

custRowStatus OBJECT-TYPE
    SYNTAX          RowStatus
    MAX-ACCESS      read-create
    STATUS          current
    DESCRIPTION     "The value of the object  custRowStatus specifies the
                     status of this row."
    ::= { custInfoEntry 2 }

custDescription OBJECT-TYPE
    SYNTAX          ServObjDesc
    MAX-ACCESS      read-create
    STATUS          current
    DESCRIPTION     "The value of the object custDescription specifies
                     optional, generic information about this customer
                     in a displayable format."
    DEFVAL          { "" }
    ::= { custInfoEntry 3 }

custContact OBJECT-TYPE
    SYNTAX          ServObjDesc
    MAX-ACCESS      read-create
    STATUS          current
    DESCRIPTION     "The value of the object custContact specifies the name of
                     the primary contact person for this customer."
    DEFVAL          { "" }
    ::= { custInfoEntry 4 }

custPhone OBJECT-TYPE
    SYNTAX          ServObjDesc
    MAX-ACCESS      read-create
    STATUS          current
    DESCRIPTION     "The value of the object custPhone specifies the
                     phone/pager number used to reach the primary contact
                     person."
    DEFVAL          { "" }
    ::= { custInfoEntry 5 }

custLastMgmtChange OBJECT-TYPE
    SYNTAX          TimeStamp
    MAX-ACCESS      read-only
    STATUS          current
    DESCRIPTION     "The value of the object custLastMgmtChange indicates the
                     value of the object sysUpTime at the time of the
                     most recent management-initiated change to
                     this customer."
    ::= { custInfoEntry 6 }

-- ------------------------------------
-- Customer Multi-Service Site Table
-- ------------------------------------
custMultiServiceSiteTable OBJECT-TYPE
    SYNTAX          SEQUENCE OF CustMultiServiceSiteEntry
    MAX-ACCESS      not-accessible
    STATUS          current
    DESCRIPTION     ""
    ::= { tmnxCustObjs 4 }

custMultiServiceSiteEntry OBJECT-TYPE
    SYNTAX          CustMultiServiceSiteEntry
    MAX-ACCESS      not-accessible
    STATUS          current
    DESCRIPTION     "Information about a specific customer's
                     multi-service site."
    INDEX           { custId, IMPLIED custMultSvcSiteName }
    ::= { custMultiServiceSiteTable 1 }

CustMultiServiceSiteEntry ::=
    SEQUENCE {
        custMultSvcSiteName                     TNamedItem,
        custMultSvcSiteRowStatus                RowStatus,
        custMultSvcSiteDescription              ServObjDesc,
        custMultSvcSiteScope                    INTEGER,
        custMultSvcSiteAssignment               Unsigned32,
        custMultSvcSiteIngressSchedulerPolicy   ServObjName,
        custMultSvcSiteEgressSchedulerPolicy    ServObjName,
        custMultSvcSiteLastMgmtChange           TimeStamp,
        custMultSvcSiteTodSuite                 TNamedItemOrEmpty,
        custMultSvcSiteCurrentIngrSchedPlcy     ServObjName,
        custMultSvcSiteCurrentEgrSchedPlcy      ServObjName,
        custMultSvcSiteEgressAggRateLimit       TPortSchedulerPIR,
        custMultSvcSiteIntendedIngrSchedPlcy    ServObjName,
        custMultSvcSiteIntendedEgrSchedPlcy     ServObjName,
        custMultSvcSiteFrameBasedAccnt          TruthValue
    }

custMultSvcSiteName OBJECT-TYPE
    SYNTAX          TNamedItem
    MAX-ACCESS      read-only
    STATUS          current
    DESCRIPTION     ""
    ::= { custMultiServiceSiteEntry 1 }

custMultSvcSiteRowStatus OBJECT-TYPE
    SYNTAX          RowStatus
    MAX-ACCESS      read-create
    STATUS          current
    DESCRIPTION     "The value of the object  custMultSvcSiteRowStatus
                     specifies the status of this row."
    ::= { custMultiServiceSiteEntry 2 }

custMultSvcSiteDescription OBJECT-TYPE
    SYNTAX          ServObjDesc
    MAX-ACCESS      read-create
    STATUS          current
    DESCRIPTION     "The value of the object custMultSvcSiteDescription
                     specifies option, generic information about this
                     customer's Multi-Service Site."
    DEFVAL          { "" }
    ::= { custMultiServiceSiteEntry 3 }

custMultSvcSiteScope OBJECT-TYPE
    SYNTAX          INTEGER {
                        port (1),
                        card (2)
                    }
    MAX-ACCESS      read-create
    STATUS          current
    DESCRIPTION     "The value of the object custMultSvcSiteScope specifies
                     the scope of the ingress and egress QoS scheduler policies
                     assigned to this Multi-Service Site. When the value is
                    'port' all the SAPs that are members of this
                     Multi-Service Site must be defined on the same port.
                     Similarly for the case of'card'."
    DEFVAL          { port }
    ::= { custMultiServiceSiteEntry 4 }

custMultSvcSiteAssignment OBJECT-TYPE
    SYNTAX          Unsigned32
    MAX-ACCESS      read-create
    STATUS          current
    DESCRIPTION     "The value of the object custMultSvcSiteAssignment
                     specifies the port ID, MDA, or card number, where
                     the SAPs that are members of this Multi-
                     Service Site are defined."
    DEFVAL          { 0 }
    ::= { custMultiServiceSiteEntry 5 }

custMultSvcSiteIngressSchedulerPolicy OBJECT-TYPE
    SYNTAX          ServObjName
    MAX-ACCESS      read-create
    STATUS          current
    DESCRIPTION     "The value of the object
                     custMultSvcSiteIngressSchedulerPolicy specifies the
                     ingress QoS scheduler policy assigned to this
                     Multi-Service Site."
    DEFVAL          { "" }
    ::= { custMultiServiceSiteEntry 6 }

custMultSvcSiteEgressSchedulerPolicy OBJECT-TYPE
    SYNTAX          ServObjName
    MAX-ACCESS      read-create
    STATUS          current
    DESCRIPTION     "The value of the object
                     custMultSvcSiteEgressSchedulerPolicy specifies the egress
                     QoS scheduler policy assigned to this Multi-Service Site."
    DEFVAL          { "" }
    ::= { custMultiServiceSiteEntry 7 }

custMultSvcSiteLastMgmtChange OBJECT-TYPE
    SYNTAX          TimeStamp
    MAX-ACCESS      read-only
    STATUS          current
    DESCRIPTION     "The value of the object custMultSvcSiteLastMgmtChange
                     indicates the value of sysUpTime at the time of the
                     most recent management-initiated change to
                     this multi-service site."
    ::= { custMultiServiceSiteEntry 8 }

custMultSvcSiteTodSuite OBJECT-TYPE
    SYNTAX          TNamedItemOrEmpty
    MAX-ACCESS      read-create
    STATUS          current
    DESCRIPTION     "The value of the object custMultSvcSiteTodSuite specifies
                     the Time of Day (ToD) suite to be applied on this
                     multi-service site. An empty string indicates that no ToD
                     suite is applied on this multi-service Site.
                     A set request will only be allowed, if the indicated suite
                     is defined is TIMETRA-SCHEDULER-MIB::tmnxTodSuiteTable.
                     Using a suite the values of
                     custMultSvcSiteIngressSchedulerPolicy and
                     custMultSvcSiteEgressSchedulerPolicy can be time based
                     manipulated."
    DEFVAL          { ''H }
    ::= { custMultiServiceSiteEntry 9 }

custMultSvcSiteCurrentIngrSchedPlcy OBJECT-TYPE
    SYNTAX          ServObjName
    MAX-ACCESS      read-only
    STATUS          current
    DESCRIPTION     "The value of the object
                     custMultSvcSiteCurrentIngrSchedPlcy indicates the Ingress
                     QoS scheduler on this multi-service Site, or zero if none
                     is currently active.
                     The active policy may deviate from
                     custMultSvcSiteIngressSchedulerPolicy
                     in case it is overruled by a ToD-suite policy defined on
                     this multi-service site."
    ::= { custMultiServiceSiteEntry 10 }

custMultSvcSiteCurrentEgrSchedPlcy OBJECT-TYPE
    SYNTAX          ServObjName
    MAX-ACCESS      read-only
    STATUS          current
    DESCRIPTION     "The value of the object custMultSvcSiteCurrentEgrSchedPlcy
                     indicates the Egress QoS scheduler on this SAP, or zero if
                     none is currently active.
                     The active policy may deviate from the
                     sapEgressQosSchedulerPolicy in case it is overruled by a
                     ToD-suite policy defined on this multi-service site."
    ::= { custMultiServiceSiteEntry 11 }

custMultSvcSiteEgressAggRateLimit       OBJECT-TYPE
    SYNTAX          TPortSchedulerPIR
    UNITS           "kbps"
    MAX-ACCESS      read-create
    STATUS          current
    DESCRIPTION     "The value of the object custMultSvcSiteEgressAggRateLimit
                     specifies the maximum total rate of all egress queues for
                     this multi-service site. The value '-1' means that there
                     is no limit."
    DEFVAL          { -1 }
    ::= { custMultiServiceSiteEntry 12 }

custMultSvcSiteIntendedIngrSchedPlcy OBJECT-TYPE
    SYNTAX          ServObjName
    MAX-ACCESS      read-only
    STATUS          current
    DESCRIPTION     "The value of the object custMultSvcSiteIntendedIngrSchedPlcy
                     indicates  indicates the Ingress QoS scheduler on this
                     multi-service Site that should be applied.
                     If it deviates from custMultSvcSiteCurrentIngrSchedPlcy,
                     this  means that there was a problem when trying to
                     activate this filter. It can only deviate when using
                     tod-suites for the SAP. When the tod-suites decides that
                     a new filter must be applied, it will try to do this.
                     If it fails, the current and intended field are
                     not equal."
    ::= { custMultiServiceSiteEntry 13 }

custMultSvcSiteIntendedEgrSchedPlcy OBJECT-TYPE
    SYNTAX          ServObjName
    MAX-ACCESS      read-only
    STATUS          current
    DESCRIPTION     "The value of the object custMultSvcSiteIntendedEgrSchedPlcy
                     indicates  indicates the Egress QoS scheduler on this
                     multi-service Site that should be applied.
                     If it deviates from custMultSvcSiteCurrentEgrSchedPlcy,
                     this  means that there was a problem when trying to
                     activate this filter. It can only deviate when using
                     tod-suites for the SAP. When the tod-suites decides that
                     a new filter must be applied, it will try to do this.
                     If it fails, the current and intended field are
                     not equal."
    ::= { custMultiServiceSiteEntry 14 }

custMultSvcSiteFrameBasedAccnt OBJECT-TYPE
    SYNTAX       TruthValue
    MAX-ACCESS   read-create
    STATUS       current
    DESCRIPTION
        "The value of custMultSvcSiteFrameBasedAccnt specifies whether
         to use frame-based accounting when evaluating 
         custMultSvcSiteEgressAggRateLimit for the egress queues for
         this multi-service site.

         If the value is 'false', the default packet-based accounting
         method will be used."
    DEFVAL { false }
    ::= { custMultiServiceSiteEntry 15 }

-- ----------------------------------------------------
-- Customer Multi-Service Site Ingress Statistics Table
-- ----------------------------------------------------
custMultiSvcSiteIngStatsTable OBJECT-TYPE
    SYNTAX          SEQUENCE OF CustMultiSvcSiteIngQosSchedStatsEntry
    MAX-ACCESS      not-accessible
    STATUS          current
    DESCRIPTION     "A table that contains ingress QoS scheduler
                     statistics for the customer multi service site."
    ::= { tmnxCustObjs 5 }

custMultiSvcSiteIngStatsEntry OBJECT-TYPE
    SYNTAX          CustMultiSvcSiteIngQosSchedStatsEntry
    MAX-ACCESS      not-accessible
    STATUS          current
    DESCRIPTION     "Ingress statistics about a specific customer
                     multi service site ingress scheduler."
    INDEX           { custId, custMultSvcSiteName, IMPLIED custIngQosSchedName}
    ::= { custMultiSvcSiteIngStatsTable 1 }

CustMultiSvcSiteIngQosSchedStatsEntry ::=
    SEQUENCE {
        custIngQosSchedName                     TNamedItem,
        custIngQosSchedStatsForwardedPackets    Counter64,
        custIngQosSchedStatsForwardedOctets     Counter64
    }

custIngQosSchedName OBJECT-TYPE
    SYNTAX          TNamedItem
    MAX-ACCESS      not-accessible
    STATUS          current
    DESCRIPTION     "The index of the ingress QoS scheduler of
                     this customer multi service site."
    ::= { custMultiSvcSiteIngStatsEntry 1 }

custIngQosSchedStatsForwardedPackets OBJECT-TYPE
    SYNTAX          Counter64
    MAX-ACCESS      read-only
    STATUS          current
    DESCRIPTION     "The value of the object
                     custIngQosSchedStatsForwardedPackets indicates the number
                     of forwarded packets, as determined by the customer
                     multi service site ingress scheduler policy."
    ::= { custMultiSvcSiteIngStatsEntry 2 }

custIngQosSchedStatsForwardedOctets OBJECT-TYPE
    SYNTAX          Counter64
    MAX-ACCESS      read-only
    STATUS          current
    DESCRIPTION     "The value of the object
                     custIngQosSchedStatsForwardedOctets indicates the number
                     of forwarded octets, as determined by the customer
                     multi service site ingress scheduler policy."
    ::= { custMultiSvcSiteIngStatsEntry 3 }

-- -----------------------------------------------------
-- Customer Multi-Service Site Egress Statistics Table
-- -----------------------------------------------------
custMultiSvcSiteEgrStatsTable OBJECT-TYPE
    SYNTAX          SEQUENCE OF CustMultiSvcSiteEgrQosSchedStatsEntry
    MAX-ACCESS      not-accessible
    STATUS          current
    DESCRIPTION     "A table that contains egress QoS scheduler
                     statistics for the customer multi service site."
    ::= { tmnxCustObjs 6 }

custMultiSvcSiteEgrStatsEntry OBJECT-TYPE
    SYNTAX          CustMultiSvcSiteEgrQosSchedStatsEntry
    MAX-ACCESS      not-accessible
    STATUS          current
    DESCRIPTION     "Egress statistics about a specific customer
                     multi service site egress scheduler."
    INDEX           { custId, custMultSvcSiteName, IMPLIED custEgrQosSchedName}
    ::= { custMultiSvcSiteEgrStatsTable 1 }

CustMultiSvcSiteEgrQosSchedStatsEntry ::=
    SEQUENCE {
        custEgrQosSchedName                     TNamedItem,
        custEgrQosSchedStatsForwardedPackets    Counter64,
        custEgrQosSchedStatsForwardedOctets     Counter64
    }

custEgrQosSchedName OBJECT-TYPE
    SYNTAX          TNamedItem
    MAX-ACCESS      not-accessible
    STATUS          current
    DESCRIPTION     "The index of the egress QoS scheduler of
                     this customer multi service site."
    ::= { custMultiSvcSiteEgrStatsEntry 1 }

custEgrQosSchedStatsForwardedPackets OBJECT-TYPE
    SYNTAX          Counter64
    MAX-ACCESS      read-only
    STATUS          current
    DESCRIPTION     "The value of the object
                     custEgrQosSchedStatsForwardedPackets indicates number of
                     forwarded packets, as determined by the customer
                     multi service site egress scheduler policy."
    ::= { custMultiSvcSiteEgrStatsEntry 2 }

custEgrQosSchedStatsForwardedOctets OBJECT-TYPE
    SYNTAX          Counter64
    MAX-ACCESS      read-only
    STATUS          current
    DESCRIPTION     "The value of the object
                     custEgrQosSchedStatsForwardedOctets indicates the number
                     of forwarded octets, as determined by the customer
                     multi service site egress scheduler policy."
    ::= { custMultiSvcSiteEgrStatsEntry 3 }

-- ----------------------------------------------------
-- Customer Multi-Service Site Ingress Statistics Table
-- with specific portId
-- ----------------------------------------------------
custIngQosPortIdSchedStatsTable OBJECT-TYPE
    SYNTAX          SEQUENCE OF CustIngQosPortIdSchedStatsEntry
    MAX-ACCESS      not-accessible
    STATUS          current
    DESCRIPTION
        "The custIngQosPortIdSchedStatsTable contains ingress QoS scheduler
         statistics for the customer multi service site."
    ::= { tmnxCustObjs 7 }

custIngQosPortIdSchedStatsEntry OBJECT-TYPE
    SYNTAX          CustIngQosPortIdSchedStatsEntry
    MAX-ACCESS      not-accessible
    STATUS          current
    DESCRIPTION
        "Each entry represents the ingress statistics about a specific customer
         multi service site ingress scheduler. Entries are created when
         a scheduler policy is applied to an MSS."
    INDEX           { custId, custMultSvcSiteName,
                      custIngQosPortIdSchedName, custIngQosAssignmentPortId }
    ::= { custIngQosPortIdSchedStatsTable 1 }

CustIngQosPortIdSchedStatsEntry ::=
    SEQUENCE {
        custIngQosPortIdSchedName                     TNamedItem,
        custIngQosAssignmentPortId                    TmnxPortID,
        custIngQosPortSchedFwdPkts                    Counter64,
        custIngQosPortSchedFwdOctets                  Counter64
    }

custIngQosPortIdSchedName OBJECT-TYPE
    SYNTAX          TNamedItem
    MAX-ACCESS      not-accessible
    STATUS          current
    DESCRIPTION
        "The value of custIngQosPortIdSchedName is used as an index
         of the ingress QoS scheduler of this customer multi service site."
    ::= { custIngQosPortIdSchedStatsEntry 1 }

custIngQosAssignmentPortId OBJECT-TYPE
    SYNTAX          TmnxPortID
    MAX-ACCESS      not-accessible
    STATUS          current
    DESCRIPTION
        "The value of custIngQosAssignmentPortId is used as an index
         of the ingress QoS scheduler of this customer multi service site.
         When an MSS assignment is an aps/ccag/lag in 'link' mode, each
         member-port of the aps/ccag/lag has its own scheduler. This object
         refers to the TmnxPortID of these member-ports."
    ::= {custIngQosPortIdSchedStatsEntry 2}

custIngQosPortSchedFwdPkts OBJECT-TYPE
    SYNTAX          Counter64
    MAX-ACCESS      read-only
    STATUS          current
    DESCRIPTION
        "The value of custIngQosPortSchedFwdPkts indicates the
         number of forwarded packets, as determined by the customer
         multi service site ingress scheduler policy."
    ::= { custIngQosPortIdSchedStatsEntry 3 }

custIngQosPortSchedFwdOctets OBJECT-TYPE
    SYNTAX          Counter64
    MAX-ACCESS      read-only
    STATUS          current
    DESCRIPTION
        "The value of custIngQosPortSchedFwdOctets indicates the
         number of forwarded octets, as determined by the customer
         multi service site ingress scheduler policy."
    ::= { custIngQosPortIdSchedStatsEntry 4 }

-- --------------------------------------------------------
-- Customer Multi-Service Site Egress Statistics Table
-- with specific portId
-- --------------------------------------------------------
custEgrQosPortIdSchedStatsTable OBJECT-TYPE
    SYNTAX          SEQUENCE OF CustEgrQosPortIdSchedStatsEntry
    MAX-ACCESS      not-accessible
    STATUS          current
    DESCRIPTION
        "The custEgrQosPortIdSchedStatsTable contains egress QoS scheduler
         statistics for the customer multi service site."
    ::= { tmnxCustObjs 8 }

custEgrQosPortIdSchedStatsEntry OBJECT-TYPE
    SYNTAX          CustEgrQosPortIdSchedStatsEntry
    MAX-ACCESS      not-accessible
    STATUS          current
    DESCRIPTION
        "Each row entry represents the egress statistics for a customer
         multi-service-site egress scheduler. Entries are created when
         a scheduler policy is applied to an MSS."
    INDEX           { custId, custMultSvcSiteName,
                      custEgrQosPortIdSchedName, custEgrQosAssignmentPortId }
    ::= { custEgrQosPortIdSchedStatsTable 1 }

CustEgrQosPortIdSchedStatsEntry ::=
    SEQUENCE {
        custEgrQosPortIdSchedName       TNamedItem,
        custEgrQosAssignmentPortId      TmnxPortID,
        custEgrQosPortSchedFwdPkts      Counter64,
        custEgrQosPortSchedFwdOctets    Counter64
    }

custEgrQosPortIdSchedName OBJECT-TYPE
    SYNTAX          TNamedItem
    MAX-ACCESS      not-accessible
    STATUS          current
    DESCRIPTION
        "The value of custEgrQosPortIdSchedName is used as an index
         of the egress QoS scheduler of this customer multi service site."
    ::= { custEgrQosPortIdSchedStatsEntry 1}

custEgrQosAssignmentPortId OBJECT-TYPE
    SYNTAX          TmnxPortID
    MAX-ACCESS      not-accessible
    STATUS          current
    DESCRIPTION
        "The value of custEgrQosAssignmentPortId is used as an index
         of the egress QoS scheduler of this customer multi service site.
         When an MSS assignment is an aps/ccag/lag in 'link' mode, each
         member-port of the aps/ccag/lag has its own scheduler. This object
         refers to the TmnxPortID of these member-ports."
    ::= { custEgrQosPortIdSchedStatsEntry 2}

custEgrQosPortSchedFwdPkts OBJECT-TYPE
    SYNTAX          Counter64
    MAX-ACCESS      read-only
    STATUS          current
    DESCRIPTION
        "The value of custEgrQosPortSchedFwdPkts indicates the
         number of forwarded packets, as determined by the customer
         multi service site egress scheduler policy."
    ::= { custEgrQosPortIdSchedStatsEntry 3 }

custEgrQosPortSchedFwdOctets OBJECT-TYPE
    SYNTAX          Counter64
    MAX-ACCESS      read-only
    STATUS          current
    DESCRIPTION
        "The value of custEgrQosPortSchedFwdOctets indicates the
         number of forwarded octets, as determined by the customer
         multi service site egress scheduler policy."
    ::= { custEgrQosPortIdSchedStatsEntry 4 }

-- --------------------------------------------------------
-- Customer Multi-Service Site Ingress QoS Scheduler Table
-- --------------------------------------------------------
custMssIngQosSchedInfoTable OBJECT-TYPE
    SYNTAX          SEQUENCE OF CustMssIngQosSchedInfoEntry
    MAX-ACCESS      not-accessible
    STATUS          current
    DESCRIPTION     "A table that contains ingress QoS scheduler
                     statistics for the customer multi service site."
    ::= { tmnxCustObjs 9 }

custMssIngQosSchedInfoEntry OBJECT-TYPE
    SYNTAX          CustMssIngQosSchedInfoEntry
    MAX-ACCESS      not-accessible
    STATUS          current
    DESCRIPTION     "Ingress statistics about a specific customer
                     multi service site ingress scheduler."
    INDEX           { custId,
                      custMultSvcSiteName,
                      IMPLIED custMssIngQosSName }
    ::= { custMssIngQosSchedInfoTable 1 }

CustMssIngQosSchedInfoEntry ::=
    SEQUENCE {
        custMssIngQosSName              TNamedItem,
        custMssIngQosSRowStatus         RowStatus,
        custMssIngQosSLastMgmtChange    TimeStamp,
        custMssIngQosSOverrideFlags     TVirtSchedAttribute,
        custMssIngQosSPIR               TPIRRate,
        custMssIngQosSCIR               TCIRRate,
        custMssIngQosSSummedCIR         TruthValue
    }

custMssIngQosSName OBJECT-TYPE
    SYNTAX          TNamedItem
    MAX-ACCESS      not-accessible
    STATUS          current
    DESCRIPTION     "The value of custMssIngQosSName indicates the name of
                     the virtual scheduler whose parameters are to be
                     overridden."
    ::= { custMssIngQosSchedInfoEntry 1 }

custMssIngQosSRowStatus OBJECT-TYPE
    SYNTAX          RowStatus
    MAX-ACCESS      read-create
    STATUS          current
    DESCRIPTION     "The value of custMssIngQosSRowStatus controls the
                     creation and deletion of rows in this table."
    ::= { custMssIngQosSchedInfoEntry 2 }

custMssIngQosSLastMgmtChange OBJECT-TYPE
    SYNTAX          TimeStamp
    MAX-ACCESS      read-only
    STATUS          current
    DESCRIPTION     "The value of custMssIngQosSLastMgmtChange indicates the
                     value of sysUpTime at the time of the last management
                     change of any writable object of this row."
    ::= { custMssIngQosSchedInfoEntry 3 }

custMssIngQosSOverrideFlags OBJECT-TYPE
    SYNTAX          TVirtSchedAttribute
    MAX-ACCESS      read-create
    STATUS          current
    DESCRIPTION     "The value of custMssIngQosSOverrideFlags specifies the
                     set of attributes whose values have been overridden
                     via management on this virtual scheduler. Clearing a
                     given flag will return the corresponding overridden
                     attribute to the value defined on the SAP's ingress
                     scheduler policy."
    ::= { custMssIngQosSchedInfoEntry 4 }

custMssIngQosSPIR OBJECT-TYPE
    SYNTAX          TPIRRate
    UNITS           "kilo bits per second"
    MAX-ACCESS      read-create
    STATUS          current
    DESCRIPTION     "The value of custMssIngQosSPIR specifies the desired
                     PIR value for this virtual scheduler."
    DEFVAL { -1 }
    ::= { custMssIngQosSchedInfoEntry 5 }

custMssIngQosSCIR OBJECT-TYPE
    SYNTAX          TCIRRate
    UNITS           "kilo bits per second"
    MAX-ACCESS      read-create
    STATUS          current
    DESCRIPTION     "The value of custMssIngQosSCIR specifies the desired
                     CIR value for this virtual scheduler."
    DEFVAL { -1 }
    ::= { custMssIngQosSchedInfoEntry 6 }

custMssIngQosSSummedCIR OBJECT-TYPE
    SYNTAX          TruthValue
    MAX-ACCESS      read-create
    STATUS          current
    DESCRIPTION     "The value of custMssIngQosSSummedCIR specifies if the CIR
                     should be used as the summed CIR values of the children
                     schedulers or queues. If set to 'true', the applicable
                     scheduler CIR (custMssIngQosSCIR) loses its meaning."
    DEFVAL { true }
    ::= { custMssIngQosSchedInfoEntry 7 }

-- --------------------------------------------------------
-- Customer Multi-Service Site Egrress QoS Scheduler Table
-- --------------------------------------------------------
custMssEgrQosSchedInfoTable OBJECT-TYPE
    SYNTAX          SEQUENCE OF CustMssEgrQosSchedInfoEntry
    MAX-ACCESS      not-accessible
    STATUS          current
    DESCRIPTION     "A table that contains egress QoS scheduler
                     statistics for the customer multi service site."
    ::= { tmnxCustObjs 10 }

custMssEgrQosSchedInfoEntry OBJECT-TYPE
    SYNTAX          CustMssEgrQosSchedInfoEntry
    MAX-ACCESS      not-accessible
    STATUS          current
    DESCRIPTION     "Egrress statistics about a specific customer
                     multi service site egress scheduler."
    INDEX           { custId,
                      custMultSvcSiteName,
                      IMPLIED custMssEgrQosSName }
    ::= { custMssEgrQosSchedInfoTable 1 }

CustMssEgrQosSchedInfoEntry ::=
    SEQUENCE {
        custMssEgrQosSName              TNamedItem,
        custMssEgrQosSRowStatus         RowStatus,
        custMssEgrQosSLastMgmtChange    TimeStamp,
        custMssEgrQosSOverrideFlags     TVirtSchedAttribute,
        custMssEgrQosSPIR               TPIRRate,
        custMssEgrQosSCIR               TCIRRate,
        custMssEgrQosSSummedCIR         TruthValue
    }

custMssEgrQosSName OBJECT-TYPE
    SYNTAX          TNamedItem
    MAX-ACCESS      not-accessible
    STATUS          current
    DESCRIPTION     "The value of custMssEgrQosSName indicates the name of
                     the virtual scheduler whose parameters are to be
                     overridden."
    ::= { custMssEgrQosSchedInfoEntry 1 }

custMssEgrQosSRowStatus OBJECT-TYPE
    SYNTAX          RowStatus
    MAX-ACCESS      read-create
    STATUS          current
    DESCRIPTION     "The value of custMssEgrQosSRowStatus controls the
                     creation and deletion of rows in this table."
    ::= { custMssEgrQosSchedInfoEntry 2 }

custMssEgrQosSLastMgmtChange OBJECT-TYPE
    SYNTAX          TimeStamp
    MAX-ACCESS      read-only
    STATUS          current
    DESCRIPTION     "The value of custMssEgrQosSLastMgmtChange indicates the
                     value of sysUpTime at the time of the last management
                     change of any writable object of this row."
    ::= { custMssEgrQosSchedInfoEntry 3 }

custMssEgrQosSOverrideFlags OBJECT-TYPE
    SYNTAX          TVirtSchedAttribute
    MAX-ACCESS      read-create
    STATUS          current
    DESCRIPTION     "The value of custMssEgrQosSOverrideFlags specifies the
                     set of attributes whose values have been overridden
                     via management on this virtual scheduler. Clearing a
                     given flag will return the corresponding overridden
                     attribute to the value defined on the SAP's ingress
                     scheduler policy."
    ::= { custMssEgrQosSchedInfoEntry 4 }

custMssEgrQosSPIR OBJECT-TYPE
    SYNTAX          TPIRRate
    UNITS           "kilo bits per second"
    MAX-ACCESS      read-create
    STATUS          current
    DESCRIPTION     "The value of custMssEgrQosSPIR specifies the desired
                     PIR value for this virtual scheduler."
    DEFVAL { -1 }
    ::= { custMssEgrQosSchedInfoEntry 5 }

custMssEgrQosSCIR OBJECT-TYPE
    SYNTAX          TCIRRate
    UNITS           "kilo bits per second"
    MAX-ACCESS      read-create
    STATUS          current
    DESCRIPTION     "The value of custMssEgrQosSCIR specifies the desired
                     CIR value for this virtual scheduler."
    DEFVAL { -1 }
    ::= { custMssEgrQosSchedInfoEntry 6 }

custMssEgrQosSSummedCIR OBJECT-TYPE
    SYNTAX          TruthValue
    MAX-ACCESS      read-create
    STATUS          current
    DESCRIPTION     "The value of custMssEgrQosSSummedCIR specifies if the CIR
                     should be used as the summed CIR values of the children
                     schedulers or queues. If set to 'true', the applicable
                     scheduler CIR (custMssEgrQosSCIR) loses its meaning."
    DEFVAL { true }
    ::= { custMssEgrQosSchedInfoEntry 7 }

-- --------------------------------------------------------
-- Customer Multi-Service Site Ingress Per-Policy 
-- Statistics Table
-- --------------------------------------------------------
custMultiSvcSiteIngSchedPlcyStatsTable OBJECT-TYPE
    SYNTAX          SEQUENCE OF CustMultiSvcSiteIngSchedPlcyStatsEntry
    MAX-ACCESS      not-accessible
    STATUS          current
    DESCRIPTION     "A table that contains ingress QoS scheduler
                     statistics for the customer multi service site, organized
                     by scheduler policy."
    ::= { tmnxCustObjs 11 }

custMultiSvcSiteIngSchedPlcyStatsEntry OBJECT-TYPE
    SYNTAX          CustMultiSvcSiteIngSchedPlcyStatsEntry
    MAX-ACCESS      not-accessible
    STATUS          current
    DESCRIPTION     "Ingress statistics about a specific customer
                     multi service site egress scheduler. Entries are created 
                     when a scheduler policy of a MSS is replaced with another 
                     one due to Time-Of-Day policies."
    INDEX           { custId, custMultSvcSiteName, 
                      tSchedulerPolicyName, IMPLIED tVirtualSchedulerName}
    ::= { custMultiSvcSiteIngSchedPlcyStatsTable 1 }

CustMultiSvcSiteIngSchedPlcyStatsEntry ::=
    SEQUENCE {
        custIngSchedPlcyStatsFwdPkt    Counter64,
        custIngSchedPlcyStatsFwdOct     Counter64
    }

custIngSchedPlcyStatsFwdPkt OBJECT-TYPE
    SYNTAX          Counter64
    MAX-ACCESS      read-only
    STATUS          current
    DESCRIPTION     "The value of the object
                     custIngSchedPlcyStatsFwdPkt indicates 
                     the number of forwarded packets, as determined by the 
                     customer multi service site ingress scheduler policy."
    ::= { custMultiSvcSiteIngSchedPlcyStatsEntry 1 }

custIngSchedPlcyStatsFwdOct OBJECT-TYPE
    SYNTAX          Counter64
    MAX-ACCESS      read-only
    STATUS          current
    DESCRIPTION     "The value of the object
                     custIngSchedPlcyStatsFwdOct indicates 
                     the number of forwarded octets, as determined by the 
                     customer multi service site ingress scheduler policy."
    ::= { custMultiSvcSiteIngSchedPlcyStatsEntry 2 }

-- --------------------------------------------------------
-- Customer Multi-Service Site Egress Per-Policy  
-- Statistics Table
-- --------------------------------------------------------
custMultiSvcSiteEgrSchedPlcyStatsTable OBJECT-TYPE
    SYNTAX          SEQUENCE OF CustMultiSvcSiteEgrSchedPlcyStatsEntry
    MAX-ACCESS      not-accessible
    STATUS          current
    DESCRIPTION     "A table that contains egress QoS scheduler
                     statistics for the customer multi service site, organized
                     by scheduler policy."
    ::= { tmnxCustObjs 12 }

custMultiSvcSiteEgrSchedPlcyStatsEntry OBJECT-TYPE
    SYNTAX          CustMultiSvcSiteEgrSchedPlcyStatsEntry
    MAX-ACCESS      not-accessible
    STATUS          current
    DESCRIPTION     "Egress statistics about a specific customer
                     multi service site egress scheduler. Entries are created 
                     when a scheduler policy of a MSS is replaced with another 
                     one due to Time-Of-Day policies."
    INDEX           { custId, custMultSvcSiteName, 
                      tSchedulerPolicyName, IMPLIED tVirtualSchedulerName}
    ::= { custMultiSvcSiteEgrSchedPlcyStatsTable 1 }

CustMultiSvcSiteEgrSchedPlcyStatsEntry ::=
    SEQUENCE {
        custEgrSchedPlcyStatsFwdPkt    Counter64,
        custEgrSchedPlcyStatsFwdOct    Counter64
    }

custEgrSchedPlcyStatsFwdPkt OBJECT-TYPE
    SYNTAX          Counter64
    MAX-ACCESS      read-only
    STATUS          current
    DESCRIPTION     "The value of the object
                     custEgrSchedPlcyStatsFwdPkt indicates 
                     the number of forwarded packets, as determined by 
                     the customer multi service site egress scheduler policy."
    ::= { custMultiSvcSiteEgrSchedPlcyStatsEntry 1 }

custEgrSchedPlcyStatsFwdOct OBJECT-TYPE
    SYNTAX          Counter64
    MAX-ACCESS      read-only
    STATUS          current
    DESCRIPTION     "The value of the object
                     custEgrSchedPlcyStatsFwdOct indicates 
                     the number of forwarded octets, as determined by 
                     the customer multi service site egress scheduler policy."
    ::= { custMultiSvcSiteEgrSchedPlcyStatsEntry 2 }

-- --------------------------------------------------------
-- Customer Multi-Service Site Ingress Per-Policy Statistics 
-- Table with specific portId
-- --------------------------------------------------------
custMultiSvcSiteIngSchedPlcyPortStatsTable OBJECT-TYPE
    SYNTAX          SEQUENCE OF CustMultiSvcSiteIngSchedPlcyPortStatsEntry
    MAX-ACCESS      not-accessible
    STATUS          current
    DESCRIPTION
        "The custMultiSvcSiteIngSchedPlcyPortStatsTable contains 
         ingress QoS scheduler statistics for the customer multi service site,
         organized by scheduler policy."
    ::= { tmnxCustObjs 13 }

custMultiSvcSiteIngSchedPlcyPortStatsEntry OBJECT-TYPE
    SYNTAX          CustMultiSvcSiteIngSchedPlcyPortStatsEntry
    MAX-ACCESS      not-accessible
    STATUS          current
    DESCRIPTION
        "Each entry represents the ingress statistics about a specific customer
         multi service site ingress scheduler. Entries are created when
         a scheduler policy of a MSS is replaced with another one due
         to Time-Of-Day policies."
    INDEX           { custId, custMultSvcSiteName, tSchedulerPolicyName, 
                      tVirtualSchedulerName, 
                      custIngSchedPlcyPortStatsPort }
    ::= { custMultiSvcSiteIngSchedPlcyPortStatsTable 1 }

CustMultiSvcSiteIngSchedPlcyPortStatsEntry ::=
    SEQUENCE {
        custIngSchedPlcyPortStatsPort           TmnxPortID,
        custIngSchedPlcyPortStatsFwdPkt         Counter64,
        custIngSchedPlcyPortStatsFwdOct         Counter64
    }

custIngSchedPlcyPortStatsPort OBJECT-TYPE
    SYNTAX          TmnxPortID
    MAX-ACCESS      not-accessible
    STATUS          current
    DESCRIPTION
        "The value of custIngSchedPlcyPortStatsPort is used as 
         an index of the ingress QoS scheduler of this customer multi service 
         site.
         When an MSS assignment is an aps/ccag/lag in 'link' mode, each
         member-port of the aps/ccag/lag has its own scheduler. This object
         refers to the TmnxPortID of these member-ports."
    ::= { custMultiSvcSiteIngSchedPlcyPortStatsEntry 1}

custIngSchedPlcyPortStatsFwdPkt OBJECT-TYPE
    SYNTAX          Counter64
    MAX-ACCESS      read-only
    STATUS          current
    DESCRIPTION
        "The value of custIngSchedPlcyPortStatsFwdPkt indicates the
         number of forwarded packets, as determined by the customer
         multi service site ingress scheduler policy."
    ::= { custMultiSvcSiteIngSchedPlcyPortStatsEntry 2 }

custIngSchedPlcyPortStatsFwdOct OBJECT-TYPE
    SYNTAX          Counter64
    MAX-ACCESS      read-only
    STATUS          current
    DESCRIPTION
        "The value of custIngSchedPlcyPortStatsFwdOct indicates the
         number of forwarded octets, as determined by the customer
         multi service site ingress scheduler policy."
    ::= { custMultiSvcSiteIngSchedPlcyPortStatsEntry 3 }


-- --------------------------------------------------------
-- Customer Multi-Service Site Egress Per-Policy Statistics 
-- Table with specific portId
-- --------------------------------------------------------
custMultiSvcSiteEgrSchedPlcyPortStatsTable OBJECT-TYPE
    SYNTAX          SEQUENCE OF CustMultiSvcSiteEgrSchedPlcyPortStatsEntry
    MAX-ACCESS      not-accessible
    STATUS          current
    DESCRIPTION
        "The custMultiSvcSiteEgrSchedPlcyPortStatsTable contains 
         egress QoS scheduler statistics for the customer multi service site,
         organized by scheduler policy."
    ::= { tmnxCustObjs 14 }

custMultiSvcSiteEgrSchedPlcyPortStatsEntry OBJECT-TYPE
    SYNTAX          CustMultiSvcSiteEgrSchedPlcyPortStatsEntry
    MAX-ACCESS      not-accessible
    STATUS          current
    DESCRIPTION
        "Each entry represents the egress statistics about a specific customer
         multi service site egress scheduler. Entries are created when
         a scheduler policy of a MSS is replaced with another one due
         to Time-Of-Day policies."
    INDEX           { custId, custMultSvcSiteName, tSchedulerPolicyName,
                      tVirtualSchedulerName, 
                      custEgrSchedPlcyPortStatsPort }
    ::= { custMultiSvcSiteEgrSchedPlcyPortStatsTable 1 }

CustMultiSvcSiteEgrSchedPlcyPortStatsEntry ::=
    SEQUENCE {
        custEgrSchedPlcyPortStatsPort      TmnxPortID,
        custEgrSchedPlcyPortStatsFwdPkt    Counter64,
        custEgrSchedPlcyPortStatsFwdOct    Counter64
    }

custEgrSchedPlcyPortStatsPort OBJECT-TYPE
    SYNTAX          TmnxPortID
    MAX-ACCESS      not-accessible
    STATUS          current
    DESCRIPTION
        "The value of custEgrSchedPlcyPortStatsPort is used as 
         an index of the egress QoS scheduler of this customer multi service 
         site.
         When an MSS assignment is an aps/ccag/lag in 'link' mode, each
         member-port of the aps/ccag/lag has its own scheduler. This object
         refers to the TmnxPortID of these member-ports."
    ::= { custMultiSvcSiteEgrSchedPlcyPortStatsEntry 1}

custEgrSchedPlcyPortStatsFwdPkt OBJECT-TYPE
    SYNTAX          Counter64
    MAX-ACCESS      read-only
    STATUS          current
    DESCRIPTION
        "The value of custEgrSchedPlcyPortStatsFwdPkt indicates the
         number of forwarded packets, as determined by the customer
         multi service site egress scheduler policy."
    ::= { custMultiSvcSiteEgrSchedPlcyPortStatsEntry 2 }

custEgrSchedPlcyPortStatsFwdOct OBJECT-TYPE
    SYNTAX          Counter64
    MAX-ACCESS      read-only
    STATUS          current
    DESCRIPTION
        "The value of custEgrSchedPlcyPortStatsFwdOct indicates the
         number of forwarded octets, as determined by the customer
         multi service site egress scheduler policy."
    ::= { custMultiSvcSiteEgrSchedPlcyPortStatsEntry 3 }

-- ------------------------------------
-- Customer traps
-- ------------------------------------
custCreated NOTIFICATION-TYPE
    OBJECTS {
        custId
    }
    STATUS          obsolete
    DESCRIPTION     "The trap custCreated is sent when a new row is created
                     in the custInfoTable."
    ::= { custTraps 1 }

custDeleted NOTIFICATION-TYPE
    OBJECTS {
        custId
    }
    STATUS          obsolete
    DESCRIPTION     "The trap custDeleted is sent when an existing row is
                     deleted from the custInfoTable."
    ::= { custTraps 2 }

custMultSvcSiteCreated NOTIFICATION-TYPE
    OBJECTS {
        custId,
        custMultSvcSiteName
    }
    STATUS          obsolete
    DESCRIPTION     "The trap custMultSvcSiteCreated is sent when a new row is
                     created in the custMultiServiceSiteTable."
    ::= { custTraps 3 }

custMultSvcSiteDeleted NOTIFICATION-TYPE
    OBJECTS {
        custId,
        custMultSvcSiteName
    }
    STATUS          obsolete
    DESCRIPTION     "The trap custMultSvcSiteDeleted is sent when an existing
                     row is deleted from the custMultiServiceSiteTable."
    ::= { custTraps 4 }

-- --------------------------------------------------------------------
-- Service related objects
-- --------------------------------------------------------------------
-- ------------------------------
-- tmnxSvcObjs group
-- ------------------------------
svcNumEntries OBJECT-TYPE
    SYNTAX          Integer32
    MAX-ACCESS      read-only
    STATUS          current
    DESCRIPTION     "The current number of services configured on this node."
    ::= { tmnxSvcObjs 1 }

-- --------------------------------
-- Base Service Table
-- --------------------------------
svcBaseInfoTable OBJECT-TYPE
    SYNTAX          SEQUENCE OF SvcBaseInfoEntry
    MAX-ACCESS      not-accessible
    STATUS          current
    DESCRIPTION     "A table that contains basic service information."
    ::= { tmnxSvcObjs 2 }

svcBaseInfoEntry OBJECT-TYPE
    SYNTAX          SvcBaseInfoEntry
    MAX-ACCESS      not-accessible
    STATUS          current
    DESCRIPTION     "Basic information about a specific service."
    INDEX           { svcId }
    ::= { svcBaseInfoTable 1 }

SvcBaseInfoEntry ::=
    SEQUENCE {
        svcId                 TmnxServId,
        svcRowStatus          RowStatus,
        svcType               ServType,
        svcCustId             TmnxCustId,
        svcIpRouting          TmnxEnabledDisabled,
        svcDescription        ServObjDesc,
        svcMtu                INTEGER,
        svcAdminStatus        ServiceAdminStatus,
        svcOperStatus         ServiceOperStatus,
        svcNumSaps            Integer32,
        svcNumSdps            Integer32,
        svcLastMgmtChange     TimeStamp,
        svcDefMeshVcId        Unsigned32,
        svcVpnId              VpnId,
        svcVRouterId          TmnxVRtrIDOrZero,
        svcAutoBind           INTEGER,
        svcLastStatusChange   TimeStamp,
        svcVllType            INTEGER,
        svcMgmtVpls           TruthValue,
        svcRadiusDiscovery    TruthValue,
        svcRadiusUserNameType INTEGER,
        svcRadiusUserName     DisplayString,
        svcVcSwitching        TruthValue,
        svcRadiusPEDiscPolicy TNamedItemOrEmpty,
        svcRadiusDiscoveryShutdown ServiceAdminStatus,
        svcVplsType           INTEGER
    }       

svcId OBJECT-TYPE
    SYNTAX          TmnxServId
    MAX-ACCESS      read-only
    STATUS          current
    DESCRIPTION     "The value of the object svcId specifies the
                     Service identifier. This value should be unique within the
                     service domain."
    ::= { svcBaseInfoEntry 1 }

svcRowStatus OBJECT-TYPE
    SYNTAX          RowStatus
    MAX-ACCESS      read-create
    STATUS          current
    DESCRIPTION     "This value of the object  svcRowStatus specifies the
                     status of this row.

                     To delete an entry from this table, the corresponding
                     service must be administratively down, have no SAP's
                     defined on it, and have no SDP bindings.

                     For svcType 'vprn', the service can be associated
                     with a routing instance by specifying svcVRouterId
                     during the creation of the service.

                     The value of the object svcVplsType specifies the VPLS
                     service type. The value of this object must be specified
                     when the row is created and cannot be changed while the
                     svcRowStatus is 'active'."

    ::= { svcBaseInfoEntry 2 }

svcType OBJECT-TYPE
    SYNTAX          ServType
    MAX-ACCESS      read-create
    STATUS          current
    DESCRIPTION     "The value of the object svcType specifies the service
                     type: e.g. epipe, tls, etc. The value of this object
                     must be specified when the row is created and cannot be
                     changed while the row status is 'active'."
    ::= { svcBaseInfoEntry 3 }

svcCustId OBJECT-TYPE
    SYNTAX          TmnxCustId
    MAX-ACCESS      read-create
    STATUS          current
    DESCRIPTION     "The value of the object svcCustId specifies the ID of the
                     customer who owns this service.
                     The value of this object must be specified when the row is
                     created and cannot be changed while the row status is
                     'active'."
    ::= { svcBaseInfoEntry 4 }

svcIpRouting OBJECT-TYPE
    SYNTAX          TmnxEnabledDisabled 
    MAX-ACCESS      read-create
    STATUS          current
    DESCRIPTION     "The value of the object svcIpRouting specifies, for a
                     'tls' service, whether IP routing is enabled.
                     For 'epipe', 'p3pipe', 'apipe', 'fpipe', 'ipipe'
                     and 'cpipe' services, this object cannot be set and has
                     the value 'disabled', whereas for 'vprn' and 'ies'
                     services the value is 'enabled' and cannot be set either.
                     For 'tls' services the value of this object must be
                     specified when the row is created and cannot be changed
                     while the row status is 'active'."
    ::= { svcBaseInfoEntry 5 }

svcDescription OBJECT-TYPE
    SYNTAX          ServObjDesc
    MAX-ACCESS      read-create
    STATUS          current
    DESCRIPTION     "The value of the object svcDescription specifiers an
                     optional, generic information about this service."
    DEFVAL          { "" }
    ::= { svcBaseInfoEntry 6 }

svcMtu OBJECT-TYPE
    SYNTAX          INTEGER (0..9194)
    MAX-ACCESS      read-create
    STATUS          current
    DESCRIPTION     "The value of the object svcMtu specifies the largest frame
                     size (in octets) that this service can handle.
                     The default value of this object depends on the service
                     type:
                     1514 octets for epipe, p3pipe and tls, 1508 for apipe
                     and fpipe, and 1500 octets for vprn, ipipe and ies, 1514
                     octets for cpipe."
    ::= { svcBaseInfoEntry 7 }

svcAdminStatus OBJECT-TYPE
    SYNTAX          ServiceAdminStatus
    MAX-ACCESS      read-create
    STATUS          current
    DESCRIPTION     "The value of the object svcAdminStatus specifies the
                     desired state of this service."
    DEFVAL          { down }
    ::= { svcBaseInfoEntry 8 }

svcOperStatus OBJECT-TYPE
    SYNTAX          ServiceOperStatus
    MAX-ACCESS      read-only
    STATUS          current
    DESCRIPTION     "The value of the object svcOperStatus indicates the
                     operating state of this service. The requirements for a
                     service to be operationally up depend on the service type:

                     epipe, p3pipe, apipe, fpipe, ipipe and cpipe services are
                     'up' when the service is administratively up and either
                     both SAP's or a SAP and a spoke SDP Bind are operationally
                     up.

                     tls services are 'up' when the service is
                     administratively up and either at least two SAP's or
                     spoke SDP Bind's, or one SAP or spoke SDP Bind and
                     at least one mesh SDP Bind are operationally up.

                     vprn and ies services are 'up' when the service is
                     administratively up and at least one interface is
                     operationally up."
    ::= { svcBaseInfoEntry 9 }

svcNumSaps OBJECT-TYPE
    SYNTAX          Integer32
    MAX-ACCESS      read-only
    STATUS          current
    DESCRIPTION     "The value of the object svcNumSaps indicates the number of
                     SAPs defined on this service."
    ::= { svcBaseInfoEntry 10 }

svcNumSdps OBJECT-TYPE
    SYNTAX          Integer32
    MAX-ACCESS      read-only
    STATUS          current
    DESCRIPTION     "The value of the object svcNumSdps indicates the number of
                     SDPs bound to this service."
    ::= { svcBaseInfoEntry 11 }

svcLastMgmtChange OBJECT-TYPE
    SYNTAX          TimeStamp
    MAX-ACCESS      read-only
    STATUS          current
    DESCRIPTION     "The value of of the object svcLastMgmtChange indicates
                     the value of sysUpTime at the time of the most recent
                     management-initiated change to this service."
    ::= { svcBaseInfoEntry 12 }

svcDefMeshVcId OBJECT-TYPE
    SYNTAX          Unsigned32
    MAX-ACCESS      read-create
    STATUS          current
    DESCRIPTION     "The value of the object svcDefMeshVcId specifies, only in
                     services that accept mesh SDP bindings, the VC ID portion
                     of the sdpBindId index of each mesh SDP binding defined in
                     the service. The default value of this object is equal to
                     the service ID."
    ::= { svcBaseInfoEntry 13 }

svcVpnId OBJECT-TYPE
    SYNTAX          VpnId
    MAX-ACCESS      read-create
    STATUS          current
    DESCRIPTION     "The value of the object  svcVpnId specifies the VPN ID
                     assigned to this service.  The value of this object can
                     be specified only when the row is created. If the value is
                     not specified, it defaults to the service ID."
    DEFVAL          { 0 }
    ::= { svcBaseInfoEntry 14 }

svcVRouterId OBJECT-TYPE
    SYNTAX          TmnxVRtrIDOrZero
    MAX-ACCESS      read-create
    STATUS          current
    DESCRIPTION     "The value of the object svcVRouterId specifies, for a IES
                     or VPRN service the associated virtual router instance
                     where its interfaces are defined.

                     This object has a special significance for the VPRN
                     service as it can be used to associate the service to a
                     specific virtual router instance.

                     If no routing instance is specified or a value of zero (0)
                     is specified, the agent will assign the vRtrID index value
                     that would have been returned by the vRtrNextVRtrID object
                     in the ALCATEL-IND1-TIMETRA-VRTR-MIB. The agent supports an SNMP SET
                     operation to the svcVRouterId object only during
                     row creation."
    DEFVAL { 0 }
    ::= { svcBaseInfoEntry 15 }

svcAutoBind OBJECT-TYPE
    SYNTAX          INTEGER {
                        none (1),
                        gre  (2),
                        ldp  (3)
                    }
    MAX-ACCESS      read-create
    STATUS          current
    DESCRIPTION     "The value of the object svcAutoBind specifies, for a VPRN
                     service, the type of lookup to be used by the routing
                     instance if no SDP to the destination exists."
    DEFVAL          { none }
    ::= { svcBaseInfoEntry 16 }

svcLastStatusChange OBJECT-TYPE
    SYNTAX          TimeStamp
    MAX-ACCESS      read-only
    STATUS          current
    DESCRIPTION     "The value of the object svcLastStatusChange indicates the
                     value of sysUpTime at the time of the most recent
                     operating status change to his service."
    ::= { svcBaseInfoEntry 17 }

svcVllType OBJECT-TYPE
    SYNTAX          INTEGER {
                        undef     (1),
                        atmSdu    (6),
                        atmCell   (7),
                        atmVcc    (8),
                        atmVpc    (9),
                        frDlci    (10),
                        satopE1   (12),
                        satopT1   (13),
                        satopE3   (14),
                        satopT3   (15),
                        cesopsn   (16),
                        cesopsnCas(17)
                    }
    MAX-ACCESS      read-create
    STATUS          current
    DESCRIPTION     "The value of the object svcVllType specifies, for a apipe,
                     fpipe or cpipe service, the type of pseudo-wire to be
                     signalled for the service.  The default for this object
                     depends on the service type:
                     'atmSdu' for apipes, 'frDlci' for fpipes, satopE1 for
                     cpipes, and 'undef' for all other service types."
    ::= { svcBaseInfoEntry 18 }

svcMgmtVpls OBJECT-TYPE
    SYNTAX          TruthValue
    MAX-ACCESS      read-create
    STATUS          current
    DESCRIPTION    "The value of the object svcMgmtVpls specifies, only if
                    svcType = 'tls' whether or not the service is a management
                    vpls.
                    If set to false the service is acting as a regular VPLS
                    service. If set to true, the service is  acting  as  a
                    management  VPLS  service. This implies that RSTP will
                    always be enabled, and that the  conclusions of this RSTP
                    can be associated to different (regular) VPLSs.
                    The value of this object cannot be changed after creation."
    DEFVAL          { false }
    ::= { svcBaseInfoEntry 19 }

svcRadiusDiscovery OBJECT-TYPE
    SYNTAX           TruthValue
    MAX-ACCESS       read-create
    STATUS           current
    DESCRIPTION
        "The value of the object svcRadiusDiscovery specifies whether RADIUS
         auto-discovery is enabled on this service."
    DEFVAL          { false }
    ::= { svcBaseInfoEntry 20 }


svcRadiusUserNameType OBJECT-TYPE
    SYNTAX           INTEGER {
                     none                 (0),
                     vpn-id               (1),
                     router-distinguisher (2)
                     }
    MAX-ACCESS       read-create
    STATUS           current
    DESCRIPTION
        "The value of the object svcRadiusUserNameType specifies whether RADIUS
         user name is vpn-id or router-distinguisher.  By default, the 
         value of this object is 'none'.  
         
         svcRadiusUserNameType and svcRadiusUserName, which indicates the 
         RADIUS username, must be set together in the same SNMP request 
         PDU if svcRadiusUserNameType is vpn-id or router-distinguisher or
         else the set request will fail with an inconsistentValue error."
    DEFVAL          { none }
    ::= { svcBaseInfoEntry 21 }

svcRadiusUserName OBJECT-TYPE
    SYNTAX           DisplayString (SIZE (0..64))
    MAX-ACCESS       read-create
    STATUS           current
    DESCRIPTION
        "The value of the object svcRadiusUserName specifies the  RADIUS
         user name.  svcRadiusUserNameType specifies the type of the 
         username and has to be set along with svcRadiusUserName when 
         svcRadiusUserName can either be a vpn-id or a router-distinguisher."    
    DEFVAL          { "" }
    ::= { svcBaseInfoEntry 22 }

svcVcSwitching OBJECT-TYPE
    SYNTAX           TruthValue
    MAX-ACCESS       read-create
    STATUS           current
    DESCRIPTION
        "The value of the object svcVcSwitching specifies if the PW 
         switching signalling is used for the Spokes configured under the 
         service.  
         This object can only be specified when the row is created."
    DEFVAL     { false }
    ::= { svcBaseInfoEntry 23 }

svcRadiusPEDiscPolicy OBJECT-TYPE
    SYNTAX           TNamedItemOrEmpty
    MAX-ACCESS       read-create
    STATUS           current
    DESCRIPTION
        "The value of the object svcRadiusPEDiscPolicy specifies the 
         RADIUS PE Discovery Policy name. "    
    DEFVAL     { "" }
    ::= { svcBaseInfoEntry 24 }
    
svcRadiusDiscoveryShutdown OBJECT-TYPE
    SYNTAX     ServiceAdminStatus
    MAX-ACCESS read-create
    STATUS     current
    DESCRIPTION
      "The value of svcRadiusDiscoveryShutdown specifies the desired 
       administrative state for the RADIUS auto-discovery server. When 
       the server is 'down' the operational state of the server is
       disabled.  

       By default, state of the RADIUS auto-discovery server is 'down'."
    DEFVAL { down }
    ::= { svcBaseInfoEntry 25 }   

svcVplsType OBJECT-TYPE
    SYNTAX          INTEGER {
                        none  (1),
                        bVpls (2),
                        iVpls (3)
                    }
    MAX-ACCESS      read-create
    STATUS          current
    DESCRIPTION     "Backbone VPLS ('bVpls') refers to the B-Component instance
                     of the Provider Backbone Bridging (PBB/IEEE 802.1ah)
                     feature. It represents the Multi-point tunneling component
                     that multiplexes multiple Customer VPNs (ISIDs) together.
                     It is similar to a regular VPLS instance that operates
                     on the Backbone MAC addresses.

                     ISID VPLS ('iVpls') or I-VPLS refers to the I-Component
                     instance of the Provider Backbone Bridging (PBB/IEEE
                     802.1ah) feature. It identifies the specific VPN entity
                     associated to a customer Multipoint (ELAN) service. It is
                     similar to a regular VPLS instance that operates on the
                     Customer MAC addresses.

                     The value of the object svcVplsType specifies the VPLS
                     service type. The value of this object must be specified
                     when the row is created and cannot be changed while the
                     svcRowStatus is 'active'."
    DEFVAL     { none }
    ::= { svcBaseInfoEntry 26 }

-- ------------------------------------
-- TLS Service Table
-- ------------------------------------
svcTlsInfoTable OBJECT-TYPE
    SYNTAX          SEQUENCE OF SvcTlsInfoEntry
    MAX-ACCESS      not-accessible
    STATUS          current
    DESCRIPTION     "A table that contains TLS service information."
    ::= { tmnxSvcObjs 3 }

svcTlsInfoEntry OBJECT-TYPE
    SYNTAX          SvcTlsInfoEntry
    MAX-ACCESS      not-accessible
    STATUS          current
    DESCRIPTION     "TLS specific information about a service."
    INDEX           { svcId }
    ::= { svcTlsInfoTable 1 }

SvcTlsInfoEntry ::=
    SEQUENCE {
        svcTlsMacLearning                   TmnxEnabledDisabled,
        svcTlsDiscardUnknownDest            TmnxEnabledDisabled,
        svcTlsFdbTableSize                  Integer32,
        svcTlsFdbNumEntries                 Integer32,
        svcTlsFdbNumStaticEntries           Integer32,
        svcTlsFdbLocalAgeTime               Integer32,
        svcTlsFdbRemoteAgeTime              Integer32,
        svcTlsStpAdminStatus                TmnxEnabledDisabled,
        svcTlsStpPriority                   Integer32,
        svcTlsStpBridgeAddress              MacAddress,
        svcTlsStpTimeSinceTopologyChange    TimeTicks,
        svcTlsStpTopologyChanges            Integer32,
        svcTlsStpDesignatedRoot             BridgeId,
        svcTlsStpRootCost                   Integer32,
        svcTlsStpRootPort                   Integer32,
        svcTlsStpMaxAge                     Integer32,
        svcTlsStpHelloTime                  Integer32,
        svcTlsStpHoldTime                   Integer32,
        svcTlsStpForwardDelay               Integer32,
        svcTlsStpBridgeMaxAge               Integer32,
        svcTlsStpBridgeHelloTime            Integer32,
        svcTlsStpBridgeForwardDelay         Integer32,
        svcTlsStpOperStatus                 INTEGER,
        svcTlsStpVirtualRootBridgeStatus    INTEGER,
        svcTlsMacAgeing                     TmnxEnabledDisabled,
        svcTlsStpTopologyChangeActive       TruthValue,
        svcTlsFdbTableFullHighWatermark     Integer32,
        svcTlsFdbTableFullLowWatermark      Integer32,
        svcTlsVpnId                         VpnId,
        svcTlsCustId                        TmnxCustId,
        svcTlsStpVersion                    INTEGER,
        svcTlsStpHoldCount                  Integer32,
        svcTlsStpPrimaryBridge              BridgeId,
        svcTlsStpBridgeInstanceId           Integer32,
        svcTlsStpVcpOperProtocol            StpProtocol,
        svcTlsMacMoveMaxRate                Unsigned32,
        svcTlsMacMoveRetryTimeout           Unsigned32,
        svcTlsMacMoveAdminStatus            TmnxEnabledDisabled,
        svcTlsMacRelearnOnly                TruthValue,
        svcTlsMfibTableSize                 Integer32,
        svcTlsMfibTableFullHighWatermark    Integer32,
        svcTlsMfibTableFullLowWatermark     Integer32,
        svcTlsMacFlushOnFail                TmnxEnabledDisabled,
        svcTlsStpRegionName                 DisplayString,
        svcTlsStpRegionRevision             Integer32,
        svcTlsStpBridgeMaxHops              Integer32,
        svcTlsStpCistRegionalRoot           BridgeId,
        svcTlsStpCistIntRootCost            Integer32,
        svcTlsStpCistRemainingHopCount      Integer32,
        svcTlsStpCistRegionalRootPort       Integer32,
        svcTlsFdbNumLearnedEntries          Integer32,
        svcTlsFdbNumOamEntries              Integer32,
        svcTlsFdbNumDhcpEntries             Integer32,
        svcTlsFdbNumHostEntries             Integer32,
        svcTlsShcvAction                    INTEGER,                
        svcTlsShcvSrcIp                     IpAddress,
        svcTlsShcvSrcMac                    MacAddress,
        svcTlsShcvInterval                  Unsigned32,
        svcTlsPriPortsCumulativeFactor      Unsigned32,
        svcTlsSecPortsCumulativeFactor      Unsigned32,
        svcTlsL2ptTermEnabled               TruthValue,
        svcTlsPropagateMacFlush             TruthValue,
        svcTlsMrpAdminStatus                TmnxEnabledDisabled,
        svcTlsMrpMaxAttributes              Unsigned32,
        svcTlsMrpAttributeCount             Unsigned32,
        svcTlsMrpFailedRegisterCount        Unsigned32,
        svcTlsMcPathMgmtPlcyName            TNamedItem,
        svcTlsMrpFloodTime                  Unsigned32,
        svcTlsMrpAttrTblHighWatermark       Integer32,
        svcTlsMrpAttrTblLowWatermark        Integer32
     }

svcTlsMacLearning OBJECT-TYPE
    SYNTAX          TmnxEnabledDisabled
    MAX-ACCESS      read-write
    STATUS          current
    DESCRIPTION     "The value of the object svcTlsMacLearning specifies
                     whether the MAC learning process is enabled in this TLS."
    DEFVAL          { enabled }
    ::= { svcTlsInfoEntry 1 }

svcTlsDiscardUnknownDest OBJECT-TYPE
    SYNTAX          TmnxEnabledDisabled
    MAX-ACCESS      read-write
    STATUS          current
    DESCRIPTION     "The value of the object svcTlsDiscardUnknownDest
                     specifies whether frames received with an unknown
                     destination MAC are discarded in this TLS."
    DEFVAL          { disabled }
    ::= { svcTlsInfoEntry 2 }

svcTlsFdbTableSize OBJECT-TYPE
    SYNTAX          Integer32 (1..196607)
    MAX-ACCESS      read-write
    STATUS          current
    DESCRIPTION     "The value of the object svcTlsFdbTableSize specifies the
                     maximum number of learned and static entries allowed in
                     the FDB of this service. When the value of
                     ALCATEL-IND1-TIMETRA-CHASSIS-MIB::tmnxChassisOperMode is not 'c', the
                     maximum value of svcTlsFdbTableSize is '131071'."
    DEFVAL          { 250 }
    ::= { svcTlsInfoEntry 3 }

svcTlsFdbNumEntries OBJECT-TYPE
    SYNTAX          Integer32
    MAX-ACCESS      read-only
    STATUS          current
    DESCRIPTION     "The value of the object svcTlsFdbNumEntries indicates the
                     current number of entries in the FDB of this service."
    ::= { svcTlsInfoEntry 4 }

svcTlsFdbNumStaticEntries OBJECT-TYPE
    SYNTAX          Integer32
    MAX-ACCESS      read-only
    STATUS          current
    DESCRIPTION     "The value of the object svcTlsFdbNumStaticEntries
                     indicates the current number of static entries in the FDB
                     of this service."
    ::= { svcTlsInfoEntry 5 }

svcTlsFdbLocalAgeTime OBJECT-TYPE
    SYNTAX          Integer32 (60..86400)
    MAX-ACCESS      read-write
    STATUS          current
    DESCRIPTION     "The value of the object svcTlsFdbLocalAgeTime specifies
                     the number of seconds used to age out TLS FDB entries
                     learned on local SAPs."
    DEFVAL          { 300 }
    ::= { svcTlsInfoEntry 6 }

svcTlsFdbRemoteAgeTime OBJECT-TYPE
    SYNTAX          Integer32 (60..86400)
    MAX-ACCESS      read-write
    STATUS          current
    DESCRIPTION     "The value of the object svcTlsFdbRemoteAgeTime specifies
                     the number of seconds used to age out TLS FDB entries
                     learned on an SDP. These entries correspond to MAC
                     addresses learned on remote SAPs."
    DEFVAL          { 900 }
    ::= { svcTlsInfoEntry 7 }

svcTlsStpAdminStatus OBJECT-TYPE
    SYNTAX          TmnxEnabledDisabled
    MAX-ACCESS      read-write
    STATUS          current
    DESCRIPTION     "The value of the object svcTlsStpAdminStatus specifies the
                     administrative state of the Spanning Tree Protocol
                     instance associated with this service."
    DEFVAL          { disabled }
    ::= { svcTlsInfoEntry 8 }

svcTlsStpPriority OBJECT-TYPE
    SYNTAX          Integer32 (0..65535)
    MAX-ACCESS      read-write
    STATUS          current
    DESCRIPTION     "The value of the object  svcTlsStpPriority specifies
                     the priority of the Spanning Tree Protocol instance
                     associated with this service.
                     It is used as the highest 4 bits of the Bridge ID
                     included in the Configuration BPDU's generated by
                     this bridge.
                     The svcTlsStpPriority can only take-on values which
                     multiples of 4096 (4k). If a value is specified which
                     is not a multiple of 4K, then this value will be
                     replaced by the closest multiple of 4K which is lower
                     then the value entered."
    DEFVAL          { 32768 }
    ::= { svcTlsInfoEntry 9 }

svcTlsStpBridgeAddress OBJECT-TYPE
    SYNTAX          MacAddress
    MAX-ACCESS      read-only
    STATUS          current
    DESCRIPTION     "The value of the  object svcTlsStpBridgeAddress indicates
                     the MAC address used to identify this bridge in the
                     network. It is used as the last six octets of the
                     Bridge ID included in the Configuration BPDU's generated
                     by this bridge. The most significant 38 bits of the bridge
                     address are taken from the base MAC address of the
                     device, while the least significant 10 bits are
                     based on the corresponding TLS instance ID."
    ::= { svcTlsInfoEntry 10 }

svcTlsStpTimeSinceTopologyChange OBJECT-TYPE
    SYNTAX          TimeTicks
    MAX-ACCESS      read-only
    STATUS          current
    DESCRIPTION     "The value of the object svcTlsStpTimeSinceTopologyChange
                     indicates the time (in hundredths of a second) since the
                     last time a topology change was detected by the Spanning
                     Tree Protocol instance associated with this service."
    ::= { svcTlsInfoEntry 11 }

svcTlsStpTopologyChanges OBJECT-TYPE
    SYNTAX          Integer32
    MAX-ACCESS      read-only
    STATUS          current
    DESCRIPTION     "The value of the object svcTlsStpTopologyChanges indicates
                     the total number of topology changes detected by the
                     Spanning Tree Protocol instance associated with this
                     service since the management entity was last reset or
                     initialized."
    ::= { svcTlsInfoEntry 12 }

svcTlsStpDesignatedRoot OBJECT-TYPE
    SYNTAX          BridgeId
    MAX-ACCESS      read-only
    STATUS          current
    DESCRIPTION     "The value of the object svcTlsStpDesignatedRoot indicates
                     the bridge identifier of the root of the spanning tree as
                     determined by the Spanning Tree Protocol instance
                     associated with this service. This value is used as the
                     Root Identifier parameter in all Configuration BPDUs
                     originated by this node."
    ::= { svcTlsInfoEntry 13 }

svcTlsStpRootCost OBJECT-TYPE
    SYNTAX          Integer32
    MAX-ACCESS      read-only
    STATUS          current
    DESCRIPTION     "The value of the object svcTlsStpRootCost indicates the
                     cost of the path to the root bridge as seen from this
                     bridge."
    ::= { svcTlsInfoEntry 14 }

svcTlsStpRootPort OBJECT-TYPE
    SYNTAX          Integer32
    MAX-ACCESS      read-only
    STATUS          current
    DESCRIPTION     "The value of the object svcTlsStpRootPort indicates the
                     port number of the port which offers the lowest cost path
                     from this bridge to the root bridge."
    ::= { svcTlsInfoEntry 15 }

svcTlsStpMaxAge OBJECT-TYPE
    SYNTAX          Integer32
    MAX-ACCESS      read-only
    STATUS          current
    DESCRIPTION     "The value of the object svcTlsStpMaxAge indicates the
                     maximum age of Spanning Tree Protocol information learned
                     from the network on any port before it is discarded. This
                     is the actual value that this bridge is currently using."
    ::= { svcTlsInfoEntry 16 }

svcTlsStpHelloTime OBJECT-TYPE
    SYNTAX          Integer32
    MAX-ACCESS      read-only
    STATUS          current
    DESCRIPTION     "The value of the object svcTlsStpHelloTime indicates the
                     amount of time between the transmission of Configuration
                     BPDUs. This is the actual value that this bridge is
                     currently using."
    ::= { svcTlsInfoEntry 17 }

svcTlsStpHoldTime OBJECT-TYPE
    SYNTAX          Integer32
    MAX-ACCESS      read-only
    STATUS          obsolete
    DESCRIPTION     "The value of the object svcTlsStpHoldTime indicates the
                     interval length during which no more than two
                     Configuration BPDUs shall be transmitted by this bridge.
                     This object is no longer used. It is replaced by the
                     object svcTlsStpHoldCount.
                     This object was made obsolete in the 3.0 release."
    ::= { svcTlsInfoEntry 18 }

svcTlsStpForwardDelay OBJECT-TYPE
    SYNTAX          Integer32
    MAX-ACCESS      read-only
    STATUS          current
    DESCRIPTION     "The value of the object svcTlsStpForwardDelay indicates
                     how fast a port changes its state when moving towards the
                     Forwarding state. The value determines how long the port
                     stays in each of the Listening and Learning states, which
                     precede the Forwarding state. This value is also used to
                     age all dynamic entries in the Forwarding Database when a
                     topology change has been detected and is underway. This is
                     the actual value that this bridge is currently using."
    ::= { svcTlsInfoEntry 19 }

svcTlsStpBridgeMaxAge OBJECT-TYPE
    SYNTAX          Integer32 (6..40)
    MAX-ACCESS      read-write
    STATUS          current
    DESCRIPTION     "The value of the object svcTlsStpBridgeMaxAge specifies
                     the value that all bridges should use for 'MaxAge' when this
                     bridge is acting as the root bridge."
    ::= { svcTlsInfoEntry 20 }

svcTlsStpBridgeHelloTime OBJECT-TYPE
    SYNTAX          Integer32 (1..10)
    MAX-ACCESS      read-write
    STATUS          current
    DESCRIPTION     "The value of the object svcTlsStpBridgeHelloTime specifies
                     the value that all bridges should use for 'HelloTime' when
                     this bridge is acting as the root bridge."
    ::= { svcTlsInfoEntry 21 }

svcTlsStpBridgeForwardDelay OBJECT-TYPE
    SYNTAX          Integer32 (4..30)
    MAX-ACCESS      read-write
    STATUS          current
    DESCRIPTION     "The value of the object svcTlsStpBridgeForwardDelay
                     specifies the value that all bridges should use for
                     'ForwardDelay' when this bridge is acting as the root
                     bridge."
    ::= { svcTlsInfoEntry 22 }

svcTlsStpOperStatus OBJECT-TYPE
    SYNTAX          INTEGER {
                        up   (1),
                        down (2)
                    }
    MAX-ACCESS      read-only
    STATUS          current
    DESCRIPTION     "The value of the object  svcTlsStpOperStatus indicates the
                     operating status of the Spanning Tree Protocol instance
                     associated with this service."
    ::= { svcTlsInfoEntry 30 }

svcTlsStpVirtualRootBridgeStatus OBJECT-TYPE
    SYNTAX          INTEGER {
                        up   (1),
                        down (2)
                    }
    MAX-ACCESS      read-only
    STATUS          current
    DESCRIPTION     "The value of the object  svcTlsStpVirtualRootBridgeStatus
                     indicates the operating status of the  Virtual Root Bridge
                     of the Spanning Tree Protocol instance associated with
                     this service. The status of the Virtual Root Bridge is
                    'up' when there is connectivity to the core: i.e. one or
                     more SDP's in this service are operationally up."
    ::= { svcTlsInfoEntry 31 }

svcTlsMacAgeing OBJECT-TYPE
    SYNTAX          TmnxEnabledDisabled
    MAX-ACCESS      read-write
    STATUS          current
    DESCRIPTION     "The value of the object svcTlsMacAgeing specifies whether
                     the MAC aging process is enabled in this TLS."
    DEFVAL          { enabled }
    ::= { svcTlsInfoEntry 32 }

svcTlsStpTopologyChangeActive OBJECT-TYPE
    SYNTAX          TruthValue
    MAX-ACCESS      read-only
    STATUS          current
    DESCRIPTION     "The value of the object svcTlsStpTopologyChangeActive
                     indicates, when set to 'true', that a topology change is
                     currently in progress."
    ::= { svcTlsInfoEntry 33 }

svcTlsFdbTableFullHighWatermark OBJECT-TYPE
    SYNTAX          Integer32 (0..100)
    MAX-ACCESS      read-write
    STATUS          current
    DESCRIPTION     "The value of the object svcTlsFdbTableFullHighWatermark
                     specifies the utilization of the FDB table of this TLS
                     service at which a table full alarm will be raised
                     by the agent."
    DEFVAL          { 95 }
    ::= { svcTlsInfoEntry 34 }

svcTlsFdbTableFullLowWatermark OBJECT-TYPE
    SYNTAX          Integer32 (0..100)
    MAX-ACCESS      read-write
    STATUS          current
    DESCRIPTION     "The value of the object svcTlsFdbTableFullLowWatermark
                     specifies the utilization of the FDB table of this TLS
                     service at which a table full alarm will be raised
                     by the agent."
    DEFVAL          { 90 }
    ::= { svcTlsInfoEntry 35 }

svcTlsVpnId OBJECT-TYPE
    SYNTAX          VpnId
    MAX-ACCESS      read-only
    STATUS          current
    DESCRIPTION     "The value of the object svcTlsVpnId indicates the VPN ID
                     of the associated TLS service."
    ::= { svcTlsInfoEntry 36 }

svcTlsCustId OBJECT-TYPE
    SYNTAX          TmnxCustId
    MAX-ACCESS      read-only
    STATUS          current
    DESCRIPTION     "The vakue of the object svcTlsCustId indicates the
                     Customer ID of the associated TLS service."
    ::= { svcTlsInfoEntry 37 }

svcTlsStpVersion OBJECT-TYPE
    SYNTAX          INTEGER {
                        rstp         (2),
                        compDot1w    (3),
                        dot1w        (4),
                        mstp         (5),
                        pmstp        (6)
                    }
    MAX-ACCESS      read-write
    STATUS          current
    DESCRIPTION     "The value of the object svcTlsStpVersion specifies the
                     version of Spanning Tree Protocol the bridge is currently
                     running.

                     The value 'rstp' corresponds to  the Rapid Spanning
                     Tree Protocol specified in IEEE 802.1D/D4-2003.

                     The value 'compDot1w' corresponds to the mode where the
                     Rapid Spanning Tree is backward compatible with IEEE
                     802.1w.

                     The value 'dot1w' corresponds to  the Rapid Spanning
                     Tree Protocol fully conformant to IEEE 802.1w.

                     The value 'mstp' corresponds to the Multiple Spanning
                     Tree Protocol specified in IEEE 802.1Q-REV/D3.0-04/2005.
                     
                     The value 'pmstp' corresponds to Provider MSTP protocol
                     compliant with IEEE-802.1ad-2005.

                     New values may be defined as future versions of the
                     protocol become available."
    DEFVAL          { rstp }
    ::= { svcTlsInfoEntry 38 }

svcTlsStpHoldCount OBJECT-TYPE
    SYNTAX          Integer32 (1..10)
    MAX-ACCESS      read-write
    STATUS          current
    DESCRIPTION     "The value of the object svcTlsStpHoldCount specifies the
                     maximum number of BPDUs that are transmitted in any
                     'HelloTime' interval.
                     The value used by the bridge to limit the maximum
                     transmission rate of BPDUs."
    REFERENCE
                    "IEEE 802.1w clause 17.16.6"
    DEFVAL          { 6 }
    ::= { svcTlsInfoEntry 39 }

svcTlsStpPrimaryBridge OBJECT-TYPE
    SYNTAX          BridgeId
    MAX-ACCESS      read-only
    STATUS          current
    DESCRIPTION     "The value of the object svcTlsStpPrimaryBridge indicates
                     the BridgeId of the bridge that acts as the primary bridge,
                     being the gateway from the core mesh towards the root
                     bridge."
    ::= { svcTlsInfoEntry 40 }

svcTlsStpBridgeInstanceId OBJECT-TYPE
    SYNTAX          Integer32 (0 ..4095)
    MAX-ACCESS      read-only
    STATUS          current
    DESCRIPTION     "The value of the object svcTlsStpBridgeInstanceId
                     indicates a 12 bit value chosen by the the system. It is
                     part of the STP bridge Id, which consists of 8 octets:
                     - 4 highest bits of octet 1:
                         the bridge priority (ref svcTlsStpPriority)
                     - 12 bits (4 lowest bits of octet 1 + 8 bits of octet 2):
                         bridge instance Id (this object!).
                     - 6 octets: bridge MAC addess
                         ref svcTlsStpBridgeAddress
                     The value is set to 0 if svcTlsStpOperStatus is not 'up'."
    ::= { svcTlsInfoEntry 41 }

svcTlsStpVcpOperProtocol OBJECT-TYPE
    SYNTAX          StpProtocol
    MAX-ACCESS      read-only
    STATUS          current
    DESCRIPTION     "The value of the object svcTlsStpVcpOperProtocol indicates
                     whether stp, rstp or mstp is running on this VCP.
                     If the protocol is not enabled on this VCP, the value
                     notApplicable is returned."
    ::= { svcTlsInfoEntry 42 }

svcTlsMacMoveMaxRate OBJECT-TYPE
    SYNTAX          Unsigned32 (1..10)
    MAX-ACCESS      read-write
    STATUS          current
    DESCRIPTION     "The value of the object svcTlsMacMoveMaxRate specifies the
                     maximum rate at which MAC's can be re-learned in this TLS
                     service, before the SAP where the moving MAC was last seen
                     is automatically disabled in order to protect the system
                     against undetected loops or duplicate MAC's.
                     The rate is computed as the maximum number of re-learns
                     allowed in a 5 second interval: e.g. the default rate
                     of 2 re-learns per second corresponds to 10 re-learns
                     in a 5 second period."
    DEFVAL          { 2 }
    ::= { svcTlsInfoEntry 43 }

svcTlsMacMoveRetryTimeout OBJECT-TYPE
    SYNTAX          Unsigned32 (0..600)
    MAX-ACCESS      read-write
    STATUS          current
    DESCRIPTION     "The value of the object  svcTlsMacMoveRetryTimeout
                     specifies the time in seconds to wait before a SAP that
                     has been disabled after exceeding the maximum re-learn
                     rate is re-enabled.

                     A value of zero indicates that the SAP will not be
                     automatically re-enabled after being disabled. If after
                     the SAP is re-enabled it is disabled again, the effective
                     retry timeout is doubled in order to avoid thrashing.
                     
                     An inconsistentValue error is returned if the value of this
                     object is set to less than fie times the value of 
                     svcTlsSecPortsCumulativeFactor."
    DEFVAL { 10 }
    ::= { svcTlsInfoEntry 44 }

svcTlsMacMoveAdminStatus OBJECT-TYPE
    SYNTAX          TmnxEnabledDisabled
    MAX-ACCESS      read-write
    STATUS          current
    DESCRIPTION     "The value of the object svcTlsMacMoveAdminStatus
                     specifies the administrative state of the
                     MAC movement feature associated with this service."
    DEFVAL          { disabled }
    ::= { svcTlsInfoEntry 45 }

svcTlsMacRelearnOnly OBJECT-TYPE
    SYNTAX          TruthValue
    MAX-ACCESS      read-only
    STATUS          current
    DESCRIPTION     "The value of the object svcTlsMacRelearnOnly indicates
                     when set to 'true' that either the FDB table of this TLS
                     service is full, or that the maximum system-wide number of
                     MAC's supported by the agent has been reached, and thus
                     MAC learning is temporary disabled, and only MAC re-learns
                     can take place."
    ::= { svcTlsInfoEntry 46 }

svcTlsMfibTableSize OBJECT-TYPE
    SYNTAX          Integer32 (0..16383)
    MAX-ACCESS      read-write
    STATUS          current
    DESCRIPTION     "The value of the object  svcTlsMfibTableSize specifies the
                     maximum number of entries allowed in the MFIB table of
                     this service. If the value is 0, then there is no limit."
    DEFVAL          { 0 }
    ::= { svcTlsInfoEntry 47 }

svcTlsMfibTableFullHighWatermark OBJECT-TYPE
    SYNTAX          Integer32 (0..100)
    MAX-ACCESS      read-write
    STATUS          current
    DESCRIPTION     "The value of the object svcTlsMfibTableFullHighWatermark
                     specifies the utilization of the MFIB table of this TLS
                     service at which a table full alarm will be raised by the
                     agent."
    DEFVAL          { 95 }
    ::= { svcTlsInfoEntry 48 }

svcTlsMfibTableFullLowWatermark OBJECT-TYPE
    SYNTAX          Integer32 (0..100)
    MAX-ACCESS      read-write
    STATUS          current
    DESCRIPTION     "The value of the object svcTlsMfibTableFullLowWatermark
                     specifies utilization of the MFIB table of this TLS
                     service at which a table full alarm will be cleared by the
                     agent."
    DEFVAL          { 90 }
    ::= { svcTlsInfoEntry 49 }

svcTlsMacFlushOnFail OBJECT-TYPE
    SYNTAX          TmnxEnabledDisabled
    MAX-ACCESS      read-write
    STATUS          current
    DESCRIPTION     "The value of the object svcTlsMacFlushOnFail specifies
                     whether a special mac-flush is sent when a
                     port or sap becomes operational down."
    DEFVAL          { disabled }
    ::= { svcTlsInfoEntry 50 }

svcTlsStpRegionName OBJECT-TYPE
    SYNTAX          DisplayString (SIZE (0..32))
    MAX-ACCESS      read-write
    STATUS          current
    DESCRIPTION     "The value of the object svcTlsStpRegionName specifies
                     the MSTP region name. Together with region revision and
                     VLAN-to-instance assignment it defines the MSTP region."
    DEFVAL          { "" }
    ::= { svcTlsInfoEntry 51 }

svcTlsStpRegionRevision OBJECT-TYPE
    SYNTAX          Integer32 (0..65535)
    MAX-ACCESS      read-write
    STATUS          current
    DESCRIPTION     "The value of the object svcTlsStpRegionRevision specifies
                     the MSTP region revision number. Together with region
                     name and VLAN-to-instance assignment it defines the MSTP
                     region."
    DEFVAL          { 0 }
    ::= { svcTlsInfoEntry 52 }

svcTlsStpBridgeMaxHops OBJECT-TYPE
    SYNTAX          Integer32 (1..40)
    MAX-ACCESS      read-write
    STATUS          current
    DESCRIPTION     "The value of the object svcTlsStpBridgeMaxHops specifies
                     the maximum number of hops (known as 'MaxHops' in 802.1Q)."
    DEFVAL          { 20 }
    ::= { svcTlsInfoEntry 53 }

svcTlsStpCistRegionalRoot OBJECT-TYPE
    SYNTAX          BridgeId
    MAX-ACCESS      read-only
    STATUS          current
    DESCRIPTION     "The value of the object svcTlsStpCistRegionalRoot
                     indicates the bridge identifier of the regional root of
                     the CIST spanning tree as determined by the Spanning Tree
                     Protocol instance associated with this service. This value
                     is used as the CIST Regional Root Identifier parameter in
                     all MSTP BPDUs originated by this node."
    ::= { svcTlsInfoEntry 54 }

svcTlsStpCistIntRootCost OBJECT-TYPE
    SYNTAX          Integer32
    MAX-ACCESS      read-only
    STATUS          current
    DESCRIPTION     "The value of the object svcTlsStpCistIntRootCost indicates
                     the cost of the path to the CIST regional root bridge
                     as seen from this bridge."
    ::= { svcTlsInfoEntry 55 }

svcTlsStpCistRemainingHopCount OBJECT-TYPE
    SYNTAX          Integer32
    MAX-ACCESS      read-only
    STATUS          current
    DESCRIPTION     "The value of the object svcTlsStpCistRemainingHopCount
                     specifies the remaining number of hops."
    ::= { svcTlsInfoEntry 56 }

svcTlsStpCistRegionalRootPort OBJECT-TYPE
    SYNTAX          Integer32
    MAX-ACCESS      read-only
    STATUS          current
    DESCRIPTION     "The value of the object svcTlsStpCistRegionalRootPort
                     indicates the port number of the port which offers the
                     lowest cost path from this bridge to the regional root
                     bridge."
    ::= { svcTlsInfoEntry 57 }

svcTlsFdbNumLearnedEntries OBJECT-TYPE
    SYNTAX          Integer32
    MAX-ACCESS      read-only
    STATUS          current
    DESCRIPTION     "The value of the object svcTlsFdbNumLearnedEntries
                     indicates the current number of learned entries in the FDB
                     of this service."
    ::= { svcTlsInfoEntry 58 }

svcTlsFdbNumOamEntries OBJECT-TYPE
    SYNTAX          Integer32
    MAX-ACCESS      read-only
    STATUS          current
    DESCRIPTION     "The value of the object svcTlsFdbNumOamEntries
                     indicates the current number of OAM entries in the FDB
                     of this service."
    ::= { svcTlsInfoEntry 59 }

svcTlsFdbNumDhcpEntries OBJECT-TYPE
    SYNTAX          Integer32
    MAX-ACCESS      read-only
    STATUS          current
    DESCRIPTION     "The value of the object svcTlsFdbNumDhcpEntries
                     indicates the current number of dhcp-learned entries in the
                     FDB of this service."
    ::= { svcTlsInfoEntry 60 }

svcTlsFdbNumHostEntries OBJECT-TYPE
    SYNTAX          Integer32
    MAX-ACCESS      read-only
    STATUS          current
    DESCRIPTION     "The value of the object svcTlsFdbNumHostEntries
                     indicates the current number of host-learned entries in the
                     FDB of this service."
    ::= { svcTlsInfoEntry 61 }

svcTlsShcvAction OBJECT-TYPE
    SYNTAX          INTEGER {
                         alarm  (1),
                         remove (2)
                    }
    MAX-ACCESS      read-write
    STATUS          current
    DESCRIPTION     "The value of the object svcTlsShcvAction
                     indicates whether any action should be triggered when
                     the connectivity check fails."
    DEFVAL          { alarm }
    ::= { svcTlsInfoEntry 62 }


svcTlsShcvSrcIp OBJECT-TYPE
    SYNTAX          IpAddress
    MAX-ACCESS      read-write
    STATUS          current
    DESCRIPTION     "The value of the object svcTlsShcvSrcIp
                     specifies the source IP address used when doing the
                     connectivity check. The value 0.0.0.0 indicates that
                     no host IP address is specified."
    ::= { svcTlsInfoEntry 63 }

svcTlsShcvSrcMac OBJECT-TYPE
    SYNTAX          MacAddress
    MAX-ACCESS      read-write
    STATUS          current
    DESCRIPTION     "The value of the object svcTlsShcvSrcMac
                     specifies the MAC address used when doing the connectivity
                     check. The value 0:0:0:0:0:0 indicates that no host MAC
                     address is specified."
    ::= { svcTlsInfoEntry 64 }

svcTlsShcvInterval OBJECT-TYPE
    SYNTAX          Unsigned32 (0..6000)
    UNITS           "minutes"
    MAX-ACCESS      read-write
    STATUS          current
    DESCRIPTION     "The value of the object svcTlsShcvInterval specifies
                     the interval in minutes between connectivity checks.
                     Zero means no connectivity checking."
    DEFVAL          { 0 }
    ::= { svcTlsInfoEntry 65 }

svcTlsPriPortsCumulativeFactor OBJECT-TYPE
    SYNTAX          Unsigned32 (3..10)
    MAX-ACCESS      read-write
    STATUS          current
    DESCRIPTION     "The value of the object svcTlsPriPortsCumulativeFactor
                     specifies a factor for the primary ports defining how
                     many MAC-relearn periods should be used to measure the
                     MAC-relearn rate, svcTlsMacMoveMaxRate. This rate must
                     be exceeded during consecutive periods before the
                     corresponding ports (SAP and/or spoke-SDP) are blocked by
                     the MAC-move feature.

                     An inconsistentValue error is returned if an attempt is
                     made to set the value of svcTlsPriPortsCumulativeFactor to
                     a value lower than or equal to
                     svcTlsSecPortsCumulativeFactor."
    DEFVAL          { 3 }
    ::= { svcTlsInfoEntry 66 }

svcTlsSecPortsCumulativeFactor OBJECT-TYPE
    SYNTAX          Unsigned32 (2..9)
    MAX-ACCESS      read-write
    STATUS          current
    DESCRIPTION     "The value of the object svcTlsSecPortsCumulativeFactor
                     specifies a factor for the secondary ports defining how
                     many MAC-relearn periods should be used to measure the
                     MAC-relearn rate, svcTlsMacMoveMaxRate. This rate must
                     be exceeded during consecutive periods before the
                     corresponding ports (SAP and/or spoke-SDP) are blocked by
                     the MAC-move feature.

                     An inconsistentValue error is returned if an attempt is
                     made to set the value of svcTlsSecPortsCumulativeFactor to
                     a value greater than or equal to
                     svcTlsPriPortsCumulativeFactor."
    DEFVAL          { 2 }
    ::= { svcTlsInfoEntry 67 }

svcTlsL2ptTermEnabled OBJECT-TYPE
    SYNTAX          TruthValue
    MAX-ACCESS      read-only
    STATUS          current
    DESCRIPTION     "The value of the object svcTlsL2ptTermEnabled 
                     indicates if L2PT-termination and/or Bpdu-translation 
                     is in use in this service by at least one SAP or 
                     spoke SDP Bind. If the value is 'true', it means that
                     at least one of L2PT-termination or Bpdu-translation
                     is enabled.

                     When enabled it is not possible to enable
                     stp on this service." 
    ::= { svcTlsInfoEntry 68 }

svcTlsPropagateMacFlush OBJECT-TYPE
    SYNTAX          TruthValue
    MAX-ACCESS      read-write
    STATUS          current
    DESCRIPTION     "The value of svcTlsPropagateMacFlush specifies whether
                     'MAC flush' messages received from the given LDP are
                     propagated to all spoke-SDPs and mesh-SDPs within the
                     context of this VPLS service. The propagation will follow
                     the 'split-horizon' principle and any data-path blocking in
                     order to avoid the looping of these messages.

                     The value of 'true' enables the propagation."
    DEFVAL         { false }
    ::= { svcTlsInfoEntry 69 }

svcTlsMrpAdminStatus OBJECT-TYPE
    SYNTAX          TmnxEnabledDisabled
    MAX-ACCESS      read-write
    STATUS          current
    DESCRIPTION     "The value of the object svcTlsMrpAdminStatus specifies
                     whether the Multiple Registration Protocol (MRP) is
                     enabled in this TLS."
    DEFVAL          { disabled }
    ::= { svcTlsInfoEntry 70 }

svcTlsMrpMaxAttributes OBJECT-TYPE
    SYNTAX          Unsigned32 (1..2048)
    MAX-ACCESS      read-write
    STATUS          current
    DESCRIPTION     "The value of the object svcTlsMrpMaxAttributes indicates
                     maximum number of MRP attributes supported in this TLS.

                     In most cases the default value is 2048 MRP attributes.
                     For some platform and chassis types, especially single slot
                     chassises, the default value will be lower due to resource
                     constraints.

                     An inconsistentValue error is returned if an attempt is
                     made to set this object to a value the platform cannot
                     support."
    ::= { svcTlsInfoEntry 71 }

svcTlsMrpAttributeCount OBJECT-TYPE
    SYNTAX          Unsigned32
    MAX-ACCESS      read-only
    STATUS          current
    DESCRIPTION     "The value of the object svcTlsMrpAttributeCount indicates
                     number of MRP attributes currently registered in this TLS."
    ::= { svcTlsInfoEntry 72 }

svcTlsMrpFailedRegisterCount OBJECT-TYPE
    SYNTAX          Unsigned32
    MAX-ACCESS      read-only
    STATUS          current
    DESCRIPTION     "The value of the object svcTlsMrpFailedRegisterCount
                     indicates number of failed MRP attribute registrations in
                     this TLS."
    ::= { svcTlsInfoEntry 73 }

svcTlsMcPathMgmtPlcyName OBJECT-TYPE
    SYNTAX          TNamedItem
    MAX-ACCESS      read-write
    STATUS          current
    DESCRIPTION     "The value of svcTlsMcPathMgmtPlcyName specifies the 
                     multicast policy name configured on this service."
    DEFVAL          { "default" }
    ::= { svcTlsInfoEntry 74 }

svcTlsMrpFloodTime OBJECT-TYPE
    SYNTAX          Unsigned32 (0|3..600)
    UNITS           "seconds"
    MAX-ACCESS      read-write
    STATUS          current
    DESCRIPTION     "The value of the object svcTlsMrpFloodTime specifies
                     the amount of time in seconds after a status change in the
                     TLS during which traffic is flooded.  Once that time
                     expires, traffic will be delivered according to the MRP
                     registrations which exist in the TLS.

                     The value of 0 indicates that no flooding will occur on
                     state changes in the TLS."
    DEFVAL          { 0 }
    ::= { svcTlsInfoEntry 75 }

svcTlsMrpAttrTblHighWatermark OBJECT-TYPE
    SYNTAX          Integer32 (0..100)
    MAX-ACCESS      read-write
    STATUS          current
    DESCRIPTION     "The value of the object svcTlsMrpAttrTblHighWatermark
                     specifies the utilization of the MRP attribute table of
                     this TLS service at which a table full alarm will be raised
                     by the agent."
    DEFVAL          { 95 }
    ::= { svcTlsInfoEntry 76 }

svcTlsMrpAttrTblLowWatermark OBJECT-TYPE
    SYNTAX          Integer32 (0..100)
    MAX-ACCESS      read-write
    STATUS          current
    DESCRIPTION     "The value of the object svcTlsMrpAttrTblLowWatermark
                     specifies utilization of the MRP attribute table of this
                     TLS service at which a table full alarm will be cleared by
                     the agent."
    DEFVAL          { 90 }
    ::= { svcTlsInfoEntry 77 }

-- ------------------------------------
-- TLS FDB Table
-- ------------------------------------
tlsFdbInfoTable OBJECT-TYPE
    SYNTAX          SEQUENCE OF TlsFdbInfoEntry
    MAX-ACCESS      not-accessible
    STATUS          current
    DESCRIPTION     "A table that contains TLS FDB information."
    ::= { tmnxSvcObjs 4 }

tlsFdbInfoEntry OBJECT-TYPE
    SYNTAX          TlsFdbInfoEntry
    MAX-ACCESS      not-accessible
    STATUS          current
    DESCRIPTION     "Information about a specific TLS FDB."
    INDEX           { svcId, tlsFdbMacAddr }
    ::= { tlsFdbInfoTable 1 }

TlsFdbInfoEntry ::=
    SEQUENCE {
        tlsFdbMacAddr           MacAddress,
        tlsFdbRowStatus         RowStatus,
        tlsFdbType              INTEGER,
        tlsFdbLocale            INTEGER,
        tlsFdbPortId            TmnxPortID,
        tlsFdbEncapValue        TmnxEncapVal,
        tlsFdbSdpId             SdpId,
        tlsFdbVcId              Unsigned32,
        tlsFdbVpnId             VpnId,
        tlsFdbCustId            TmnxCustId,
        tlsFdbLastStateChange   TimeStamp,
        tlsFdbProtected         TruthValue,
        tlsFdbBackboneDstMac    MacAddress,
        tlsFdbNumIVplsMac       Unsigned32,
        tlsFdbEndPointName      TNamedItemOrEmpty,
        tlsFdbEPMacOperSdpId    SdpId,
        tlsFdbEPMacOperVcId     Unsigned32,
        tlsFdbPbbNumEpipes      Unsigned32
    }

tlsFdbMacAddr OBJECT-TYPE
    SYNTAX          MacAddress
    MAX-ACCESS      read-only
    STATUS          current
    DESCRIPTION     "The value of the object tlsFdbMacAddr specifies the
                     48-bit IEEE 802.3 MAC address."
    ::= { tlsFdbInfoEntry 1 }

tlsFdbRowStatus OBJECT-TYPE
    SYNTAX          RowStatus
    MAX-ACCESS      read-create
    STATUS          current
    DESCRIPTION     "The value of the object tlsFdbRowStatus specifies the
                     status of this row. The only values supported during a set
                     operation are 'createAndGo' and 'destroy'."
    ::= { tlsFdbInfoEntry 2 }

tlsFdbType OBJECT-TYPE
    SYNTAX          INTEGER {
                        static  (1),
                        learned (2),
                        oam     (3),
                        dhcp    (4),
                        host    (5)
                    }
    MAX-ACCESS      read-create
    STATUS          current
    DESCRIPTION     " The value of the object tlsFdbType specifies:
                     - 'static':  Static TLS FDB entries created via management
                     - 'learned': dynamic entries created via the learning
                                  process
                     - 'oam':     entries created via the OAM process
                     - 'dhcp':    learned  addresses can be temporarily frozen
                                  by the DHCP snooping application for the
                                  duration of a DHCP lease
                     - 'host':    entry added by the system for a static
                                  configured subscriber host."
    ::= { tlsFdbInfoEntry 3 }

tlsFdbLocale OBJECT-TYPE
    SYNTAX          INTEGER {
                        sap      (1),
                        sdp      (2),
                        cpm      (3),
                        endpoint (4)
                    }
    MAX-ACCESS      read-create
    STATUS          current
    DESCRIPTION     "The value of the object tlsFdbLocale specifies for TLS
                     FDB entries defined on a local SAP the value 'sap',
                     remote entries defined on an SDP have the value 'sdp',
                     entries associated with the Control Processor have the
                     value 'cpm' and entries associated with the explicit
                     endpoint have the value 'endpoint'.

                     The value of this object must be specified when
                     the row is created and cannot be changed while
                     the row status is 'active'."
    ::= { tlsFdbInfoEntry 4 }

tlsFdbPortId OBJECT-TYPE
    SYNTAX          TmnxPortID
    MAX-ACCESS      read-create
    STATUS          current
    DESCRIPTION     "When the value of tlsFdbLocale is 'sap', this
                     object, along with tlsFdbEncapValue, specifies
                     the SAP associated with the MAC address defined
                     by tlsFdbMacAddr. This object is otherwise
                     insignificant and should contain a value of 0."
    ::= { tlsFdbInfoEntry 5 }

tlsFdbEncapValue OBJECT-TYPE
    SYNTAX          TmnxEncapVal
    MAX-ACCESS      read-create
    STATUS          current
    DESCRIPTION     "The value of the object tlsFdbEncapValue specifies, when
                     the value of tlsFdbLocale is 'sap', along with
                     tlsFdbPortId, SAP associated with the MAC address defined
                     by tlsFdbMacAddr. This object is otherwise insignificant
                     and should contain a value of 0."
    ::= { tlsFdbInfoEntry 6 }

tlsFdbSdpId OBJECT-TYPE
    SYNTAX          SdpId
    MAX-ACCESS      read-create
    STATUS          current
    DESCRIPTION     "The value of the object tlsFdbSdpId specifies, when the
                     value of tlsFdbLocale is 'sdp', along with tlsFdbVcId,the
                     SDP Binding associated with the MAC address
                     defined by tlsFdbMacAddr. This object is other-
                     wise insignificant and should contain a value of 0."
    ::= { tlsFdbInfoEntry 7 }

tlsFdbVcId OBJECT-TYPE
    SYNTAX          Unsigned32
    MAX-ACCESS      read-create
    STATUS          current
    DESCRIPTION     "The value of the object tlsFdbVcId specifies, when the
                     value of tlsFdbLocale is 'sdp', along with tlsFdbSdpId,
                     the SDP Binding associated with the MAC address defined by
                     tlsFdbMacAddr. This object is other-wise insignificant and
                     should contain a value of 0."
    ::= { tlsFdbInfoEntry 8 }

tlsFdbVpnId OBJECT-TYPE
    SYNTAX          VpnId
    MAX-ACCESS      read-only
    STATUS          current
    DESCRIPTION     "The value of the object tlsFdbVpnId indicates the VPN ID
                     of the associated TLS."
    ::= { tlsFdbInfoEntry 9 }

tlsFdbCustId OBJECT-TYPE
    SYNTAX          TmnxCustId
    MAX-ACCESS      read-only
    STATUS          current
    DESCRIPTION     "The value of the object tlsFdbCustId indicates the
                     Customer ID of the associated TLS."
    ::= { tlsFdbInfoEntry 10 }

tlsFdbLastStateChange OBJECT-TYPE
    SYNTAX          TimeStamp
    MAX-ACCESS      read-only
    STATUS          current
    DESCRIPTION     "The value of the object tlsFdbLastStateChange indicates
                     the value of sysUpTime at the time of the most recent
                     state change of this entry. A state change is defined as a
                     change in the value of: tlsFdbRowStatus, tlsFdbType,
                     tlsFdbLocale, tlsFdbPortId, tlsFdbEncapValue,
                     tlsFdbSdpId or tlsFdbVcId."
    ::= { tlsFdbInfoEntry 11 }

tlsFdbProtected OBJECT-TYPE
    SYNTAX          TruthValue
    MAX-ACCESS      read-only
    STATUS          current
    DESCRIPTION     "The value of the object tlsFdbProtected indicates
                     whether or not this MAC is protected. When the value
                     of this object is 'true' the agent will protect
                     the MAC from being learned or re-learned on a SAP
                     that has restricted learning enabled."
    ::= { tlsFdbInfoEntry 12 }

tlsFdbBackboneDstMac OBJECT-TYPE
    SYNTAX          MacAddress
    MAX-ACCESS      read-only
    STATUS          current
    DESCRIPTION     "The value of the object tlsFdbBackboneDstMac indicates the
                     Backbone VPLS service MAC address used as destination MAC 
                     address in the Provider Backbone Bridging frames for this
                     tlsFdbMacAddr.
        
                     This object is insignificant for services with svcVplsType
                     not set to 'iVpls' and should contain a value of
                     0:0:0:0:0:0."
    ::= { tlsFdbInfoEntry 13 }

tlsFdbNumIVplsMac OBJECT-TYPE
    SYNTAX          Unsigned32
    MAX-ACCESS      read-only
    STATUS          current
    DESCRIPTION     "The value of the object tlsFdbNumIVplsMac indicates the
                     number of ISID VPLS service MAC addressess which are using
                     this Backbone MAC address defined by tlsFdbMacAddr.
        
                     This object is insignificant for services with svcVplsType
                     not set to 'bVpls' and should contain a value of 0."
    ::= { tlsFdbInfoEntry 14 }

tlsFdbEndPointName         OBJECT-TYPE
    SYNTAX      TNamedItemOrEmpty
    MAX-ACCESS  read-create
    STATUS      current
    DESCRIPTION
        "The value of tlsFdbEndPointName specifies the name of the service
        endpoint associated with the MAC Address."
    DEFVAL     { "" }
    ::= { tlsFdbInfoEntry 15 }

tlsFdbEPMacOperSdpId OBJECT-TYPE
    SYNTAX          SdpId
    MAX-ACCESS      read-only
    STATUS          current
    DESCRIPTION
        "The value of the object tlsFdbEPMacOperSdpId along with
        tlsFdbEPMacOperVcId indicates the SDP binding associated with this
        static MAC address for this endpoint.

        This object is valid when tlsFdbLocale is 'endpoint', otherwise 
        it should contain a value of 0."
    ::= { tlsFdbInfoEntry 16 }

tlsFdbEPMacOperVcId OBJECT-TYPE
    SYNTAX          Unsigned32
    MAX-ACCESS      read-only
    STATUS          current
    DESCRIPTION
        "The value of the object tlsFdbEPMacOperVcId along with
        tlsFdbEPMacOperSdpId indicates the SDP binding associated with this
        static MAC address for this endpoint.

        This object is valid when tlsFdbLocale is 'endpoint', otherwise 
        it should contain a value of 0."
    ::= { tlsFdbInfoEntry 17 }

tlsFdbPbbNumEpipes OBJECT-TYPE
    SYNTAX          Unsigned32
    MAX-ACCESS      read-only
    STATUS          current
    DESCRIPTION
        "The value of the object tlsFdbPbbNumEpipes indicates number of E-Pipes
        that resolve to this MAC Address.

        This object is valid for service with svcVplsType set to 'bVpls',
        otherwise it should contain a value of 0."
    ::= { tlsFdbInfoEntry 18 }

-- ------------------------------------
-- IES Interface Table
-- ------------------------------------
iesIfTable OBJECT-TYPE
    SYNTAX          SEQUENCE OF IesIfEntry
    MAX-ACCESS      not-accessible
    STATUS          current
    DESCRIPTION     "A table that contains IES interface information."
    ::= { tmnxSvcObjs 5 }

iesIfEntry OBJECT-TYPE
    SYNTAX          IesIfEntry
    MAX-ACCESS      not-accessible
    STATUS          current
    DESCRIPTION     "Information about a specific IES interface."
    INDEX           { svcId, iesIfIndex }
    ::= { iesIfTable 1 }

IesIfEntry ::=
    SEQUENCE {
        iesIfIndex              InterfaceIndex,
        iesIfRowStatus          RowStatus,
        iesIfName               TNamedItem,
        iesIfDescription        ServObjLongDesc,
        iesIfAdminStatus        ServiceAdminStatus,
        iesIfOperStatus         ServiceOperStatus,
        iesIfLastMgmtChange     TimeStamp,
        iesIfVpnId              VpnId,
        iesIfCustId             TmnxCustId,
        iesIfLoopback           TruthValue,
        iesIfLastStatusChange   TimeStamp,
        iesIfType               INTEGER,
        iesIfParentIf           InterfaceIndexOrZero,
        iesIfShcvSource         INTEGER,
        iesIfShcvAction         INTEGER,
        iesIfShcvInterval       Unsigned32,
        iesIfFwdServId          TmnxServId,
        iesIfFwdSubIf           InterfaceIndexOrZero
    }

iesIfIndex OBJECT-TYPE
    SYNTAX          InterfaceIndex
    MAX-ACCESS      read-only
    STATUS          current
    DESCRIPTION     "The secondary index of the row in the vRtrIfTable
                     corresponding to this IES interface. The primary
                     index is 1; i.e. all IES interfaces are defined in
                     the Base virtual router context."
    ::= { iesIfEntry 1 }

iesIfRowStatus OBJECT-TYPE
    SYNTAX          RowStatus
    MAX-ACCESS      read-create
    STATUS          current
    DESCRIPTION     "The value of the object iesIfRowStatus specifies the
                     status of this row.
                     The only values supported during a set operation are
                     'createAndGo' and 'destroy'."
    ::= { iesIfEntry 2 }

iesIfName OBJECT-TYPE
    SYNTAX          TNamedItem
    MAX-ACCESS      read-create
    STATUS          current
    DESCRIPTION     "The value of the object iesIfName specifies the name used
                     to refer to this IES interface. This  name must be unique
                     within the Base virtual router context.
                     This object must be specified when the row is created, and
                     cannot be changed while the rowstatus is 'active'."
    ::= { iesIfEntry 3 }

iesIfDescription OBJECT-TYPE
    SYNTAX          ServObjLongDesc
    MAX-ACCESS      read-create
    STATUS          current
    DESCRIPTION     "The value of the object iesIfDescription specifies
                     generic information about this IES interface."
    DEFVAL          { "" }
    ::= { iesIfEntry 4 }

iesIfAdminStatus OBJECT-TYPE
    SYNTAX          ServiceAdminStatus
    MAX-ACCESS      read-create
    STATUS          current
    DESCRIPTION     "The value of the object iesIfAdminStatus specifies the
                     desired state of this IES interface."
    DEFVAL          { up }
    ::= { iesIfEntry 5 }

iesIfOperStatus OBJECT-TYPE
    SYNTAX          ServiceOperStatus
    MAX-ACCESS      read-only
    STATUS          current
    DESCRIPTION     "The value of the object iesIfOperStatus indicates the
                     operating state of this IES interface."
    ::= { iesIfEntry 6 }

iesIfLastMgmtChange OBJECT-TYPE
    SYNTAX          TimeStamp
    MAX-ACCESS      read-only
    STATUS          current
    DESCRIPTION     "The value of the object iesIfLastMgmtChange indicates the
                     value of sysUpTime at the time of the most recent
                     management-initiated change to this IES interface."
    ::= { iesIfEntry 7 }

iesIfVpnId OBJECT-TYPE
    SYNTAX          VpnId
    MAX-ACCESS      read-only
    STATUS          current
    DESCRIPTION     "The value of the object iesIfVpnId indicates the VPN ID of
                     the associated IES service."
    ::= { iesIfEntry 8 }

iesIfCustId OBJECT-TYPE
    SYNTAX          TmnxCustId
    MAX-ACCESS      read-only
    STATUS          current
    DESCRIPTION     "The value of the object iesIfCustId indicates the Customer
                     ID of the associated IES service."
    ::= { iesIfEntry 9 }

iesIfLoopback OBJECT-TYPE
    SYNTAX          TruthValue
    MAX-ACCESS      read-create
    STATUS          current
    DESCRIPTION     "When the value of iesIfLoopback is set to 'true',
                     loopback is enabled on the  IES interface represented
                     by this row entry.  When the value is 'false',
                     loopback is disabled."
    ::= { iesIfEntry 10 }

iesIfLastStatusChange OBJECT-TYPE
    SYNTAX          TimeStamp
    MAX-ACCESS      read-only
    STATUS          current
    DESCRIPTION     "The value of the object iesIfLastStatusChange indicates
                     the value of sysUpTime at the time of the most recent
                     operating status change to his interface."
    ::= { iesIfEntry 11 }

iesIfType  OBJECT-TYPE
    SYNTAX          INTEGER {
                        service    (1),
                        subscriber (2),
                        group      (3),
                        redundant  (4),
                        cem        (5),
                        ipsec      (6),
                        ipMirror   (7)
                    }
    MAX-ACCESS      read-create
    STATUS          current
    DESCRIPTION     "The value of iesIfType specifies the type
                     of this IES interface. This object can only be set at
                     row creation time.
                     'service'     - This is a normal IES interface.
                     'subscriber'  - This is a subscriber interface, 
                                     under which multiple group interfaces 
                                     can be configured.
                     'group'       - This is a group interface, belonging 
                                     to a parent subscriber interface.
                     'redundant'   - This is a redundant interface, used 
                                     for dual homing.
                     'cem'         - This is a CEM interface, used for 
                                     IP/UDP encapsulated CEM IES interface.
                     'ipsec'       - This is an IPsec interface, used for 
                                     IPsec tunneling.
                     'ipMirror'    - This is an IP interface, used for 
                                     IP Mirroring."
    DEFVAL          { service }
    ::= { iesIfEntry 12 }

iesIfParentIf   OBJECT-TYPE
    SYNTAX          InterfaceIndexOrZero
    MAX-ACCESS      read-create
    STATUS          current
    DESCRIPTION     "The value of iesIfParentIf specifies the ifIndex of
                     this interface's parent. This value can only be set at
                     row creation time, and is only valid when
                     iesIfType is 'group'. The interface pointed to by
                     iesIfParentIf must be of type 'subscriber'."
    DEFVAL          { 0 }
    ::= { iesIfEntry 13 }

iesIfShcvSource    OBJECT-TYPE
    SYNTAX          INTEGER {
                        interface (1),
                        vrrp      (2)
                    }
    MAX-ACCESS      read-create
    STATUS          current
    DESCRIPTION     "The value of iesIfShcvSource specifies the source used
                     for subscriber host connectivity checking"
    DEFVAL          { interface }
    ::= { iesIfEntry 14 }

iesIfShcvAction    OBJECT-TYPE
    SYNTAX          INTEGER {
                        alarm  (1),
                        remove (2)
                    }
    MAX-ACCESS      read-create
    STATUS          current
    DESCRIPTION     "The value of iesIfShcvAction specifies the action to be
                     taken for hosts on this interface whose host connectivity
                     checking fails"
    DEFVAL          { alarm }
    ::= { iesIfEntry 15 }

iesIfShcvInterval   OBJECT-TYPE
    SYNTAX          Unsigned32 (0..6000)
    UNITS           "minutes"
    MAX-ACCESS      read-create
    STATUS          current
    DESCRIPTION     "The value of the object iesIfShcvInterval specifies
                     the interval in minutes between connectivity checks.
                     Zero means no in host-connection-verify"
    DEFVAL          { 0 }
    ::= { iesIfEntry 16 }

iesIfFwdServId       OBJECT-TYPE
    SYNTAX           TmnxServId
    MAX-ACCESS       read-create
    STATUS           current
    DESCRIPTION      "The value of iesIfFwdServId specifies the forwarding 
                      service ID for a subscriber interface in a retailer 
                      context. This value can only be set at row creation time
                      along with iesIfFwdSubIf, and it is only valid when 
                      iesIfType is 'subscriber'. The iesIfFwdServId MUST 
                      correspond to a service of type 'vprn'."
    DEFVAL           { 0 }
    ::= { iesIfEntry 17 }

iesIfFwdSubIf        OBJECT-TYPE
    SYNTAX           InterfaceIndexOrZero
    MAX-ACCESS       read-create
    STATUS           current
    DESCRIPTION      "The value of iesIfFwdSubIf specifies the forwarding 
                      subscriber interface for a subscriber interface in a 
                      retailer context. This value can only be set at row 
                      creation time along with iesIfFwdServId, and it is only 
                      valid when iesIfType is 'subscriber'. The interface 
                      pointed to by iesIfFwdSubIf MUST be of type 'subscriber' 
                      in the the service context defined by iesIfFwdServId."
    DEFVAL           { 0 }
    ::= { iesIfEntry 18 }

-- ------------------------------------
-- TLS Split-Horizon Group Table
-- ------------------------------------
tlsShgInfoTable OBJECT-TYPE
    SYNTAX          SEQUENCE OF TlsShgInfoEntry
    MAX-ACCESS      not-accessible
    STATUS          current
    DESCRIPTION     "A table that contains TLS service split-horizon group
                     information. A maximum of 30 split-horizon groups can
                     be created in a given TLS service. Maximum is set to 15
                     for a TLS service with svcVplsType set to 'bVpls', or 
                     'iVpls'."
    ::= { tmnxSvcObjs 6 }

tlsShgInfoEntry OBJECT-TYPE
    SYNTAX          TlsShgInfoEntry
    MAX-ACCESS      not-accessible
    STATUS          current
    DESCRIPTION     "Split-horizon group information about a TLS service."
    INDEX           { svcId, IMPLIED tlsShgName }
    ::= { tlsShgInfoTable 1 }

TlsShgInfoEntry ::=
    SEQUENCE {
        tlsShgName                  TNamedItem,
        tlsShgRowStatus             RowStatus,
        tlsShgCustId                TmnxCustId,
        tlsShgInstanceId            Unsigned32,
        tlsShgDescription           ServObjDesc,
        tlsShgLastMgmtChange        TimeStamp,
        tlsShgResidential           TruthValue,
        tlsShgRestProtSrcMac        TruthValue,
        tlsShgRestUnprotDstMac      TruthValue,
        tlsShgRestProtSrcMacAction  INTEGER,
        tlsShgCreationOrigin        L2RouteOrigin
    }

tlsShgName OBJECT-TYPE
    SYNTAX          TNamedItem
    MAX-ACCESS      not-accessible
    STATUS          current
    DESCRIPTION     "The value of the object tlsShgName specifies the name of
                     the split-horizon group. The name must be unique within
                     a TLS, however the same name can appear in different
                     TLS services, in which case they denote different
                     split-horizon groups."
    ::= { tlsShgInfoEntry 1 }

tlsShgRowStatus OBJECT-TYPE
    SYNTAX          RowStatus
    MAX-ACCESS      read-create
    STATUS          current
    DESCRIPTION     "The value of the object  tlsShgRowStatus specifies the
                     status of this row.
                     The only values supported during a set operation are
                     'createAndGo' and 'destroy'. To delete an entry
                     from this table, there should be no TLS SAP's or
                     TLS spoke SDP Bindings refering to it."
    ::= { tlsShgInfoEntry 2 }

tlsShgCustId OBJECT-TYPE
    SYNTAX          TmnxCustId
    MAX-ACCESS      read-only
    STATUS          current
    DESCRIPTION     "The value of the object tlsShgCustId indicates the
                     Customer ID of the associated TLS service."
    ::= { tlsShgInfoEntry 3 }

tlsShgInstanceId OBJECT-TYPE
    SYNTAX          Unsigned32
    MAX-ACCESS      read-only
    STATUS          current
    DESCRIPTION     "The value of the object tlsShgInstanceId indicates the
                     instance identifier for the split horizon group."
    ::= { tlsShgInfoEntry 4 }

tlsShgDescription OBJECT-TYPE
    SYNTAX          ServObjDesc
    MAX-ACCESS      read-create
    STATUS          current
    DESCRIPTION     "The value of the object tlsShgDescription specifies
                     generic information about this split-horizon group."
    DEFVAL { "" }
    ::= { tlsShgInfoEntry 5 }

tlsShgLastMgmtChange OBJECT-TYPE
    SYNTAX          TimeStamp
    MAX-ACCESS      read-only
    STATUS          current
    DESCRIPTION     "The value of the object tlsShgLastMgmtChange indicates the
                     value of sysUpTime at the time of the most recent
                     management-initiated change to this split-horizon group."
    ::= { tlsShgInfoEntry 6 }

tlsShgResidential OBJECT-TYPE
    SYNTAX          TruthValue
    MAX-ACCESS      read-create
    STATUS          current
    DESCRIPTION     "The value of the object tlsShgResidential  specifies
                     whether  or not the split-horizon-group is residential.In
                     a Residential Split Horizon Group (RSHG) there is no
                     downstream broadcast, and all saps in the group will share
                     the default ingress queue. The value can be specified
                     during  row-creation, cannot be changed later on."
    DEFVAL { false }
    ::= { tlsShgInfoEntry 7 }

tlsShgRestProtSrcMac OBJECT-TYPE
    SYNTAX          TruthValue
    MAX-ACCESS      read-create
    STATUS          current
    DESCRIPTION     "The value of the object tlsShgRestProtSrcMac indicates
                     how the agent will handle relearn requests for protected
                     MAC addresses received on SAP's belonging to this SHG.
                     When the value of this object is 'true' requests to 
                     relearn a protected MAC address will be ignored.
                     In addition, if the value of tlsShgRestProtSrcMacAction
                     is 'disable', then the SAP where the protected source
                     MAC was seen will be brought operationally down."
    DEFVAL          { false }
    ::= { tlsShgInfoEntry 8 }

tlsShgRestUnprotDstMac OBJECT-TYPE
    SYNTAX          TruthValue
    MAX-ACCESS      read-create
    STATUS          current
    DESCRIPTION     "The value of the object tlsShgRestUnprotDstMac indicates
                     how the system will forward packets destined to an
                     unprotected MAC address. When the value of this object is
                     'true' packets destined to an unprotected MAC address
                     will be dropped."
    DEFVAL          { false }
    ::= { tlsShgInfoEntry 9 }
    
tlsShgRestProtSrcMacAction OBJECT-TYPE
    SYNTAX          INTEGER {
                        disable    (1),
                        alarm-only (2)
                    }
    MAX-ACCESS      read-create
    STATUS          current
    DESCRIPTION     "The value of the object tlsShgRestProtSrcMacAction
                     indicates the action to take whenever a relearn request
                     for a protected MAC is received on a restricted SAP
                     belonging to this SHG.
                     When the value of this object is 'disable' the SAP
                     will be placed in the operational down state, with the
                     operating flag 'recProtSrcMac' set. When the value of
                     this object is 'alarm-only', the SAP will be left up
                     and only a notification, sapReceivedProtSrcMac,  will be 
                     generated."
    DEFVAL          { disable }    
    ::= { tlsShgInfoEntry 10 }

tlsShgCreationOrigin  OBJECT-TYPE
    SYNTAX          L2RouteOrigin
    MAX-ACCESS      read-only
    STATUS          current
    DESCRIPTION     "The value of tlsShgCreationOrigin indicates the protocol or 
                     mechanism which created this SHG."
    ::= { tlsShgInfoEntry 11 }

-- ------------------------------------
-- APIPE Service Table
-- ------------------------------------
svcApipeInfoTable OBJECT-TYPE
    SYNTAX          SEQUENCE OF SvcApipeInfoEntry
    MAX-ACCESS      not-accessible
    STATUS          current
    DESCRIPTION     "A table that contains APIPE service information."
    ::= { tmnxSvcObjs 7 }

svcApipeInfoEntry OBJECT-TYPE
    SYNTAX          SvcApipeInfoEntry
    MAX-ACCESS      not-accessible
    STATUS          current
    DESCRIPTION     "APIPE specific information about a service."
    INDEX           { svcId }
    ::= { svcApipeInfoTable 1 }

SvcApipeInfoEntry ::=
    SEQUENCE {
        svcApipeInterworking                   INTEGER
    }

svcApipeInterworking OBJECT-TYPE
    SYNTAX          INTEGER {
                        none              (1),
                        frf-5             (2),
                        frf-8-2-translate (3)
                    }
    MAX-ACCESS      read-write
    STATUS          current
    DESCRIPTION     "The value of the object svcApipeInterworking specifies the
                     interworking function that should be applied for packets
                     that ingress/egress SAPs that are part of a APIPE
                     service."
    DEFVAL          { none }
    ::= { svcApipeInfoEntry 1 }

-- ------------------------------------
-- TLS MFIB Information Table
-- ------------------------------------
tlsMFibInfoTable OBJECT-TYPE
    SYNTAX          SEQUENCE OF TlsMFibInfoEntry
    MAX-ACCESS      not-accessible
    STATUS          obsolete
    DESCRIPTION     "tlsMFibInfoTable contains the IPv4 Multicast FIB for
                     this Tls.
                     
                     This table was made obsolete in the 6.0 release.
                     It is replaced by tlsMFibTable."
    ::= { tmnxSvcObjs 8 }

tlsMFibInfoEntry OBJECT-TYPE
    SYNTAX          TlsMFibInfoEntry
    MAX-ACCESS      not-accessible
    STATUS          obsolete
    DESCRIPTION     "An  entry in the tlsMFibInfoTable. Each entry indicates
                     whether  traffic from a certain source to a certain
                     multicast destination (group) needs to be forwarded or
                     blocked on the indicated SAP/SDP."
    INDEX           { svcId,
                      tlsMFibInfoGrpAddr,
                      tlsMFibInfoSrcAddr,
                      tlsMFibInfoLocale,
                      tlsMFibInfoPortId,
                      tlsMFibInfoEncapValue,
                      tlsMFibInfoSdpId,
                      tlsMFibInfoVcId }

    ::= { tlsMFibInfoTable 1 }

TlsMFibInfoEntry ::=
    SEQUENCE {
        tlsMFibInfoGrpAddr      IpAddress,
        tlsMFibInfoSrcAddr      IpAddress,
        tlsMFibInfoLocale       MfibLocation,
        tlsMFibInfoPortId       TmnxPortID,
        tlsMFibInfoEncapValue   TmnxEncapVal,
        tlsMFibInfoSdpId        SdpId,
        tlsMFibInfoVcId         Unsigned32,
        tlsMFibInfoFwdOrBlk     MfibGrpSrcFwdOrBlk,
        tlsMFibInfoSvcId        TmnxServId
    }

tlsMFibInfoGrpAddr OBJECT-TYPE
    SYNTAX          IpAddress
    MAX-ACCESS      not-accessible
    STATUS          obsolete
    DESCRIPTION     "The value of the object tlsMFibInfoGrpAddr indicates the
                     IPv4 multicast destination address for which this table
                     entry contains information."
    ::= { tlsMFibInfoEntry 1 }

tlsMFibInfoSrcAddr OBJECT-TYPE
    SYNTAX          IpAddress
    MAX-ACCESS      not-accessible
    STATUS          obsolete
    DESCRIPTION     "tlsMFibInfoSrcAddr indicates the IPv4 unicast source
                     address for which this table entry contains information."
    ::= { tlsMFibInfoEntry 2 }

tlsMFibInfoLocale OBJECT-TYPE
    SYNTAX          MfibLocation
    MAX-ACCESS      not-accessible
    STATUS          obsolete
    DESCRIPTION     "tlsMFibInfoLocale indicates if the information in
                     this entry pertains to a 'sap' or to an 'sdp'."
    ::= { tlsMFibInfoEntry 3 }

tlsMFibInfoPortId OBJECT-TYPE
    SYNTAX          TmnxPortID
    MAX-ACCESS      not-accessible
    STATUS          obsolete
    DESCRIPTION     "When the value of tlsMFibInfoLocale is 'sap', the object
                     tlsMFibInfoPortId along with the object
                     tlsMFibInfoEncapValue, indicates the SAP for which this
                     entry contains information. This object is otherwise
                     insignificant and contains the value 0."
    ::= { tlsMFibInfoEntry 4 }

tlsMFibInfoEncapValue OBJECT-TYPE
    SYNTAX          TmnxEncapVal
    MAX-ACCESS      not-accessible
    STATUS          obsolete
    DESCRIPTION     "When the value of tlsMFibInfoLocale is 'sap', the object
                     tlsMFibInfoEncapValue, along with the object
                     tlsMFibInfoPortId, indicates the SAP for which this entry
                     contains information. This object is otherwise
                     insignificant and contains the value 0."
    ::= { tlsMFibInfoEntry 5 }

tlsMFibInfoSdpId OBJECT-TYPE
    SYNTAX          SdpId
    MAX-ACCESS      not-accessible
    STATUS          obsolete
    DESCRIPTION     "When the value of tlsMFibInfoLocale is 'sdp', the object
                     tlsMFibInfoSdpId, along with tlsMFibInfoVcId, indicates
                     the SDP Binding for which this entry contains information.
                     This object is otherwise insignificant and contains the
                     value 0."
    ::= { tlsMFibInfoEntry 6 }

tlsMFibInfoVcId OBJECT-TYPE
    SYNTAX          Unsigned32
    MAX-ACCESS      not-accessible
    STATUS          obsolete
    DESCRIPTION     "When the value of tlsMFibInfoLocale is 'sdp', the object
                     tlsMFibInfoVcId, along with tlsMFibInfoSdpId, indicates
                     the SDP Binding for which this entry contains information.
                     This object is otherwise insignificant and contains the
                     value 0."
    ::= { tlsMFibInfoEntry 7 }

tlsMFibInfoFwdOrBlk OBJECT-TYPE
    SYNTAX          MfibGrpSrcFwdOrBlk
    MAX-ACCESS      read-only
    STATUS          obsolete
    DESCRIPTION     "tlsMFibInfoFwdOrBlk indicates if traffic for the
                     indicated (S,G) pair will be blocked or forwarded on the
                     indicated SAP or SDP."
    ::= { tlsMFibInfoEntry 8 }

tlsMFibInfoSvcId OBJECT-TYPE
    SYNTAX          TmnxServId
    MAX-ACCESS      read-only
    STATUS          obsolete
    DESCRIPTION     "tlsMFibInfoSvcId indicates the TLS service to which
                     the indicated SAP or SDP belongs."
    ::= { tlsMFibInfoEntry 9 }

-- ----------------------------------------
-- TLS MFIB Group Source Statistics Table
-- ----------------------------------------
tlsMFibGrpSrcStatsTable OBJECT-TYPE
    SYNTAX          SEQUENCE OF TlsMFibGrpSrcStatsEntry
    MAX-ACCESS      not-accessible
    STATUS          obsolete
    DESCRIPTION     "tlsMFibGrpSrcStatsTable contains statistics for the
                     entries in the IPv4 Multicast FIB for this Tls. These
                     statistics are collected by the forwarding engine.
                     
                     This table was made obsolete in the 6.0 release.
                     It is replaced by tlsMFibStatsTable."
    ::= { tmnxSvcObjs 9 }

tlsMFibGrpSrcStatsEntry OBJECT-TYPE
    SYNTAX          TlsMFibGrpSrcStatsEntry
    MAX-ACCESS      not-accessible
    STATUS          obsolete
    DESCRIPTION     "An entry in the tlsMFibGrpSrcStatsTable."
    INDEX           { svcId,
                      tlsMFibGrpSrcStatsGrpAddr,
                      tlsMFibGrpSrcStatsSrcAddr }
    ::= { tlsMFibGrpSrcStatsTable 1 }

TlsMFibGrpSrcStatsEntry ::=
    SEQUENCE {
        tlsMFibGrpSrcStatsGrpAddr          IpAddress,
        tlsMFibGrpSrcStatsSrcAddr          IpAddress,
        tlsMFibGrpSrcStatsForwardedPkts    Counter64,
        tlsMFibGrpSrcStatsForwardedOctets  Counter64
    }

tlsMFibGrpSrcStatsGrpAddr OBJECT-TYPE
    SYNTAX          IpAddress
    MAX-ACCESS      not-accessible
    STATUS          obsolete
    DESCRIPTION     "tlsMFibGrpSrcStatsGrpAddr indicates the IPv4 multicast
                     destination address for which this table entry contains
                     information."
    ::= { tlsMFibGrpSrcStatsEntry 1 }

tlsMFibGrpSrcStatsSrcAddr OBJECT-TYPE
    SYNTAX          IpAddress
    MAX-ACCESS      not-accessible
    STATUS          obsolete
    DESCRIPTION     "tlsMFibGrpSrcStatsSrcAddr indicates the IPv4 unicast
                     source address for which this table entry contains
                     information."
    ::= { tlsMFibGrpSrcStatsEntry 2 }

tlsMFibGrpSrcStatsForwardedPkts OBJECT-TYPE
    SYNTAX          Counter64
    MAX-ACCESS      read-only
    STATUS          obsolete
    DESCRIPTION     "tlsMFibGrpSrcStatsForwardedPkts indicates the number of
                     IPv4 multicast packets that were forwarded to the SAPs
                     and SDPs listed in the tlsMFibInfoTable."
    ::= { tlsMFibGrpSrcStatsEntry 3 }

tlsMFibGrpSrcStatsForwardedOctets OBJECT-TYPE
    SYNTAX          Counter64
    MAX-ACCESS      read-only
    STATUS          obsolete
    DESCRIPTION     "tlsMFibGrpSrcStatsForwardedOctets indicates the number
                     of octets that were forwarded to the SAPs and SDPs
                     listed in the tlsMFibInfoTable."
    ::= { tlsMFibGrpSrcStatsEntry 4 }

-- --------------------------------
-- Redundant Group Table
-- --------------------------------
tlsRdntGrpTable OBJECT-TYPE
    SYNTAX          SEQUENCE OF TlsRdntGrpEntry
    MAX-ACCESS      not-accessible
    STATUS          current
    DESCRIPTION     "A table that contains TLS service Redundant Group
                     information.  There is no limit on the number of
                     Redundant Groups that can be created globally or
                     within a service."
    ::= {tmnxSvcObjs 10}

tlsRdntGrpEntry OBJECT-TYPE
    SYNTAX          TlsRdntGrpEntry
    MAX-ACCESS      not-accessible
    STATUS          current
    DESCRIPTION     "Redundant Group information"
    INDEX           { svcId, IMPLIED tlsRdntGrpName }
    ::= { tlsRdntGrpTable 1 }

TlsRdntGrpEntry ::=
    SEQUENCE {
        tlsRdntGrpName           TNamedItem,
        tlsRdntGrpRowStatus      RowStatus,
        tlsRdntGrpDescription    ServObjDesc,
        tlsRdntGrpLastMgmtChange TimeStamp
    }

tlsRdntGrpName OBJECT-TYPE
    SYNTAX          TNamedItem
    MAX-ACCESS      not-accessible
    STATUS          current
    DESCRIPTION     "The value of the object tlsRdntGrpName specifies the
                     name of the redundant group.
                     The name must be unique within a TLS, however the same
                     name can appear in different TLS services, in which
                     case they denote different redundant groups."
    ::= { tlsRdntGrpEntry 1 }

tlsRdntGrpRowStatus OBJECT-TYPE
    SYNTAX          RowStatus
    MAX-ACCESS      read-create
    STATUS          current
    DESCRIPTION     "The value of the object tlsRdntGrpRowStatus specifies
                     the status of this row. The only values supported are
                     'active', 'createAndGo' and 'destroy'."
    ::= { tlsRdntGrpEntry 2 }

tlsRdntGrpDescription OBJECT-TYPE
    SYNTAX          ServObjDesc
    MAX-ACCESS      read-create
    STATUS          current
    DESCRIPTION     "The value of the object tlsRdntGrpDescription specifies
                     generic information about this redundant group."
    DEFVAL          { ''H }
    ::= { tlsRdntGrpEntry 3 }

tlsRdntGrpLastMgmtChange OBJECT-TYPE
    SYNTAX          TimeStamp
    MAX-ACCESS      read-only
    STATUS          current
    DESCRIPTION     "The value of the object tlsRdntGrpLastMgmtChange
                     indicates the sysUpTime at the time of the most
                     recent management-initiated change to this redundant
                     group."
    ::= { tlsRdntGrpEntry 4 }

-- ---------------------------------
-- Redundant Group Member Table
-- ---------------------------------
tlsRdntGrpMemberTable OBJECT-TYPE
    SYNTAX          SEQUENCE OF TlsRdntGrpMemberEntry
    MAX-ACCESS      not-accessible
    STATUS          current
    DESCRIPTION     "A table that holds information about the members of
                     TLS redundant groups."
    ::= { tmnxSvcObjs 11 }

tlsRdntGrpMemberEntry OBJECT-TYPE
    SYNTAX          TlsRdntGrpMemberEntry
    MAX-ACCESS      not-accessible
    STATUS          current
    DESCRIPTION     "Redundant Group Member information."
    INDEX           { tlsRdntGrpName,
                      tlsRdntGrpMemberRemoteNodeAddrTp,
                      tlsRdntGrpMemberRemoteNodeAddr,
                      tlsRdntGrpMemberIsSap,
                      tlsRdntGrpMemberPort,
                      tlsRdntGrpMemberEncap
                    }
    ::= { tlsRdntGrpMemberTable 1 }

TlsRdntGrpMemberEntry ::=
    SEQUENCE {
        tlsRdntGrpMemberRemoteNodeAddrTp InetAddressType,
        tlsRdntGrpMemberRemoteNodeAddr   InetAddress,
        tlsRdntGrpMemberIsSap            TruthValue,
        tlsRdntGrpMemberPort             TmnxPortID,
        tlsRdntGrpMemberEncap            TmnxEncapVal,
        tlsRdntGrpMemberRowStatus        RowStatus,
        tlsRdntGrpMemberLastMgmtChange   TimeStamp
    }

tlsRdntGrpMemberRemoteNodeAddrTp OBJECT-TYPE
    SYNTAX          InetAddressType
    MAX-ACCESS      not-accessible
    STATUS          current
    DESCRIPTION     "The value of the object tlsRdntGrpMemberRemoteNodeAddrTp
                     specifies the addresstype of the remote ldp peer."
    ::= { tlsRdntGrpMemberEntry 1}

tlsRdntGrpMemberRemoteNodeAddr OBJECT-TYPE
    SYNTAX          InetAddress
    MAX-ACCESS      not-accessible
    STATUS          current
    DESCRIPTION     "The value of the object tlsRdntGrpMemberRemoteNodeAddr
                     specifies the ip address of the remote ldp peer."
    ::= { tlsRdntGrpMemberEntry 2}

tlsRdntGrpMemberIsSap OBJECT-TYPE
    SYNTAX          TruthValue
    MAX-ACCESS      not-accessible
    STATUS          current
    DESCRIPTION     "The value of the object tlsRdntGrpMemberIsSap
                     specifies whether the Port ID and Encap describe a sap
                     or a port (in which case Encap has no meaning)."
    ::= { tlsRdntGrpMemberEntry 3}

tlsRdntGrpMemberPort OBJECT-TYPE
    SYNTAX          TmnxPortID
    MAX-ACCESS      not-accessible
    STATUS          current
    DESCRIPTION     "When the value of tlsRdntGrpMemberIsSap is 'sap',
                     the value of the object  tlsRdntGrpMemberPort, along
                     with tlsRdntGrpMemberEncap, specifies
                     a SAP, otherwise a port (in which case
                     tlsRdntGrpMemberEncap is insignificant)."
    ::= { tlsRdntGrpMemberEntry 4}

tlsRdntGrpMemberEncap OBJECT-TYPE
    SYNTAX          TmnxEncapVal
    MAX-ACCESS      not-accessible
    STATUS          current
    DESCRIPTION     "When the value of tlsRdntGrpMemberIsSap is 'sap',
                     the value of the object  tlsRdntGrpMemberEncap, along
                     with tlsRdntGrpMemberPort, specifies a SAP. This object
                     is otherwise insignificant and  should contain a
                     value of 0."
    ::= { tlsRdntGrpMemberEntry 5}

tlsRdntGrpMemberRowStatus OBJECT-TYPE
    SYNTAX          RowStatus
    MAX-ACCESS      read-create
    STATUS          current
    DESCRIPTION     "The value of the object tlsRdntGrpMemberRowStatus
                     specifies the status of this row. The
                     only values supported are 'active', 'createAndGo'
                     and 'destroy'."
    ::= { tlsRdntGrpMemberEntry 6 }

tlsRdntGrpMemberLastMgmtChange OBJECT-TYPE
    SYNTAX          TimeStamp
    MAX-ACCESS      read-only
    STATUS          current
    DESCRIPTION     "The value of the object tlsRdntGrpMemberLastMgmtChange
                     indicates the time of the most recent management-initiated
                     change to this redundant group member."
    ::= { tlsRdntGrpMemberEntry 7}


-- -----------------------------------------
-- TLS MSTI Table
-- -----------------------------------------
tlsMstiTable OBJECT-TYPE
    SYNTAX          SEQUENCE OF TlsMstiEntry
    MAX-ACCESS      not-accessible
    STATUS          current
    DESCRIPTION     "A table that contains Multiple Spanning Tree Instance
                     (MSTI) information. Each management VPLS running MSTP can
                     have upto 15 MSTI, not including the CIST."
    ::= { tmnxSvcObjs 12 }

tlsMstiEntry OBJECT-TYPE
    SYNTAX          TlsMstiEntry
    MAX-ACCESS      not-accessible
    STATUS          current
    DESCRIPTION     "Information about a specific MSTI."
    INDEX           { svcId, tlsMstiInstanceId}
    ::= { tlsMstiTable 1 }

TlsMstiEntry ::=
    SEQUENCE {
        tlsMstiInstanceId        MstiInstanceId,
        tlsMstiRowStatus         RowStatus,
        tlsMstiPriority          Integer32,
        tlsMstiLastMgmtChange    TimeStamp,
        tlsMstiRegionalRoot      BridgeId,
        tlsMstiIntRootCost       Integer32,
        tlsMstiRemainingHopCount Integer32,
        tlsMstiRegionalRootPort  Integer32
    }

tlsMstiInstanceId OBJECT-TYPE
    SYNTAX          MstiInstanceId
    MAX-ACCESS      not-accessible
    STATUS          current
    DESCRIPTION     "The value of the object tlsMstiInstanceId specifies the
                     Multiple Spanning Tree Instance."
    ::= { tlsMstiEntry 1 }


tlsMstiRowStatus OBJECT-TYPE
    SYNTAX          RowStatus
    MAX-ACCESS      read-create
    STATUS          current
    DESCRIPTION     "The value of the object tlsMstiRowStatus specifies the
                     status of this row.
                     The only values supported during a set operation are
                     'active', 'createAndGo' and 'destroy'."
    ::= { tlsMstiEntry 2 }

tlsMstiPriority OBJECT-TYPE
    SYNTAX          Integer32 (0..65535)
    MAX-ACCESS      read-create
    STATUS          current
    DESCRIPTION     "The value of the object tlsMstiPriority specifies the
                     priority of this spcecific Multiple Spanning Tree
                     Instance for this service.
                     It is used as the highest 4 bits of the Bridge ID
                     included in the MSTP BPDU's generated by
                     this bridge.
                     The tlsMstiPriority can only take-on values which
                     multiples of 4096 (4k). If a value is specified which
                     is not a multiple of 4K, then this value will be
                     replaced by the closest multiple of 4K which is lower
                     then the value entered."
    DEFVAL          { 32768 }
    ::= { tlsMstiEntry 3 }

tlsMstiLastMgmtChange OBJECT-TYPE
    SYNTAX          TimeStamp
    MAX-ACCESS      read-only
    STATUS          current
    DESCRIPTION     "The value of the object tlsMstiLastMgmtChange indicates
                     the value of sysUpTime at the time of the most recent
                     management-initiated change to this MSTI."
    ::= { tlsMstiEntry 4 }

tlsMstiRegionalRoot OBJECT-TYPE
    SYNTAX          BridgeId
    MAX-ACCESS      read-only
    STATUS          current
    DESCRIPTION     "The value of the object tlsMstiRegionalRoot
                     indicates the bridge identifier of the regional root of
                     the MSTI spanning tree as determined by the Spanning Tree
                     Protocol instance associated with this service. This value
                     is used as the CIST Regional Root Identifier parameter in
                     all MSTP BPDUs originated by this node."
    ::= { tlsMstiEntry 5 }

tlsMstiIntRootCost OBJECT-TYPE
    SYNTAX          Integer32
    MAX-ACCESS      read-only
    STATUS          current
    DESCRIPTION     "The value of the object tlsMstiIntRootCost indicates the
                     cost of the path to the regional root bridge as seen from
                     this bridge."
    ::= { tlsMstiEntry 6 }

tlsMstiRemainingHopCount OBJECT-TYPE
    SYNTAX          Integer32
    MAX-ACCESS      read-only
    STATUS          current
    DESCRIPTION     "The value of the object tlsMstiRemainingHopCount
                     specifies the remaining number of hops."
    ::= { tlsMstiEntry 7 }

tlsMstiRegionalRootPort OBJECT-TYPE
    SYNTAX          Integer32
    MAX-ACCESS      read-only
    STATUS          current
    DESCRIPTION     "The value of the object tlsMstiRegionalRootPort indicates
                     the port number of the port which offers the lowest cost
                     path from this bridge to the regional root bridge."
    ::= { tlsMstiEntry 8 }

-- -----------------------------------------
-- TLS MSTI Managed VLAN List Table
-- -----------------------------------------
tlsMstiManagedVlanListTable OBJECT-TYPE
    SYNTAX          SEQUENCE OF TlsMstiManagedVlanListEntry
    MAX-ACCESS      not-accessible
    STATUS          current
    DESCRIPTION     "This table is used only for a management VPLS when MSTP
                     is running. It indicates for each multiple spanning tree
                     instance the ranges of associated VLANs that will be
                     affected when a certain SAP changes state."
    ::= { tmnxSvcObjs 13 }

tlsMstiManagedVlanListEntry OBJECT-TYPE
    SYNTAX          TlsMstiManagedVlanListEntry
    MAX-ACCESS      not-accessible
    STATUS          current
    DESCRIPTION     "Each row specifies a range of VLANS associated
                     with a SAP of a MVPLS. Ranges may contains overlapping
                     sections only for Mvpls SAPs that belong to the same
                     service."
    INDEX           { svcId,
                      tlsMstiInstanceId,
                      tlsMstiMvplsMinVlanTag,
                      tlsMstiMvplsMaxVlanTag }
    ::= { tlsMstiManagedVlanListTable 1 }

TlsMstiManagedVlanListEntry ::=
    SEQUENCE {
        tlsMstiMvplsMinVlanTag  QTag, -- integer(1 .. 4094)
        tlsMstiMvplsMaxVlanTag  QTag,
        tlsMstiMvplsRowStatus   RowStatus
    }

tlsMstiMvplsMinVlanTag OBJECT-TYPE
    SYNTAX          QTag
    MAX-ACCESS      not-accessible
    STATUS          current
    DESCRIPTION     "The value of tlsMstiMvplsMinVlanTag specifies
                     the left bound (i.e. min. value) of a range of VLANs
                     that are associated with the Mvpls SAP.
                     tlsMstiMvplsMinVlanTag must be smaller than (or equal
                     to) tlsMstiMvplsMaxVlanTag."
    ::= { tlsMstiManagedVlanListEntry 1 }

tlsMstiMvplsMaxVlanTag OBJECT-TYPE
    SYNTAX          QTag
    MAX-ACCESS      not-accessible
    STATUS          current
    DESCRIPTION     "The value of tlsMstiMvplsMaxVlanTag specifies the
                     right bound (i.e. max. value) of a range of VLANs that
                     are associated with the Mvpls SAP."
    ::= { tlsMstiManagedVlanListEntry 2 }

tlsMstiMvplsRowStatus OBJECT-TYPE
    SYNTAX           RowStatus
    MAX-ACCESS       read-create
    STATUS           current
    DESCRIPTION      "The value of tlsMstiMvplsRowStatus specifies
                      the status of this row. The only values supported
                      during a set operation are 'active', 'createAndGo' and
                      'destroy'."
    ::= { tlsMstiManagedVlanListEntry 3 }

-- -----------------------------------------
-- TLS Egress Multicast Group Table
-- -----------------------------------------
tlsEgressMulticastGroupTable OBJECT-TYPE
    SYNTAX          SEQUENCE OF TlsEgressMulticastGroupEntry
    MAX-ACCESS      not-accessible
    STATUS          current
    DESCRIPTION     "This table is used to manage VPLS Egress Multicast
                     Groups. These groups are used to group together VPLS
                     SAP's in order to improve the efficiency of the egress
                     multicast replication process."
    ::= { tmnxSvcObjs 14 }

tlsEgressMulticastGroupEntry OBJECT-TYPE
    SYNTAX          TlsEgressMulticastGroupEntry
    MAX-ACCESS      not-accessible
    STATUS          current
    DESCRIPTION     "An entry containing management information applicable
                     to a particular VPLS Egress Multicast Group."
    INDEX           { IMPLIED tlsEgrMcGrpName }
    ::= { tlsEgressMulticastGroupTable 1 }

TlsEgressMulticastGroupEntry ::=
    SEQUENCE {
        tlsEgrMcGrpName                 TNamedItem,
        tlsEgrMcGrpRowStatus            RowStatus,
        tlsEgrMcGrpLastMgmtChange       TimeStamp,
        tlsEgrMcGrpDescription          ServObjDesc,
        tlsEgrMcGrpChainLimit           Unsigned32,
        tlsEgrMcGrpEncapType            INTEGER,
        tlsEgrMcGrpDot1qEtherType       Unsigned32,
        tlsEgrMcGrpMacFilterId          TFilterID,
        tlsEgrMcGrpIpFilterId           TFilterID,
        tlsEgrMcGrpIpv6FilterId         TFilterID,
        tlsEgrMcGrpQinqEtherType        Unsigned32,
        tlsEgrMcGrpQinqFixedTagPosition INTEGER,
        tlsEgrMcGrpAdminQinqFixedTagVal Unsigned32,
        tlsEgrMcGrpOperQinqFixedTagVal  Unsigned32
    }

tlsEgrMcGrpName OBJECT-TYPE
    SYNTAX          TNamedItem
    MAX-ACCESS      not-accessible
    STATUS          current
    DESCRIPTION     "The value of tlsEgrMcGrpName indicates the name of
                     the Egress Multicast Group."
    ::= { tlsEgressMulticastGroupEntry 1 }

tlsEgrMcGrpRowStatus OBJECT-TYPE
    SYNTAX          RowStatus
    MAX-ACCESS      read-create
    STATUS          current
    DESCRIPTION     "The value of tlsEgrMcGrpRowStatus controls the creation
                     and deletion of rows in this table."
    ::= { tlsEgressMulticastGroupEntry 2 }

tlsEgrMcGrpLastMgmtChange OBJECT-TYPE
    SYNTAX          TimeStamp
    MAX-ACCESS      read-only
    STATUS          current
    DESCRIPTION     "The value of tlsEgrMcGrpLastMgmtChange indicates the
                     value of sysUpTime at the time of the last management
                     change of any writable object of this row."
    ::= { tlsEgressMulticastGroupEntry 3 }

tlsEgrMcGrpDescription OBJECT-TYPE
    SYNTAX          ServObjDesc
    MAX-ACCESS      read-create
    STATUS          current
    DESCRIPTION     "Generic information about this Egress Multicast Group."
    DEFVAL          { "" }
    ::= { tlsEgressMulticastGroupEntry 4 }

tlsEgrMcGrpChainLimit OBJECT-TYPE
    SYNTAX          Unsigned32 (1..30)
    MAX-ACCESS      read-create
    STATUS          current
    DESCRIPTION     "The value of tlsEgrMcGrpChainLimit specifies the maximum
                     number of SAP's that can be placed together in a single
                     chain on this Egress Multicast Group."
    DEFVAL          { 16 }
    ::= { tlsEgressMulticastGroupEntry 5 }

tlsEgrMcGrpEncapType OBJECT-TYPE
    SYNTAX          INTEGER {
                        unknown   (0),
                        nullEncap (1),
                        qEncap    (2),
                        qinqEncap (10)
                    }
    MAX-ACCESS      read-create
    STATUS          current
    DESCRIPTION     "The value of tlsEgrMcGrpEncapType specifies the common
                     service encapsulation type used by all the SAP's on this
                     Egress Multicast Group."
    DEFVAL          { nullEncap }
    ::= { tlsEgressMulticastGroupEntry 6 }

tlsEgrMcGrpDot1qEtherType OBJECT-TYPE
    SYNTAX          Unsigned32 ('600'H..'ffff'H)
    MAX-ACCESS      read-create
    STATUS          current
    DESCRIPTION     "The value of tlsEgrMcGrpDot1qEtherType specifies the
                     common ethertype value used by all the 802.1Q SAP's on
                     this Egress Multicast Group."
    DEFVAL          { '8100'H }
    ::= { tlsEgressMulticastGroupEntry 7 }

tlsEgrMcGrpMacFilterId OBJECT-TYPE
    SYNTAX          TFilterID
    MAX-ACCESS      read-create
    STATUS          current
    DESCRIPTION     "The value of tlsEgrMcGrpMacFilterId specifies the common
                     egress MAC filter ID used by all the SAP's on this
                     Egress Multicast Group."
    DEFVAL          { 0 }
    ::= { tlsEgressMulticastGroupEntry 8 }

tlsEgrMcGrpIpFilterId OBJECT-TYPE
    SYNTAX          TFilterID
    MAX-ACCESS      read-create
    STATUS          current
    DESCRIPTION     "The value of tlsEgrMcGrpIpFilterId specifies the common
                     egress IP filter ID used by all the SAP's on this
                     Egress Multicast Group."
    DEFVAL          { 0 }
    ::= { tlsEgressMulticastGroupEntry 9 }

tlsEgrMcGrpIpv6FilterId OBJECT-TYPE
    SYNTAX          TFilterID
    MAX-ACCESS      read-create
    STATUS          current
    DESCRIPTION     "The value of tlsEgrMcGrpIpv6FilterId specifies the common
                     egress IPv6 filter ID used by all the SAP's on this
                     Egress Multicast Group."
    DEFVAL          { 0 }
    ::= { tlsEgressMulticastGroupEntry 10 }

tlsEgrMcGrpQinqEtherType OBJECT-TYPE
    SYNTAX          Unsigned32 ('600'H..'ffff'H)
    MAX-ACCESS      read-create
    STATUS          current
    DESCRIPTION     "The value of tlsEgrMcGrpQinqEtherType specifies the
                     common ethertype value used by all the 'QinQ' SAP's in
                     this Egress Multicast Group."
    DEFVAL          { '8100'H }
    ::= { tlsEgressMulticastGroupEntry 11 }

tlsEgrMcGrpQinqFixedTagPosition OBJECT-TYPE
    SYNTAX          INTEGER {
                        topTag    (2),   -- top (outter) tag is fixed
                        bottomTag (3)    -- bottom (inner) tag is fixed
                    }
    MAX-ACCESS      read-create
    STATUS          current
    DESCRIPTION     "The value of tlsEgrMcGrpQinqFixedTagPosition specifies
                     the common position of the fixed 802.1Q tag of all the
                     'QinQ' SAP's in this Egress Multicast Group. This object
                     has no meaning when the value of tlsEgrMcGrpEncapType
                     is not 'qinqEncap'."
    DEFVAL          { bottomTag }
    ::= { tlsEgressMulticastGroupEntry 12 }

tlsEgrMcGrpAdminQinqFixedTagVal OBJECT-TYPE
    SYNTAX          Unsigned32 (0|1..4094)
    MAX-ACCESS      read-create
    STATUS          current
    DESCRIPTION     "The value of tlsEgrMcGrpAdminQinqFixedTagVal 
                     specifies the provisioned common value of the fixed 
                     802.1Q tag of all the 'QinQ' SAP's in this Egress 
                     Multicast Group.

                     The value 0 is used to indicate that the actual value 
                     of the fixed tag will be defined implicitly by the 
                     corresponding tag of the first SAP added to this Egress
                     Multicast Group."
    DEFVAL          { 0 }
    ::= { tlsEgressMulticastGroupEntry 13 } 

tlsEgrMcGrpOperQinqFixedTagVal OBJECT-TYPE
    SYNTAX          Unsigned32
    MAX-ACCESS      read-only
    STATUS          current
    DESCRIPTION     "The value of tlsEgrMcGrpOperQinqFixedTagVal 
                     specifies the operating common value of the fixed 
                     802.1Q tag of all the 'QinQ' SAP's in this Egress 
                     Multicast Group."
    ::= { tlsEgressMulticastGroupEntry 14 }

-- ----------------------------------------
-- DHCP Lease State Table
-- ----------------------------------------
svcDhcpLeaseStateTable OBJECT-TYPE
    SYNTAX          SEQUENCE OF SvcDhcpLeaseStateEntry
    MAX-ACCESS      not-accessible
    STATUS          current
    DESCRIPTION     "A table that contains DHCP lease states."
    ::= { tmnxSvcObjs 16 }

svcDhcpLeaseStateEntry OBJECT-TYPE
    SYNTAX          SvcDhcpLeaseStateEntry
    MAX-ACCESS      not-accessible
    STATUS          current
    DESCRIPTION     "Information about a specific DHCP lease state."
    INDEX           { svcId,
                      svcDhcpLseStateCiAddrType,
                      svcDhcpLseStateCiAddr }
    ::= { svcDhcpLeaseStateTable 1 }

SvcDhcpLeaseStateEntry ::=
    SEQUENCE {
        svcDhcpLseStateCiAddrType           InetAddressType,
        svcDhcpLseStateCiAddr               InetAddress,
        svcDhcpLseStateLocale               INTEGER,
        svcDhcpLseStatePortId               TmnxPortID,
        svcDhcpLseStateEncapValue           TmnxEncapVal,
        svcDhcpLseStateSdpId                SdpId,
        svcDhcpLseStateVcId                 Unsigned32,
        svcDhcpLseStateChAddr               MacAddress,
        svcDhcpLseStateRemainLseTime        Unsigned32,
        svcDhcpLseStateOption82             OCTET STRING,
        svcDhcpLseStatePersistKey           Unsigned32,
        svcDhcpLseStateSubscrIdent          DisplayString,
        svcDhcpLseStateSubProfString        DisplayString,
        svcDhcpLseStateSlaProfString        DisplayString,
        svcDhcpLseStateShcvOperState        INTEGER,
        svcDhcpLseStateShcvChecks           Unsigned32,
        svcDhcpLseStateShcvReplies          Unsigned32,
        svcDhcpLseStateShcvReplyTime        TimeStamp,
        svcDhcpLseStateClientId             OCTET STRING,
        svcDhcpLseStateIAID                 Unsigned32,
        svcDhcpLseStateIAIDType             IAIDType,
        svcDhcpLseStateCiAddrMaskLen        Unsigned32,
        svcDhcpLseStateRetailerSvcId        TmnxServId,
        svcDhcpLseStateRetailerIf           InterfaceIndexOrZero,
        svcDhcpLseStateAncpString           DisplayString,
        svcDhcpLseStateFramedIpNetMaskTp    InetAddressType,
        svcDhcpLseStateFramedIpNetMask      InetAddress,
        svcDhcpLseStateBCastIpAddrType      InetAddressType,
        svcDhcpLseStateBCastIpAddr          InetAddress,
        svcDhcpLseStateDefaultRouterTp      InetAddressType,
        svcDhcpLseStateDefaultRouter        InetAddress,
        svcDhcpLseStatePrimaryDnsType       InetAddressType,
        svcDhcpLseStatePrimaryDns           InetAddress,
        svcDhcpLseStateSecondaryDnsType     InetAddressType,
        svcDhcpLseStateSecondaryDns         InetAddress,
        svcDhcpLseStateSessionTimeout       Unsigned32,
        svcDhcpLseStateServerLeaseStart     DateAndTime,
        svcDhcpLseStateServerLastRenew      DateAndTime,
        svcDhcpLseStateServerLeaseEnd       DateAndTime,
        svcDhcpLseStateDhcpServerAddrType   InetAddressType,
        svcDhcpLseStateDhcpServerAddr       InetAddress,
        svcDhcpLseStateOriginSubscrId       DhcpLseStateInfoOrigin,
        svcDhcpLseStateOriginStrings        DhcpLseStateInfoOrigin,
        svcDhcpLseStateOriginLeaseInfo      DhcpLseStateInfoOrigin,
        svcDhcpLseStateDhcpClientAddrType   InetAddressType,
        svcDhcpLseStateDhcpClientAddr       InetAddress,
        svcDhcpLseStateLeaseSplitActive     TruthValue,
        svcDhcpLseStateInterDestId          DisplayString,
        svcDhcpLseStatePrimaryNbnsType      InetAddressType,
        svcDhcpLseStatePrimaryNbns          InetAddress,
        svcDhcpLseStateSecondaryNbnsType    InetAddressType,
        svcDhcpLseStateSecondaryNbns        InetAddress,
        svcDhcpLseStateAppProfString        DisplayString,
        svcDhcpLseStateNextHopMacAddr       MacAddress
    }

svcDhcpLseStateCiAddrType OBJECT-TYPE
    SYNTAX          InetAddressType
    MAX-ACCESS      not-accessible
    STATUS          current
    DESCRIPTION     "The value of svcDhcpLseStateCiAddrType indicates the
                     address type of svcDhcpLseStateCiAddr."
    ::= { svcDhcpLeaseStateEntry 1 }

svcDhcpLseStateCiAddr OBJECT-TYPE
    SYNTAX          InetAddress
    MAX-ACCESS      not-accessible
    STATUS          current
    DESCRIPTION     "The value of svcDhcpLseStateCiAddr indicates the IP
                     address of the DHCP lease state."
    ::= { svcDhcpLeaseStateEntry 2 }

svcDhcpLseStateLocale OBJECT-TYPE
    SYNTAX          INTEGER {
                        sap (1),
                        sdp (2)
                    }
    MAX-ACCESS      read-only
    STATUS          current
    DESCRIPTION     "The value of svcDhcpLseStateLocale specifies if the DHCP
                     lease state is learned via a SAP or SDP."
    ::= { svcDhcpLeaseStateEntry 3 }

svcDhcpLseStatePortId OBJECT-TYPE
    SYNTAX          TmnxPortID
    MAX-ACCESS      read-only
    STATUS          current
    DESCRIPTION     "When the value of svcDhcpLseStateLocale is 'sap', the
                     object svcDhcpLseStatePortId along with the object
                     svcDhcpLseStateEncapValue, indicates the SAP for which
                     this entry contains information. This object is otherwise
                     insignificant and contains the value 0."
    ::= { svcDhcpLeaseStateEntry 4 }

svcDhcpLseStateEncapValue OBJECT-TYPE
    SYNTAX          TmnxEncapVal
    MAX-ACCESS      read-only
    STATUS          current
    DESCRIPTION     "When the value of svcDhcpLseStateLocale is 'sap', the
                     object svcDhcpLseStatePortId along with the object
                     svcDhcpLseStateEncapValue, indicates the SAP for which
                     this entry contains information. This object is otherwise
                     insignificant and contains the value 0."
    ::= { svcDhcpLeaseStateEntry 5 }

svcDhcpLseStateSdpId OBJECT-TYPE
    SYNTAX          SdpId
    MAX-ACCESS      read-only
    STATUS          current
    DESCRIPTION     "When the value of svcDhcpLseStateLocale is 'sdp', the
                     object svcDhcpLseStateSdpId, along with the object
                     svcDhcpLseStateVcId, indicates the SDP Binding for which
                     this entry contains information. This object is otherwise
                     insignificant and contains the value 0."
    ::= { svcDhcpLeaseStateEntry 6 }

svcDhcpLseStateVcId OBJECT-TYPE
    SYNTAX          Unsigned32
    MAX-ACCESS      read-only
    STATUS          current
    DESCRIPTION     "When the value of svcDhcpLseStateLocale is 'sdp', the
                     object svcDhcpLseStateSdpId, along with the object
                     svcDhcpLseStateVcId, indicates the SDP Binding for which
                     this entry contains information. This object is otherwise
                     insignificant and contains the value 0."
    ::= { svcDhcpLeaseStateEntry 7 }

svcDhcpLseStateChAddr OBJECT-TYPE
    SYNTAX          MacAddress
    MAX-ACCESS      read-only
    STATUS          current
    DESCRIPTION     "The value of svcDhcpLseStateChAddr indicates the MAC
                     address of the DHCP lease state."
    ::= { svcDhcpLeaseStateEntry 8 }

svcDhcpLseStateRemainLseTime OBJECT-TYPE
    SYNTAX          Unsigned32
    UNITS           "seconds"
    MAX-ACCESS      read-only
    STATUS          current
    DESCRIPTION     "The value of svcDhcpLseStateRemainLseTime indicates the
                     remaining lease time of the DHCP lease state."
    ::= { svcDhcpLeaseStateEntry 9 }

svcDhcpLseStateOption82 OBJECT-TYPE
    SYNTAX          OCTET STRING
    MAX-ACCESS      read-only
    STATUS          current
    DESCRIPTION     "The value of svcDhcpLseStateOption82 indicates the content
                     of option 82 for this DHCP lease state."
    ::= { svcDhcpLeaseStateEntry 10 }

svcDhcpLseStatePersistKey OBJECT-TYPE
    SYNTAX          Unsigned32
    MAX-ACCESS      read-only
    STATUS          current
    DESCRIPTION     "The value of svcDhcpLseStatePersistKey indicates a key
                     value that can be used to track this lease state in the
                     persistence file."
    ::= { svcDhcpLeaseStateEntry 11 }

svcDhcpLseStateSubscrIdent OBJECT-TYPE
    SYNTAX          DisplayString
    MAX-ACCESS      read-only
    STATUS          current
    DESCRIPTION     "The value of svcDhcpLseStateSubscrIdent indicates the
                     id of the parent subscriber of this DHCP lease state.
                     
                     The value of svcDhcpLseStateOriginSubscrId indicates
                     whether this subscriber identification was received from
                     the DHCP or from the Radius server."
    ::= { svcDhcpLeaseStateEntry 12 }

svcDhcpLseStateSubProfString OBJECT-TYPE
    SYNTAX          DisplayString
    MAX-ACCESS      read-only
    STATUS          current
    DESCRIPTION     "The value of svcDhcpLseStateSubProfString indicates the
                     subscriber profile string applicable for this DHCP lease
                     state.
                     
                     The value of svcDhcpLseStateOriginStrings indicates
                     whether this subscriber profile string was received from
                     the DHCP or from the Radius server."
    ::= { svcDhcpLeaseStateEntry 13 }

svcDhcpLseStateSlaProfString OBJECT-TYPE
    SYNTAX          DisplayString
    MAX-ACCESS      read-only
    STATUS          current
    DESCRIPTION     "The value of svcDhcpLseStateSlaProfString indicates the
                     SLA profile string applicable for this DHCP lease state.
                     
                     The value of svcDhcpLseStateOriginStrings indicates
                     whether this SLA profile string was received from
                     the DHCP or from the Radius server."
    ::= { svcDhcpLeaseStateEntry 14 }

svcDhcpLseStateShcvOperState OBJECT-TYPE
    SYNTAX          INTEGER{
                        disabled  (1),
                        undefined (2),
                        down      (3),
                        up        (4)
                    }
    MAX-ACCESS      read-only
    STATUS          current
    DESCRIPTION     "The value of svcDhcpLseStateShcvOperState indicates the
                     state of the subscriber host connectivity check for
                     this DHCP lease state."
    ::= { svcDhcpLeaseStateEntry 15 }

svcDhcpLseStateShcvChecks OBJECT-TYPE
    SYNTAX          Unsigned32
    MAX-ACCESS      read-only
    STATUS          current
    DESCRIPTION     "The value of svcDhcpLseStateShcvChecks indicates the
                     number of host connectivity check requests for
                     this DHCP lease state."
    ::= { svcDhcpLeaseStateEntry 16 }

svcDhcpLseStateShcvReplies OBJECT-TYPE
    SYNTAX          Unsigned32
    MAX-ACCESS      read-only
    STATUS          current
    DESCRIPTION     "The value of svcDhcpLseStateShcvReplies indicates the
                     number of host connectivity replies for
                     this DHCP lease state."
    ::= { svcDhcpLeaseStateEntry 17 }

svcDhcpLseStateShcvReplyTime OBJECT-TYPE
    SYNTAX          TimeStamp
    MAX-ACCESS      read-only
    STATUS          current
    DESCRIPTION     "The value of svcDhcpLseStateShcvReplyTime indicates the
                     time of the last successful host connectivity check for
                     this DHCP lease state."
    ::= { svcDhcpLeaseStateEntry 18 }

svcDhcpLseStateClientId OBJECT-TYPE
    SYNTAX          OCTET STRING
    MAX-ACCESS      read-only
    STATUS          current
    DESCRIPTION     "The value of svcDhcpLseStateClientId indicates the 
                     DHCPv6 clients unique identifier (DUID) as generated
                     by the client." 
    ::= { svcDhcpLeaseStateEntry 19 }

svcDhcpLseStateIAID OBJECT-TYPE
    SYNTAX          Unsigned32
    MAX-ACCESS      read-only
    STATUS          current
    DESCRIPTION     "The value of svcDhcpLseStateIAID indicates the
                     Identity Association ID (IAID)
                     the address or prefix defined by
                     svcDhcpLseStateCiAddr/svcDhcpLseStateCiAddrMaskLen
                     has been assigned to.
                     
                     This object is only meaningful for DHCPv6 leases."
    REFERENCE
                    "RFC 3315 section 10"
    ::= { svcDhcpLeaseStateEntry 20 }

svcDhcpLseStateIAIDType OBJECT-TYPE
    SYNTAX          IAIDType
    MAX-ACCESS      read-only
    STATUS          current
    DESCRIPTION     "The value of svcDhcpLseStateIAIDType indicates the
                     type of svcDhcpLseStateIAID.

                     This object is only meaningful for DHCPv6 leases."
    REFERENCE
                    "RFC 3315"
    ::= { svcDhcpLeaseStateEntry 21 }

svcDhcpLseStateCiAddrMaskLen OBJECT-TYPE
    SYNTAX          Unsigned32 (0..128)
    MAX-ACCESS      read-only
    STATUS          current
    DESCRIPTION     "The value of svcDhcpLseStateCiAddrMaskLen indicates the 
                     prefix length of the svcDhcpLseStateCiAddr for a DHCPv6
                     lease."
    ::= { svcDhcpLeaseStateEntry 22 }

svcDhcpLseStateRetailerSvcId OBJECT-TYPE  
    SYNTAX          TmnxServId
    MAX-ACCESS      read-only
    STATUS          current
    DESCRIPTION     "The value of svcDhcpLseStateRetailerSvcId indicates the
                     service ID of the retailer VPRN service to which this 
                     DHCP lease belongs. When this object is non zero, the
                     DHCP lease belongs to a retailer VPRN."
    ::= { svcDhcpLeaseStateEntry 23 }

svcDhcpLseStateRetailerIf OBJECT-TYPE
     SYNTAX         InterfaceIndexOrZero
     MAX-ACCESS      read-only
     STATUS          current
     DESCRIPTION     "The value of svcDhcpLseStateRetailerIf indicates the
                      interface index of the retailer VPRN interface to 
                      which this DHCP lease belongs. When this object is 
                      non zero, the DHCP lease belongs to a retailer VPRN."
     ::= { svcDhcpLeaseStateEntry 24 }

svcDhcpLseStateAncpString OBJECT-TYPE
    SYNTAX          DisplayString (SIZE (1..63))
    MAX-ACCESS      read-only
    STATUS          current
    DESCRIPTION     "The object svcDhcpLseStateAncpString indicates the
                     value of the ancp-string received from either the DHCP
                     or the Radius server as indicated by the value of 
                     svcDhcpLseStateOriginStrings."
    ::= { svcDhcpLeaseStateEntry 25 }

svcDhcpLseStateFramedIpNetMaskTp OBJECT-TYPE
    SYNTAX          InetAddressType
    MAX-ACCESS      read-only
    STATUS          current
    DESCRIPTION     "The value of svcDhcpLseStateFramedIpNetMaskTp indicates the
                     address type of svcDhcpLseStateFramedIpNetMask."
    ::= { svcDhcpLeaseStateEntry 26 }

svcDhcpLseStateFramedIpNetMask OBJECT-TYPE
    SYNTAX          InetAddress
    MAX-ACCESS      read-only
    STATUS          current
    DESCRIPTION     "The value of svcDhcpLseStateFramedIpNetMask indicates the
                     framed IP netmask received from either the DHCP or the
                     Radius server as indicated by the value of
                     svcDhcpLseStateOriginLeaseInfo.
                     
                     The value of this object is ''H when not applicable."
    ::= { svcDhcpLeaseStateEntry 27 }

svcDhcpLseStateBCastIpAddrType OBJECT-TYPE
    SYNTAX          InetAddressType
    MAX-ACCESS      read-only
    STATUS          current
    DESCRIPTION     "The value of svcDhcpLseStateBCastIpAddrType indicates the
                     address type of svcDhcpLseStateBCastIpAddr."
    ::= { svcDhcpLeaseStateEntry 28 }

svcDhcpLseStateBCastIpAddr OBJECT-TYPE
    SYNTAX          InetAddress
    MAX-ACCESS      read-only
    STATUS          current
    DESCRIPTION     "The value of svcDhcpLseStateBCastIpAddr indicates the
                     broadcast IP address received from either the DHCP or the
                     Radius server as indicated by the value of
                     svcDhcpLseStateOriginLeaseInfo.
                     
                     The value of this object is ''H when not applicable."
    ::= { svcDhcpLeaseStateEntry 29 }

svcDhcpLseStateDefaultRouterTp OBJECT-TYPE
    SYNTAX          InetAddressType
    MAX-ACCESS      read-only
    STATUS          current
    DESCRIPTION     "The value of svcDhcpLseStateDefaultRouterTp indicates the
                     address type of svcDhcpLseStateDefaultRouter."
    ::= { svcDhcpLeaseStateEntry 30 }

svcDhcpLseStateDefaultRouter OBJECT-TYPE
    SYNTAX          InetAddress
    MAX-ACCESS      read-only
    STATUS          current
    DESCRIPTION     "The value of svcDhcpLseStateDefaultRouter indicates the
                     default router received from either the DHCP or the
                     Radius server as indicated by the value of
                     svcDhcpLseStateOriginLeaseInfo.
                     
                     The value of this object is ''H when not applicable."
    ::= { svcDhcpLeaseStateEntry 31 }

svcDhcpLseStatePrimaryDnsType OBJECT-TYPE
    SYNTAX          InetAddressType
    MAX-ACCESS      read-only
    STATUS          current
    DESCRIPTION     "The value of svcDhcpLseStatePrimaryDnsType indicates the
                     address type of svcDhcpLseStatePrimaryDns."
    ::= { svcDhcpLeaseStateEntry 32 }

svcDhcpLseStatePrimaryDns OBJECT-TYPE
    SYNTAX          InetAddress
    MAX-ACCESS      read-only
    STATUS          current
    DESCRIPTION     "The value of svcDhcpLseStatePrimaryDns indicates the
                     primary DNS server received from either the DHCP or the
                     Radius server as indicated by the value of
                     svcDhcpLseStateOriginLeaseInfo.
                     
                     The value of this object is ''H when not applicable."
    ::= { svcDhcpLeaseStateEntry 33 }

svcDhcpLseStateSecondaryDnsType OBJECT-TYPE
    SYNTAX          InetAddressType
    MAX-ACCESS      read-only
    STATUS          current
    DESCRIPTION     "The value of svcDhcpLseStateSecondaryDnsType indicates the
                     address type of svcDhcpLseStateSecondaryDns."
    ::= { svcDhcpLeaseStateEntry 34 }

svcDhcpLseStateSecondaryDns OBJECT-TYPE
    SYNTAX          InetAddress
    MAX-ACCESS      read-only
    STATUS          current
    DESCRIPTION     "The value of svcDhcpLseStateSecondaryDns indicates the
                     secondary DNS server received from either the DHCP or the
                     Radius server as indicated by the value of
                     svcDhcpLseStateOriginLeaseInfo.
                     
                     The value of this object is ''H when not applicable."
    ::= { svcDhcpLeaseStateEntry 35 }

svcDhcpLseStateSessionTimeout OBJECT-TYPE
    SYNTAX          Unsigned32 (0..65535)
    UNITS           "seconds"
    MAX-ACCESS      read-only
    STATUS          current
    DESCRIPTION     "The value of svcDhcpLseStateSessionTimeout indicates the
                     session timeout received from either the DHCP or the
                     Radius server as indicated by the value of
                     svcDhcpLseStateOriginLeaseInfo."
    ::= { svcDhcpLeaseStateEntry 36 }

svcDhcpLseStateServerLeaseStart OBJECT-TYPE
    SYNTAX          DateAndTime
    MAX-ACCESS      read-only
    STATUS          current
    DESCRIPTION     "The value of svcDhcpLseStateServerLeaseStart indicates
                     when this lease was created."
    ::= { svcDhcpLeaseStateEntry 37 }

svcDhcpLseStateServerLastRenew OBJECT-TYPE
    SYNTAX          DateAndTime
    MAX-ACCESS      read-only
    STATUS          current
    DESCRIPTION     "The value of svcDhcpLseStateServerLastRenew indicates
                     when we last received a renewal from either the DHCP or the
                     Radius server."
    ::= { svcDhcpLeaseStateEntry 38 }

svcDhcpLseStateServerLeaseEnd OBJECT-TYPE
    SYNTAX          DateAndTime
    MAX-ACCESS      read-only
    STATUS          current
    DESCRIPTION     "The value of svcDhcpLseStateServerLeaseEnd indicates
                     when the server will consider the lease as being
                     expired."
    ::= { svcDhcpLeaseStateEntry 39 }

svcDhcpLseStateDhcpServerAddrType OBJECT-TYPE
    SYNTAX          InetAddressType
    MAX-ACCESS      read-only
    STATUS          current
    DESCRIPTION     "The value of svcDhcpLseStateDhcpServerAddrType indicates
                     the address type of svcDhcpLseStateDhcpServerAddr."
    ::= { svcDhcpLeaseStateEntry 40 }

svcDhcpLseStateDhcpServerAddr OBJECT-TYPE
    SYNTAX          InetAddress
    MAX-ACCESS      read-only
    STATUS          current
    DESCRIPTION     "The value of svcDhcpLseStateDhcpServerAddr indicates the
                     IP address of the DHCP server received from either the
                     DHCP or the Radius server as indicated by the value of
                     svcDhcpLseStateOriginLeaseInfo.
                     
                     The value of this object is ''H when not applicable."
    ::= { svcDhcpLeaseStateEntry 41 }

svcDhcpLseStateOriginSubscrId OBJECT-TYPE
    SYNTAX          DhcpLseStateInfoOrigin
    MAX-ACCESS      read-only
    STATUS          current
    DESCRIPTION     "The value of svcDhcpLseStateOriginSubscrId indicates
                     which source provided the subscriber-id."
    ::= { svcDhcpLeaseStateEntry 42 }

svcDhcpLseStateOriginStrings OBJECT-TYPE
    SYNTAX          DhcpLseStateInfoOrigin
    MAX-ACCESS      read-only
    STATUS          current
    DESCRIPTION     "The value of svcDhcpLseStateOriginStrings indicates
                     which server provided the Sub-profile, SLA profile,
                     Ancp string and Intermediate Destination Id."
    ::= { svcDhcpLeaseStateEntry 43 }

svcDhcpLseStateOriginLeaseInfo OBJECT-TYPE
    SYNTAX          DhcpLseStateInfoOrigin
    MAX-ACCESS      read-only
    STATUS          current
    DESCRIPTION     "The value of svcDhcpLseStateOriginLeaseInfo indicates
                     which server provided the lease state information."
    ::= { svcDhcpLeaseStateEntry 44 }

svcDhcpLseStateDhcpClientAddrType OBJECT-TYPE
    SYNTAX          InetAddressType
    MAX-ACCESS      read-only
    STATUS          current
    DESCRIPTION     "The value of svcDhcpLseStateDhcpClientAddrType indicates
                     the address type of svcDhcpLseStateDhcpClientAddr."
    ::= { svcDhcpLeaseStateEntry 45 }

svcDhcpLseStateDhcpClientAddr OBJECT-TYPE
    SYNTAX          InetAddress
    MAX-ACCESS      read-only
    STATUS          current
    DESCRIPTION     "The value of svcDhcpLseStateDhcpClientAddr indicates the
                     IP address of the DHCP Client that owns the lease info.

                     In some cases this address can be different from the
                     address specified in svcDhcpLseStateCiAddr, e.g. in case of
                     DHCPv6 prefix delegation."
    ::= { svcDhcpLeaseStateEntry 46 }

svcDhcpLseStateLeaseSplitActive OBJECT-TYPE
    SYNTAX          TruthValue
    MAX-ACCESS      read-only
    STATUS          current
    DESCRIPTION     "The value of svcDhcpLseStateLeaseSplitActive indicates
                     whether or not the current lease time resulted from a
                     lease split.
                     If svcDhcpLseStateLeaseSplitActive is 'true',
                     the lease time passed to the client is determined by the
                     value of the object sapTlsDhcpProxyLeaseTime for VPLS SAPs,
                     or by the value of the object vRtrIfDHCPProxyLeaseTime
                     for Layer 3 interfaces."
    ::= { svcDhcpLeaseStateEntry 47 }

svcDhcpLseStateInterDestId OBJECT-TYPE
    SYNTAX          DisplayString (SIZE (0..32))
    MAX-ACCESS      read-only
    STATUS          current
    DESCRIPTION     "The object svcDhcpLseStateInterDestId indicates the
                     intermediate destination identifier received from either
                     the DHCP or the Radius server or the local user database
                     as indicated by the value of svcDhcpLseStateOriginStrings."
    ::= { svcDhcpLeaseStateEntry 48 }

svcDhcpLseStatePrimaryNbnsType OBJECT-TYPE
    SYNTAX          InetAddressType
    MAX-ACCESS      read-only
    STATUS          current
    DESCRIPTION     "The value of svcDhcpLseStatePrimaryNbnsType indicates the
                     address type of svcDhcpLseStatePrimaryNbns."
    ::= { svcDhcpLeaseStateEntry 49 }

svcDhcpLseStatePrimaryNbns OBJECT-TYPE
    SYNTAX          InetAddress
    MAX-ACCESS      read-only
    STATUS          current
    DESCRIPTION     "The value of svcDhcpLseStatePrimaryNbns indicates the
                     primary NBNS server received from either the DHCP or the
                     Radius server as indicated by the value of
                     svcDhcpLseStateOriginLeaseInfo.

                     The value of this object is ''H when not applicable."
    ::= { svcDhcpLeaseStateEntry 50 }

svcDhcpLseStateSecondaryNbnsType OBJECT-TYPE
    SYNTAX          InetAddressType
    MAX-ACCESS      read-only
    STATUS          current
    DESCRIPTION     "The value of svcDhcpLseStateSecondaryNbnsType indicates
                     the address type of svcDhcpLseStateSecondaryNbns."
    ::= { svcDhcpLeaseStateEntry 51 }

svcDhcpLseStateSecondaryNbns OBJECT-TYPE
    SYNTAX          InetAddress
    MAX-ACCESS      read-only
    STATUS          current
    DESCRIPTION     "The value of svcDhcpLseStateSecondaryNbns indicates the
                     secondary NBNS server received from either the DHCP or the
                     Radius server as indicated by the value of
                     svcDhcpLseStateOriginLeaseInfo.

                     The value of this object is ''H when not applicable."
    ::= { svcDhcpLeaseStateEntry 52 }

svcDhcpLseStateAppProfString OBJECT-TYPE
    SYNTAX          DisplayString
    MAX-ACCESS      read-only
    STATUS          current
    DESCRIPTION     "The value of svcDhcpLseStateAppProfString indicates the
                     application profile string applicable for this DHCP lease
                     state.
                     
                     The value of svcDhcpLseStateOriginStrings indicates
                     whether this application profile string was received from
                     DHCP or from the Radius server."
    ::= { svcDhcpLeaseStateEntry 53 }

svcDhcpLseStateNextHopMacAddr OBJECT-TYPE
    SYNTAX          MacAddress
    MAX-ACCESS      read-only
    STATUS          current
    DESCRIPTION     "The value of svcDhcpLseStateNextHopMacAddr indicates the
                     MAC address of the next hop of this DHCP lease state.
                     
                     Normally, the next hop MAC address equals the value of
                     svcDhcpLseStateChAddr. If the value of the object
                     ALCATEL-IND1-TIMETRA-VRTR-MIB::vRtrIfDHCPLayer2Header is set to 'true',
                     a routing device can be present between this node and
                     the DHCP client. In that case, the value of the next hop
                     MAC address contains the MAC address of this routing
                     device."
    ::= { svcDhcpLeaseStateEntry 54 }

-- -----------------------------------------
-- TLS Protected MAC Address Table
-- -----------------------------------------
tlsProtectedMacTable OBJECT-TYPE
    SYNTAX          SEQUENCE OF TlsProtectedMacEntry
    MAX-ACCESS      not-accessible
    STATUS          current
    DESCRIPTION     "This table is used to manage protected MAC addresses
                     within a VPLS's FDB."
    ::= { tmnxSvcObjs 17 }

tlsProtectedMacEntry OBJECT-TYPE
    SYNTAX          TlsProtectedMacEntry
    MAX-ACCESS      not-accessible
    STATUS          current
    DESCRIPTION     "An entry containing management information applicable
                     to a particular protected MAC address."
    INDEX           { svcId, tlsProtMacAddress }
    ::= { tlsProtectedMacTable 1 }

TlsProtectedMacEntry ::=
    SEQUENCE {
        tlsProtMacAddress           MacAddress,
        tlsProtMacRowStatus         RowStatus,
        tlsProtMacLastMgmtChange    TimeStamp
    }

tlsProtMacAddress OBJECT-TYPE
    SYNTAX          MacAddress
    MAX-ACCESS      not-accessible
    STATUS          current
    DESCRIPTION     "The value of tlsProtMacAddress indicates the address
                     of the protected MAC."
    ::= { tlsProtectedMacEntry 1 }

tlsProtMacRowStatus OBJECT-TYPE
    SYNTAX          RowStatus
    MAX-ACCESS      read-create
    STATUS          current
    DESCRIPTION     "The value of tlsProtMacRowStatus controls the creation
                     and deletion of rows in this table."
    ::= { tlsProtectedMacEntry 2 }

tlsProtMacLastMgmtChange OBJECT-TYPE
    SYNTAX          TimeStamp
    MAX-ACCESS      read-only
    STATUS          current
    DESCRIPTION     "The value of tlsProtMacLastMgmtChange indicates the
                     value of sysUpTime at the time of the last management
                     change of any writable object of this row."
    ::= { tlsProtectedMacEntry 3 }

-- ----------------------------------------
-- svcDhcpLeaseStateModifyTable
-- ----------------------------------------
svcDhcpLeaseStateModifyTable OBJECT-TYPE
    SYNTAX          SEQUENCE OF SvcDhcpLeaseStateModifyEntry
    MAX-ACCESS      not-accessible
    STATUS          current
    DESCRIPTION     "The svcDhcpLeaseStateModifyTable augments the
                     svcDhcpLeaseStateTable.
                     The table allows the operator to modify attributes of the
                     lease state."
    ::= { tmnxSvcObjs 18 }

svcDhcpLeaseStateModifyEntry OBJECT-TYPE
    SYNTAX          SvcDhcpLeaseStateModifyEntry
    MAX-ACCESS      not-accessible
    STATUS          current
    DESCRIPTION     "Each row entry contains parameters that allow to modify a
                     lease-state's  attributes."
    AUGMENTS        { svcDhcpLeaseStateEntry }
    ::= { svcDhcpLeaseStateModifyTable 1 }

SvcDhcpLeaseStateModifyEntry ::=
    SEQUENCE {
        svcDhcpLseStateModifySubIndent   DisplayString,
        svcDhcpLseStateModifySubProfile  DisplayString,
        svcDhcpLseStateModifySlaProfile  DisplayString,
        svcDhcpLseStateEvaluateState     TruthValue,
        svcDhcpLseStateModInterDestId    DisplayString,
        svcDhcpLseStateModifyAncpString  TmnxAncpStringOrZero,
        svcDhcpLseStateModifyAppProfile  DisplayString
    }

svcDhcpLseStateModifySubIndent OBJECT-TYPE
    SYNTAX          DisplayString (SIZE (0..32))
    MAX-ACCESS      read-write
    STATUS          current
    DESCRIPTION     "The value of svcDhcpLseStateModifySubIndent allows to
                     specify a new subscriber name for this lease state.

                     When a SET of this object is done with a non empty string, the
                     system will attempt to assign a new subscriber name.

                     A SET with an empty string has no effect on the system.
                     (NOOP).

                     GETs and GETNEXTs on this variable return an empty string."
    DEFVAL           { ''H }   -- the empty string
    ::= { svcDhcpLeaseStateModifyEntry 1 }

svcDhcpLseStateModifySubProfile OBJECT-TYPE
    SYNTAX          DisplayString (SIZE (0..16))
    MAX-ACCESS      read-write
    STATUS          current
    DESCRIPTION     "The value of svcDhcpLseStateModifySubProfile allows to
                     specify a new subscriber profile string for this lease
                     state.

                     When a SET of this object is done with a non empty string,
                     the system will attempt to assign a new subscriber profile.

                     A SET with an empty string has no effect on the system.
                     (NOOP).

                     GETs and GETNEXTs on this variable return an empty string."
    DEFVAL           { ''H }   -- the empty string
    ::= { svcDhcpLeaseStateModifyEntry 2 }

svcDhcpLseStateModifySlaProfile OBJECT-TYPE
    SYNTAX          DisplayString (SIZE (0..16))
    MAX-ACCESS      read-write
    STATUS          current
    DESCRIPTION     "The value of svcDhcpLseStateModifySlaProfile allows to
                     specify a new SLA profile string for this lease state.

                     When a SET of this object is done with a non empty string,
                     the system will attempt to assign a new SLA profile.

                     A SET with an empty string has no effect on the system.
                     (NOOP).

                     GETs and GETNEXTs on this variable return an empty string."
    DEFVAL           { ''H }   -- the empty string
    ::= { svcDhcpLeaseStateModifyEntry 3 }

svcDhcpLseStateEvaluateState OBJECT-TYPE
    SYNTAX          TruthValue
    MAX-ACCESS      read-write
    STATUS          current
    DESCRIPTION     "The value of svcDhcpLseStateEvaluateState allows to
                     cause a re-evaluation of the specified lease state.

                     When this object is set to 'true', the system will perform
                     a re-evaluation of the lease state.

                     GETs and GETNEXTs on this variable return false.

                     It is not possible to simultaneously request for a
                     lease-state re-evaluation, and modify any of the 
                     svcDhcpLseStateModifySubIndent,
                     svcDhcpLseStateModifySubProfile or 
                     svcDhcpLseStateModifySlaProfile values."
    DEFVAL          { false }
    ::= { svcDhcpLeaseStateModifyEntry 4 }

svcDhcpLseStateModInterDestId OBJECT-TYPE
    SYNTAX          DisplayString (SIZE (0..32))
    MAX-ACCESS      read-write
    STATUS          current
    DESCRIPTION     "The value of svcDhcpLseStateModInterDestId allows to
                     specify a new intermediate destination id for this lease
                     state.

                     When a SET of this object is done with a non empty string,
                     the system will attempt to assign a new intermediate
                     destination id.

                     A SET with an empty string has no effect on the system.
                     (NOOP).

                     GETs and GETNEXTs on this variable return an empty string."
    DEFVAL           { ''H }
    ::= { svcDhcpLeaseStateModifyEntry 5 }

svcDhcpLseStateModifyAncpString OBJECT-TYPE
    SYNTAX          TmnxAncpStringOrZero
    MAX-ACCESS      read-write
    STATUS          current
    DESCRIPTION     "The value of svcDhcpLseStateModifyAncpString allows to
                     specify a new ANCP-string for this lease state.

                     When a SET of this object is done with a non empty string,
                     the system will attempt to assign a new ANCP-string.

                     A SET with an empty string has no effect on the system.
                     (NOOP).

                     GETs and GETNEXTs on this variable return an empty string."
    DEFVAL           { ''H }   -- the empty string
    ::= { svcDhcpLeaseStateModifyEntry 6 }

svcDhcpLseStateModifyAppProfile OBJECT-TYPE
    SYNTAX          DisplayString (SIZE (0..16))
    MAX-ACCESS      read-write
    STATUS          current
    DESCRIPTION     "The value of svcDhcpLseStateModifyAppProfile specifies
                     a new application profile string for this lease state.

                     When a SET of this object is done with a non empty string,
                     the system assigns a new application profile.

                     A SET with an empty string has no effect on the system.
                     (NOOP).

                     GETs and GETNEXTs on this variable return an empty
                     string."
    DEFVAL           { ''H }   -- the empty string
    ::= { svcDhcpLeaseStateModifyEntry 7 }

-- ----------------------------------------
-- svcEndPointTable
-- ----------------------------------------
svcEndPointTable        OBJECT-TYPE
    SYNTAX      SEQUENCE OF SvcEndPointEntry
    MAX-ACCESS  not-accessible
    STATUS      current
    DESCRIPTION "The svcEndPointTable has an entry for each service endpoint
                 configured on this system."
    ::= { tmnxSvcObjs 19 }

svcEndPointEntry        OBJECT-TYPE
    SYNTAX      SvcEndPointEntry
    MAX-ACCESS  not-accessible
    STATUS      current
    DESCRIPTION "Each row entry represents a particular service endpoint. 
                 Entries are created/deleted by the user."
    INDEX       { svcId, svcEndPointName }
    ::= { svcEndPointTable 1 }

SvcEndPointEntry ::=
    SEQUENCE {
        svcEndPointName                 TNamedItem,
        svcEndPointRowStatus            RowStatus,
        svcEndPointDescription          ServObjDesc,
        svcEndPointRevertTime           Integer32,
        svcEndPointTxActiveType         INTEGER,
        svcEndPointTxActivePortId       TmnxPortID,
        svcEndPointTxActiveEncap        TmnxEncapVal,
        svcEndPointTxActiveSdpId        SdpBindId,
        svcEndPointForceSwitchOver      TmnxActionType,
        svcEndPointForceSwitchOverSdpId SdpBindId,
        svcEndPointActiveHoldDelay      Unsigned32, 
        svcEndPointIgnoreStandbySig     TruthValue,
        svcEndPointMacPinning           TmnxEnabledDisabled,
        svcEndPointMacLimit             Integer32,
        svcEndPointSuppressStandbySig   TruthValue,
        svcEndPointRevertTimeCountDn    Integer32,
        svcEndPointTxActiveChangeCount  Counter32,
        svcEndPointTxActiveLastChange   TimeStamp,
        svcEndPointTxActiveUpTime       TimeTicks
    }

svcEndPointName         OBJECT-TYPE
    SYNTAX      TNamedItem
    MAX-ACCESS  not-accessible
    STATUS      current
    DESCRIPTION "The value of svcEndPointName specifies the name of the service
                 endpoint."
    ::= { svcEndPointEntry 1 }

svcEndPointRowStatus    OBJECT-TYPE
    SYNTAX      RowStatus
    MAX-ACCESS  read-create
    STATUS      current
    DESCRIPTION "The value of svcEndPointRowStatus is used for the creation and
                 deletion of service endpoints."
    ::= { svcEndPointEntry 2 }

svcEndPointDescription  OBJECT-TYPE
    SYNTAX      ServObjDesc
    MAX-ACCESS  read-create
    STATUS      current
    DESCRIPTION "The value of svcEndPointDescription specifies the textual
                 description of this service endpoint."
    DEFVAL      { "" }
    ::= { svcEndPointEntry 3 }

svcEndPointRevertTime  OBJECT-TYPE
    SYNTAX      Integer32 (-1 | 0..600)
    UNITS       "seconds"
    MAX-ACCESS  read-create
    STATUS      current
    DESCRIPTION "The value of svcEndPointRevertTime specifies the time to wait
                 before reverting back to the primary spoke-sdp defined on this
                 service endpoint, after having failed over to a backup 
                 spoke-sdp. When the value is '-1', the spoke-sdp will never 
                 revert back."
    DEFVAL      { 0 }
    ::= { svcEndPointEntry 4 }

svcEndPointTxActiveType OBJECT-TYPE
    SYNTAX      INTEGER {
                    none    (0), -- No end-point objects are active
                    sap     (1), -- A SAP is Tx active
                    sdpBind (2)  -- An SDP bind is Tx Active
                }
    MAX-ACCESS  read-only
    STATUS      current
    DESCRIPTION "The value of svcEndPointTxActiveType indicates the type of
                 end-point object that is current transmit active. "
    ::= { svcEndPointEntry 5 }
        
svcEndPointTxActivePortId       OBJECT-TYPE
    SYNTAX      TmnxPortID
    MAX-ACCESS  read-only
    STATUS      current
    DESCRIPTION "The value of svcEndPointTxActivePortId indicates the Port ID
                 of the SAP that is transmit active. This object is only valid
                 when svcEndPointTxActiveType is 'sap'."
    ::= { svcEndPointEntry 6 }

svcEndPointTxActiveEncap       OBJECT-TYPE
    SYNTAX      TmnxEncapVal
    MAX-ACCESS  read-only
    STATUS      current
    DESCRIPTION "The value of svcEndPointTxActiveEncap indicates the 
                 encapsulation value of the SAP that is transmit active. This
                 object is only valid when svcEndPointTxActiveType is 'sap'."
    ::= { svcEndPointEntry 7 }

svcEndPointTxActiveSdpId       OBJECT-TYPE
    SYNTAX      SdpBindId
    MAX-ACCESS  read-only
    STATUS      current
    DESCRIPTION "The value of svcEndPointTxActiveSdpId indicates the SDP bind
                 ID of the SDP bind that is transmit active. This object is only
                 valid when svcEndPointTxActiveType is 'sdpBind'."
    ::= { svcEndPointEntry 8 }

svcEndPointForceSwitchOver      OBJECT-TYPE
    SYNTAX      TmnxActionType
    MAX-ACCESS  read-create
    STATUS      current
    DESCRIPTION "The value of svcEndPointForceSwitchOver specifies whether to
                 force a switchover of the active SDP bind. When it is set to
                 'doAction', the SDP bind specified by 
                 svcEndPointForceSwitchOverSdpId will become active."
    DEFVAL      { notApplicable }
    ::= { svcEndPointEntry 9 }  

svcEndPointForceSwitchOverSdpId   OBJECT-TYPE
    SYNTAX      SdpBindId
    MAX-ACCESS  read-create
    STATUS      current
    DESCRIPTION "The value of svcEndPointForceSwitchOverSdpId specifies the SDP
                 bind to switch over to when svcEndPointForceSwitchOver is set
                 to 'doAction'. If the value of this object is non default, it 
                 indicates that a forced switchover has taken place. Setting 
                 this object to the default value clears any previous forced 
                 switchover. "
    DEFVAL      { '0000000000000000'H }
    ::= { svcEndPointEntry 10 } 
    
svcEndPointActiveHoldDelay     OBJECT-TYPE
    SYNTAX      Unsigned32 (0..60) 
    UNITS       "deci-seconds"
    MAX-ACCESS  read-create
    STATUS      current
    DESCRIPTION "The value of svcEndPointActiveHoldDelay specifies the amount
                 of time in deci-seconds to hold the active state before going
                 into the standby state when a local MC-LAG SAP goes down."
    DEFVAL      { 0 }
    ::= { svcEndPointEntry 11 } 

svcEndPointIgnoreStandbySig     OBJECT-TYPE
    SYNTAX      TruthValue
    MAX-ACCESS  read-create
    STATUS      current
    DESCRIPTION "The value of svcEndPointIgnoreStandbySig specifies whether the
                 local internal tasks will take into account the 'pseudo-wire
                 forwarding standby' bit received from the LDP peer which is
                 normally ignored.  

                 When set to 'true', this bit is not considered in the internal
                 tasks.

                 A similar object sdpBindTlsIgnoreStandbySig is present at the
                 SDP level. The value of sdpBindTlsIgnoreStandbySig is set to
                 the value of svcEndPointIgnoreStandbySig for the spoke-SDP
                 associated with this endpoint."
    DEFVAL      { false }
    ::= { svcEndPointEntry 12 } 

svcEndPointMacPinning OBJECT-TYPE
    SYNTAX      TmnxEnabledDisabled
    MAX-ACCESS  read-create
    STATUS      current
    DESCRIPTION "The value of svcEndPointMacPinning specifies whether or not
                 MAC address pinning is active on this end-point."
    DEFVAL { disabled }    
    ::= { svcEndPointEntry 13 }

svcEndPointMacLimit OBJECT-TYPE
    SYNTAX      Integer32(0..196607)
    MAX-ACCESS  read-create
    STATUS      current
    DESCRIPTION "The value of the object svcEndPointMacLimit specifies the
                 maximum number of learned and static entries allowed for this
                 end-point.
        
                 The value 0 means: no limit for this end-point. 

                 When the value of ALCATEL-IND1-TIMETRA-CHASSIS-MIB::tmnxChassisOperMode is
                 not 'c', the maximum value of svcEndPointMacLimit is '131071'."
    DEFVAL          { 0 }
    ::= { svcEndPointEntry 14 }

svcEndPointSuppressStandbySig     OBJECT-TYPE
    SYNTAX      TruthValue
    MAX-ACCESS  read-create
    STATUS      current
    DESCRIPTION "The value of the object svcEndPointSuppressStandbySig specifies
                 whether the 'pseudo wire forwarding standby' bit will be sent
                 to the LDP peer whenever the spoke SDP
                 'svcEndPointTxActiveSdpId' is selected as standby. 

                 When set to 'true', this bit will not be sent."
    DEFVAL      { true }
    ::= { svcEndPointEntry 15 } 

svcEndPointRevertTimeCountDn  OBJECT-TYPE
    SYNTAX      Integer32 (-1 | 0..600)
    UNITS       "seconds"
    MAX-ACCESS  read-only
    STATUS      current
    DESCRIPTION "The value of svcEndPointRevertTimeCountDn indicates the timer
                 count down before reverting back to the primary spoke-sdp
                 defined on this service endpoint, after having failed over to
                 a backup spoke-sdp.

                 This timer count down begins after primary Spoke SDP becomes
                 operational.
                 
                 The value of -1 indicates when revert is not-applicable."
    ::= { svcEndPointEntry 16 }

svcEndPointTxActiveChangeCount  OBJECT-TYPE
    SYNTAX      Counter32
    MAX-ACCESS  read-only
    STATUS      current
    DESCRIPTION "The value of svcEndPointTxActiveChangeCount indicates the
                 number of times active transmit change has taken place in this
                 endpoint."
    ::= { svcEndPointEntry 17 }

svcEndPointTxActiveLastChange  OBJECT-TYPE
    SYNTAX      TimeStamp
    MAX-ACCESS  read-only
    STATUS      current
    DESCRIPTION "The value of svcEndPointTxActiveLastChange indicates the
                 value of sysUpTime at the time of the last active transmit
                 change in this endpoint."
    ::= { svcEndPointEntry 18 }

svcEndPointTxActiveUpTime OBJECT-TYPE
    SYNTAX      TimeTicks
    MAX-ACCESS  read-only
    STATUS      current
    DESCRIPTION "The value of svcEndPointTxActiveUpTime indicates the active
                'up' time (in hundredths of a second) of the end-point object 
                that is current transmit active."
    ::= { svcEndPointEntry 19 }

------------------------------------------
-- iesGrpIfTable
-- ----------------------------------------

iesGrpIfTable   OBJECT-TYPE
    SYNTAX      SEQUENCE OF IesGrpIfEntry
    MAX-ACCESS  not-accessible
    STATUS      current
    DESCRIPTION "The iesGrpIfTable has entry for each group interface
                 configured on this system."
    ::= { tmnxSvcObjs 21 }

iesGrpIfEntry   OBJECT-TYPE
    SYNTAX      IesGrpIfEntry
    MAX-ACCESS  not-accessible
    STATUS      current
    DESCRIPTION "Each row entry represents the attributes of a group interface.
                 Entries are create/destroyed when entries in iesIfEntry with
                 iesIfType 'group' are created/destroyed."
    INDEX       { svcId, iesIfIndex }
    ::= { iesGrpIfTable 1 }

IesGrpIfEntry   ::=
    SEQUENCE {
        iesGrpIfRedInterface     InterfaceIndexOrZero,
        iesGrpIfOperUpWhileEmpty TruthValue
   }

iesGrpIfRedInterface    OBJECT-TYPE
    SYNTAX      InterfaceIndexOrZero
    MAX-ACCESS  read-write
    STATUS      current
    DESCRIPTION "The value of iesGrpIfRedInterface specifies the ifIndex
                 of the redundant interface this group interface is tied to.
                 The interface pointed to by this object must be of
                 type 'redundant'."
    DEFVAL      { 0 }
    ::= { iesGrpIfEntry 1 }

iesGrpIfOperUpWhileEmpty    OBJECT-TYPE
    SYNTAX      TruthValue
    MAX-ACCESS  read-write
    STATUS      current
    DESCRIPTION "The value of iesGrpIfOperUpWhileEmpty specifies the
                 whether that operational status of the the IES group
                 interface, as indicated by iesIfOperStatus, should have
                 a value of 'up' even when there are no SAPs on the
                 group interface.

                 If the value of iesGrpIfOperUpWhileEmpty is 'true', the
                 value of iesIfOperStatus for the IES group interface will
                 be 'up' when there are no SAPs on the group interface. When
                 the value of iesGrpIfOperUpWhileEmpty is 'false', the value
                 of iesIfOperStatus will depend on the operational state of
                 the SAPs on the group interface. The value of
                 iesGrpIfOperUpWhileEmpty will be ignored when there are
                 SAPs on the IES group interface."
    DEFVAL      { false }
    ::= { iesGrpIfEntry 2 }

-- ----------------------------------------
-- svcPEDiscoveryPolicyTable
-- ----------------------------------------
svcPEDiscoveryPolicyTable  OBJECT-TYPE
    SYNTAX        SEQUENCE OF SvcPEDiscoveryPolicyEntry
    MAX-ACCESS    not-accessible
    STATUS        current
    DESCRIPTION   "The svcPEDiscoveryPolicyTable has an entry for each PE policy."      
    ::= { tmnxSvcObjs 22 }
    
svcPEDiscoveryPolicyEntry  OBJECT-TYPE
    SYNTAX      SvcPEDiscoveryPolicyEntry
    MAX-ACCESS  not-accessible
    STATUS      current
    DESCRIPTION
        "svcPEDiscoveryPolicyEntry is an entry (conceptual row) in the
         svcPEDiscoveryPolicyTable. Each entry represents the configuration
         of a PE Discovery Policy.

         Entries in this table can be created and deleted via SNMP SET
         operations to svcPEDiscoveryPolicyRowStatus."
    INDEX {IMPLIED svcPEDiscoveryPolicyName}
    ::= { svcPEDiscoveryPolicyTable 1 }

SvcPEDiscoveryPolicyEntry ::= SEQUENCE {
            svcPEDiscoveryPolicyName          TNamedItem,
            svcPEDiscoveryPolicyRowStatus     RowStatus,    
            svcPEDiscoveryPolicyPassword      OCTET STRING,
            svcPEDiscoveryPolicyInterval      Unsigned32,   
            svcPEDiscoveryPolicyTimeout       Unsigned32                 
}

svcPEDiscoveryPolicyName       OBJECT-TYPE
    SYNTAX           TNamedItem
    MAX-ACCESS       not-accessible
    STATUS           current
    DESCRIPTION      
        "The value of the object svcPEDiscoveryPolicyName specifies the 
         RADIUS PE Discovery Policy name." 
    ::= { svcPEDiscoveryPolicyEntry 1 }

svcPEDiscoveryPolicyRowStatus OBJECT-TYPE
    SYNTAX      RowStatus
    MAX-ACCESS  read-create
    STATUS      current
    DESCRIPTION
        "svcPEDiscoveryPolicyRowStatus controls the creation and deletion
         of rows in the table.

         To create a row in the svcPEDiscoveryPolicyTable,
         set svcPEDiscoveryPolicyRowStatus to 'createAndGo'. All objects will take
         on default values and the agent will change svcPEDiscoveryPolicyRowStatus
         to 'active'.

         To delete a row in the svcPEDiscoveryPolicyTable, set
         svcPEDiscoveryPolicyRowStatus to 'delete'."
    ::= { svcPEDiscoveryPolicyEntry 2 }
               
svcPEDiscoveryPolicyPassword  OBJECT-TYPE
    SYNTAX      OCTET STRING (SIZE(0..32))
    MAX-ACCESS  read-create
    STATUS      current
    DESCRIPTION
        "The value of svcPEDiscoveryPolicyPassword specifies the password that is
         used when contacting the RADIUS server for VPLS auto-discovery.


         The value of svcPEDiscPolServerSecret cannot be set to an empty 
         string.  GETs and GETNEXTs on this variable return an empty string."
    DEFVAL { ''H }
    ::= { svcPEDiscoveryPolicyEntry 3 }

svcPEDiscoveryPolicyInterval  OBJECT-TYPE
    SYNTAX      Unsigned32 (1..30)
    UNITS       "minutes"
    MAX-ACCESS  read-create
    STATUS      current
    DESCRIPTION
        "The value of svcPEDiscoveryPolicyInterval specifies the polling
         interval for Radius PE discovery in minutes."
    DEFVAL { 5 }
    ::= { svcPEDiscoveryPolicyEntry 4 }

svcPEDiscoveryPolicyTimeout  OBJECT-TYPE
    SYNTAX      Unsigned32 (1..90)
    UNITS       "seconds"
    MAX-ACCESS  read-create
    STATUS      current
    DESCRIPTION
        "The value of svcPEDiscoveryPolicyTimeout specifies the number of 
         seconds to wait before timing out a RADIUS server."
    DEFVAL { 3 }
    ::= { svcPEDiscoveryPolicyEntry 5 }

-- ----------------------------------------
-- svcPEDiscoveryPolicyServerTable
-- ----------------------------------------
svcPEDiscPolServerTable OBJECT-TYPE
    SYNTAX      SEQUENCE OF SvcPEDiscPolServerEntry
    MAX-ACCESS  not-accessible
    STATUS      current
    DESCRIPTION
        "The svcPEDiscPolServerTable has an entry for each RADIUS server.
         The table can have up to a maximum of 5 entries."
::= { tmnxSvcObjs 23 }

svcPEDiscPolServerEntry OBJECT-TYPE
    SYNTAX      SvcPEDiscPolServerEntry
    MAX-ACCESS  not-accessible
    STATUS      current
    DESCRIPTION
        "svcPEDiscPolServerEntry is an entry (conceptual row) in the
         svcPEDiscPolServerTable. Each entry represents the configuration
         for a RADIUS server.

         Entries in this table can be created and deleted via SNMP SET
         operations to svcPEDiscPolServerRowStatus."
    INDEX {svcPEDiscPolServerIndex,
             IMPLIED svcPEDiscoveryPolicyName }
    ::= { svcPEDiscPolServerTable 1 }

SvcPEDiscPolServerEntry ::= SEQUENCE {
    svcPEDiscPolServerIndex           Unsigned32,
    svcPEDiscPolServerRowStatus       RowStatus,
    svcPEDiscPolServerAddressType     InetAddressType,
    svcPEDiscPolServerAddress         InetAddress,
    svcPEDiscPolServerSecret          OCTET STRING,
    svcPEDiscPolServerOperStatus      ServiceOperStatus,
    svcPEDiscPolServerPort            Unsigned32 
}

svcPEDiscPolServerIndex OBJECT-TYPE
    SYNTAX      Unsigned32 (1..5)
    MAX-ACCESS  not-accessible
    STATUS      current
    DESCRIPTION
        "The svcPEDiscPolServerIndex indicates the unique value which 
         identifies a specific radius server."
    ::= { svcPEDiscPolServerEntry 1 }

svcPEDiscPolServerRowStatus OBJECT-TYPE
    SYNTAX      RowStatus
    MAX-ACCESS  read-create
    STATUS      current
    DESCRIPTION
        "svcPEDiscPolServerRowStatus controls the creation and deletion
         of rows in the table.

         To create a row in the svcPEDiscPolServerTable,
         set svcPEDiscPolServerRowStatus to 'createAndGo'. All objects 
         except svcPEDiscPolServerSecret will take
         on default values and the agent will change svcPEDiscPolServerRowStatus
         to 'active'.  A value for svcPEDiscPolServerSecret must be always specified  
         or else the row creation will fail.

         To delete a row in the svcPEDiscPolServerTable, set
         tmnxRadiusServerRowStatus to 'delete'."
    ::= { svcPEDiscPolServerEntry 2 }

svcPEDiscPolServerAddressType OBJECT-TYPE
    SYNTAX      InetAddressType
    MAX-ACCESS  read-create
    STATUS      current
    DESCRIPTION
        "The value of svcPEDiscPolServerAddressType is used to configure 
         the address type of svcPEDiscPolServerAddress address."
    DEFVAL { unknown }
    ::= { svcPEDiscPolServerEntry 3 }

svcPEDiscPolServerAddress OBJECT-TYPE
    SYNTAX      InetAddress
    MAX-ACCESS  read-create
    STATUS      current
    DESCRIPTION
        "The value of svcPEDiscPolServerAddress is used to configure the
         IP address of the RADIUS server."
    DEFVAL { ''H }  
    ::= { svcPEDiscPolServerEntry 4 }

svcPEDiscPolServerSecret OBJECT-TYPE
    SYNTAX      OCTET STRING (SIZE(0..20))
    MAX-ACCESS  read-create
    STATUS      current
    DESCRIPTION
        "The svcPEDiscPolServerSecret is used to configure the secret key
         associated with the RADIUS server.  

         The value of svcPEDiscPolServerSecret cannot be set to an empty 
         string.  GETs and GETNEXTs on this variable return an empty string."
    ::= { svcPEDiscPolServerEntry 5 }

svcPEDiscPolServerOperStatus OBJECT-TYPE
    SYNTAX      ServiceOperStatus
    MAX-ACCESS  read-only
    STATUS      current
    DESCRIPTION
        "The svcPEDiscPolServerOperStatus indicates the current status 
         of the RADIUS server."
    ::= { svcPEDiscPolServerEntry 6 }

svcPEDiscPolServerPort  OBJECT-TYPE
    SYNTAX      Unsigned32 (1..65535)
    MAX-ACCESS  read-create
    STATUS      current
    DESCRIPTION
        "The svcPEDiscPolServerPort is used to configure the UDP port 
         number on which to contact the RADIUS server."
     DEFVAL { 1812 }
    ::= { svcPEDiscPolServerEntry 7 }

-- ------------------------------
-- Service Whole saler table
-- ------------------------------

svcWholesalerInfoTable OBJECT-TYPE
    SYNTAX      SEQUENCE OF SvcWholesalerInfoEntry
    MAX-ACCESS  not-accessible
    STATUS      current
    DESCRIPTION
        "The svcWholesalerInfoTable has an entry for each wholesaler service
         associated with a retailer service on this system."
    ::= { tmnxSvcObjs 24 }

svcWholesalerInfoEntry    OBJECT-TYPE
    SYNTAX      SvcWholesalerInfoEntry
    MAX-ACCESS  not-accessible
    STATUS      current
    DESCRIPTION
        "Each row entry represents the attributes of a wholesaler-retailer 
         pairing. Entries are created/destroyed when forwarding interfaces
         are defined."
    INDEX { svcId, svcWholesalerID }
    ::= { svcWholesalerInfoTable 1}

SvcWholesalerInfoEntry ::= SEQUENCE
    {
        svcWholesalerID                 TmnxServId,
        svcWholesalerNumStaticHosts     Unsigned32,
        svcWholesalerNumDynamicHosts    Unsigned32    
    }

svcWholesalerID        OBJECT-TYPE
    SYNTAX      TmnxServId
    MAX-ACCESS  not-accessible
    STATUS      current
    DESCRIPTION
        "The value of svcWholesalerID is used to specify the service ID of the
         wholesaler."
    ::= { svcWholesalerInfoEntry 1 }

svcWholesalerNumStaticHosts        OBJECT-TYPE
    SYNTAX      Unsigned32
    MAX-ACCESS  read-only
    STATUS      current
    DESCRIPTION
        "The value of svcWholesalerNumStaticHosts indicates the number of 
         static hosts in the wholesaler indicated by svcWholesalerID that
         belong to subnets of the retailer service."
    ::= { svcWholesalerInfoEntry 2 }

svcWholesalerNumDynamicHosts        OBJECT-TYPE
    SYNTAX      Unsigned32
    MAX-ACCESS  read-only
    STATUS      current
    DESCRIPTION
        "The value of svcWholesalerNumDynamicHosts indicates the number of 
         dynamic hosts in the wholesaler indicated by svcWholesalerID that
         belong to subnets of the retailer service."
    ::= { svcWholesalerInfoEntry 3 }

-- ----------------------------------------
-- svcDhcpLeaseStateActionTable
-- ----------------------------------------
svcDhcpLeaseStateActionTable OBJECT-TYPE
    SYNTAX          SEQUENCE OF SvcDhcpLeaseStateActionEntry
    MAX-ACCESS      not-accessible
    STATUS          current
    DESCRIPTION     "The svcDhcpLeaseStateActionTable augments the
                     svcDhcpLeaseStateTable.
                     The table allows the operator to perform actions on the
                     lease state."
    ::= { tmnxSvcObjs 25 }

svcDhcpLeaseStateActionEntry OBJECT-TYPE
    SYNTAX          SvcDhcpLeaseStateActionEntry
    MAX-ACCESS      not-accessible
    STATUS          current
    DESCRIPTION     "Each row entry contains parameters that allow to perform
                     an action on the corresponding lease-state."
    AUGMENTS        { svcDhcpLeaseStateEntry }
    ::= { svcDhcpLeaseStateActionTable 1 }

SvcDhcpLeaseStateActionEntry ::=
    SEQUENCE {
        svcDhcpLseStateForceRenew        TruthValue
    }

svcDhcpLseStateForceRenew OBJECT-TYPE
    SYNTAX          TruthValue
    MAX-ACCESS      read-write
    STATUS          current
    DESCRIPTION     "The value of svcDhcpLseStateForceRenew allows to force the
                     DHCP client to renew its lease.

                     When the value of this object is set to 'true', the system
                     will send a forcerenew DHCP message to the client.

                     GETs and GETNEXTs on this variable return false."
    DEFVAL          { false }
    ::= { svcDhcpLeaseStateActionEntry 1 }

--
--  Alcatel 7x50 SR series Service Itf DHCP6 msg type Stats Table
--
svcIfDHCP6MsgStatTable OBJECT-TYPE
    SYNTAX  SEQUENCE OF SvcIfDHCP6MsgStatEntry
    MAX-ACCESS  not-accessible
    STATUS      current
    DESCRIPTION
        "The vRtrDHCP6MsgStatTable has an entry for each interface defined
         in a service for which DHCP6 can be enabled."
    ::= { tmnxSvcObjs 26 }

svcIfDHCP6MsgStatEntry  OBJECT-TYPE
    SYNTAX      SvcIfDHCP6MsgStatEntry
    MAX-ACCESS  not-accessible
    STATUS      current
    DESCRIPTION
        "Each row entry represents a collection of counters for each DHCP6
         message type for an interface in a service.

        Entries cannot be created and deleted via SNMP SET operations."
    INDEX { svcId,
            iesIfIndex }
    ::= { svcIfDHCP6MsgStatTable 1 }

SvcIfDHCP6MsgStatEntry ::=
     SEQUENCE {
         svcIfDHCP6MsgStatsLstClrd  TimeStamp,
         svcIfDHCP6MsgStatsRcvd     Gauge32,
         svcIfDHCP6MsgStatsSent     Gauge32,
         svcIfDHCP6MsgStatsDropped  Gauge32
     }

svcIfDHCP6MsgStatsLstClrd  OBJECT-TYPE
    SYNTAX      TimeStamp
    MAX-ACCESS  read-only
    STATUS      current
    DESCRIPTION
        "The value of svcIfDHCP6MsgStatsLstClrd indicates the sysUpTime
         when the counters of this row were last reset. A value of zero for
         this object indicates that the counters have not been reset since the
         system has last been initialized." 
    ::= { svcIfDHCP6MsgStatEntry 1 }

svcIfDHCP6MsgStatsRcvd  OBJECT-TYPE
    SYNTAX      Gauge32
    MAX-ACCESS  read-only
    STATUS      current
    DESCRIPTION
        "The value of svcIfDHCP6MsgStatsRcvd indicates the number of
         DHCP6 packets were received on this service interface."
    ::= { svcIfDHCP6MsgStatEntry 2 }

svcIfDHCP6MsgStatsSent  OBJECT-TYPE
    SYNTAX      Gauge32
    MAX-ACCESS  read-only
    STATUS      current
    DESCRIPTION
        "The value of svcIfDHCP6MsgStatsSent indicates the number of
         DHCP6 packets were sent on this service interface."
    ::= { svcIfDHCP6MsgStatEntry 3 }

svcIfDHCP6MsgStatsDropped  OBJECT-TYPE
    SYNTAX      Gauge32
    MAX-ACCESS  read-only
    STATUS      current
    DESCRIPTION
        "The value of svcIfDHCP6MsgStatsDropped indicates the number of
         DHCP6 packets were dropped on this service interface."
    ::= { svcIfDHCP6MsgStatEntry 4 }

-- ----------------------------------------
-- TLS PBB Information Table
-- ----------------------------------------
svcTlsBackboneInfoTable OBJECT-TYPE
    SYNTAX          SEQUENCE OF SvcTlsBackboneInfoEntry
    MAX-ACCESS      not-accessible
    STATUS          current
    DESCRIPTION     "The svcTlsBackboneInfoTable augments the svcTlsInfoTable.
                     The table allows the operator to modify attributes of the
                     Provider Backbone Bridging feature."
    ::= { tmnxSvcObjs 27 }

svcTlsBackboneInfoEntry OBJECT-TYPE
    SYNTAX          SvcTlsBackboneInfoEntry
    MAX-ACCESS      not-accessible
    STATUS          current
    DESCRIPTION     "Each row entry contains objects that allows the
                     modification of the Provider Backbone Bridging feature
                     for a specific TLS service"
    AUGMENTS        { svcTlsInfoEntry }
    ::= { svcTlsBackboneInfoTable 1 }

SvcTlsBackboneInfoEntry ::=
    SEQUENCE {
        svcTlsBackboneSrcMac             MacAddress,
        svcTlsBackboneVplsSvcId          TmnxServId,
        svcTlsBackboneVplsSvcISID        SvcISID,
        svcTlsBackboneOperSrcMac         MacAddress,
        svcTlsBackboneOperVplsSvcISID    SvcISID,
        svcTlsBackboneLDPMacFlush        TruthValue,
        svcTlsBackboneVplsStp            TmnxEnabledDisabled
    }

svcTlsBackboneSrcMac OBJECT-TYPE
    SYNTAX          MacAddress
    MAX-ACCESS      read-write
    STATUS          current
    DESCRIPTION     "The value of svcTlsBackboneSrcMac specifies the Backbone
                     Source MAC-Address for Provider Backbone Bridging packets.
                     If not provisioned, it defaults to the loopback chassis
                     MAC-Address.

                     An inconsistentValue error is returned if an attempt
                     is made to set this object when the value of
                     svcVplsType is not 'bVpls'."
    DEFVAL { '000000000000'h }
    ::= { svcTlsBackboneInfoEntry 1 }

svcTlsBackboneVplsSvcId OBJECT-TYPE
    SYNTAX          TmnxServId
    MAX-ACCESS      read-write
    STATUS          current
    DESCRIPTION     "The value of svcTlsBackboneVplsSvcId specifies the
                     Backbone-VPLS service associated with this service.

                     An inconsistentValue error is returned if an attempt
                     is made to set this object when the value of
                     svcVplsType is not 'iVpls'.
                     
                     Setting the value of this object to its default
                     value will also set the value of
                     svcTlsBackboneVplsStp to its default value."
    DEFVAL          { 0 }
    ::= { svcTlsBackboneInfoEntry 2 }

svcTlsBackboneVplsSvcISID OBJECT-TYPE
    SYNTAX          SvcISID
    MAX-ACCESS      read-write
    STATUS          current
    DESCRIPTION     "The value of the object svcTlsBackboneVplsSvcISID specifies
                     a 24 bit (0..16777215) service instance identifier for
                     this service. As part of the Provider Backbone Bridging
                     frames, it is used at the destination PE as a
                     demultiplexor field.

                     The default value of -1 is used to indicate the value of
                     this object is un-specified.  
                     
                     This object must be set along with svcTlsBackboneVplsSvcId.
                     An inconsistentValue error is returned if an attempt
                     is made to set this object when the value of
                     svcVplsType is not 'iVpls'."
    DEFVAL          { -1 }
    ::= { svcTlsBackboneInfoEntry 3 }

svcTlsBackboneOperSrcMac OBJECT-TYPE
    SYNTAX          MacAddress
    MAX-ACCESS      read-only
    STATUS          current
    DESCRIPTION     "The value of svcTlsBackboneOperSrcMac indicates the
                     operational Backbone Source MAC-Address for Provider
                     Backbone Bridging packets."
    ::= { svcTlsBackboneInfoEntry 4 }

svcTlsBackboneOperVplsSvcISID OBJECT-TYPE
    SYNTAX          SvcISID
    MAX-ACCESS      read-only
    STATUS          current
    DESCRIPTION     "The value of svcTlsBackboneOperVplsSvcISID indicates
                     operational value of service instance identifier used for
                     this service. As part of the Provider Backbone Bridging
                     frames, it is used at the destination PE as a
                     demultiplexor field."
    ::= { svcTlsBackboneInfoEntry 5 }

svcTlsBackboneLDPMacFlush OBJECT-TYPE
    SYNTAX          TruthValue
    MAX-ACCESS      read-write
    STATUS          current
    DESCRIPTION     "The value of svcTlsBackboneLDPMacFlush specifies whether
                     'LDP MAC withdraw all from me' message received in the
                     'iVpls' domain should attempt to generate a new 'LDP MAC
                     withdraw all from me' message in the 'bVpls' domain.
                     Generation of the 'LDP MAC withdraw all from me'
                     message is still constrained by the svcTlsMacFlushOnFail
                     value in the 'bVpls'.

                     An inconsistentValue error is returned if an attempt
                     is made to set this object when the value of
                     svcVplsType is not 'iVpls'."
    DEFVAL          { false }
    ::= { svcTlsBackboneInfoEntry 6 }

svcTlsBackboneVplsStp OBJECT-TYPE
    SYNTAX          TmnxEnabledDisabled
    MAX-ACCESS      read-write
    STATUS          current
    DESCRIPTION     "The value of svcTlsBackboneVplsStp specifies whether
                     STP is enabled on the Backbone VPLS specified by
                     svcTlsBackboneVplsSvcId.

                     An inconsistentValue error is returned if an attempt
                     is made to set this object when the value of
                     svcVplsType is not 'iVpls' or if an attempt is made
                     to set this object to enable when the value of 
                     svcTlsBackboneVplsSvcId is set to the default.
                     
                     The value of this object is set to disable
                     when the value of svcTlsBackboneVplsSvcId is set to
                     default."
    DEFVAL          { disabled }
    ::= { svcTlsBackboneInfoEntry 7 }

-- ------------------------------------
-- TLS MFIB Table
-- ------------------------------------
tlsMFibTable OBJECT-TYPE
    SYNTAX          SEQUENCE OF TlsMFibEntry
    MAX-ACCESS      not-accessible
    STATUS          current
    DESCRIPTION     "tlsMFibTable contains the Multicast FIB for this Tls."
    ::= { tmnxSvcObjs 28 }

tlsMFibEntry OBJECT-TYPE
    SYNTAX          TlsMFibEntry
    MAX-ACCESS      not-accessible
    STATUS          current
    DESCRIPTION     "An entry in the tlsMFibTable. Each entry indicates
                     whether  traffic from a certain source to a certain
                     multicast destination (group) needs to be forwarded or
                     blocked on the indicated SAP/SDP."
    INDEX           { svcId,
                      tlsMFibEntryType,
                      tlsMFibGrpMacAddr,
                      tlsMFibGrpInetAddrType,
                      tlsMFibGrpInetAddr,
                      tlsMFibSrcInetAddrType,
                      tlsMFibSrcInetAddr,
                      tlsMFibLocale,
                      tlsMFibPortId,
                      tlsMFibEncapValue,
                      tlsMFibSdpId,
                      tlsMFibVcId }
    ::= { tlsMFibTable 1 }

TlsMFibEntry ::=
    SEQUENCE {
        tlsMFibEntryType            INTEGER,
        tlsMFibGrpMacAddr           MacAddress,
        tlsMFibGrpInetAddrType      InetAddressType,
        tlsMFibGrpInetAddr          InetAddress,
        tlsMFibSrcInetAddrType      InetAddressType,
        tlsMFibSrcInetAddr          InetAddress,
        tlsMFibLocale               MfibLocation,
        tlsMFibPortId               TmnxPortID,
        tlsMFibEncapValue           TmnxEncapVal,
        tlsMFibSdpId                SdpId,
        tlsMFibVcId                 Unsigned32,
        tlsMFibFwdOrBlk             MfibGrpSrcFwdOrBlk,
        tlsMFibSvcId                TmnxServId
    }

tlsMFibEntryType OBJECT-TYPE
    SYNTAX          INTEGER {
                        ipBased  (1),
                        macBased (2)
                    }
    MAX-ACCESS      not-accessible
    STATUS          current
    DESCRIPTION     "The value of the object tlsMFibEntryType indicates
                     the type of this tlsMFibEntry. 

                     - macBased: entry used for macBased multicast, as for
                                 MLD-snooping and 802.1ak MMRP.
                     - ipBased:  entry used for ip_based multicast, as for
                                 IGMP-snooping and PIM-snooping."
    ::= { tlsMFibEntry 1 }

tlsMFibGrpMacAddr OBJECT-TYPE
    SYNTAX          MacAddress
    MAX-ACCESS      not-accessible
    STATUS          current
    DESCRIPTION     "The value of the object tlsMFibGrpMacAddr indicates the
                     MAC address for which this table entry contains
                     information.
                     
                     This value is only meaningful if the value of
                     tlsMFibEntryType is 'macBased (2)'."
    ::= { tlsMFibEntry 2 }

tlsMFibGrpInetAddrType OBJECT-TYPE
    SYNTAX          InetAddressType
    MAX-ACCESS      not-accessible
    STATUS          current
    DESCRIPTION     "The value of the object tlsMFibGrpInetAddrType indicates
                     the type of tlsMFibGrpInetAddr."
    ::= { tlsMFibEntry 3 }

tlsMFibGrpInetAddr OBJECT-TYPE
    SYNTAX          InetAddress (SIZE(0|4|16))
    MAX-ACCESS      not-accessible
    STATUS          current
    DESCRIPTION     "The value of the object tlsMFibGrpInetAddr indicates
                     the multicast destination IP address for which this table
                     entry contains information."
    ::= { tlsMFibEntry 4 }

tlsMFibSrcInetAddrType OBJECT-TYPE
    SYNTAX          InetAddressType
    MAX-ACCESS      not-accessible
    STATUS          current
    DESCRIPTION     "The value of tlsMFibSrcInetAddrType indicates the type
                     of tlsMFibSrcInetAddr."
    ::= { tlsMFibEntry 5 }

tlsMFibSrcInetAddr OBJECT-TYPE
    SYNTAX          InetAddress (SIZE(0|4|16))
    MAX-ACCESS      not-accessible
    STATUS          current
    DESCRIPTION     "The value of tlsMFibSrcInetAddr indicates the unicast
                     source IP address for which this table entry contains
                     information."
    ::= { tlsMFibEntry 6 }

tlsMFibLocale OBJECT-TYPE
    SYNTAX          MfibLocation
    MAX-ACCESS      not-accessible
    STATUS          current
    DESCRIPTION     "The value of tlsMFibLocale indicates if the information in
                     this entry pertains to a 'sap' or to an 'sdp'."
    ::= { tlsMFibEntry 7 }

tlsMFibPortId OBJECT-TYPE
    SYNTAX          TmnxPortID
    MAX-ACCESS      not-accessible
    STATUS          current
    DESCRIPTION     "The value of tlsMFibPortId indicates, together with the
                     object tlsMFibEncapValue, the SAP for which this entry
                     contains information.
                     
                     This value of this object is only meaningful when the
                     value of tlsMFibLocale is 'sap'. Otherwise it contains
                     the value 0."
    ::= { tlsMFibEntry 8 }

tlsMFibEncapValue OBJECT-TYPE
    SYNTAX          TmnxEncapVal
    MAX-ACCESS      not-accessible
    STATUS          current
    DESCRIPTION     "The value of tlsMFibEncapValue indicates, together with
                     the object tlsMFibPortId, the SAP for which this entry
                     contains information.

                     This value of this object is only meaningful when the
                     value of tlsMFibLocale is 'sap'. Otherwise it contains
                     the value 0."
    ::= { tlsMFibEntry 9 }

tlsMFibSdpId OBJECT-TYPE
    SYNTAX          SdpId
    MAX-ACCESS      not-accessible
    STATUS          current
    DESCRIPTION     "The value of tlsMFibSdpId indicates, together with
                     the object tlsMFibVcId, the SDP Binding for which this
                     entry contains information.

                     This value of this object is only meaningful when the
                     value of tlsMFibLocale is 'sdp'. Otherwise it contains
                     the value 0."
    ::= { tlsMFibEntry 10 }

tlsMFibVcId OBJECT-TYPE
    SYNTAX          Unsigned32
    MAX-ACCESS      not-accessible
    STATUS          current
    DESCRIPTION     " The value of tlsMFibVcId indicates, together with
                     the object tlsMFibSdpId, the SDP Binding for which this
                     entry contains information.

                     This value of this object is only meaningful when the
                     value of tlsMFibLocale is 'sdp'. Otherwise it contains
                     the value 0."
    ::= { tlsMFibEntry 11 }

tlsMFibFwdOrBlk OBJECT-TYPE
    SYNTAX          MfibGrpSrcFwdOrBlk
    MAX-ACCESS      read-only
    STATUS          current
    DESCRIPTION     "The value of tlsMFibFwdOrBlk indicates if traffic for the
                     indicated (S,G) pair will be blocked or forwarded on the
                     indicated SAP or SDP."
    ::= { tlsMFibEntry 12 }

tlsMFibSvcId OBJECT-TYPE
    SYNTAX          TmnxServId
    MAX-ACCESS      read-only
    STATUS          current
    DESCRIPTION     "The value of tlsMFibSvcId indicates the TLS service
                     to which the indicated SAP or SDP belongs."
    ::= { tlsMFibEntry 13 }

-- ----------------------------------------
-- TLS MFIB Statistics Table
-- ----------------------------------------
tlsMFibStatsTable OBJECT-TYPE
    SYNTAX          SEQUENCE OF TlsMFibStatsEntry
    MAX-ACCESS      not-accessible
    STATUS          current
    DESCRIPTION     "tlsMFibStatsTable contains statistics for the
                     entries in the IPv4 Multicast FIB for this Tls. These
                     statistics are collected by the forwarding engine."
    ::= { tmnxSvcObjs 29 }

tlsMFibStatsEntry OBJECT-TYPE
    SYNTAX          TlsMFibStatsEntry
    MAX-ACCESS      not-accessible
    STATUS          current
    DESCRIPTION     "An entry in the tlsMFibStatsTable."
    INDEX           { svcId,
                      tlsMFibStatsEntryType,
                      tlsMFibStatsGrpMacAddr,
                      tlsMFibStatsGrpInetAddrType,
                      tlsMFibStatsGrpInetAddr,
                      tlsMFibStatsSrcInetAddrType,
                      tlsMFibStatsSrcInetAddr }
    ::= { tlsMFibStatsTable 1 }

TlsMFibStatsEntry ::=
    SEQUENCE {
        tlsMFibStatsEntryType        INTEGER,
        tlsMFibStatsGrpMacAddr       MacAddress,
        tlsMFibStatsGrpInetAddrType  InetAddressType,
        tlsMFibStatsGrpInetAddr      InetAddress,
        tlsMFibStatsSrcInetAddrType  InetAddressType,
        tlsMFibStatsSrcInetAddr      InetAddress,
        tlsMFibStatsForwardedPkts    Counter64,
        tlsMFibStatsForwardedOctets  Counter64
    }

tlsMFibStatsEntryType OBJECT-TYPE
    SYNTAX          INTEGER {
                        ipBased  (1),
                        macBased (2)
                    }
    MAX-ACCESS      not-accessible
    STATUS          current
    DESCRIPTION     "The value of the object tlsMFibStatsEntryType indicates
                     the type of this tlsMFibStatsEntry.

                     - macBased: entry used for macBased multicast, as for
                                 MLD-snooping and 802.1ak MMRP.
                     - ipBased:  entry used for ip_based multicast, as for
                                 IGMP-snooping and PIM-snooping."
    ::= { tlsMFibStatsEntry 1 }

tlsMFibStatsGrpMacAddr OBJECT-TYPE
    SYNTAX          MacAddress
    MAX-ACCESS      not-accessible
    STATUS          current
    DESCRIPTION     "The value of tlsMFibStatsGrpMacAddr indicates the
                     MAC address for which this table entry contains information.

                     This value is only meaningful if the value of
                     tlsMFibStatsEntryType is 'macBased (2)'."
    ::= { tlsMFibStatsEntry 2 }

tlsMFibStatsGrpInetAddrType OBJECT-TYPE
    SYNTAX          InetAddressType
    MAX-ACCESS      not-accessible
    STATUS          current
    DESCRIPTION     "The value of tlsMFibStatsGrpInetAddrType indicates
                     the type of tlsMFibStatsGrpInetAddr."
    ::= { tlsMFibStatsEntry 3 }

tlsMFibStatsGrpInetAddr OBJECT-TYPE
    SYNTAX          InetAddress (SIZE(0|4|16))
    MAX-ACCESS      not-accessible
    STATUS          current
    DESCRIPTION     "The value of tlsMFibStatsGrpInetAddr indicates
                     the multicast destination IP address for which this table
                     entry contains information."
    ::= { tlsMFibStatsEntry 4 }

tlsMFibStatsSrcInetAddrType OBJECT-TYPE
    SYNTAX          InetAddressType
    MAX-ACCESS      not-accessible
    STATUS          current
    DESCRIPTION     "The value of tlsMFibStatsSrcInetAddrType indicates
                     the type of tlsMFibStatsSrcInetAddr."
    ::= { tlsMFibStatsEntry 5 }

tlsMFibStatsSrcInetAddr OBJECT-TYPE
    SYNTAX          InetAddress (SIZE(0|4|16))
    MAX-ACCESS      not-accessible
    STATUS          current
    DESCRIPTION     "The value of tlsMFibStatsSrcInetAddr indicates the unicast
                     source IP address for which this table entry contains
                     information."
    ::= { tlsMFibStatsEntry 6 }

tlsMFibStatsForwardedPkts OBJECT-TYPE
    SYNTAX          Counter64
    MAX-ACCESS      read-only
    STATUS          current
    DESCRIPTION     "The value of tlsMFibStatsForwardedPkts indicates
                     the number of multicast packets that were forwarded
                     to the SAPs and SDPs listed in the tlsMFibInfoTable."
    ::= { tlsMFibStatsEntry 7 }

tlsMFibStatsForwardedOctets OBJECT-TYPE
    SYNTAX          Counter64
    MAX-ACCESS      read-only
    STATUS          current
    DESCRIPTION     "The value of tlsMFibStatsForwardedOctets indicates
                     the number of octets that were forwarded to the SAPs
                     and SDPs listed in the tlsMFibInfoTable."
    ::= { tlsMFibStatsEntry 8 }

-- ----------------------------------------
-- TLS BGP Auto-Discovery Table
-- ----------------------------------------

svcTlsBgpADTableLastChanged  OBJECT-TYPE
    SYNTAX          TimeStamp
    MAX-ACCESS      read-only
    STATUS          current
    DESCRIPTION     "The value of svcTlsBgpADTableLastChanged indicates the
                     sysUpTime at the time of the last modification
                     of svcTlsBgpADTable.

                     If no changes were made to the entry since the last
                     re-initialization of the local network management subsystem,
                     then this object contains a zero value."
    ::= { tmnxSvcObjs 30 }

svcTlsBgpADTable OBJECT-TYPE
    SYNTAX          SEQUENCE OF SvcTlsBgpADEntry
    MAX-ACCESS      not-accessible
    STATUS          current
    DESCRIPTION     "svcTlsBgpADTable contains entries for BGP Auto-Discovery
                     in a VPLS service context." 
    ::= { tmnxSvcObjs 31 }

svcTlsBgpADEntry    OBJECT-TYPE
    SYNTAX          SvcTlsBgpADEntry
    MAX-ACCESS      not-accessible
    STATUS          current
    DESCRIPTION     "A BGP Auto-Discovery entry in the svcTlsBgpADTable."
    INDEX           { svcId }
    ::= { svcTlsBgpADTable 1}

SvcTlsBgpADEntry ::=    SEQUENCE {
    svcTlsBgpADRowStatus           RowStatus,
    svcTlsBgpADLastChanged         TimeStamp,
    svcTlsBgpADVplsId              TmnxVPNRouteDistinguisher,
    svcTlsBgpADVsiPrefix           Unsigned32,
    svcTlsBgpADVsiRD               TmnxVPNRouteDistinguisher,
    svcTlsBgpADExportRteTarget     TNamedItemOrEmpty,
    svcTlsBgpADVsiExportPolicy1    TPolicyStatementNameOrEmpty,
    svcTlsBgpADVsiExportPolicy2    TPolicyStatementNameOrEmpty,
    svcTlsBgpADVsiExportPolicy3    TPolicyStatementNameOrEmpty,
    svcTlsBgpADVsiExportPolicy4    TPolicyStatementNameOrEmpty,
    svcTlsBgpADVsiExportPolicy5    TPolicyStatementNameOrEmpty,
    svcTlsBgpADImportRteTarget     TNamedItemOrEmpty,
    svcTlsBgpADVsiImportPolicy1    TPolicyStatementNameOrEmpty,
    svcTlsBgpADVsiImportPolicy2    TPolicyStatementNameOrEmpty,
    svcTlsBgpADVsiImportPolicy3    TPolicyStatementNameOrEmpty,
    svcTlsBgpADVsiImportPolicy4    TPolicyStatementNameOrEmpty,
    svcTlsBgpADVsiImportPolicy5    TPolicyStatementNameOrEmpty,
    svcTlsBgpADAdminStatus         TmnxEnabledDisabled
}

svcTlsBgpADRowStatus        OBJECT-TYPE
    SYNTAX          RowStatus
    MAX-ACCESS      read-create
    STATUS          current
    DESCRIPTION     "The value of svcTlsBgpADRowStatus is used for the
                     creation and deletion of BGP Auto-Discovery
                     context in a VPLS service."
    ::= { svcTlsBgpADEntry 1 }

svcTlsBgpADLastChanged        OBJECT-TYPE
    SYNTAX          TimeStamp
    MAX-ACCESS      read-only
    STATUS          current
    DESCRIPTION     "The value of svcTlsBgpADLastChanged indicates the 
                     sysUpTime at the time of the last modification of
                     this entry.
                     
                     If no changes were made to the entry since the last 
                     re-initialization of the local network management 
                     subsystem, then this object contains a zero value."
    ::= { svcTlsBgpADEntry 2 }

svcTlsBgpADVplsId        OBJECT-TYPE
    SYNTAX          TmnxVPNRouteDistinguisher
    MAX-ACCESS      read-create
    STATUS          current
    DESCRIPTION     "The value of svcTlsBgpADVplsId specifies the globally
                     unique VPLS-id for BGP Auto-Discovery in this VPLS
                     service.

                     The value of svcTlsBgpADAdminStatus cannot be 'enabled'
                     until a VPLS-id has been assigned which is not all zeros."
    DEFVAL          { '0000000000000000'H }
    ::= { svcTlsBgpADEntry 3 }

svcTlsBgpADVsiPrefix OBJECT-TYPE
    SYNTAX          Unsigned32
    MAX-ACCESS      read-create
    STATUS          current
    DESCRIPTION     "The value of svcTlsBgpADVsiPrefix specifies the
                     low-order 4 bytes used to compose the Virtual Switch
                     Instance identifier (VSI-id) to use for NLRI in BGP
                     Auto-Discovery in this VPLS service.

                     If the value of svcTlsBgpADVsiPrefix is 0, the
                     system IP address will be used."
    DEFVAL          { 0 }
    ::= { svcTlsBgpADEntry 4 }

svcTlsBgpADVsiRD     OBJECT-TYPE
    SYNTAX          TmnxVPNRouteDistinguisher
    MAX-ACCESS      read-create
    STATUS          current
    DESCRIPTION     "The value of svcTlsBgpADVsiRD specifies the high-order
                     6 bytes used to compose the Virtual Switch Instance
                     identifier (VSI-id) to use for NLRI in BGP Auto-Discovery
                     in this VPLS service.

                     If the value of svcTlsBgpADVsiRD is 0x0000000000000000,
                     the lower 6 bytes of the VPLS-id, as specified by
                     svcTlsBgpADVplsId, will be used."
    DEFVAL          { '0000000000000000'H }
    ::= { svcTlsBgpADEntry 5 }

svcTlsBgpADExportRteTarget       OBJECT-TYPE
    SYNTAX          TNamedItemOrEmpty
    MAX-ACCESS      read-create
    STATUS          current
    DESCRIPTION     "The value of svcTlsBgpADExportRteTarget specifies the
                     extended community name for the default export policy
                     to use for BGP Auto-Discovery in this VPLS service.

                     This object cannot be set to a non-empty if
                     svcTlsBgpADExportRteTarget has a non-empty value, 
                     otherwise an 'inconsistentValue' error will be
                     returned."
    DEFVAL          { "" }
    ::= { svcTlsBgpADEntry 6 }

svcTlsBgpADVsiExportPolicy1  OBJECT-TYPE
    SYNTAX          TPolicyStatementNameOrEmpty
    MAX-ACCESS      read-create
    STATUS          current
    DESCRIPTION    "The value of svcTlsBgpADVsiExportPolicy1 specifies the
                    name of the first VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 7 }

svcTlsBgpADVsiExportPolicy2  OBJECT-TYPE
    SYNTAX          TPolicyStatementNameOrEmpty
    MAX-ACCESS      read-create
    STATUS          current
    DESCRIPTION    "The value of svcTlsBgpADVsiExportPolicy2 specifies the
                    name of the second VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 8 }

svcTlsBgpADVsiExportPolicy3  OBJECT-TYPE
    SYNTAX          TPolicyStatementNameOrEmpty
    MAX-ACCESS      read-create
    STATUS          current
    DESCRIPTION    "The value of svcTlsBgpADVsiExportPolicy3 specifies the
                    name of the third VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 9 }

svcTlsBgpADVsiExportPolicy4  OBJECT-TYPE
    SYNTAX          TPolicyStatementNameOrEmpty
    MAX-ACCESS      read-create
    STATUS          current
    DESCRIPTION    "The value of svcTlsBgpADVsiExportPolicy4 specifies the
                    name of the forth VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 10 }

svcTlsBgpADVsiExportPolicy5  OBJECT-TYPE
    SYNTAX          TPolicyStatementNameOrEmpty
    MAX-ACCESS      read-create
    STATUS          current
    DESCRIPTION    "The value of svcTlsBgpADVsiExportPolicy5 specifies the
                    name of the fifth VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 11 }

svcTlsBgpADImportRteTarget       OBJECT-TYPE
    SYNTAX          TNamedItemOrEmpty
    MAX-ACCESS      read-create
    STATUS          current
    DESCRIPTION     "The value of svcTlsBgpADImportRteTarget specifies the
                     extended community name for the default import policy
                     to use for BGP Auto-Discovery in this VPLS service.

                     This object cannot be set to a non-empty if
                     svcTlsBgpADImportRteTarget has a non-empty value, 
                     otherwise an 'inconsistentValue' error will be
                     returned."
    DEFVAL          { "" }
    ::= { svcTlsBgpADEntry 12 }

svcTlsBgpADVsiImportPolicy1  OBJECT-TYPE
    SYNTAX          TPolicyStatementNameOrEmpty
    MAX-ACCESS      read-create
    STATUS          current
    DESCRIPTION    "The value of svcTlsBgpADVsiImportPolicy1 specifies the
                    name of the first VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 13 }

svcTlsBgpADVsiImportPolicy2  OBJECT-TYPE
    SYNTAX          TPolicyStatementNameOrEmpty
    MAX-ACCESS      read-create
    STATUS          current
    DESCRIPTION    "The value of svcTlsBgpADVsiImportPolicy2 specifies the
                    name of the second VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 14 }

svcTlsBgpADVsiImportPolicy3  OBJECT-TYPE
    SYNTAX          TPolicyStatementNameOrEmpty
    MAX-ACCESS      read-create
    STATUS          current
    DESCRIPTION    "The value of svcTlsBgpADVsiImportPolicy3 specifies the
                    name of the third VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 15 }

svcTlsBgpADVsiImportPolicy4  OBJECT-TYPE
    SYNTAX          TPolicyStatementNameOrEmpty
    MAX-ACCESS      read-create
    STATUS          current
    DESCRIPTION    "The value of svcTlsBgpADVsiImportPolicy4 specifies the
                    name of the forth VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 16 }

svcTlsBgpADVsiImportPolicy5  OBJECT-TYPE
    SYNTAX          TPolicyStatementNameOrEmpty
    MAX-ACCESS      read-create
    STATUS          current
    DESCRIPTION    "The value of svcTlsBgpADVsiImportPolicy5 specifies the
                    name of the fifth VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpADEntry 17 }

svcTlsBgpADAdminStatus        OBJECT-TYPE
    SYNTAX          TmnxEnabledDisabled
    MAX-ACCESS      read-create
    STATUS          current
    DESCRIPTION     "The value of svcTlsBgpADAdminStatus specifies the desired
                     administrative state for BGP Auto-Discovery in this VPLS
                     service."
    DEFVAL          { disabled }
    ::= { svcTlsBgpADEntry 18 }

-- ----------------------------------------
-- PIPE Service Table
-- ----------------------------------------
svcEpipePbbTableLastChanged  OBJECT-TYPE
    SYNTAX          TimeStamp
    MAX-ACCESS      read-only
    STATUS          current
    DESCRIPTION     "The value of svcEpipePbbTableLastChanged indicates the
                     sysUpTime at the time of the last modification of
                     svcEpipePbbTable.

                     If no changes were made to the entry since the last
                     re-initialization of the local network management subsystem,
                     then this object contains a zero value."
    ::= { tmnxSvcObjs 36 }

svcEpipePbbTable OBJECT-TYPE
    SYNTAX          SEQUENCE OF SvcEpipePbbEntry
    MAX-ACCESS      not-accessible
    STATUS          current
    DESCRIPTION     "The svcEpipePbbTable contains objects related to Provider
                     Backbone Bridging (PBB) feature as relates to 'epipe'
                     services.
                     
                     Entries are created and destroyed using svcEpipePbbRowStatus
                     object."
    ::= { tmnxSvcObjs 37 }

svcEpipePbbEntry OBJECT-TYPE
    SYNTAX          SvcEpipePbbEntry
    MAX-ACCESS      not-accessible
    STATUS          current
    DESCRIPTION     "Each row entry contains objects that allows the
                     modification of the PBB objects for an 'epipe' service."
    INDEX        { svcId }
    ::= { svcEpipePbbTable 1 }

SvcEpipePbbEntry ::=
    SEQUENCE {
        svcEpipePbbRowStatus               RowStatus,
        svcEpipePbbLastChngd               TimeStamp,
        svcEpipePbbBvplsSvcId              TmnxServId,
        svcEpipePbbBvplsDstMac             MacAddress,
        svcEpipePbbSvcISID                 SvcISID
    }

svcEpipePbbRowStatus OBJECT-TYPE
    SYNTAX          RowStatus
    MAX-ACCESS      read-create
    STATUS          current
    DESCRIPTION     "The value of svcEpipePbbRowStatus is used for the
                     creation and deletion of Provider Backbone Bridging
                     information in a EPIPE service.

                     To create an entry in the table, svcEpipePbbBvplsSvcId,
                     svcEpipePbbBvplsDstMac, svcEpipePbbSvcISID objects
                     must be set."
    ::= { svcEpipePbbEntry 1 }

svcEpipePbbLastChngd        OBJECT-TYPE
    SYNTAX          TimeStamp
    MAX-ACCESS      read-only
    STATUS          current
    DESCRIPTION     "The value of svcEpipePbbLastChngd indicates the sysUpTime at
                     the time of the last modification of this entry.
                     
                     If no changes were made to the entry since the last 
                     re-initialization of the local network management 
                     subsystem, then this object contains a zero value."
    ::= { svcEpipePbbEntry 2 }

svcEpipePbbBvplsSvcId OBJECT-TYPE
    SYNTAX          TmnxServId
    MAX-ACCESS      read-create
    STATUS          current
    DESCRIPTION     "The value of svcEpipePbbBvplsSvcId specifies the
                     Backbone-VPLS service for the PBB tunnel associated with
                     this service.

                     This object must be set at the creation time and can not
                     be modified later."
    ::= { svcEpipePbbEntry 3 }

svcEpipePbbBvplsDstMac OBJECT-TYPE
    SYNTAX          MacAddress
    MAX-ACCESS      read-create
    STATUS          current
    DESCRIPTION     "The value of svcEpipePbbBvplsDstMac specifies the Backbone
                     Destination MAC-Address for Provider Backbone Bridging
                     packets.

                     This object must be set along with svcEpipePbbBvplsSvcId."
    ::= { svcEpipePbbEntry 4 }

svcEpipePbbSvcISID OBJECT-TYPE
    SYNTAX          SvcISID
    MAX-ACCESS      read-create
    STATUS          current
    DESCRIPTION     "The value of the object svcEpipePbbSvcISID specifies
                     a 24 bit (0..16777215) service instance identifier for the
                     PBB tunnel associated with this service.
                     
                     As part of the Provider Backbone Bridging frames, it is
                     used at the destination PE as a demultiplexor field.

                     This object must be set along with svcEpipePbbBvplsSvcId."
    ::= { svcEpipePbbEntry 5 }

-- -------------------------------------
-- TLS PIP uplink Table
-- -------------------------------------
tlsPipInfoTable OBJECT-TYPE
    SYNTAX          SEQUENCE OF TlsPipInfoEntry
    MAX-ACCESS      not-accessible
    STATUS          current
    DESCRIPTION
        "A table that contains TLS PIP (Provider Internal Port) uplink
        information. PIP is the virtual link between I and B components of PBB
        (Provider Backbone Bridging) model. I component refers to a service
        with svcVplsType set to 'iVpls (3)' and B component refers to a service
        with svcVplsType set to 'bVpls (2)'. When any form of STP is enabled in
        the iVpls domain, the PIP uplink is modeled as a regular STP port."
    ::= { tmnxSvcObjs 40 }

tlsPipInfoEntry OBJECT-TYPE
    SYNTAX          TlsPipInfoEntry
    MAX-ACCESS      not-accessible
    STATUS          current
    DESCRIPTION     "TLS specific information about PIP uplink."
    INDEX           { svcId }
    ::= { tlsPipInfoTable 1 }

TlsPipInfoEntry ::=
    SEQUENCE {
        tlsPipStpPortState              TStpPortState,
        tlsPipStpPortRole               StpPortRole,
        tlsPipStpDesignatedBridge       BridgeId,
        tlsPipStpDesignatedPort         Integer32,
        tlsPipStpException              StpExceptionCondition,
        tlsPipStpForwardTransitions     Counter32,
        tlsPipStpInConfigBpdus          Counter32,
        tlsPipStpInTcnBpdus             Counter32,
        tlsPipStpInRstBpdus             Counter32,
        tlsPipStpInMstBpdus             Counter32,
        tlsPipStpInBadBpdus             Counter32,
        tlsPipStpOutConfigBpdus         Counter32,
        tlsPipStpOutTcnBpdus            Counter32,
        tlsPipStpOutRstBpdus            Counter32,
        tlsPipStpOutMstBpdus            Counter32,
        tlsPipStpOperStatus             ServiceOperStatus,
        tlsPipStpMvplsPruneState        MvplsPruneState,
        tlsPipStpOperProtocol           StpProtocol,
        tlsPipStpPortNum                Unsigned32
    }

tlsPipStpPortState OBJECT-TYPE
    SYNTAX          TStpPortState
    MAX-ACCESS      read-only
    STATUS          current
    DESCRIPTION
        "The value of tlsPipStpPortState indicates the PIP uplink's current
        state as defined by application of the Spanning Tree Protocol. This
        state controls what action PIP uplink takes on reception of a frame.
        If the bridge has detected a port that is malfunctioning it will
        place that port into the 'broken (6)' state."
    ::= { tlsPipInfoEntry 1 }

tlsPipStpPortRole OBJECT-TYPE
    SYNTAX          StpPortRole
    MAX-ACCESS      read-only
    STATUS          current
    DESCRIPTION
        "The value of tlsPipStpPortRole indicates the current role of the PIP
        uplink as defined by the Rapid Spanning Tree Protocol."
    ::= { tlsPipInfoEntry 2 }

tlsPipStpDesignatedBridge OBJECT-TYPE
    SYNTAX          BridgeId
    MAX-ACCESS      read-only
    STATUS          current
    DESCRIPTION
        "The value of tlsPipStpDesignatedBridge indicates the Bridge Identifier
        of the bridge which this PIP uplink considers to be the Designated
        Bridge for this port's segment."
    ::= { tlsPipInfoEntry 3 }

tlsPipStpDesignatedPort OBJECT-TYPE
    SYNTAX          Integer32
    MAX-ACCESS      read-only
    STATUS          current
    DESCRIPTION
        "The value of tlsPipStpDesignatedPort indicates the Port Identifier of
        the port on the Designated Bridge for this port's segment."
    ::= { tlsPipInfoEntry 4 }

tlsPipStpException OBJECT-TYPE
    SYNTAX          StpExceptionCondition
    MAX-ACCESS      read-only
    STATUS          current
    DESCRIPTION     "The value of the object tlsPipStpException indicates
                     whether an STP exception condition is present on this
                     Pip.
                     - none : no exception condition found.
                     - oneWayCommuniation : The neighbor RSTP peer on this link
                                            is not able to detect our presence.
                     - downstreamLoopDetected :A loop is detected on this link."
    ::= { tlsPipInfoEntry 5 }

tlsPipStpForwardTransitions OBJECT-TYPE
    SYNTAX          Counter32
    MAX-ACCESS      read-only
    STATUS          current
    DESCRIPTION     "The value of the object tlsPipStpForwardTransitions
                     indicates the number of times this port has transitioned
                     from the Learning state to the Forwarding state."
    ::= { tlsPipInfoEntry 6 }

tlsPipStpInConfigBpdus OBJECT-TYPE
    SYNTAX          Counter32
    MAX-ACCESS      read-only
    STATUS          current
    DESCRIPTION     "The value of the object tlsPipStpInConfigBpdus indicates
                     the number of Configuration BPDUs received on this
                     PIP uplink."
    ::= { tlsPipInfoEntry 7 }

tlsPipStpInTcnBpdus OBJECT-TYPE
    SYNTAX          Counter32
    MAX-ACCESS      read-only
    STATUS          current
    DESCRIPTION     "The value of the object  tlsPipStpInTcnBpdus indicates the
                     number of Topology Change Notification BPDUs received on
                     this PIP uplink."
    ::= { tlsPipInfoEntry 8 }

tlsPipStpInRstBpdus OBJECT-TYPE
    SYNTAX          Counter32
    MAX-ACCESS      read-only
    STATUS          current
    DESCRIPTION     "The value of the object  tlsPipStpInRstBpdus indicates
                     the number of Rapid Spanning Tree (RST) BPDUs received on
                     this PIP uplink."
    ::= { tlsPipInfoEntry 9 }

tlsPipStpInMstBpdus OBJECT-TYPE
    SYNTAX          Counter32
    MAX-ACCESS      read-only
    STATUS          current
    DESCRIPTION     "The value of the object tlsPipStpInMstBpdus indicates
                     the number of Multiple Spanning Tree (MST) BPDUs received
                     on this PIP uplink."
    ::= { tlsPipInfoEntry 10 }

tlsPipStpInBadBpdus OBJECT-TYPE
    SYNTAX          Counter32
    MAX-ACCESS      read-only
    STATUS          current
    DESCRIPTION     "This object specifies the number of bad
                     BPDUs received on this PIP uplink."
    ::= { tlsPipInfoEntry 11 }

tlsPipStpOutConfigBpdus OBJECT-TYPE
    SYNTAX          Counter32
    MAX-ACCESS      read-only
    STATUS          current
    DESCRIPTION     "The value of the object tlsPipStpOutConfigBpdus indicates
                     the number of Configuration BPDUs sent out this PIP uplink."
    ::= { tlsPipInfoEntry 12 }

tlsPipStpOutTcnBpdus OBJECT-TYPE
    SYNTAX          Counter32
    MAX-ACCESS      read-only
    STATUS          current
    DESCRIPTION     "This object specifies the number of Topology
                     Change Notification BPDUs sent out this PIP uplink."
    ::= { tlsPipInfoEntry 13 }

tlsPipStpOutRstBpdus OBJECT-TYPE
    SYNTAX          Counter32
    MAX-ACCESS      read-only
    STATUS          current
    DESCRIPTION     "The value of the  object tlsPipStpOutRstBpdus indicates
                     the number of Rapid Spanning Tree (RST) BPDUs sent out on
                     this PIP uplink."
    ::= { tlsPipInfoEntry 14 }

tlsPipStpOutMstBpdus OBJECT-TYPE
    SYNTAX          Counter32
    MAX-ACCESS      read-only
    STATUS          current
    DESCRIPTION     "The value of the object tlsPipStpOutMstBpdus indicates
                     the number of Multiple Spanning Tree (MST) BPDUs sent out
                     on this PIP uplink."
    ::= { tlsPipInfoEntry 15 }

tlsPipStpOperStatus OBJECT-TYPE
    SYNTAX          ServiceOperStatus
    MAX-ACCESS      read-only
    STATUS          current
    DESCRIPTION     "The value of the object tlsPipStpOperStatus indicates the
                     operational status of this PIP uplink."
    ::= { tlsPipInfoEntry 16 }

tlsPipStpMvplsPruneState OBJECT-TYPE
    SYNTAX          MvplsPruneState
    MAX-ACCESS      read-only
    STATUS          current
    DESCRIPTION     "The value of tlsPipStpMvplsPruneState indicates the mVPLS
                     prune state of this PIP uplink.  The state reflects
                     whether or not this uplink is pruned by the STP instance
                     running in the mVPLS instance."
    ::= { tlsPipInfoEntry 17 }

tlsPipStpOperProtocol OBJECT-TYPE
    SYNTAX          StpProtocol
    MAX-ACCESS      read-only
    STATUS          current
    DESCRIPTION     "The value of tlsPipStpOperProtocol indicates whether 'stp',
                    'rstp' or 'mstp' is running on this PIP uplink. If the
                    protocol is not enabled on this PIP uplink, the value
                    'notApplicable' is returned."
    ::= { tlsPipInfoEntry 18 }

tlsPipStpPortNum OBJECT-TYPE
    SYNTAX          Unsigned32 (0..4094)
    MAX-ACCESS      read-only
    STATUS          current
    DESCRIPTION     "The value of the object tlsPipStpPortNum specifies the
                     value of the port number field which is contained in the
                     least significant 12 bits of the 16-bit Port ID associated
                     with this PIP uplink."
    ::= { tlsPipInfoEntry 19 }

-- -----------------------------------------
-- PIP TLS MSTI Table
-- -----------------------------------------
tlsPipMstiTable OBJECT-TYPE
    SYNTAX          SEQUENCE OF TlsPipMstiEntry
    MAX-ACCESS      not-accessible
    STATUS          current
    DESCRIPTION
        "This table contains Multiple Spanning Tree Instance information for
        the PIP uplink. Each management VPLS running MSTP can have upto 15
        MSTI. An entry in this table is automatically created when a
        tlsMstiEntry is created."
    ::= { tmnxSvcObjs 41 }

tlsPipMstiEntry OBJECT-TYPE
    SYNTAX          TlsPipMstiEntry
    MAX-ACCESS      not-accessible
    STATUS          current
    DESCRIPTION     "Information about a specific MSTI for a PIP uplink."
    INDEX           { svcId, tlsMstiInstanceId}
    ::= { tlsPipMstiTable 1 }

TlsPipMstiEntry ::=
    SEQUENCE {
        tlsPipMstiPortRole          StpPortRole,
        tlsPipMstiPortState         TStpPortState,
        tlsPipMstiDesignatedBridge  BridgeId,
        tlsPipMstiDesignatedPort    Integer32
    }

tlsPipMstiPortRole OBJECT-TYPE
    SYNTAX          StpPortRole
    MAX-ACCESS      read-only
    STATUS          current
    DESCRIPTION     "tlsPipMstiPortRole indicates the current role of the
                     PIP uplink in the MSTI as defined by the Spanning Tree
                     Protocol."
    ::= { tlsPipMstiEntry 1 }

tlsPipMstiPortState OBJECT-TYPE
    SYNTAX          TStpPortState
    MAX-ACCESS      read-only
    STATUS          current
    DESCRIPTION     "The value of the object tlsPipMstiPortState indicates the
                     port's current state as defined by application of the
                     Spanning Tree Protocol. This state controls what action a
                     port takes on reception of a frame. If the bridge has
                     detected a port that is malfunctioning it will
                     place that port into the broken(6) state."
    ::= { tlsPipMstiEntry 2 }

tlsPipMstiDesignatedBridge OBJECT-TYPE
    SYNTAX          BridgeId
    MAX-ACCESS      read-only
    STATUS          current
    DESCRIPTION     "The value of the object tlsPipMstiDesignatedBridge
                     indicates  the Bridge Identifier of the bridge which this
                     port considers to be the Designated Bridge for this port's
                     segment for this MSTI."
    ::= { tlsPipMstiEntry 3 }

tlsPipMstiDesignatedPort OBJECT-TYPE
    SYNTAX          Integer32
    MAX-ACCESS      read-only
    STATUS          current
    DESCRIPTION     "The value of the object tlsPipMstiDesignatedPort indicates
                     the Port Identifier of the port on the Designated Bridge
                     for this port's segment for this MSTI."
    ::= { tlsPipMstiEntry 4 }

-- ----------------------
-- System service objects
-- ----------------------
svcTotalFdbMimDestIdxEntries OBJECT-TYPE
    SYNTAX         Unsigned32
    MAX-ACCESS     read-only
    STATUS         current
    DESCRIPTION    "The value of the object svcTotalFdbMimDestIdxEntries
                    indicates the number of system wide Backbone MAC address
                    indices in use."
    ::= { tmnxSvcObjs 42 }

-- ----------------------------------------
-- DHCP Managed Route Table
-- ----------------------------------------
svcDhcpManagedRouteTable OBJECT-TYPE
    SYNTAX          SEQUENCE OF SvcDhcpManagedRouteEntry
    MAX-ACCESS      not-accessible
    STATUS          current
    DESCRIPTION     "A table that contains DHCP managed routes."
    ::= { tmnxSvcObjs 43 }

svcDhcpManagedRouteEntry OBJECT-TYPE
    SYNTAX          SvcDhcpManagedRouteEntry
    MAX-ACCESS      not-accessible
    STATUS          current
    DESCRIPTION     "A specific DHCP managed route."
    INDEX           { svcId,
                      svcDhcpLseStateCiAddrType,
                      svcDhcpLseStateCiAddr,
                      svcDhcpManagedRouteInetAddrType,
                      svcDhcpManagedRouteInetAddr,
                      svcDhcpManagedRoutePrefixLen }
    ::= { svcDhcpManagedRouteTable 1 }

SvcDhcpManagedRouteEntry ::=
    SEQUENCE {
        svcDhcpManagedRouteInetAddrType  InetAddressType,
        svcDhcpManagedRouteInetAddr      InetAddress,
        svcDhcpManagedRoutePrefixLen     InetAddressPrefixLength,
        svcDhcpManagedRouteStatus        TmnxManagedRouteStatus
    }

svcDhcpManagedRouteInetAddrType OBJECT-TYPE
    SYNTAX          InetAddressType
    MAX-ACCESS      not-accessible
    STATUS          current
    DESCRIPTION     "The value of svcDhcpManagedRouteInetAddrType indicates
                     the address type of svcDhcpManagedRouteInetAddr."
    ::= { svcDhcpManagedRouteEntry 1 }

svcDhcpManagedRouteInetAddr OBJECT-TYPE
    SYNTAX          InetAddress
    MAX-ACCESS      not-accessible
    STATUS          current
    DESCRIPTION     "The value of svcDhcpManagedRouteInetAddr indicates
                     the IP address of the managed route."
    ::= { svcDhcpManagedRouteEntry 2 }

svcDhcpManagedRoutePrefixLen OBJECT-TYPE
    SYNTAX          InetAddressPrefixLength (0..32)
    MAX-ACCESS      not-accessible
    STATUS          current
    DESCRIPTION     "The value of svcDhcpManagedRoutePrefixLen indicates
                     the prefix length of the subnet associated with
                     svcDhcpManagedRouteInetAddr."
    ::= { svcDhcpManagedRouteEntry 3 }

svcDhcpManagedRouteStatus OBJECT-TYPE
    SYNTAX          TmnxManagedRouteStatus
    MAX-ACCESS      read-only
    STATUS          current
    DESCRIPTION     "The value of svcDhcpManagedRouteStatus indicates
                     the state of this managed route."
    ::= { svcDhcpManagedRouteEntry 4 }

-- ------------------------------
-- Service trap objects
-- ------------------------------
macPinningMacAddress OBJECT-TYPE
    SYNTAX         MacAddress
    MAX-ACCESS     accessible-for-notify
    STATUS         current
    DESCRIPTION    "The value of the object macPinningMacAddress indicates
                    the pinned MAC address."
    ::= { tmnxSvcNotifyObjs 1 }

macPinningPinnedRow OBJECT-TYPE
    SYNTAX         RowPointer
    MAX-ACCESS     accessible-for-notify
    STATUS         current
    DESCRIPTION    "The value of the object macPinningPinnedRow indicates
                    where the MAC address is currently pinned on.
                    Its value will be the OID of the first accessible
                    object in the row of the sapTlsInfoTable or in the
                    sdpBindTable, depending on whether the MAC address is
                    pinned on a SAP or a SDP Bind."
    ::= { tmnxSvcNotifyObjs 2 }

macPinningPinnedRowDescr OBJECT-TYPE
    SYNTAX         DisplayString
    MAX-ACCESS     accessible-for-notify
    STATUS         current
    DESCRIPTION    "The value of the object macPinningPinnedRowDescr indicates
                    where the MAC address is currently pinned on. The value
                    will either be a SAP-id or a SDP id, presented in readable
                    format, depending on whether the MAC is pinned to a SAP
                    or a SDP."
    ::= { tmnxSvcNotifyObjs 3 }

macPinningViolatingRow OBJECT-TYPE
    SYNTAX         RowPointer
    MAX-ACCESS     accessible-for-notify
    STATUS         current
    DESCRIPTION    "The value of the object macPinningViolatingRow indicates
                    where the MAC address relearn attempt was detected.
                    Its value will be the OID of the first accessible object
                    in the row of the sapTlsInfoTable or in the sdpBindTable,
                    depending on whether the MAC address is pinned on a SAP
                    or a SDP Bind."
    ::= { tmnxSvcNotifyObjs 4 }

macPinningViolatingRowDescr OBJECT-TYPE
    SYNTAX         DisplayString
    MAX-ACCESS     accessible-for-notify
    STATUS         current
    DESCRIPTION    "The value of the object macPinningViolatingRowDescr
                    indicates where the MAC address relearn attempt was
                    detected. The value will either be a SAP-id or a SDP id,
                    presented in readable format, depending on whether the
                    MAC address relearn attempt was detected on a SAP or a
                    SDP."
    ::= { tmnxSvcNotifyObjs 5 }

tlsDHCPClientLease OBJECT-TYPE
    SYNTAX         Integer32
    MAX-ACCESS     accessible-for-notify
    STATUS         obsolete
    DESCRIPTION    "The value of the object tlsDHCPClientLease indicates the
                    lease time specified in the PDU causing the trap.
                    Used by tmnxVRtrDHCPAFEntriesExceeded to report the lease
                    time.
                    This object was made obsolete in the 4.0 release."
    ::= { tmnxSvcNotifyObjs 6 }

tlsDhcpLseStateOldCiAddr OBJECT-TYPE
    SYNTAX         IpAddress
    MAX-ACCESS     accessible-for-notify
    STATUS         obsolete
    DESCRIPTION    "The value of the object tlsDhcpLseStateOldCiAddr indicates
                    the Client IP address that was formerly assigned to this
                    Least state. Used in sapTlsDHCPLeaseStateOverride trap.
                    This object was made obsolete in the 4.0 release."
    ::= { tmnxSvcNotifyObjs 7 }

tlsDhcpLseStateOldChAddr OBJECT-TYPE
    SYNTAX         MacAddress
    MAX-ACCESS     accessible-for-notify
    STATUS         obsolete
    DESCRIPTION    "The value of the object tlsDhcpLseStateOldChAddr indicates
                    the Client MAC address that was formerly assigned to this
                    Least state. Used in sapTlsDHCPLeaseStateOverride trap.
                    This object was made obsolete in the 4.0 release."
    ::= { tmnxSvcNotifyObjs 8 }

tlsDhcpLseStateNewCiAddr OBJECT-TYPE
    SYNTAX         IpAddress
    MAX-ACCESS     accessible-for-notify
    STATUS         obsolete
    DESCRIPTION    "The value of the object tlsDhcpLseStateNewCiAddr indicates
                    the Client IP address specified in the PDU causing
                    the trap.
                    This object was made obsolete in the 4.0 release."
    ::= { tmnxSvcNotifyObjs 9 }

tlsDhcpLseStateNewChAddr OBJECT-TYPE
    SYNTAX         MacAddress
    MAX-ACCESS     accessible-for-notify
    STATUS         obsolete
    DESCRIPTION    "The value of the object tlsDhcpLseStateNewChAddr indicates
                    the Client MAC address specified in the PDU causing
                    the trap.
                    This object was made obsolete in the 4.0 release."
    ::= { tmnxSvcNotifyObjs 10 }

tlsDhcpRestoreLseStateCiAddr OBJECT-TYPE
    SYNTAX         IpAddress
    MAX-ACCESS     accessible-for-notify
    STATUS         obsolete
    DESCRIPTION    "The value of the object tlsDhcpRestoreLseStateCiAddr
                    indicates the IP address specified in the persistency
                    record causing the trap.
                    This object was made obsolete in the 4.0 release."
    ::= { tmnxSvcNotifyObjs 11 }

tlsDhcpRestoreLseStateSvcId OBJECT-TYPE
    SYNTAX         TmnxServId
    MAX-ACCESS     accessible-for-notify
    STATUS         obsolete
    DESCRIPTION    "The value of the object tlsDhcpRestoreLseStateSvcId
                    indicates the serviceId specified in the persistency record
                    causing the trap.
                    This object was made obsolete in the 4.0 release."
    ::= { tmnxSvcNotifyObjs 12 }

tlsDhcpRestoreLseStatePortId OBJECT-TYPE
    SYNTAX         TmnxPortID
    MAX-ACCESS     accessible-for-notify
    STATUS         obsolete
    DESCRIPTION    "The value of the object tlsDhcpRestoreLseStatePortId
                    indicates the Port ID specified in the persistency record
                    causing the trap.
                    This object was made obsolete in the 4.0 release."
    ::= { tmnxSvcNotifyObjs 13 }

tlsDhcpRestoreLseStateEncapVal OBJECT-TYPE
    SYNTAX         TmnxEncapVal
    MAX-ACCESS     accessible-for-notify
    STATUS         obsolete
    DESCRIPTION    "The value of the object tlsDhcpRestoreLseStateEncapVal
                    indicates the SAP encap value specified in the persistency
                    record causing the trap.
                    This object was made obsolete in the 4.0 release."
    ::= { tmnxSvcNotifyObjs 14 }

tlsDhcpRestoreLseStateProblem OBJECT-TYPE
    SYNTAX         DisplayString
    MAX-ACCESS     accessible-for-notify
    STATUS         obsolete
    DESCRIPTION    "The value of the object tlsDhcpRestoreLseStateProblem
                    indicates why the persistency record cannot be restored.
                    This object was made obsolete in the 4.0 release."
    ::= { tmnxSvcNotifyObjs 15 }

tlsDhcpPacketProblem OBJECT-TYPE
    SYNTAX         DisplayString
    MAX-ACCESS     accessible-for-notify
    STATUS         obsolete
    DESCRIPTION    "The value of the object tlsDhcpPacketProblem indicates
                    information on a received DHCP packet is considered
                    suspicious by the system.
                    This object was made obsolete in the 4.0 release."
    ::= { tmnxSvcNotifyObjs 16 }

tlsDhcpLseStatePopulateError OBJECT-TYPE
    SYNTAX         DisplayString
    MAX-ACCESS     accessible-for-notify
    STATUS         obsolete
    DESCRIPTION    "The value of the object tlsDhcpLseStatePopulateError
                    indicates  why the system was unable to update the
                    Lease State Table upon reception of a DHCP ACK message.
                    This object was made obsolete in the 4.0 release."
    ::= { tmnxSvcNotifyObjs 17 }

svcDhcpRestoreLseStateCiAddr OBJECT-TYPE
    SYNTAX         IpAddress
    MAX-ACCESS     accessible-for-notify
    STATUS         current
    DESCRIPTION    "The value of the object svcDhcpRestoreLseStateCiAddr
                    indicates the IP address specified in the persistency
                    record causing the trap."
    ::= { tmnxSvcNotifyObjs 18 }

svcDhcpRestoreLseStateProblem OBJECT-TYPE
    SYNTAX         DisplayString
    MAX-ACCESS     accessible-for-notify
    STATUS         current
    DESCRIPTION    "The value of the object svcDhcpRestoreLseStateProblem
                    indicates why the persistency record cannot be restored."
    ::= { tmnxSvcNotifyObjs 19 }

svcDhcpLseStateOldCiAddr OBJECT-TYPE
    SYNTAX         IpAddress
    MAX-ACCESS     accessible-for-notify
    STATUS         current
    DESCRIPTION    "The value of the object svcDhcpLseStateOldCiAddr indicates
                    the client IP address that was formerly assigned to the
                    specified DHCP lease state."
    ::= { tmnxSvcNotifyObjs 20 }

svcDhcpLseStateOldChAddr OBJECT-TYPE
    SYNTAX         MacAddress
    MAX-ACCESS     accessible-for-notify
    STATUS         current
    DESCRIPTION    "The value of the object svcDhcpLseStateOldChAddr indicates
                    the client MAC address that was formerly assigned to the
                    specified DHCP lease state."
    ::= { tmnxSvcNotifyObjs 21 }

svcDhcpLseStateNewCiAddr OBJECT-TYPE
    SYNTAX         IpAddress
    MAX-ACCESS     accessible-for-notify
    STATUS         current
    DESCRIPTION    "The value of the object svcDhcpLseStateNewCiAddr indicates
                    the client IP address specified in the DHCP PDU causing the
                    trap."
    ::= { tmnxSvcNotifyObjs 22 }

svcDhcpLseStateNewChAddr OBJECT-TYPE
    SYNTAX         MacAddress
    MAX-ACCESS     accessible-for-notify
    STATUS         current
    DESCRIPTION    "The value of the object svcDhcpLseStateNewChAddr indicates
                    the client MAC address specified in the DHCP PDU causing
                    the trap."
    ::= { tmnxSvcNotifyObjs 23 }

svcDhcpClientLease OBJECT-TYPE
    SYNTAX         Integer32
    MAX-ACCESS     accessible-for-notify
    STATUS         current
    DESCRIPTION    "The value of the object svcDhcpClientLease indicates the
                    lease time specified in the DHCP PDU causing the trap."
    ::= { tmnxSvcNotifyObjs 24 }

svcDhcpPacketProblem OBJECT-TYPE
    SYNTAX         DisplayString
    MAX-ACCESS     accessible-for-notify
    STATUS         current
    DESCRIPTION    "The value of the object svcDhcpPacketProblem indicates
                    information on a received DHCP packet that is considered
                    suspicious by the system."
    ::= { tmnxSvcNotifyObjs 25 }

svcDhcpLseStatePopulateError OBJECT-TYPE
    SYNTAX         DisplayString
    MAX-ACCESS     accessible-for-notify
    STATUS         current
    DESCRIPTION    "The value of the object svcDhcpLseStatePopulateError
                    indicates the reason why the system was unable to update
                    the Lease State table upon reception of a DHCP ACK
                    message."
    ::= { tmnxSvcNotifyObjs 26 }

hostConnectivityCiAddrType OBJECT-TYPE
    SYNTAX         InetAddressType
    MAX-ACCESS     accessible-for-notify
    STATUS         current
    DESCRIPTION    "The value of the object hostConnectivityCiAddrType indicates
                    the client address type causing the trap."
    ::= { tmnxSvcNotifyObjs 27 }

hostConnectivityCiAddr OBJECT-TYPE
    SYNTAX         InetAddress
    MAX-ACCESS     accessible-for-notify
    STATUS         current
    DESCRIPTION    "The value of the object hostConnectivityCiAddr indicates
                    the client INET address causing the trap."
    ::= { tmnxSvcNotifyObjs 28 }

hostConnectivityChAddr OBJECT-TYPE
    SYNTAX         MacAddress
    MAX-ACCESS     accessible-for-notify
    STATUS         current
    DESCRIPTION    "The value of the object hostConnectivityChAddr indicates
                    the client MAC address causing the trap."
    ::= { tmnxSvcNotifyObjs 29 }

protectedMacForNotify OBJECT-TYPE
    SYNTAX         MacAddress
    MAX-ACCESS     accessible-for-notify
    STATUS         current
    DESCRIPTION    "The value of the object protectedMacForNotify indicates
                    the protected MAC address that was received, causing the
                    sapReceivedProtSrcMac notification."
    ::= { tmnxSvcNotifyObjs 30 }

staticHostDynamicMacIpAddress OBJECT-TYPE
    SYNTAX         IpAddress
    MAX-ACCESS     accessible-for-notify
    STATUS         current
    DESCRIPTION    "The value of the object staticHostDynamicMacIpAddress
                    indicates the IP address of the static host for which the
                    sapStaticHostDynMacConflict notification is generated."
    ::= { tmnxSvcNotifyObjs 31 }

staticHostDynamicMacConflict OBJECT-TYPE
    SYNTAX         DisplayString
    MAX-ACCESS     accessible-for-notify
    STATUS         current
    DESCRIPTION    "The value of the object staticHostDynamicMacConflict
                    indicates the reason causing the sapStaticHostDynMacConflict
                    notification."
    ::= { tmnxSvcNotifyObjs 32 }

tmnxSvcObjRow OBJECT-TYPE
    SYNTAX         RowPointer
    MAX-ACCESS     accessible-for-notify
    STATUS         current
    DESCRIPTION    "The value of the object tmnxSvcObjRow indicates
                    the object that has failed to perform the set action
                    requested by the Time-Of-Day Suite.
                    Its value will be the OID of the first accessible
                    object in the row of the sapBaseInfoTable or in the
                    custMultiServiceSiteTable, depending on whether the object
                    is a SAP or a Customer Multi-Service Site."
    ::= { tmnxSvcNotifyObjs 33 }

tmnxSvcObjRowDescr OBJECT-TYPE
    SYNTAX         DisplayString
    MAX-ACCESS     accessible-for-notify
    STATUS         current
    DESCRIPTION    "The value of the object tmnxSvcObjRowDescr indicates
                    the object that has failed to perform the set action
                    requested by the Time-Of-Day Suite. 
                    The value will either be a SAP-id or 
                    a Customer Multi-Service Site id, presented in readable
                    format, depending on whether the object
                    is a SAP or a Customer Multi-Service Site."
    ::= { tmnxSvcNotifyObjs 34 }

tmnxSvcObjTodSuite OBJECT-TYPE
    SYNTAX     DisplayString
    MAX-ACCESS accessible-for-notify
    STATUS     current
    DESCRIPTION
        "The value of the object tmnxSvcObjTodSuite indicates the name of the
         involved ToD Suite."
    ::= { tmnxSvcNotifyObjs 35 }

tmnxFailureDescription OBJECT-TYPE
    SYNTAX         DisplayString
    MAX-ACCESS     accessible-for-notify
    STATUS         current
    DESCRIPTION    "The value of the object tmnxFailureDescription is a
                    printable character string which contains information about
                    the reason why the notification is sent."
    ::= { tmnxSvcNotifyObjs 36 }

svcDhcpProxyError OBJECT-TYPE
    SYNTAX         DisplayString
    MAX-ACCESS     accessible-for-notify
    STATUS         current
    DESCRIPTION    "The value of the object svcDhcpProxyError indicates
                    the reason why the proxy server failed to operate."
    ::= { tmnxSvcNotifyObjs 37 }

svcDhcpCoAError OBJECT-TYPE
    SYNTAX         DisplayString
    MAX-ACCESS     accessible-for-notify
    STATUS         current
    DESCRIPTION    "The value of the object svcDhcpCoAError indicates
                    the reason why the node failed to process a Change of
                    Authorization (CoA) request from a Radius server."
    ::= { tmnxSvcNotifyObjs 38 }

svcDhcpSubAuthError OBJECT-TYPE
    SYNTAX         DisplayString
    MAX-ACCESS     accessible-for-notify
    STATUS         current
    DESCRIPTION    "The value of the object svcDhcpSubAuthError is a printable
                    character string which contains information about the
                    problem that occurred while trying to authenticate the
                    subscriber."
    ::= { tmnxSvcNotifyObjs 39 }

svcTlsMrpAttrRegFailedReason OBJECT-TYPE
    SYNTAX         INTEGER {
                      unknown                   (1),
                      attribute-limit-reached   (2),
                      system-attr-limit-reached (3),
                      unsupported-attribute     (4),
                      mfib-entry-create-failed  (5)
                      }
    MAX-ACCESS     accessible-for-notify
    STATUS         current
    DESCRIPTION    "The value of the object svcTlsMrpAttrRegFailedReason
                    indicates the reason for MRP attribute registration
                    failure."
    ::= { tmnxSvcNotifyObjs 40 }

svcTlsMrpAttrType OBJECT-TYPE
    SYNTAX         Unsigned32 (1..255)
    MAX-ACCESS     accessible-for-notify
    STATUS         current
    DESCRIPTION    "The value of the object svcTlsMrpAttrType indicates the
                    type of MRP attribute."
    ::= { tmnxSvcNotifyObjs 41 }

svcTlsMrpAttrValue OBJECT-TYPE
    SYNTAX         OCTET STRING (SIZE(0..255))
    MAX-ACCESS     accessible-for-notify
    STATUS         current
    DESCRIPTION    "The value of the object svcTlsMrpAttrValue indicates the
                    value of MRP attribute."
    ::= { tmnxSvcNotifyObjs 42 }

svcMstiInstanceId OBJECT-TYPE
    SYNTAX         MstiInstanceId
    MAX-ACCESS     accessible-for-notify
    STATUS         current
    DESCRIPTION    "The value of the object svcMstiInstanceId indicates the
                    Multiple Spanning Tree Instance."
    ::= { tmnxSvcNotifyObjs 43 }

-- ------------------------------------
-- Service traps
-- ------------------------------------
svcCreated NOTIFICATION-TYPE
    OBJECTS {
        custId,
        svcId,
        svcVpnId,
        svcType
    }
    STATUS          obsolete
    DESCRIPTION     "This trap is sent when a new row is created
                     in the svcBaseInfoTable."
    ::= { svcTraps 1 }

svcDeleted NOTIFICATION-TYPE
    OBJECTS {
        custId,
        svcId,
        svcVpnId
    }
    STATUS          obsolete
    DESCRIPTION     "This trap is sent when an existing row is
                     deleted from the svcBaseInfoTable."
    ::= { svcTraps 2 }

svcStatusChanged NOTIFICATION-TYPE
    OBJECTS {
        custId,
        svcId,
        svcVpnId,
        svcAdminStatus,
        svcOperStatus
    }
    STATUS          current
    DESCRIPTION     "The svcStatusChanged notification is generated when
                     there is a change in the administrative or operating
                     status of a service."
    ::= { svcTraps 3 }

svcTlsFdbTableFullAlarmRaised NOTIFICATION-TYPE
    OBJECTS {
        custId,
        svcId,
        svcVpnId
    }
    STATUS          current
    DESCRIPTION     "The svcTlsFdbTableFullAlarmRaised notification is
                     generated when the utilization of the FDB table is
                     above the value specified by
                     svcTlsFdbTableFullHighWatermark."
    ::= { svcTraps 4 }

svcTlsFdbTableFullAlarmCleared NOTIFICATION-TYPE
    OBJECTS {
        custId,
        svcId,
        svcVpnId
    }
    STATUS          current
    DESCRIPTION     "The svcTlsFdbTableFullAlarmCleared notification is
                     generated when the utilization of the FDB table is
                     below the value specified by
                     svcTlsFdbTableFullLowWatermark."
    ::= { svcTraps 5 }

iesIfCreated NOTIFICATION-TYPE
    OBJECTS {
        custId,
        svcId,
        svcVpnId,
        iesIfIndex
    }
    STATUS          obsolete
    DESCRIPTION     "The iesIfCreated notification is generated
                     when a new row is created in the iesIfTable."
    ::= { svcTraps 6 }

iesIfDeleted NOTIFICATION-TYPE
    OBJECTS {
        custId,
        svcId,
        svcVpnId,
        iesIfIndex
    }
    STATUS          obsolete
    DESCRIPTION     "The iesIfDeleted notification is sent when an existing
                     row is deleted from the iesIfTable."
    ::= { svcTraps 7 }

iesIfStatusChanged NOTIFICATION-TYPE
    OBJECTS {
        custId,
        svcId,
        svcVpnId,
        iesIfIndex,
        iesIfAdminStatus,
        iesIfOperStatus
    }
    STATUS          current
    DESCRIPTION     "The iesIfStatusChanged notification is generated
                     when there is a change in the administrative or
                     operating status of an IES interface."
    ::= { svcTraps 8 }

svcTlsMfibTableFullAlarmRaised NOTIFICATION-TYPE
    OBJECTS {
        custId,
        svcId,
        svcVpnId
    }
    STATUS          current
    DESCRIPTION     "The svcTlsMfibTableFullAlarmRaised notification is
                     generated when the utilization of the MFIB table is above
                     the value specified by svcTlsMfibTableFullHighWatermark."
    ::= { svcTraps 9 }

svcTlsMfibTableFullAlarmCleared NOTIFICATION-TYPE
    OBJECTS {
        custId,
        svcId,
        svcVpnId
    }
    STATUS          current
    DESCRIPTION     "The svcTlsMfibTableFullAlarmCleared notification is
                     generated when the utilization of the MFIB table is below
                     the value specified by svcTlsMfibTableFullLowWatermark."
    ::= { svcTraps 10 }

svcTlsMacPinningViolation NOTIFICATION-TYPE
    OBJECTS {
        custId,
        svcId,
        svcVpnId,
        macPinningMacAddress,
        macPinningPinnedRow,
        macPinningPinnedRowDescr,
        macPinningViolatingRow,
        macPinningViolatingRowDescr
    }
    STATUS          current
    DESCRIPTION     "The svcTlsMacPinningViolation notification is
                     generated when an attempt is made to assign a MAC
                     address to another interface while this MAC address
                     is pinned (i.e. assigned fixed to an interface)."
    ::= { svcTraps 11 }

svcTlsDHCPLseStRestoreProblem NOTIFICATION-TYPE
    OBJECTS {
        tlsDhcpRestoreLseStateSvcId,
        tlsDhcpRestoreLseStatePortId,
        tlsDhcpRestoreLseStateEncapVal,
        tlsDhcpRestoreLseStateCiAddr,
        tlsDhcpRestoreLseStateProblem
    }
    STATUS          obsolete
    DESCRIPTION     "The svcTlsDHCPLseStRestoreProblem notification is
                     generated when an an error is detected while
                     processing a persistency record."
    ::= { svcTraps 12 }

svcTlsDHCPLseStatePopulateErr NOTIFICATION-TYPE
    OBJECTS {
        custId,
        svcId,
        tlsDhcpLseStatePopulateError
    }
    STATUS          obsolete
    DESCRIPTION     "The svcTlsDHCPLseStatePopulateErr notification
                     indicates that the system was unable to update the
                     Lease State Table with the information contained in
                     the DHCP ACK message. The DHCP ACK message has been
                     discarded."
    ::= { svcTraps 13 }

svcDHCPLseStateRestoreProblem NOTIFICATION-TYPE
    OBJECTS {
        svcDhcpRestoreLseStateCiAddr,
        svcDhcpRestoreLseStateProblem
    }
    STATUS          current
    DESCRIPTION     "The svcDHCPLseStateRestoreProblem notification is
                     generated when an an error is detected while processing a
                     persistency record."
    ::= { svcTraps 14 }

tmnxSvcObjTodSuiteApplicFailed NOTIFICATION-TYPE
    OBJECTS {
        tmnxSvcObjRow,
        tmnxSvcObjRowDescr,
        tmnxSvcObjTodSuite,
        tmnxFailureDescription
    }
    STATUS          current
    DESCRIPTION     "The tmnxSvcObjTodSuiteApplicFailed notification is
                     generated when the object has failed to perform the set
                     action requested by the Time-Of-Day Suite. The object can
                     be either a SAP or a Customer Multi-Service Site."
    ::= { svcTraps 15 }

tmnxEndPointTxActiveChanged       NOTIFICATION-TYPE
    OBJECTS {
        svcEndPointTxActiveType,
        svcEndPointTxActivePortId,
        svcEndPointTxActiveEncap,
        svcEndPointTxActiveSdpId
    }
    STATUS          current
    DESCRIPTION     "The tmnxEndPointTxActiveChanged notification is generated
                     when the transmit active object on an endpoint changes."
    ::= { svcTraps 16 }

tmnxSvcPEDiscPolServOperStatChg NOTIFICATION-TYPE
    OBJECTS {
        svcPEDiscPolServerAddressType,
        svcPEDiscPolServerAddress,
        svcPEDiscPolServerOperStatus
    }
    STATUS  current
    DESCRIPTION
        "The tmnxSvcPEDiscPolServOperStatChg notification is generated 
         when the operational status of a Radius server, configured for use 
         as PE Discovery Policy Server, has transitioned either from 'up' to 
         'down' or from 'down' to 'up'."
    ::= { svcTraps 17 }

svcEndPointMacLimitAlarmRaised  NOTIFICATION-TYPE
    OBJECTS {
        custId,
        svcId,
        svcVpnId,
        svcEndPointMacLimit
    }
    STATUS          current
    DESCRIPTION
        "The svcEndPointMacLimitAlarmRaised notification is sent whenever the
        number of MAC addresses stored in the FDB for this endpoint exceeds the
        watermark specified by the object svcTlsFdbTableFullHighWatermark.

        This alarm also takes into consideration static MAC addresses
        configured on the endpoint and learned MAC addresses in all spokes
        associated with this endpoint."
    ::= { svcTraps 18 }

svcEndPointMacLimitAlarmCleared  NOTIFICATION-TYPE
    OBJECTS {
        custId,
        svcId,
        svcVpnId,
        svcEndPointMacLimit
    }
    STATUS          current
    DESCRIPTION
        "The svcEndPointMacLimitAlarmCleared notification is sent whenever the
        number of MAC addresses stored in the FDB for this endpoint drops below
        the watermark specified by the object svcTlsFdbTableFullLowWatermark.

        This alarm also takes into consideration static MAC addresses
        configured on the endpoint and learned MAC addresses in all spokes
        associated with this endpoint."
    ::= { svcTraps 19 }

svcTlsMrpAttrRegistrationFailed NOTIFICATION-TYPE
    OBJECTS {
        custId,
        svcId,
        svcTlsMrpAttrRegFailedReason,
        svcTlsMrpAttrType,
        svcTlsMrpAttrValue
    }
    STATUS          current
    DESCRIPTION     "The svcTlsMrpAttrRegistrationFailed notification is
                     generated when registration fails for an MRP attribute."
    ::= { svcTraps 20 }

svcFdbMimDestTblFullAlrm NOTIFICATION-TYPE
    OBJECTS {
            svcTotalFdbMimDestIdxEntries
    }
    STATUS          current
    DESCRIPTION     "The svcFdbMimDestTblFullAlrm notification is raised
                     when system limit of Backbone MAC address indices limit is
                     reached.
                     
                     Further traps are not generated as long as the value of
                     svcTotalFdbMimDestIdxEntries object remains under 5
                     percent of the limit."
   ::= { svcTraps 21 }

svcFdbMimDestTblFullAlrmCleared NOTIFICATION-TYPE
    OBJECTS {
            svcTotalFdbMimDestIdxEntries
    }
    STATUS          current
    DESCRIPTION     "The svcFdbMimDestTblFullAlrmCleared notification is raised
                     when number of Backbone MAC address indices used reaches
                     under 95 percent of the system limit after
                     svcFdbMimDestTblFullAlrm notification had been raised."
   ::= { svcTraps 22 }

svcDHCPMiscellaneousProblem NOTIFICATION-TYPE
    OBJECTS {
            tmnxFailureDescription
    }
    STATUS          current
    DESCRIPTION     "The svcDHCPMiscellaneousProblem notification is
                     generated on miscellaneous DHCP problems."
    ::= { svcTraps 23 }

svcPersistencyProblem NOTIFICATION-TYPE
    OBJECTS {
            svcId,
            tmnxFailureDescription
    }
    STATUS          current
    DESCRIPTION     "The svcPersistencyProblem notification is generated
                     on persistency problems."
    ::= { svcTraps 24 }

svcTlsMrpAttrTblFullAlarmRaised NOTIFICATION-TYPE
    OBJECTS {
        custId,
        svcId,
        svcVpnId
    }
    STATUS          current
    DESCRIPTION     "The svcTlsMrpAttrTblFullAlarmRaised notification is
                     generated when the utilization of the MRP attribute table
                     is above the value specified by
                     svcTlsMrpAttrTblHighWatermark."
    ::= { svcTraps 25 }

svcTlsMrpAttrTblFullAlarmCleared NOTIFICATION-TYPE
    OBJECTS {
        custId,
        svcId,
        svcVpnId
    }
    STATUS          current
    DESCRIPTION     "The svcTlsMrpAttrTblFullAlarmCleared notification is
                     generated when the utilization of the MRP attribute table
                     is below the value specified by
                     svcTlsMrpAttrTblLowWatermark."
    ::= { svcTraps 26 }

-- --------------------------------------------------
-- TLS STP trap notification objects
-- --------------------------------------------------
tmnxCustomerBridgeId OBJECT-TYPE
    SYNTAX         BridgeId
    MAX-ACCESS     accessible-for-notify
    STATUS         current
    DESCRIPTION    "tmnxCustomerBridgeId specifies the bridge identifier
                    of the customer's device "
    ::= { tmnxTstpNotifyObjs 1 }

tmnxCustomerRootBridgeId OBJECT-TYPE
    SYNTAX         BridgeId
    MAX-ACCESS     accessible-for-notify
    STATUS         current
    DESCRIPTION    "tmnxCustomerRootBridgeId specifies the bridge identifier
                    of the customer's designated root."
    ::= { tmnxTstpNotifyObjs 2 }

tmnxOtherBridgeId OBJECT-TYPE
    SYNTAX         BridgeId
    MAX-ACCESS     accessible-for-notify
    STATUS         current
    DESCRIPTION    "tmnxOtherBridgeId specifies the bridge identifier of
                    the device from which a BPDU was received."
    ::= { tmnxTstpNotifyObjs 3 }

tmnxOldSdpBindTlsStpPortState OBJECT-TYPE
    SYNTAX         TStpPortState
    MAX-ACCESS     accessible-for-notify
    STATUS         current
    DESCRIPTION    "tmnxOldSdpBindTlsStpPortState specifies the previous
                    state of an SDP binding."
    ::= { tmnxTstpNotifyObjs 4 }

tmnxVcpState OBJECT-TYPE
    SYNTAX         TStpPortState
    MAX-ACCESS     accessible-for-notify
    STATUS         current
    DESCRIPTION    "tmnxVcpState specifies the current state of a Virtual
                    Core Port (VCP)."
    ::= { tmnxTstpNotifyObjs 5 }

-- ------------------------------------
-- TLS STP traps
-- ------------------------------------
topologyChangeVcpState NOTIFICATION-TYPE
    OBJECTS {
        custId,
        svcId,
        tmnxVcpState
    }
    STATUS          current
    DESCRIPTION     "The topologyChangeVcpState   notification is generated
                     when a VCP has transitioned its state from disabled to
                     forwarding   or   from  forwarding  to  disabled.  The
                     spanning  tree  topology  has been modified and it may
                     denote  loss  of  customer access or redundancy. Check
                     the  new  topology against the provisioned topology to
                     determine severity of connectivity loss."
    ::= { tstpTraps 3 }

newRootVcpState NOTIFICATION-TYPE
    OBJECTS {
        custId,
        svcId
    }
    STATUS          current
    DESCRIPTION     "The newRootVcpState notification is generated when the
                     previous  root bridge has been aged out and a new root
                     bridge has been elected. The new root bridge creates a
                     new  spanning  tree topology and it may denote loss of
                     customer  access or redundancy. Check the new topology
                     against the provisioned topology to determine severity
                     of connectivity loss."
    ::= { tstpTraps 4 }

newRootBridge NOTIFICATION-TYPE
    OBJECTS {
        custId,
        svcId
    }
    STATUS          current
    DESCRIPTION     "The newRootBridge  notification is generated when this
                     bridge  has been elected as the new root bridge. A new
                     root  bridge  creates a new spanning tree topology and
                     may  denote  loss  of  customer  access or redundancy.
                     Check   the   new  topology  against  the  provisioned
                     topology to determine severity of connectivity loss."
    ::= { tstpTraps 7 }

vcpActiveProtocolChange NOTIFICATION-TYPE
    OBJECTS {
        custId,
        svcId,
        svcTlsStpVcpOperProtocol
    }
    STATUS          current
    DESCRIPTION     "The  vcpActiveProtocolChange notification is generated
                     when  the  spanning  tree protocol on this VCP changes
                     from  rstp  to  stp  or  vise  versa.  No  recovery is
                     needed."
    ::= { tstpTraps 32 }

tmnxNewCistRegionalRootBridge NOTIFICATION-TYPE
    OBJECTS {
        svcId,
        svcTlsStpCistRegionalRoot
    }
    STATUS          current
    DESCRIPTION     "The tmnxNewCistRegionalRootBridge notification is
                     generated when a new regional root bridge has been elected
                     for the Common and Internal Spanning Tree. A new regional
                     root bridge  creates a new spanning tree topology and may
                     denote  loss  of  customer  access or redundancy. Check
                     the   new  topology  against  the provisioned  topology
                     to determine severity of connectivity loss."
    ::= { tstpTraps 33 }

tmnxNewMstiRegionalRootBridge NOTIFICATION-TYPE
    OBJECTS {
        svcId,
        svcMstiInstanceId,
        tlsMstiRegionalRoot
    }
    STATUS          current
    DESCRIPTION     "The tmnxNewMstiRegionalRootBridge notification is
                     generated when a new regional root bridge has been elected
                     for the Multiple Spanning Tree Instance. A new regional
                     root bridge  creates a new spanning tree topology and may
                     denote  loss  of  customer  access or redundancy. Check
                     the   new  topology  against  the provisioned  topology
                     to determine severity of connectivity loss."
    ::= { tstpTraps 34 }

topologyChangePipMajorState NOTIFICATION-TYPE
    OBJECTS {
        custId,
        svcId
    }
    STATUS         current
    DESCRIPTION
        "The topologyChangePipMajorState notification is generated when
        a PIP Uplink has transitioned its state from learning to forwarding or
        from forwarding to blocking or broken. The spanning tree topology has
        been modified and it may denote loss of customer access or redundancy.
        Check the new topology against the provisioned topology to determine the
        severity of connectivity loss."
    ::= { tstpTraps 39 }

topologyChangePipState NOTIFICATION-TYPE
    OBJECTS {
        custId,
        svcId
    }
    STATUS          current
    DESCRIPTION
        "The topologyChangePipState notification is generated when a PIP Uplink
        has transitioned state to blocking or broken from a state other than
        forwarding. This event complements what is not covered by
        topologyChangePipMajorState. The spanning tree topology has been
        modified and it may denote loss of customer access or redundancy. Check
        the new topology against the provisioned topology to determine severity
        of connectivity loss."
    ::= { tstpTraps 40 }

tmnxPipStpExcepCondStateChng NOTIFICATION-TYPE
    OBJECTS {
        custId,
        svcId,
        tlsPipStpException
    }
    STATUS          current
    DESCRIPTION
        "The tmnxPipStpExcepCondStateChng notification is generated when the
        value of the object tlsPipStpException has changed, i.e. when the
        exception condition changes on the indicated PIP Uplink."
    ::= { tstpTraps 41 }

pipActiveProtocolChange NOTIFICATION-TYPE
    OBJECTS {
        custId,
        svcId
    }
    STATUS          current
    DESCRIPTION
        "The pipActiveProtocolChange notification is generated when the
        spanning tree protocol on this PIP Uplink changes from rstp to stp or
        vice-versa.  No recovery is needed."
    ::= { tstpTraps 42 }

-- ----------------------------------------------------------------------------
-- Conformance Information
-- ----------------------------------------------------------------------------
tmnxCustCompliances OBJECT IDENTIFIER ::= { tmnxCustConformance 1 }
tmnxCustGroups      OBJECT IDENTIFIER ::= { tmnxCustConformance 2 }

tmnxSvcCompliances  OBJECT IDENTIFIER ::= { tmnxSvcConformance 1 }
tmnxSvcGroups       OBJECT IDENTIFIER ::= { tmnxSvcConformance 2 }

tmnxTstpCompliances OBJECT IDENTIFIER ::= { tmnxTstpConformance 1 }
tmnxTstpGroups      OBJECT IDENTIFIER ::= { tmnxTstpConformance 2 }

-- ----------------------------------------------
-- Compliance Statements
-- ----------------------------------------------
tmnxCustCompliance MODULE-COMPLIANCE
    STATUS  current
    DESCRIPTION
        "The compliance statement for management of services customers
         on Alcatel 7x50 SR series systems."
    MODULE  -- this module
        MANDATORY-GROUPS
        {
            tmnxCustV6v0Group
        }
    ::= { tmnxCustCompliances 100 }

tmnxSvc7450V6v0Compliance MODULE-COMPLIANCE
    STATUS  current
    DESCRIPTION
        "The compliance statement for management of services
         on Alcatel 7450 ESS series systems release R6.0."
    MODULE  -- this module
        MANDATORY-GROUPS
        {
            tmnxSvcV6v0Group,
            tmnxSvcTlsV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV6v0Group,
            tmnxSvcEndPointV6v0Group,
            tmnxSvcPEV6v0Group,
            tmnxSvcIfDHCP6V6v0Group,
            tmnxSvcTlsBackbone6v0Group,
            tmnxSvcTlsBgpV6v0Group,
            tmnxSvcEpipeV6v0Group,
            tmnxSvcTlsPipV6v0Group,
            tmnxSvcObsoletedV6v0Group,
            tmnxSvcNotifyV6v0Group
            -- tmnxApipeV3v0Group
            -- tmnxSvcRoutedCOV5v0Group
            -- tmnxSvcBsxV6v0Group
        }
    ::= { tmnxSvcCompliances 100 }

tmnxSvc7750V6v0Compliance MODULE-COMPLIANCE
    STATUS  current
    DESCRIPTION
        "The compliance statement for management of services
         on Alcatel 7750 SR series systems release R6.0."
    MODULE  -- this module
        MANDATORY-GROUPS
        {
            tmnxSvcV6v0Group,
            tmnxSvcTlsV6v0Group,
            tmnxSvcTlsFdbV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV6v0Group,
            tmnxSvcEndPointV6v0Group,
            tmnxSvcPEV6v0Group,
            tmnxSvcIfDHCP6V6v0Group,
            tmnxSvcTlsBackbone6v0Group,
            tmnxSvcTlsBgpV6v0Group,
            tmnxSvcEpipeV6v0Group,
            tmnxSvcTlsPipV6v0Group,
            tmnxSvcObsoletedV6v0Group,
            tmnxSvcNotifyV6v0Group,
            tmnxApipeV3v0Group,
            tmnxSvcRoutedCOV5v0Group
            -- tmnxSvcBsxV6v0Group
        }
    ::= { tmnxSvcCompliances 101 }

tmnxSvc7710V6v0Compliance MODULE-COMPLIANCE
    STATUS  current
    DESCRIPTION
        "The compliance statement for management of services
         on Alcatel 7710 SR series systems release R6.0."
    MODULE  -- this module
        MANDATORY-GROUPS
        {
            tmnxSvcV6v0Group,
            tmnxSvcTlsV6v0Group,
            tmnxSvcTlsFdbV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV6v0Group,
            tmnxSvcEndPointV6v0Group,
            tmnxSvcPEV6v0Group,
            tmnxSvcIfDHCP6V6v0Group,
            tmnxSvcTlsBackbone6v0Group,
            tmnxSvcTlsBgpV6v0Group,
            tmnxSvcEpipeV6v0Group,
            tmnxSvcTlsPipV6v0Group,
            tmnxSvcObsoletedV6v0Group,
            tmnxSvcNotifyV6v0Group,
            tmnxApipeV3v0Group,
            tmnxSvcRoutedCOV5v0Group
            -- tmnxSvcBsxV6v0Group
        }
    ::= { tmnxSvcCompliances 102 }

-- ----------------------------------------------
-- customer OBJECT-GROUPs
-- ----------------------------------------------
tmnxCustV6v0Group OBJECT-GROUP
    OBJECTS {
      custNumEntries,
      custNextFreeId,
      custId,
      custRowStatus,
      custDescription,
      custContact,
      custPhone,
      custLastMgmtChange,
      custMultSvcSiteName,
      custMultSvcSiteRowStatus,
      custMultSvcSiteDescription,
      custMultSvcSiteScope,
      custMultSvcSiteAssignment,
      custMultSvcSiteIngressSchedulerPolicy,
      custMultSvcSiteEgressSchedulerPolicy,
      custMultSvcSiteLastMgmtChange,
      custMultSvcSiteTodSuite,
      custMultSvcSiteCurrentIngrSchedPlcy,
      custMultSvcSiteCurrentEgrSchedPlcy,
      custMultSvcSiteEgressAggRateLimit,
      custMultSvcSiteIntendedIngrSchedPlcy,
      custMultSvcSiteIntendedEgrSchedPlcy,
      custMultSvcSiteFrameBasedAccnt,
      custIngQosSchedStatsForwardedPackets,
      custIngQosSchedStatsForwardedOctets,
      custEgrQosSchedStatsForwardedPackets,
      custEgrQosSchedStatsForwardedOctets,
      custIngQosPortSchedFwdPkts,
      custIngQosPortSchedFwdOctets,
      custEgrQosPortSchedFwdPkts,
      custEgrQosPortSchedFwdOctets,
      custMssIngQosSRowStatus,
      custMssIngQosSLastMgmtChange,
      custMssIngQosSOverrideFlags,
      custMssIngQosSPIR,
      custMssIngQosSCIR,
      custMssIngQosSSummedCIR,
      custMssEgrQosSRowStatus,
      custMssEgrQosSLastMgmtChange,
      custMssEgrQosSOverrideFlags,
      custMssEgrQosSPIR,
      custMssEgrQosSCIR,
      custMssEgrQosSSummedCIR,
      custIngSchedPlcyStatsFwdPkt,
      custIngSchedPlcyStatsFwdOct,
      custEgrSchedPlcyStatsFwdPkt,
      custEgrSchedPlcyStatsFwdOct,
      custIngSchedPlcyPortStatsFwdPkt,
      custIngSchedPlcyPortStatsFwdOct,
      custEgrSchedPlcyPortStatsFwdPkt,
      custEgrSchedPlcyPortStatsFwdOct
    }
    STATUS      current
    DESCRIPTION
        "The group of objects supporting management of Services customers
         general capabilities on Alcatel 7x50 SR series systems."
    ::= { tmnxCustGroups 100 }

-- ----------------------------------------------
-- service OBJECT-GROUPs
-- ----------------------------------------------
tmnxSvcV6v0Group OBJECT-GROUP
    OBJECTS {
      svcNumEntries,
      svcId,
      svcRowStatus,
      svcType,
      svcCustId,
      svcIpRouting,
      svcDescription,
      svcMtu,
      svcAdminStatus,
      svcOperStatus,
      svcNumSaps,
      svcNumSdps,
      svcLastMgmtChange,
      svcDefMeshVcId,
      svcVpnId,
      svcVRouterId,
      svcAutoBind,
      svcLastStatusChange,
      svcVllType,
      svcMgmtVpls,
      svcRadiusDiscovery,
      svcRadiusUserName,
      svcRadiusUserNameType,
      svcVcSwitching,
      svcRadiusPEDiscPolicy,
      svcRadiusDiscoveryShutdown,
      svcVplsType,
      svcTotalFdbMimDestIdxEntries
    }
    STATUS      current
    DESCRIPTION
        "The group of objects supporting management of Services 
         general capabilities on Alcatel 7x50 SR series systems."
    ::= { tmnxSvcGroups 101 }

tmnxSvcTlsV6v0Group OBJECT-GROUP
    OBJECTS {
      svcTlsMacLearning,
      svcTlsDiscardUnknownDest,
      svcTlsFdbTableSize,
      svcTlsFdbNumEntries,
      svcTlsFdbNumStaticEntries,
      svcTlsFdbLocalAgeTime,
      svcTlsFdbRemoteAgeTime,
      svcTlsStpAdminStatus,
      svcTlsStpPriority,
      svcTlsStpBridgeAddress,
      svcTlsStpTimeSinceTopologyChange,
      svcTlsStpTopologyChanges,
      svcTlsStpDesignatedRoot,
      svcTlsStpRootCost,
      svcTlsStpRootPort,
      svcTlsStpMaxAge,
      svcTlsStpHelloTime,
      svcTlsStpForwardDelay,
      svcTlsStpBridgeMaxAge,
      svcTlsStpBridgeHelloTime,
      svcTlsStpBridgeForwardDelay,
      svcTlsStpOperStatus,
      svcTlsStpVirtualRootBridgeStatus,
      svcTlsMacAgeing,
      svcTlsStpTopologyChangeActive,
      svcTlsFdbTableFullHighWatermark,
      svcTlsFdbTableFullLowWatermark,
      svcTlsVpnId,
      svcTlsCustId,
      svcTlsStpVersion,
      svcTlsStpHoldCount,
      svcTlsStpPrimaryBridge,
      svcTlsStpBridgeInstanceId,
      svcTlsStpVcpOperProtocol,
      svcTlsMacMoveMaxRate,
      svcTlsMacMoveRetryTimeout,
      svcTlsMacMoveAdminStatus,
      svcTlsMacRelearnOnly,
      svcTlsMfibTableSize,
      svcTlsMfibTableFullHighWatermark,
      svcTlsMfibTableFullLowWatermark,
      svcTlsMacFlushOnFail,
      svcTlsStpRegionName,
      svcTlsStpRegionRevision,
      svcTlsStpBridgeMaxHops,
      svcTlsStpCistRegionalRoot,
      svcTlsStpCistIntRootCost,
      svcTlsStpCistRemainingHopCount,
      svcTlsStpCistRegionalRootPort,
      svcTlsFdbNumLearnedEntries,
      svcTlsFdbNumOamEntries,
      svcTlsFdbNumDhcpEntries,
      svcTlsFdbNumHostEntries,
      svcTlsShcvAction,
      svcTlsShcvSrcIp,
      svcTlsShcvSrcMac,
      svcTlsShcvInterval,
      svcTlsPriPortsCumulativeFactor,
      svcTlsSecPortsCumulativeFactor,
      svcTlsL2ptTermEnabled,
      svcTlsPropagateMacFlush,
      svcTlsMrpAdminStatus,
      svcTlsMrpMaxAttributes,
      svcTlsMrpAttributeCount,
      svcTlsMrpFailedRegisterCount,
      svcTlsMrpFloodTime,
      svcTlsMrpAttrTblHighWatermark,
      svcTlsMrpAttrTblLowWatermark,
      svcTlsMcPathMgmtPlcyName,
      tlsEgrMcGrpAdminQinqFixedTagVal
    }
    STATUS      current
    DESCRIPTION
        "The group of objects supporting management of Services TLS
         general capabilities on Alcatel 7x50 SR series systems."
    ::= { tmnxSvcGroups 102 }

tmnxSvcTlsFdbV6v0Group OBJECT-GROUP
    OBJECTS {
      tlsFdbMacAddr,
      tlsFdbRowStatus,
      tlsFdbType,
      tlsFdbLocale,
      tlsFdbPortId,
      tlsFdbEncapValue,
      tlsFdbSdpId,
      tlsFdbVcId,
      tlsFdbVpnId,
      tlsFdbCustId,
      tlsFdbLastStateChange,
      tlsFdbProtected,
      tlsFdbBackboneDstMac,
      tlsFdbNumIVplsMac,
      tlsFdbEndPointName,
      tlsFdbEPMacOperSdpId,
      tlsFdbEPMacOperVcId,
      tlsFdbPbbNumEpipes,
      tlsProtMacRowStatus,
      tlsProtMacLastMgmtChange
    }
    STATUS      current
    DESCRIPTION
        "The group of objects supporting management of Services TLS FDB
         capabilities on Alcatel 7x50 SR series systems."
    ::= { tmnxSvcGroups 103 }

tmnxSvcIesIfV6v0Group OBJECT-GROUP
    OBJECTS {
      iesIfIndex,
      iesIfRowStatus,
      iesIfName,
      iesIfDescription,
      iesIfAdminStatus,
      iesIfOperStatus,
      iesIfLastMgmtChange,
      iesIfVpnId,
      iesIfCustId,
      iesIfLoopback,
      iesIfLastStatusChange,
      iesIfType,
      iesIfShcvSource,
      iesIfShcvAction,
      iesIfShcvInterval,
      iesGrpIfOperUpWhileEmpty
    }
    STATUS      current
    DESCRIPTION
        "The group of objects supporting management of Services IES
         interface capabilities on Alcatel 7x50 SR series systems."
    ::= { tmnxSvcGroups 104 }

tmnxSvcTlsShgV6v0Group OBJECT-GROUP
    OBJECTS {
      tlsShgRowStatus,
      tlsShgCustId,
      tlsShgInstanceId,
      tlsShgDescription,
      tlsShgLastMgmtChange,
      tlsShgResidential,
      tlsShgRestProtSrcMac,
      tlsShgRestUnprotDstMac,
      tlsShgRestProtSrcMacAction,
      tlsShgCreationOrigin
    }
    STATUS      current
    DESCRIPTION
        "The group of objects supporting management of Services TLS
         Split Hoirizon Group capabilities on Alcatel 7x50 SR series systems."
    ::= { tmnxSvcGroups 105 }

tmnxSvcTlsMFibV6v0Group OBJECT-GROUP
    OBJECTS {
      tlsMFibFwdOrBlk,
      tlsMFibSvcId,
      tlsMFibStatsForwardedPkts,
      tlsMFibStatsForwardedOctets
    }
    STATUS      current
    DESCRIPTION
        "The group of objects supporting management of Services TLS MFib
         capabilities on Alcatel 7x50 SR series systems."
    ::= { tmnxSvcGroups 106 }

tmnxSvcRdntV6v0Group OBJECT-GROUP
    OBJECTS {
      tlsRdntGrpRowStatus,
      tlsRdntGrpDescription,
      tlsRdntGrpLastMgmtChange,
      tlsRdntGrpMemberRowStatus,
      tlsRdntGrpMemberLastMgmtChange
    }
    STATUS      current
    DESCRIPTION
        "The group of objects supporting management of Services Redundancy
         group capabilities on Alcatel 7x50 SR series systems."
    ::= { tmnxSvcGroups 107 }

tmnxSvcTlsMstiV6v0Group OBJECT-GROUP
    OBJECTS {
      tlsMstiRowStatus,
      tlsMstiPriority,
      tlsMstiLastMgmtChange,
      tlsMstiRegionalRoot,
      tlsMstiIntRootCost,
      tlsMstiRemainingHopCount,
      tlsMstiRegionalRootPort,
      tlsMstiMvplsRowStatus
    }
    STATUS      current
    DESCRIPTION
        "The group of objects supporting management of Services TLS MSTI
         capabilities on Alcatel 7x50 SR series systems."
    ::= { tmnxSvcGroups 108 }

tmnxSvcTlsEgrV6v0Group OBJECT-GROUP
    OBJECTS {
      tlsEgrMcGrpRowStatus,
      tlsEgrMcGrpLastMgmtChange,
      tlsEgrMcGrpDescription,
      tlsEgrMcGrpChainLimit,
      tlsEgrMcGrpEncapType,
      tlsEgrMcGrpDot1qEtherType,
      tlsEgrMcGrpQinqEtherType,
      tlsEgrMcGrpMacFilterId,
      tlsEgrMcGrpIpFilterId,
      tlsEgrMcGrpIpv6FilterId,
      tlsEgrMcGrpQinqFixedTagPosition,
      tlsEgrMcGrpOperQinqFixedTagVal
    }
    STATUS      current
    DESCRIPTION
        "The group of objects supporting management of Services TLS Egress
         capabilities on Alcatel 7x50 SR series systems."
    ::= { tmnxSvcGroups 109 }
      
tmnxSvcDhcpV6v0Group OBJECT-GROUP
    OBJECTS {
      svcDhcpLseStateLocale,
      svcDhcpLseStatePortId,
      svcDhcpLseStateEncapValue,
      svcDhcpLseStateSdpId,
      svcDhcpLseStateVcId,
      svcDhcpLseStateChAddr,
      svcDhcpLseStateRemainLseTime,
      svcDhcpLseStateOption82,
      svcDhcpLseStatePersistKey,
      svcDhcpLseStateSubscrIdent,
      svcDhcpLseStateSubProfString,
      svcDhcpLseStateSlaProfString,
      svcDhcpLseStateShcvOperState,
      svcDhcpLseStateShcvChecks,
      svcDhcpLseStateShcvReplies,
      svcDhcpLseStateShcvReplyTime,
      svcDhcpLseStateClientId,
      svcDhcpLseStateIAID,
      svcDhcpLseStateIAIDType,
      svcDhcpLseStateCiAddrMaskLen,
      svcDhcpLseStateRetailerSvcId,
      svcDhcpLseStateRetailerIf,
      svcDhcpLseStateAncpString,
      svcDhcpLseStateFramedIpNetMaskTp,
      svcDhcpLseStateFramedIpNetMask,
      svcDhcpLseStateBCastIpAddrType,
      svcDhcpLseStateBCastIpAddr,
      svcDhcpLseStateDefaultRouterTp,
      svcDhcpLseStateDefaultRouter,
      svcDhcpLseStatePrimaryDnsType,
      svcDhcpLseStatePrimaryDns,
      svcDhcpLseStateSecondaryDnsType,
      svcDhcpLseStateSecondaryDns,
      svcDhcpLseStateSessionTimeout,
      svcDhcpLseStateServerLeaseStart,
      svcDhcpLseStateServerLastRenew,
      svcDhcpLseStateServerLeaseEnd,
      svcDhcpLseStateDhcpServerAddrType,
      svcDhcpLseStateDhcpServerAddr,
      svcDhcpLseStateOriginSubscrId,
      svcDhcpLseStateOriginStrings,
      svcDhcpLseStateOriginLeaseInfo,
      svcDhcpLseStateDhcpClientAddrType,
      svcDhcpLseStateDhcpClientAddr,
      svcDhcpLseStateLeaseSplitActive,
      svcDhcpLseStateInterDestId,
      svcDhcpLseStatePrimaryNbnsType,
      svcDhcpLseStatePrimaryNbns,
      svcDhcpLseStateSecondaryNbnsType,
      svcDhcpLseStateSecondaryNbns,
      svcDhcpLseStateNextHopMacAddr,
      svcDhcpLseStateModifySubIndent,
      svcDhcpLseStateModifySubProfile,
      svcDhcpLseStateModifySlaProfile,
      svcDhcpLseStateEvaluateState,
      svcDhcpLseStateModInterDestId,
      svcDhcpLseStateModifyAncpString,
      svcDhcpLseStateForceRenew,
      svcDhcpManagedRouteStatus
    }
    STATUS      current
    DESCRIPTION
        "The group of objects supporting management of Services DHCP Lease
         capabilities on Alcatel 7x50 SR series systems."
    ::= { tmnxSvcGroups 110 }

tmnxSvcEndPointV6v0Group OBJECT-GROUP
    OBJECTS {
      svcEndPointRowStatus,
      svcEndPointDescription,
      svcEndPointTxActiveType,
      svcEndPointTxActivePortId,
      svcEndPointTxActiveEncap,
      svcEndPointTxActiveSdpId,
      svcEndPointForceSwitchOver,
      svcEndPointForceSwitchOverSdpId,
      svcEndPointActiveHoldDelay,
      svcEndPointIgnoreStandbySig,
      svcEndPointMacPinning,
      svcEndPointMacLimit,
      svcEndPointSuppressStandbySig,
      svcEndPointTxActiveChangeCount,
      svcEndPointTxActiveLastChange,
      svcEndPointTxActiveUpTime,
      svcEndPointRevertTime,
      svcEndPointRevertTimeCountDn
    }
    STATUS      current
    DESCRIPTION
        "The group of objects supporting management of Services endpoint
         capabilities on Alcatel 7x50 SR series systems."
    ::= { tmnxSvcGroups 111 }

tmnxSvcPEV6v0Group OBJECT-GROUP
    OBJECTS {
      svcPEDiscoveryPolicyRowStatus,
      svcPEDiscoveryPolicyPassword,
      svcPEDiscoveryPolicyInterval,
      svcPEDiscoveryPolicyTimeout,
      svcPEDiscPolServerRowStatus,
      svcPEDiscPolServerAddressType,
      svcPEDiscPolServerAddress,
      svcPEDiscPolServerSecret,
      svcPEDiscPolServerOperStatus,
      svcPEDiscPolServerPort
    }
    STATUS      current
    DESCRIPTION
        "The group of objects supporting management of Services PE Discovery
         capabilities on Alcatel 7x50 SR series systems."
    ::= { tmnxSvcGroups 112 }

tmnxSvcIfDHCP6V6v0Group OBJECT-GROUP
    OBJECTS {
      svcIfDHCP6MsgStatsLstClrd,
      svcIfDHCP6MsgStatsRcvd,
      svcIfDHCP6MsgStatsSent,
      svcIfDHCP6MsgStatsDropped
    }
    STATUS      current
    DESCRIPTION
        "The group of objects supporting management of Services interface DHCP
         capabilities on Alcatel 7x50 SR series systems."
    ::= { tmnxSvcGroups 114 }

tmnxSvcTlsBackbone6v0Group OBJECT-GROUP
    OBJECTS {
      svcTlsBackboneSrcMac,
      svcTlsBackboneVplsSvcId,
      svcTlsBackboneVplsSvcISID,
      svcTlsBackboneOperSrcMac,
      svcTlsBackboneOperVplsSvcISID,
      svcTlsBackboneLDPMacFlush,
      svcTlsBackboneVplsStp
    }
    STATUS      current
    DESCRIPTION
        "The group of objects supporting management of Services PBB
         capabilities on Alcatel 7x50 SR series systems."
    ::= { tmnxSvcGroups 115 }

tmnxSvcTlsBgpV6v0Group OBJECT-GROUP
    OBJECTS {
      svcTlsBgpADTableLastChanged,
      svcTlsBgpADRowStatus,
      svcTlsBgpADLastChanged,
      svcTlsBgpADVplsId,
      svcTlsBgpADVsiPrefix,
      svcTlsBgpADVsiRD,
      svcTlsBgpADExportRteTarget,
      svcTlsBgpADVsiExportPolicy1,
      svcTlsBgpADVsiExportPolicy2,
      svcTlsBgpADVsiExportPolicy3,
      svcTlsBgpADVsiExportPolicy4,
      svcTlsBgpADVsiExportPolicy5,
      svcTlsBgpADImportRteTarget,
      svcTlsBgpADVsiImportPolicy1,
      svcTlsBgpADVsiImportPolicy2,
      svcTlsBgpADVsiImportPolicy3,
      svcTlsBgpADVsiImportPolicy4,
      svcTlsBgpADVsiImportPolicy5,
      svcTlsBgpADAdminStatus
    }
    STATUS      current
    DESCRIPTION
        "The group of objects supporting management of Services BGP AD
         capabilities on Alcatel 7x50 SR series systems."
    ::= { tmnxSvcGroups 116 }
      
tmnxSvcEpipeV6v0Group OBJECT-GROUP
    OBJECTS {
      svcEpipePbbTableLastChanged,
      svcEpipePbbRowStatus,
      svcEpipePbbLastChngd,
      svcEpipePbbBvplsSvcId,
      svcEpipePbbBvplsDstMac,
      svcEpipePbbSvcISID
    }
    STATUS      current
    DESCRIPTION
        "The group of objects supporting management of Services PBB Epipe
         capabilities on Alcatel 7x50 SR series systems."
    ::= { tmnxSvcGroups 117 }

tmnxSvcTlsPipV6v0Group OBJECT-GROUP
    OBJECTS {
      tlsPipStpPortState,
      tlsPipStpPortRole,
      tlsPipStpDesignatedBridge,
      tlsPipStpDesignatedPort,
      tlsPipStpException,
      tlsPipStpForwardTransitions,
      tlsPipStpInConfigBpdus,
      tlsPipStpInTcnBpdus,
      tlsPipStpInRstBpdus,
      tlsPipStpInMstBpdus,
      tlsPipStpInBadBpdus,
      tlsPipStpOutConfigBpdus,
      tlsPipStpOutTcnBpdus,
      tlsPipStpOutRstBpdus,
      tlsPipStpOutMstBpdus,
      tlsPipStpOperStatus,
      tlsPipStpMvplsPruneState,
      tlsPipStpOperProtocol,
      tlsPipStpPortNum,
      tlsPipMstiPortRole,
      tlsPipMstiPortState,
      tlsPipMstiDesignatedBridge,
      tlsPipMstiDesignatedPort
    }
    STATUS      current
    DESCRIPTION
        "The group of objects supporting management of Services TLS PIP
         capabilities on Alcatel 7x50 SR series systems."
    ::= { tmnxSvcGroups 118 }

-- This groups is not in 7450
tmnxApipeV3v0Group OBJECT-GROUP
    OBJECTS {
        svcApipeInterworking
    }
    STATUS      current
    DESCRIPTION
        "The  group  of  objects supporting management of APIPE services on
         Alcatel 7x50 SR series systems release 3.0."
    ::= { tmnxSvcGroups 119 }

-- This groups is not in 7450
tmnxSvcRoutedCOV5v0Group OBJECT-GROUP
    OBJECTS {
        iesIfParentIf,
        iesIfFwdServId,
        iesIfFwdSubIf,
        iesGrpIfRedInterface,
        svcWholesalerNumStaticHosts,
        svcWholesalerNumDynamicHosts
    }
    STATUS      current
    DESCRIPTION
        "The group of objects supporting routed CO Alcatel 7x50 SR systems."
    ::= { tmnxSvcGroups 120 }
    
-- This group is not in 7710
tmnxSvcBsxV6v0Group OBJECT-GROUP
    OBJECTS {
      svcDhcpLseStateAppProfString,
      svcDhcpLseStateModifyAppProfile
    }
    STATUS      current
    DESCRIPTION
        "The group of objects supporting management of BSX (Application
         Assurance) capabilities on Alcatel 7x50 SR series systems."
    ::= { tmnxSvcGroups 121 }

-- Notification objects group 

tmnxSvcNotifyObjsV6v0Group OBJECT-GROUP
    OBJECTS {
      svcDhcpRestoreLseStateCiAddr,
      svcDhcpRestoreLseStateProblem,
      svcDhcpLseStateOldCiAddr,
      svcDhcpLseStateOldChAddr,
      svcDhcpLseStateNewCiAddr,
      svcDhcpLseStateNewChAddr,
      svcDhcpClientLease,
      svcDhcpPacketProblem,
      svcDhcpLseStatePopulateError,
      hostConnectivityCiAddrType,
      hostConnectivityCiAddr,
      hostConnectivityChAddr,
      protectedMacForNotify,
      staticHostDynamicMacIpAddress,
      staticHostDynamicMacConflict,
      tmnxSvcObjRow,
      tmnxSvcObjRowDescr,
      tmnxSvcObjTodSuite,
      tmnxFailureDescription,
      svcDhcpProxyError,
      svcDhcpCoAError,
      svcDhcpSubAuthError,
      svcTlsMrpAttrRegFailedReason,
      svcTlsMrpAttrType,
      svcTlsMrpAttrValue,
      svcMstiInstanceId,
      tmnxCustomerBridgeId,
      tmnxCustomerRootBridgeId,
      tmnxOtherBridgeId,
      tmnxOldSdpBindTlsStpPortState,
      tmnxVcpState,
      macPinningMacAddress,
      macPinningPinnedRow,
      macPinningPinnedRowDescr,
      macPinningViolatingRow,
      macPinningViolatingRowDescr
    }
    STATUS      current
    DESCRIPTION
        "The group of objects supporting management of Services
         notification objects on Alcatel 7x50 SR series systems."
    ::= { tmnxSvcGroups 200 }

-- Obsoleted (300)

tmnxSvcObsoletedV6v0Group OBJECT-GROUP
    OBJECTS {
      svcTlsStpHoldTime,
      tlsMFibInfoFwdOrBlk,
      tlsMFibInfoSvcId,
      tlsMFibGrpSrcStatsForwardedPkts,
      tlsMFibGrpSrcStatsForwardedOctets,
      tlsDHCPClientLease,
      tlsDhcpLseStateOldCiAddr,
      tlsDhcpLseStateOldChAddr,
      tlsDhcpLseStateNewCiAddr,
      tlsDhcpLseStateNewChAddr,
      tlsDhcpRestoreLseStateCiAddr,
      tlsDhcpRestoreLseStateSvcId,
      tlsDhcpRestoreLseStatePortId,
      tlsDhcpRestoreLseStateEncapVal,
      tlsDhcpRestoreLseStateProblem,
      tlsDhcpPacketProblem,
      tlsDhcpLseStatePopulateError
    }
    STATUS      current
    DESCRIPTION
        "The group of obsolete objects for the services feature
         on Alcatel 7x50 SR series systems."
    ::= { tmnxSvcGroups 300 }


-- ----------------------------
-- NOTIFICATION group
-- ----------------------------
tmnxSvcNotifyV6v0Group NOTIFICATION-GROUP
    NOTIFICATIONS   {
      svcStatusChanged,
      svcTlsFdbTableFullAlarmRaised,
      svcTlsFdbTableFullAlarmCleared,
      iesIfStatusChanged,
      svcTlsMfibTableFullAlarmRaised,
      svcTlsMfibTableFullAlarmCleared,
      svcTlsMacPinningViolation,
      svcDHCPLseStateRestoreProblem,
      tmnxSvcObjTodSuiteApplicFailed,
      tmnxEndPointTxActiveChanged,
      tmnxSvcPEDiscPolServOperStatChg,
      svcEndPointMacLimitAlarmRaised,
      svcEndPointMacLimitAlarmCleared,
      svcTlsMrpAttrRegistrationFailed,
      svcTlsMrpAttrTblFullAlarmRaised,
      svcTlsMrpAttrTblFullAlarmCleared,
      topologyChangeVcpState,
      newRootVcpState,
      newRootBridge,
      vcpActiveProtocolChange,
      tmnxNewCistRegionalRootBridge,
      tmnxNewMstiRegionalRootBridge,
      topologyChangePipMajorState,
      topologyChangePipState,
      tmnxPipStpExcepCondStateChng,
      pipActiveProtocolChange,
      svcFdbMimDestTblFullAlrm,
      svcFdbMimDestTblFullAlrmCleared,
      svcDHCPMiscellaneousProblem,
      svcPersistencyProblem
    }
    STATUS      current
    DESCRIPTION
        "The group of notifications for the services feature
         on Alcatel 7x50 SR series systems."
    ::= { tmnxSvcGroups 401 }

tmnxSvcNotifyObsoletedGroup NOTIFICATION-GROUP
    NOTIFICATIONS   {
      custCreated,
      custDeleted,
      custMultSvcSiteCreated,
      custMultSvcSiteDeleted,
      svcCreated,
      svcDeleted,
      iesIfCreated,
      iesIfDeleted,
      svcTlsDHCPLseStRestoreProblem,
      svcTlsDHCPLseStatePopulateErr
    }
    STATUS      current
    DESCRIPTION
        "The group of notifications for the services feature
         on Alcatel 7x50 SR series systems."
    ::= { tmnxSvcGroups 402 }

END
