-- FILE: alcatelIND1QoS.mib

-- Alcatel-Lucent Enterprise

-- This module provides authoritative enterprise-specific Simple Network
-- Management Protocol (SNMP) Management Information Base (MIB) definitions.

-- The right to make changes in specification and other information contained
-- in this document without prior notice is reserved.

-- No liability shall be assumed for any incidental, indirect, special, or
-- consequential damages whatsoever arising from or related to this document or
-- the information contained herein.

-- Vendors, end-users, and other interested parties are granted non-exclusive
-- license to use this specification in connection with management of the
-- products for which it is intended to be used.

-- Please consult with Customer Service to ensure the most appropriate version
-- of this document is used with the products in question:

-- Alcatel-Lucent Enterprise,
-- 26801 West Agoura Road
-- Agoura Hills, CA 91301-5122
-- United States Of America

-- Telephone:               +1 800 995 2696 

-- Electronic Mail: ebg_global_supportcenter@al-enterprise.com
-- World Wide Web: https://www.al-enterprise.com

-- Copyright (C) ALE USA Inc. 2014-2019
-- Copyright (C) 1995-2013 Alcatel-Lucent
-- ALL RIGHTS RESERVED WORLDWIDE

ALCATEL-IND1-QOS-MIB DEFINITIONS ::= BEGIN

IMPORTS
  OBJECT-TYPE, OBJECT-IDENTITY, MODULE-IDENTITY,
  Counter32, Counter64, Integer32, IpAddress
    FROM SNMPv2-SMI
  OBJECT-GROUP, MODULE-COMPLIANCE
    FROM SNMPv2-CONF
  DisplayString, MacAddress, RowStatus
    FROM SNMPv2-TC
  softentIND1QoS
    FROM ALCATEL-IND1-BASE
  InterfaceIndex   
    FROM IF-MIB 
  Ipv6Address
    FROM IPV6-TC;


alaQoSMIB MODULE-IDENTITY
  LAST-UPDATED "201910070000Z"
  ORGANIZATION "ALE USA Inc."
  CONTACT-INFO
        "Alcatel-Lucent Enterprise
          26801 West Agoura Road
        Agoura Hills, CA  91301-5122
          United States Of America

  Telephone:               +1 800 995 2696
  Electronic Mail:         ebg_global_supportcenter@al-enterprise.com
  World Wide Web:          https://www.al-enterprise.com"

  DESCRIPTION
		"QOS and filtering MIB"
		
  REVISION      "201910070000Z"
  DESCRIPTION
        "Updated the latest contact and Copyright information for ALE USA Inc."
  ::= { softentIND1QoS 1 }


alaQoSMIBObjects OBJECT-IDENTITY
  STATUS      current
  DESCRIPTION "Branch for QoS Managed Objects."
  ::= { alaQoSMIB 1 }


--
-- Definition of rule table
--

alaQoSRuleTable OBJECT-TYPE
  SYNTAX      SEQUENCE OF QoSRuleEntry
  MAX-ACCESS  not-accessible
  STATUS      current
  DESCRIPTION "Table of QoS Rule definitions"
  ::= { alaQoSMIBObjects 1 }

alaQoSRuleEntry OBJECT-TYPE
  SYNTAX      QoSRuleEntry
  MAX-ACCESS  not-accessible
  STATUS      current
  DESCRIPTION "Definition of QoS Rule"
  INDEX {
          alaQoSRuleName
        }
  ::= { alaQoSRuleTable 1 }

QoSRuleEntry ::=
  SEQUENCE
  {
    alaQoSRuleName                                          DisplayString,
    alaQoSRuleEnabled                                       INTEGER,
    alaQoSRuleSource                                        INTEGER,
    alaQoSRulePrecedence                                    Integer32,
    alaQoSRuleCondition                                     DisplayString,
    alaQoSRuleAction                                        DisplayString,
    alaQoSRuleReflexive                                     INTEGER,
    alaQoSRuleSave                                          INTEGER,
    alaQoSRuleLog                                           INTEGER,
    alaQoSRuleMatches                                       Counter32,
    alaQoSRuleEnforced                                      INTEGER,
    alaQoSRuleActive                                        INTEGER,
    alaQoSRuleRowStatus                                     RowStatus,
    alaQoSRuleValidityPeriod                                DisplayString,
    alaQoSRuleValidityPeriodStatus                          INTEGER,
    alaQoSRuleLogInterval                                   Integer32,
    alaQoSRuleCountType                                     INTEGER,
    alaQoSRulePacketCount                                   Counter64,
    alaQoSRuleByteCount                                     Counter64,
    alaQoSRuleExcessPacketCount                             Counter64,
    alaQoSRuleExcessByteCount                               Counter64,
    alaQoSRuleType                                          Integer32,
    alaQoSRuleTrapEvents                                    INTEGER,
    alaQoSRuleDefaultList                                   INTEGER,
    alaQoSRuleGreenCount								    Counter64,
    alaQoSRuleYellowCount                                   Counter64,
    alaQoSRuleRedCount				           				 Counter64,
    alaQoSRuleNonGreenCount                                 Counter64,
    alaQoSRuleNonRedCount                                   Counter64,
    alaQoSRuleAccounting                                    INTEGER,
    alaQoSRulePacketRate                                 Counter64,
    alaQoSRuleAccPacketCount                                           Counter64,
    alaQoSRuleAccByteCount                                    Counter64,
    alaQoSRuleBitRate                                           Counter64 
}

alaQoSRuleName OBJECT-TYPE
  SYNTAX      DisplayString (SIZE(0..31))
  MAX-ACCESS  not-accessible
  STATUS      current
  DESCRIPTION "Name of rule"
  ::= { alaQoSRuleEntry 1 }

alaQoSRuleEnabled OBJECT-TYPE
  SYNTAX      INTEGER {
                enable (1),
                disable (2)
              }
  MAX-ACCESS  read-create
  STATUS      current
  DESCRIPTION "Is this rule enabled or not"
  DEFVAL      { enable }
  ::= { alaQoSRuleEntry 2 }

alaQoSRuleSource OBJECT-TYPE
  SYNTAX      INTEGER {
                ldap (1),
                cli (2),
                blt (3),
                api (4),
                imp (5)
              }
  MAX-ACCESS  read-create
  STATUS      current
  DESCRIPTION "What entity created the rule."
  DEFVAL      { cli }
  ::= { alaQoSRuleEntry 3 }

alaQoSRulePrecedence OBJECT-TYPE
  SYNTAX      Integer32 (0..65535)
  MAX-ACCESS  read-create
  STATUS      current
  DESCRIPTION "Precedence value for rule.
               Rules are evaluated from higher precedence to lower.
               If rules have equal precedence, they are evaluated in
               the order they are received."
  DEFVAL      { 0 }
  ::= { alaQoSRuleEntry 4 }

alaQoSRuleCondition OBJECT-TYPE
  SYNTAX      DisplayString (SIZE(0..31))
  MAX-ACCESS  read-create
  STATUS      current
  DESCRIPTION "Name of the condition to use"
  ::= { alaQoSRuleEntry 5 }

alaQoSRuleAction OBJECT-TYPE
  SYNTAX      DisplayString (SIZE(0..31))
  MAX-ACCESS  read-create
  STATUS      current
  DESCRIPTION "Name of the action to use"
  ::= { alaQoSRuleEntry 6 }

alaQoSRuleReflexive OBJECT-TYPE
  SYNTAX      INTEGER {
                yes (1),
                no (2)
              }
  MAX-ACCESS  read-create
  STATUS      current
  DESCRIPTION "Indicator to tell if the rule is reflexive.  Reflexive rules
               allow specific return connections that would normally be denied."
  DEFVAL      { no }
  ::= { alaQoSRuleEntry 7 }

alaQoSRuleSave OBJECT-TYPE
  SYNTAX      INTEGER {
                yes (1),
                no (2)
              }
  MAX-ACCESS  read-create
  STATUS      current
  DESCRIPTION "Indicator to tell whether to write out the rule during
               snapshot commands."
  DEFVAL      { yes }
  ::= { alaQoSRuleEntry 8 }

alaQoSRuleLog OBJECT-TYPE
  SYNTAX      INTEGER {
                yes (1),
                no (2)
              }
  MAX-ACCESS  read-create
  STATUS      current
  DESCRIPTION "Indicator to tell whether to log matches to this rule
               in the QoS log."
  DEFVAL      { no }
  ::= { alaQoSRuleEntry 9 }

alaQoSRuleMatches OBJECT-TYPE
  SYNTAX      Counter32
  MAX-ACCESS  read-only
  STATUS      current
  DESCRIPTION "Number of times this rule has been matched."
  ::= { alaQoSRuleEntry 10 }

alaQoSRuleEnforced OBJECT-TYPE
  SYNTAX      INTEGER {
                yes (1),
                no (2)
              }
  MAX-ACCESS  read-only
  STATUS      current
  DESCRIPTION "Is this rule currenly being enforced on the switch."
  ::= { alaQoSRuleEntry 11 }

alaQoSRuleActive OBJECT-TYPE
  SYNTAX      INTEGER {
                yes (1),
                no (2)
              }
  MAX-ACCESS  read-only
  STATUS      current
  DESCRIPTION "Is this rule enforcable by the switch."
  ::= { alaQoSRuleEntry 12 }

alaQoSRuleRowStatus OBJECT-TYPE
  SYNTAX      RowStatus
  MAX-ACCESS  read-create
  STATUS      current
  DESCRIPTION "Used to create/delete rules according to the
               RowStatus convention"
  ::= { alaQoSRuleEntry 13 }

alaQoSRuleValidityPeriod OBJECT-TYPE
  SYNTAX      DisplayString (SIZE(0..31))
  MAX-ACCESS  read-create
  STATUS      current
  DESCRIPTION "Name of the validity period to use"
  ::= { alaQoSRuleEntry 14 }

alaQoSRuleValidityPeriodStatus OBJECT-TYPE
  SYNTAX      INTEGER {
                enabled (1),
                disabled (2)
              }
  MAX-ACCESS  read-create
  STATUS      current
  DESCRIPTION "Status field indicating whether there is a validity period
               associated with this rule"
  DEFVAL      { disabled }
  ::= { alaQoSRuleEntry 15 }

alaQoSRuleLogInterval OBJECT-TYPE
  SYNTAX      Integer32 (0..3600)
  MAX-ACCESS  read-create
  STATUS      current
  DESCRIPTION "How often to look for packets matching this rule when logging.  
               When 0 log as many as possible."
  DEFVAL      { 30 }
  ::= { alaQoSRuleEntry 16 }

alaQoSRuleCountType OBJECT-TYPE
  SYNTAX      INTEGER {
                packets (1),
                bytes (2)
              }
  MAX-ACCESS  read-create
  STATUS      current
  DESCRIPTION "Which rule statistics counters to update if not all are available"
  DEFVAL      { packets }
  ::= { alaQoSRuleEntry 17 }

alaQoSRulePacketCount OBJECT-TYPE
  SYNTAX      Counter64
  MAX-ACCESS  read-only
  STATUS      current
  DESCRIPTION "Counter for packets patching this rule"
  ::= { alaQoSRuleEntry 18 }

alaQoSRuleByteCount OBJECT-TYPE
  SYNTAX      Counter64
  MAX-ACCESS  read-only
  STATUS      current
  DESCRIPTION "Counter for bytes matching this rule"
  ::= { alaQoSRuleEntry 19 }

alaQoSRuleExcessPacketCount OBJECT-TYPE
  SYNTAX      Counter64
  MAX-ACCESS  read-only
  STATUS      current
  DESCRIPTION "Counter for packets out of bandwidth parameters"
  ::= { alaQoSRuleEntry 20 }

alaQoSRuleExcessByteCount OBJECT-TYPE
  SYNTAX      Counter64
  MAX-ACCESS  read-only
  STATUS      current
  DESCRIPTION "Counter for bytes out of bandwidth parameters"
  ::= { alaQoSRuleEntry 21 }

alaQoSRuleType OBJECT-TYPE
  SYNTAX      Integer32
  MAX-ACCESS  read-only
  STATUS      current
  DESCRIPTION "The type of rule this is. Each bit represents the following:
               0x1 = bridged
               0x2 = routed
               0x4 = multicast"
  ::= { alaQoSRuleEntry 22 }

alaQoSRuleTrapEvents OBJECT-TYPE
  SYNTAX      INTEGER {
                yes (1),
                no (2)
              }
  MAX-ACCESS  read-create
  STATUS      current
  DESCRIPTION "Send SNMP trap when 'qos user-port shutdown' param or
		rule having action=port-disable is matched/invoked?"
  DEFVAL      { yes }
  ::= { alaQoSRuleEntry 23 }

alaQoSRuleDefaultList OBJECT-TYPE
  SYNTAX      INTEGER {
                yes (1),
                no (2)
              }
  MAX-ACCESS  read-create
  STATUS      current
  DESCRIPTION "This rule belongs to the default policy list. "
  DEFVAL      { yes }
  ::= { alaQoSRuleEntry 24 }
	
alaQoSRuleGreenCount  OBJECT-TYPE
  SYNTAX      Counter64
  MAX-ACCESS  read-only
  STATUS      current
  DESCRIPTION "Counter for the number of  packets being green compliant."
  ::= { alaQoSRuleEntry 25 }

alaQoSRuleYellowCount  OBJECT-TYPE
  SYNTAX      Counter64
  MAX-ACCESS  read-only
  STATUS      current
  DESCRIPTION "Counter for the number of packets being yellow compliant."
  ::= { alaQoSRuleEntry 26 }

alaQoSRuleRedCount  OBJECT-TYPE
  SYNTAX      Counter64
 MAX-ACCESS  read-only
  STATUS      current
  DESCRIPTION "Counter for the number of packets being red compliant."
  ::= { alaQoSRuleEntry 27 }

alaQoSRuleNonGreenCount  OBJECT-TYPE
  SYNTAX      Counter64
  MAX-ACCESS  read-only
  STATUS      current
  DESCRIPTION "Counter for the number of packets being non-green compliant."
  ::= { alaQoSRuleEntry 28 }

alaQoSRuleNonRedCount  OBJECT-TYPE
  SYNTAX      Counter64
  MAX-ACCESS  read-only
  STATUS      current
  DESCRIPTION "Counter for the number of packets being non-red compliant."
  ::= { alaQoSRuleEntry 29 }

alaQoSRuleAccounting OBJECT-TYPE
  SYNTAX      INTEGER {
                enabled (1),
                disabled (2)
              }

  MAX-ACCESS  read-create
  STATUS      current
  DESCRIPTION "Flag for enabling/disbling the accounting mode."
  DEFVAL      {2}
  ::= { alaQoSRuleEntry 30}

alaQoSRulePacketRate OBJECT-TYPE
  SYNTAX      Counter64

  MAX-ACCESS  read-only
  STATUS      current
  DESCRIPTION " Shows the packet per second rate "
  ::= { alaQoSRuleEntry 31}

alaQoSRuleAccPacketCount OBJECT-TYPE
 SYNTAX      Counter64
 MAX-ACCESS  read-only
 STATUS      current
 DESCRIPTION "Counter for packets patching this rule"
 ::= { alaQoSRuleEntry 32 }

alaQoSRuleAccByteCount OBJECT-TYPE
SYNTAX      Counter64
MAX-ACCESS  read-only
STATUS      current
DESCRIPTION "Counter for packets patching this rule"
::= { alaQoSRuleEntry 33 }

alaQoSRuleBitRate OBJECT-TYPE
  SYNTAX      Counter64
 
  MAX-ACCESS  read-only
  STATUS      current
  DESCRIPTION " Shows the Bits per second rate "
  ::= { alaQoSRuleEntry 34}

--
-- Definition of rule table
--

alaQoSAppliedRuleTable OBJECT-TYPE
  SYNTAX      SEQUENCE OF QoSAppliedRuleEntry
  MAX-ACCESS  not-accessible
  STATUS      current
  DESCRIPTION "Table of QoS AppliedRule definitions"
  ::= { alaQoSMIBObjects 2 }

alaQoSAppliedRuleEntry OBJECT-TYPE
  SYNTAX      QoSAppliedRuleEntry
  MAX-ACCESS  not-accessible
  STATUS      current
  DESCRIPTION "Definition of QoS AppliedRule"
  INDEX {
          alaQoSAppliedRuleName
        }
  ::= { alaQoSAppliedRuleTable 1 }

QoSAppliedRuleEntry ::=
  SEQUENCE
  {
    alaQoSAppliedRuleName                                   DisplayString,
    alaQoSAppliedRuleEnabled                                INTEGER,
    alaQoSAppliedRuleSource                                 INTEGER,
    alaQoSAppliedRulePrecedence                             Integer32,
    alaQoSAppliedRuleCondition                              DisplayString,
    alaQoSAppliedRuleAction                                 DisplayString,
    alaQoSAppliedRuleReflexive                              INTEGER,
    alaQoSAppliedRuleSave                                   INTEGER,
    alaQoSAppliedRuleLog                                    INTEGER,
    alaQoSAppliedRuleMatches                                Counter32,
    alaQoSAppliedRuleEnforced                               INTEGER,
    alaQoSAppliedRuleActive                                 INTEGER,
    alaQoSAppliedRuleRowStatus                              RowStatus,
    alaQoSAppliedRuleValidityPeriod                         DisplayString,
    alaQoSAppliedRuleValidityPeriodStatus                   INTEGER,
    alaQoSAppliedRuleLogInterval                            Integer32,
    alaQoSAppliedRuleCountType                              INTEGER,
    alaQoSAppliedRulePacketCount                            Counter64,
    alaQoSAppliedRuleByteCount                              Counter64,
    alaQoSAppliedRuleExcessPacketCount                      Counter64,
    alaQoSAppliedRuleExcessByteCount                        Counter64,
    alaQoSAppliedRuleType                                   Integer32,
    alaQoSAppliedRuleTrapEvents                             INTEGER,
    alaQoSAppliedRuleDefaultList                            INTEGER,
    alaQoSAppliedRuleGreenCount    			    Counter64,
    alaQoSAppliedRuleYellowCount                            Counter64,
    alaQoSAppliedRuleRedCount				    Counter64,
    alaQoSAppliedRuleNonGreenCount                          Counter64,
    alaQoSAppliedRuleNonRedCount                            Counter64,
    alaQoSAppliedRuleAccounting                                 INTEGER,
    alaQoSAppliedRulePacketRate					Counter64,
    alaQoSAppliedRuleAccPacketCount                              Counter64,
    alaQoSAppliedRuleAccByteCount                                Counter64,
    alaQoSAppliedRuleBitRate					 Counter64
 
  }

alaQoSAppliedRuleName OBJECT-TYPE
  SYNTAX      DisplayString (SIZE(0..31))
  MAX-ACCESS  not-accessible
  STATUS      current
  DESCRIPTION "Name of rule"
  ::= { alaQoSAppliedRuleEntry 1 }

alaQoSAppliedRuleEnabled OBJECT-TYPE
  SYNTAX      INTEGER {
                enable (1),
                disable (2)
              }
  MAX-ACCESS  read-only
  STATUS      current
  DESCRIPTION "Is this rule enabled or not"
  ::= { alaQoSAppliedRuleEntry 2 }

alaQoSAppliedRuleSource OBJECT-TYPE
  SYNTAX      INTEGER {
                ldap (1),
                cli (2),
                blt (3),
                api (4),
                imp (5)
              }
  MAX-ACCESS  read-only
  STATUS      current
  DESCRIPTION "What entity created the rule."
  ::= { alaQoSAppliedRuleEntry 3 }

alaQoSAppliedRulePrecedence OBJECT-TYPE
  SYNTAX      Integer32 (0..65535)
  MAX-ACCESS  read-only
  STATUS      current
  DESCRIPTION "Precedence value for rule.
               Rules are evaluated from higher precedence to lower.
               If rules have equal precedence, they are evaluated in
               the order they are received."
  ::= { alaQoSAppliedRuleEntry 4 }

alaQoSAppliedRuleCondition OBJECT-TYPE
  SYNTAX      DisplayString (SIZE(0..31))
  MAX-ACCESS  read-only
  STATUS      current
  DESCRIPTION "Name of the condition to use"
  ::= { alaQoSAppliedRuleEntry 5 }

alaQoSAppliedRuleAction OBJECT-TYPE
  SYNTAX      DisplayString (SIZE(0..31))
  MAX-ACCESS  read-only
  STATUS      current
  DESCRIPTION "Name of the action to use"
  ::= { alaQoSAppliedRuleEntry 6 }

alaQoSAppliedRuleReflexive OBJECT-TYPE
  SYNTAX      INTEGER {
                yes (1),
                no (2)
              }
  MAX-ACCESS  read-only
  STATUS      current
  DESCRIPTION "Indicator to tell if the rule is reflexive.  Reflexive rules
               allow specific return connections that would normally be denied."
  ::= { alaQoSAppliedRuleEntry 7 }

alaQoSAppliedRuleSave OBJECT-TYPE
  SYNTAX      INTEGER {
                yes (1),
                no (2)
              }
  MAX-ACCESS  read-only
  STATUS      current
  DESCRIPTION "Indicator to tell whether to write out the rule during
               snapshot commands."
  ::= { alaQoSAppliedRuleEntry 8 }

alaQoSAppliedRuleLog OBJECT-TYPE
  SYNTAX      INTEGER {
                yes (1),
                no (2)
              }
  MAX-ACCESS  read-only
  STATUS      current
  DESCRIPTION "Indicator to tell whether to log matches to this rule
               in the QoS log."
  ::= { alaQoSAppliedRuleEntry 9 }

alaQoSAppliedRuleMatches OBJECT-TYPE
  SYNTAX      Counter32
  MAX-ACCESS  read-only
  STATUS      current
  DESCRIPTION "Number of times this rule has been matched."
  ::= { alaQoSAppliedRuleEntry 10 }

alaQoSAppliedRuleEnforced OBJECT-TYPE
  SYNTAX      INTEGER {
                yes (1),
                no (2)
              }
  MAX-ACCESS  read-only
  STATUS      current
  DESCRIPTION "Is this rule currenly being enforced on the switch."
  ::= { alaQoSAppliedRuleEntry 11 }

alaQoSAppliedRuleActive OBJECT-TYPE
  SYNTAX      INTEGER {
                yes (1),
                no (2)
              }
  MAX-ACCESS  read-only
  STATUS      current
  DESCRIPTION "Is this rule enforcable by the switch."
  ::= { alaQoSAppliedRuleEntry 12 }

alaQoSAppliedRuleRowStatus OBJECT-TYPE
  SYNTAX      RowStatus
  MAX-ACCESS  read-only
  STATUS      current
  DESCRIPTION "Used to create/delete rules according to the
               RowStatus convention"
  ::= { alaQoSAppliedRuleEntry 13 }

alaQoSAppliedRuleValidityPeriod OBJECT-TYPE
  SYNTAX      DisplayString (SIZE(0..31))
  MAX-ACCESS  read-only
  STATUS      current
  DESCRIPTION "Name of the validity period to use"
  ::= { alaQoSAppliedRuleEntry 14 }

alaQoSAppliedRuleValidityPeriodStatus OBJECT-TYPE
  SYNTAX      INTEGER {
                enabled (1),
                disabled (2)
              }
  MAX-ACCESS  read-only
  STATUS      current
  DESCRIPTION "Status field indicating whether there is a validity period
               associated with this rule"
  ::= { alaQoSAppliedRuleEntry 15 }

alaQoSAppliedRuleLogInterval OBJECT-TYPE
  SYNTAX      Integer32 (0..3600)
  MAX-ACCESS  read-only
  STATUS      current
  DESCRIPTION "How often to look for packets matching this rule when logging.  
               When 0 log as many as possible."
  ::= { alaQoSAppliedRuleEntry 16 }

alaQoSAppliedRuleCountType OBJECT-TYPE
  SYNTAX      INTEGER {
                packets (1),
                bytes (2)
              }
  MAX-ACCESS  read-only
  STATUS      current
  DESCRIPTION "Which rule statistics counters to update if not all are available"
  ::= { alaQoSAppliedRuleEntry 17 }

alaQoSAppliedRulePacketCount OBJECT-TYPE
  SYNTAX      Counter64
  MAX-ACCESS  read-only
  STATUS      current
  DESCRIPTION "Counter for packets patching this rule"
  ::= { alaQoSAppliedRuleEntry 18 }

alaQoSAppliedRuleByteCount OBJECT-TYPE
  SYNTAX      Counter64
  MAX-ACCESS  read-only
  STATUS      current
  DESCRIPTION "Counter for bytes matching this rule"
  ::= { alaQoSAppliedRuleEntry 19 }

alaQoSAppliedRuleExcessPacketCount OBJECT-TYPE
  SYNTAX      Counter64
  MAX-ACCESS  read-only
  STATUS      current
  DESCRIPTION "Counter for packets out of bandwidth parameters"
  ::= { alaQoSAppliedRuleEntry 20 }

alaQoSAppliedRuleExcessByteCount OBJECT-TYPE
  SYNTAX      Counter64
  MAX-ACCESS  read-only
  STATUS      current
  DESCRIPTION "Counter for bytes out of bandwidth parameters"
  ::= { alaQoSAppliedRuleEntry 21 }

alaQoSAppliedRuleType OBJECT-TYPE
  SYNTAX      Integer32
  MAX-ACCESS  read-only
  STATUS      current
  DESCRIPTION "The type of rule this is. Each bit represents the following:
               0x1 = bridged
               0x2 = routed
               0x4 = multicast"
  ::= { alaQoSAppliedRuleEntry 22 }

alaQoSAppliedRuleTrapEvents OBJECT-TYPE
  SYNTAX      INTEGER {
                yes (1),
                no (2)
              }
  MAX-ACCESS  read-create
  STATUS      current
  DESCRIPTION "Send SNMP trap when 'qos user-port shutdown' param or
		rule having action=port-disable is matched/invoked?"
  DEFVAL      { yes }
  ::= { alaQoSAppliedRuleEntry 23 }

alaQoSAppliedRuleDefaultList OBJECT-TYPE
  SYNTAX      INTEGER {
                yes (1),
                no (2)
              }
  MAX-ACCESS  read-create
  STATUS      current
  DESCRIPTION "This rule belongs to the default policy list. "
  DEFVAL      { yes }
  ::= { alaQoSAppliedRuleEntry 24 }

alaQoSAppliedRuleGreenCount OBJECT-TYPE
  SYNTAX      Counter64
  MAX-ACCESS  read-only
  STATUS      current
  DESCRIPTION "Counter for the number of packets being green compliant."
  ::= { alaQoSAppliedRuleEntry 25 }

alaQoSAppliedRuleYellowCount OBJECT-TYPE
  SYNTAX      Counter64
  MAX-ACCESS  read-only
  STATUS      current
  DESCRIPTION "Counter for the number of packets being yellow compliant."
  ::= { alaQoSAppliedRuleEntry 26 }

alaQoSAppliedRuleRedCount OBJECT-TYPE
  SYNTAX      Counter64
  MAX-ACCESS  read-only
  STATUS      current
  DESCRIPTION "Counter for the number of packets being red compliant."
  ::= { alaQoSAppliedRuleEntry 27 } 

alaQoSAppliedRuleNonGreenCount OBJECT-TYPE
  SYNTAX      Counter64
  MAX-ACCESS  read-only
  STATUS      current
  DESCRIPTION "Counter for the number of packets being non-green compliant."
  ::= { alaQoSAppliedRuleEntry 28 }

alaQoSAppliedRuleNonRedCount OBJECT-TYPE
  SYNTAX      Counter64
  MAX-ACCESS  read-only
  STATUS      current
  DESCRIPTION "Counter for the number of packets being non-red compliant."
  ::= { alaQoSAppliedRuleEntry 29 }

alaQoSAppliedRuleAccounting OBJECT-TYPE
  SYNTAX      INTEGER {
                enabled (1),
                disabled (2)
              }

  MAX-ACCESS  read-only
  STATUS      current
  DESCRIPTION " Flag for enabling/disabling the accounting mode."
  DEFVAL      {2}
  ::= { alaQoSAppliedRuleEntry 30}

alaQoSAppliedRulePacketRate OBJECT-TYPE
  SYNTAX      Counter64

  MAX-ACCESS  read-only
  STATUS      current
  DESCRIPTION " Shows the packet per second rate "
  ::= { alaQoSAppliedRuleEntry 31}


alaQoSAppliedRuleAccPacketCount OBJECT-TYPE
  SYNTAX      Counter64
  MAX-ACCESS  read-only
  STATUS      current
  DESCRIPTION "Counter for packets patching this rule"
  ::= { alaQoSAppliedRuleEntry 32 }
  

alaQoSAppliedRuleAccByteCount OBJECT-TYPE
  SYNTAX      Counter64
  MAX-ACCESS  read-only
  STATUS      current
  DESCRIPTION "Counter for packets patching this rule"
  ::= { alaQoSAppliedRuleEntry 33 }

alaQoSAppliedRuleBitRate OBJECT-TYPE
  SYNTAX      Counter64
  MAX-ACCESS  read-only
  STATUS      current
  DESCRIPTION " Shows the Bits per second rate "
  ::= { alaQoSAppliedRuleEntry 34}
-- Definition of extended rule table
--
alaQoSExtendedRuleTable OBJECT-TYPE
  SYNTAX      SEQUENCE OF QoSExtendedRuleEntry
  MAX-ACCESS  not-accessible
  STATUS      current
  DESCRIPTION "Table of QoS Rule definitions for extending port group behavior on individual port basis or group basis"
  ::= { alaQoSMIBObjects 54 }
alaQoSExtendedRuleEntry OBJECT-TYPE
  SYNTAX      QoSExtendedRuleEntry
  MAX-ACCESS  not-accessible
  STATUS      current
  DESCRIPTION "Definition of QoS Rule" 
  INDEX {
	   alaQoSRuleName,
	   alaQoSExtendedRuleSlot,        
	   alaQoSExtendedRulePort        
   	}
  ::= { alaQoSExtendedRuleTable 1 }
QoSExtendedRuleEntry ::=
   SEQUENCE
	{
		alaQoSExtendedRuleSlot            		Integer32,
		alaQoSExtendedRulePort            		Integer32,                             
		alaQoSExtendedRuleMatches         		Counter32,
		alaQoSExtendedRulePacketCount     		Counter64,
		alaQoSExtendedRuleByteCount       		Counter64,   
   		alaQoSExtendedRuleExcessPacketCount   	Counter64,    
		alaQoSExtendedRuleExcessByteCount     	Counter64,    
		alaQoSExtendedRuleGreenCount          	Counter64,
		alaQoSExtendedRuleYellowCount     		Counter64,
		alaQoSExtendedRuleRedCount        		Counter64,    
		alaQoSExtendedRuleNonGreenCount       	Counter64,
		alaQoSExtendedRuleNonRedCount     		Counter64    
	}	
alaQoSExtendedRuleSlot OBJECT-TYPE
  SYNTAX      Integer32
  MAX-ACCESS  not-accessible 
  STATUS      current
  DESCRIPTION "Slot on which rate-limit is enabled."
  ::= { alaQoSExtendedRuleEntry 1 }
alaQoSExtendedRulePort OBJECT-TYPE
  SYNTAX      Integer32
  MAX-ACCESS  not-accessible 
  STATUS      current
  DESCRIPTION "Port on which rate-limit is enabled."
  ::= { alaQoSExtendedRuleEntry 2 }
alaQoSExtendedRuleMatches OBJECT-TYPE
  SYNTAX      Counter32
  MAX-ACCESS  read-only
  STATUS      current
  DESCRIPTION "Number of times this rule has been matched."
  ::= { alaQoSExtendedRuleEntry 3 }
alaQoSExtendedRulePacketCount OBJECT-TYPE
  SYNTAX      Counter64
  MAX-ACCESS  read-only
  STATUS      current
  DESCRIPTION "Counter for packets matching this rule"
  ::= { alaQoSExtendedRuleEntry 4 }
alaQoSExtendedRuleByteCount OBJECT-TYPE
  SYNTAX      Counter64
  MAX-ACCESS  read-only
  STATUS      current
  DESCRIPTION "Counter for bytes matching this rule"
  ::= { alaQoSExtendedRuleEntry 5 }
alaQoSExtendedRuleExcessPacketCount OBJECT-TYPE
  SYNTAX      Counter64
  MAX-ACCESS  read-only
  STATUS      current
  DESCRIPTION "Counter for packets out of the bandwidth parameters"
  ::= { alaQoSExtendedRuleEntry 6 }
alaQoSExtendedRuleExcessByteCount OBJECT-TYPE
  SYNTAX      Counter64
  MAX-ACCESS  read-only
  STATUS      current
  DESCRIPTION "Counter for bytes out of the bandwidth parameters"
  ::= { alaQoSExtendedRuleEntry 7 }
alaQoSExtendedRuleGreenCount  OBJECT-TYPE
  SYNTAX      Counter64
  MAX-ACCESS  read-only
  STATUS      current
  DESCRIPTION "Counter for the number of packets which are green compliant."
  ::= { alaQoSExtendedRuleEntry 8 }
alaQoSExtendedRuleYellowCount  OBJECT-TYPE
  SYNTAX      Counter64
  MAX-ACCESS  read-only
  STATUS      current
  DESCRIPTION "Counter for the number of packets which are yellow compliant."
  ::= { alaQoSExtendedRuleEntry 9 }
alaQoSExtendedRuleRedCount  OBJECT-TYPE
  SYNTAX      Counter64
  MAX-ACCESS  read-only
  STATUS      current
  DESCRIPTION "Counter for the number of packets which are red compliant."
  ::= { alaQoSExtendedRuleEntry 10 }
alaQoSExtendedRuleNonGreenCount  OBJECT-TYPE
  SYNTAX      Counter64
  MAX-ACCESS  read-only
  STATUS      current
  DESCRIPTION "Counter for the number of packets which are non-green compliant."
  ::= { alaQoSExtendedRuleEntry 11 }
alaQoSExtendedRuleNonRedCount  OBJECT-TYPE
  SYNTAX      Counter64
  MAX-ACCESS  read-only
  STATUS      current
  DESCRIPTION "Counter for the number of packets which are non-red compliant."
  ::= { alaQoSExtendedRuleEntry 12 }
--

--
-- Definition of condition table
--

alaQoSConditionTable OBJECT-TYPE
  SYNTAX      SEQUENCE OF QoSConditionEntry
  MAX-ACCESS  not-accessible
  STATUS      current
  DESCRIPTION "Table of QoS Condition definitions"
  ::= { alaQoSMIBObjects 3 }

alaQoSConditionEntry OBJECT-TYPE
  SYNTAX      QoSConditionEntry
  MAX-ACCESS  not-accessible
  STATUS      current
  DESCRIPTION "Definition of QoS Condition"
  INDEX {
          alaQoSConditionName
        }
  ::= { alaQoSConditionTable 1 }

QoSConditionEntry ::=
  SEQUENCE
  {
    alaQoSConditionName                                     DisplayString,
    alaQoSConditionSource                                   INTEGER,
    alaQoSConditionSourceSlot                               Integer32,
    alaQoSConditionSourceSlotStatus                         INTEGER,
    alaQoSConditionSourcePort                               Integer32,
    alaQoSConditionSourcePortGroup                          DisplayString,
    alaQoSConditionSourcePortGroupStatus                    INTEGER,
    alaQoSConditionDestinationSlot                          Integer32,
    alaQoSConditionDestinationSlotStatus                    INTEGER,
    alaQoSConditionDestinationPort                          Integer32,
    alaQoSConditionDestinationPortGroup                     DisplayString,
    alaQoSConditionDestinationPortGroupStatus               INTEGER,
    alaQoSConditionSourceInterfaceType                      INTEGER,
    alaQoSConditionSourceInterfaceTypeStatus                INTEGER,
    alaQoSConditionDestinationInterfaceType                 INTEGER,
    alaQoSConditionDestinationInterfaceTypeStatus           INTEGER,
    alaQoSConditionSourceMacAddr                            MacAddress,
    alaQoSConditionSourceMacAddrStatus                      INTEGER,
    alaQoSConditionSourceMacMask                            MacAddress,
    alaQoSConditionSourceMacGroup                           DisplayString,
    alaQoSConditionSourceMacGroupStatus                     INTEGER,
    alaQoSConditionDestinationMacAddr                       MacAddress,
    alaQoSConditionDestinationMacAddrStatus                 INTEGER,
    alaQoSConditionDestinationMacMask                       MacAddress,
    alaQoSConditionDestinationMacGroup                      DisplayString,
    alaQoSConditionDestinationMacGroupStatus                INTEGER,
    alaQoSConditionSourceVlan                               Integer32,
    alaQoSConditionSourceVlanStatus                         INTEGER,
    alaQoSConditionDestinationVlan                          Integer32,
    alaQoSConditionDestinationVlanStatus                    INTEGER,
    alaQoSCondition8021p                                    Integer32,
    alaQoSCondition8021pStatus                              INTEGER,
    alaQoSConditionSourceIpAddr                             IpAddress,
    alaQoSConditionSourceIpAddrStatus                       INTEGER,
    alaQoSConditionSourceIpMask                             IpAddress,
    alaQoSConditionSourceNetworkGroup                       DisplayString,
    alaQoSConditionSourceNetworkGroupStatus                 INTEGER,
    alaQoSConditionDestinationIpAddr                        IpAddress,
    alaQoSConditionDestinationIpAddrStatus                  INTEGER,
    alaQoSConditionDestinationIpMask                        IpAddress,
    alaQoSConditionDestinationNetworkGroup                  DisplayString,
    alaQoSConditionDestinationNetworkGroupStatus            INTEGER,
    alaQoSConditionMulticastIpAddr                          IpAddress,
    alaQoSConditionMulticastIpAddrStatus                    INTEGER,
    alaQoSConditionMulticastIpMask                          IpAddress,
    alaQoSConditionMulticastNetworkGroup                    DisplayString,
    alaQoSConditionMulticastNetworkGroupStatus              INTEGER,
    alaQoSConditionTos                                      Integer32,
    alaQoSConditionTosStatus                                INTEGER,
    alaQoSConditionTosMask                                  Integer32,
    alaQoSConditionDscp                                     Integer32,
    alaQoSConditionDscpStatus                               INTEGER,
    alaQoSConditionDscpMask                                 Integer32,
    alaQoSConditionIpProtocol                               Integer32,
    alaQoSConditionIpProtocolStatus                         INTEGER,
    alaQoSConditionSourceIpPort                             Integer32,
    alaQoSConditionSourceIpPortStatus                       INTEGER,
    alaQoSConditionDestinationIpPort                        Integer32,
    alaQoSConditionDestinationIpPortStatus                  INTEGER,
    alaQoSConditionService                                  DisplayString,
    alaQoSConditionServiceStatus                            INTEGER,
    alaQoSConditionServiceGroup                             DisplayString,
    alaQoSConditionServiceGroupStatus                       INTEGER,
    alaQoSConditionIcmpType                                 Integer32,
    alaQoSConditionIcmpTypeStatus                           INTEGER,
    alaQoSConditionIcmpCode                                 Integer32,
    alaQoSConditionIcmpCodeStatus                           INTEGER,
    alaQoSConditionDlci                                     Integer32,
    alaQoSConditionDlciStatus                               INTEGER,
    alaQoSConditionRowStatus                                RowStatus,
    alaQoSConditionSourcePortEnd                            Integer32,
    alaQoSConditionDestinationPortEnd                       Integer32,
    alaQoSConditionSourceIpPortEnd                          Integer32,
    alaQoSConditionDestinationIpPortEnd                     Integer32,
    alaQoSConditionSourceTcpPort                            Integer32,
    alaQoSConditionSourceTcpPortStatus                      INTEGER,
    alaQoSConditionSourceTcpPortEnd                         Integer32,
    alaQoSConditionDestinationTcpPort                       Integer32,
    alaQoSConditionDestinationTcpPortStatus                 INTEGER,
    alaQoSConditionDestinationTcpPortEnd                    Integer32,
    alaQoSConditionSourceUdpPort                            Integer32,
    alaQoSConditionSourceUdpPortStatus                      INTEGER,
    alaQoSConditionSourceUdpPortEnd                         Integer32,
    alaQoSConditionDestinationUdpPort                       Integer32,
    alaQoSConditionDestinationUdpPortStatus                 INTEGER,
    alaQoSConditionDestinationUdpPortEnd                    Integer32,
    alaQoSConditionEthertype                                Integer32,
    alaQoSConditionEthertypeStatus                          INTEGER,
    alaQoSConditionTcpFlags                                 INTEGER,
    alaQoSConditionTcpFlagsStatus                           INTEGER,
    alaQoSConditionTcpFlagsVal                              Integer32,
    alaQoSConditionTcpFlagsValStatus                        INTEGER,
    alaQoSConditionTcpFlagsMask                             Integer32,
    alaQoSConditionTcpFlagsMaskStatus                       INTEGER,
    alaQoSConditionTcpEstablished                           INTEGER,
    alaQoSConditionSourceIpv6Addr                           Ipv6Address,
    alaQoSConditionSourceIpv6AddrStatus                     INTEGER,
    alaQoSConditionSourceIpv6Mask                           Ipv6Address,
    alaQoSConditionDestinationIpv6Addr                      Ipv6Address,
    alaQoSConditionDestinationIpv6AddrStatus                INTEGER,
    alaQoSConditionDestinationIpv6Mask                      Ipv6Address,
    alaQoSConditionIpv6Traffic                              INTEGER,
    alaQoSConditionIpv6NH	                                  Integer32,
    alaQoSConditionIpv6NHStatus                             INTEGER,
    alaQoSConditionIpv6FlowLabel                            Integer32,
    alaQoSConditionIpv6FlowLabelStatus                      INTEGER,
    alaQoSConditionMcastIpv6Addr                            Ipv6Address,
    alaQoSConditionMcastIpv6AddrStatus                      INTEGER,
    alaQoSConditionMcastIpv6Mask                            Ipv6Address,
    alaQoSConditionDscpEnd                                  Integer32,
    alaQoSConditionInnerSourceVlan                          Integer32,
    alaQoSConditionInnerSourceVlanStatus                    INTEGER,
    alaQoSConditionInner8021p                               Integer32,
    alaQoSConditionInner8021pStatus                         INTEGER,
    alaQoSConditionVrfName                                  DisplayString,
    alaQoSConditionVrfNameStatus                            INTEGER,
    alaQoSCondition8021pEnd				    Integer32,
    alaQoSConditionInner8021pEnd			    Integer32, 
    alaQoSConditionSourceVlanGroup			    DisplayString,
    alaQoSConditionSourceVlanGroupStatus		    INTEGER,
    alaQoSConditionInnerSourceVlanGroup 		    DisplayString,
    alaQoSConditionInnerSourceVlanGroupStatus		    INTEGER,
    alaQoSConditionSIP					     INTEGER,
    alaQoSConditionSIPStatus				     INTEGER
  }

alaQoSConditionName OBJECT-TYPE
  SYNTAX      DisplayString (SIZE(0..31))
  MAX-ACCESS  not-accessible
  STATUS      current
  DESCRIPTION "Name of condition"
  ::= { alaQoSConditionEntry 1 }

alaQoSConditionSource OBJECT-TYPE
  SYNTAX      INTEGER {
                ldap (1),
                cli (2),
                blt (3),
                api (4),
                imp (5)
              }
  MAX-ACCESS  read-create
  STATUS      current
  DESCRIPTION "What entity created the condition."
  DEFVAL      { cli }
  ::= { alaQoSConditionEntry 2 }

alaQoSConditionSourceSlot OBJECT-TYPE
  SYNTAX      Integer32 (0..16)
  MAX-ACCESS  read-create
  STATUS      current
  DESCRIPTION "Source physical slot used for traffic classification
               When 0, the port identifies an aggregate"
  DEFVAL      { 1 }
  ::= { alaQoSConditionEntry 3 }

alaQoSConditionSourceSlotStatus OBJECT-TYPE
  SYNTAX      INTEGER {
                enabled (1),
                disabled (2)
              }
  MAX-ACCESS  read-create
  STATUS      current
  DESCRIPTION "Status field indicating whether the source physical slot and
               port range needs to be matched(enabled) or not(disabled)."
  DEFVAL      { disabled }
  ::= { alaQoSConditionEntry 4 }

alaQoSConditionSourcePort OBJECT-TYPE
  SYNTAX      Integer32 (1..52)
  MAX-ACCESS  read-create
  STATUS      current
  DESCRIPTION "Source physical port range start to use for
               traffic classification"
  DEFVAL      { 1 }
  ::= { alaQoSConditionEntry 5 }

alaQoSConditionSourcePortGroup OBJECT-TYPE
  SYNTAX      DisplayString (SIZE(0..31))
  MAX-ACCESS  read-create
  STATUS      current
  DESCRIPTION "Source physical port group to use for traffic classification"
  ::= { alaQoSConditionEntry 6 }

alaQoSConditionSourcePortGroupStatus OBJECT-TYPE
  SYNTAX      INTEGER {
                enabled (1),
                disabled (2)
              }
  MAX-ACCESS  read-create
  STATUS      current
  DESCRIPTION "Status field indicating whether the source physical port group
               needs to be matched(enabled) or not(disabled)."
  DEFVAL      { disabled }
  ::= { alaQoSConditionEntry 7 }

alaQoSConditionDestinationSlot OBJECT-TYPE
  SYNTAX      Integer32 (0..16)
  MAX-ACCESS  read-create
  STATUS      current
  DESCRIPTION "Destination physical slot used for traffic classification
               When 0, the port identifies an aggregate"
  DEFVAL      { 1 }
  ::= { alaQoSConditionEntry 8 }

alaQoSConditionDestinationSlotStatus OBJECT-TYPE
  SYNTAX      INTEGER {
                enabled (1),
                disabled (2)
              }
  MAX-ACCESS  read-create
  STATUS      current
  DESCRIPTION "Status field indicating whether the destination physical slot
               and port range needs to be matched(enabled) or not(disabled)."
  DEFVAL      { disabled }
  ::= { alaQoSConditionEntry 9 }

alaQoSConditionDestinationPort OBJECT-TYPE
  SYNTAX      Integer32 (1..52)
  MAX-ACCESS  read-create
  STATUS      current
  DESCRIPTION "Destination physical port range start to use for traffic
               classification"
  DEFVAL      { 1 }
  ::= { alaQoSConditionEntry 10 }

alaQoSConditionDestinationPortGroup OBJECT-TYPE
  SYNTAX      DisplayString (SIZE(0..31))
  MAX-ACCESS  read-create
  STATUS      current
  DESCRIPTION "Destination physical port group to use for traffic
               classification"
  ::= { alaQoSConditionEntry 11 }

alaQoSConditionDestinationPortGroupStatus OBJECT-TYPE
  SYNTAX      INTEGER {
                enabled (1),
                disabled (2)
              }
  MAX-ACCESS  read-create
  STATUS      current
  DESCRIPTION "Status field indicating whether the destination physical port
               group needs to be matched(enabled) or not(disabled)."
  DEFVAL      { disabled }
  ::= { alaQoSConditionEntry 12 }

alaQoSConditionSourceInterfaceType OBJECT-TYPE
  SYNTAX      INTEGER {
                ethernet (1),
                wan (2),
                ethernet10 (3),
                ethernet100 (4),
                ethernet1G (5),
                ethernet10G (6),
                aggregate (7)
              }
  MAX-ACCESS  read-create
  STATUS      current
  DESCRIPTION "Source physical interface type to use for traffic
               classification"
  DEFVAL      { ethernet }
  ::= { alaQoSConditionEntry 13 }

alaQoSConditionSourceInterfaceTypeStatus OBJECT-TYPE
  SYNTAX      INTEGER {
                enabled (1),
                disabled (2)
              }
  MAX-ACCESS  read-create
  STATUS      current
  DESCRIPTION "Status field indicating whether the source physical
               interface type needs to be matched(enabled) or not(disabled)."
  DEFVAL      { disabled }
  ::= { alaQoSConditionEntry 14 }

alaQoSConditionDestinationInterfaceType OBJECT-TYPE
  SYNTAX      INTEGER {
                ethernet (1),
                wan (2),
                ethernet10 (3),
                ethernet100 (4),
                ethernet1G (5),
                ethernet10G (6),
                aggregate (7)
              }
  MAX-ACCESS  read-create
  STATUS      current
  DESCRIPTION "Destination physical interface type to use for traffic
               classification"
  DEFVAL      { ethernet }
  ::= { alaQoSConditionEntry 15 }

alaQoSConditionDestinationInterfaceTypeStatus OBJECT-TYPE
  SYNTAX      INTEGER {
                enabled (1),
                disabled (2)
              }
  MAX-ACCESS  read-create
  STATUS      current
  DESCRIPTION "Status field indicating whether the destination physical
               interface type needs to be matched(enabled) or not(disabled)."
  DEFVAL      { disabled }
  ::= { alaQoSConditionEntry 16 }

alaQoSConditionSourceMacAddr OBJECT-TYPE
  SYNTAX      MacAddress
  MAX-ACCESS  read-create
  STATUS      current
  DESCRIPTION "Source MAC address to use for traffic classification"
  DEFVAL      { '000000000000'h }
  ::= { alaQoSConditionEntry 17 }

alaQoSConditionSourceMacAddrStatus OBJECT-TYPE
  SYNTAX      INTEGER {
                enabled (1),
                disabled (2)
              }
  MAX-ACCESS  read-create
  STATUS      current
  DESCRIPTION "Status field indicating whether the source MAC address & mask
               needs to be matched(enabled) or not(disabled)."
  DEFVAL      { disabled }
  ::= { alaQoSConditionEntry 18 }

alaQoSConditionSourceMacMask OBJECT-TYPE
  SYNTAX      MacAddress
  MAX-ACCESS  read-create
  STATUS      current
  DESCRIPTION "Source MAC mask to use for traffic classification"
  DEFVAL      { 'ffffffffffff'h }
  ::= { alaQoSConditionEntry 19 }

alaQoSConditionSourceMacGroup OBJECT-TYPE
  SYNTAX      DisplayString (SIZE(0..31))
  MAX-ACCESS  read-create
  STATUS      current
  DESCRIPTION "Source MAC group to use for traffic classification"
  ::= { alaQoSConditionEntry 20 }

alaQoSConditionSourceMacGroupStatus OBJECT-TYPE
  SYNTAX      INTEGER {
                enabled (1),
                disabled (2)
              }
  MAX-ACCESS  read-create
  STATUS      current
  DESCRIPTION "Status field indicating whether the source MAC group
               needs to be matched(enabled) or not(disabled)."
  DEFVAL      { disabled }
  ::= { alaQoSConditionEntry 21 }

alaQoSConditionDestinationMacAddr OBJECT-TYPE
  SYNTAX      MacAddress
  MAX-ACCESS  read-create
  STATUS      current
  DESCRIPTION "Destination MAC address to use for traffic classification"
  DEFVAL      { '000000000000'h }
  ::= { alaQoSConditionEntry 22 }

alaQoSConditionDestinationMacAddrStatus OBJECT-TYPE
  SYNTAX      INTEGER {
                enabled (1),
                disabled (2)
              }
  MAX-ACCESS  read-create
  STATUS      current
  DESCRIPTION "Status field indicating whether the destination MAC address
               & mask needs to be matched(enabled) or not(disabled)."
  DEFVAL      { disabled }
  ::= { alaQoSConditionEntry 23 }

alaQoSConditionDestinationMacMask OBJECT-TYPE
  SYNTAX      MacAddress
  MAX-ACCESS  read-create
  STATUS      current
  DESCRIPTION "Destination MAC mask to use for traffic classification"
  DEFVAL      { 'ffffffffffff'h }
  ::= { alaQoSConditionEntry 24 }

alaQoSConditionDestinationMacGroup OBJECT-TYPE
  SYNTAX      DisplayString (SIZE(0..31))
  MAX-ACCESS  read-create
  STATUS      current
  DESCRIPTION "Destination MAC group to use for traffic classification"
  ::= { alaQoSConditionEntry 25 }

alaQoSConditionDestinationMacGroupStatus OBJECT-TYPE
  SYNTAX      INTEGER {
                enabled (1),
                disabled (2)
              }
  MAX-ACCESS  read-create
  STATUS      current
  DESCRIPTION "Status field indicating whether the destination MAC group
               needs to be matched(enabled) or not(disabled)."
  DEFVAL      { disabled }
  ::= { alaQoSConditionEntry 26 }

alaQoSConditionSourceVlan OBJECT-TYPE
  SYNTAX      Integer32 (0..4095)
  MAX-ACCESS  read-create
  STATUS      current
  DESCRIPTION "Source VLAN to use for traffic classification"
  DEFVAL      { 0 }
  ::= { alaQoSConditionEntry 27 }

alaQoSConditionSourceVlanStatus OBJECT-TYPE
  SYNTAX      INTEGER {
                enabled (1),
                disabled (2)
              }
  MAX-ACCESS  read-create
  STATUS      current
  DESCRIPTION "Status field indicating whether the source VLAN
               needs to be matched(enabled) or not(disabled)."
  DEFVAL      { disabled }
  ::= { alaQoSConditionEntry 28 }

alaQoSConditionDestinationVlan OBJECT-TYPE
  SYNTAX      Integer32 (0..4095)
  MAX-ACCESS  read-create
  STATUS      current
  DESCRIPTION "Destination VLAN to use for traffic classification"
  DEFVAL      { 0 }
  ::= { alaQoSConditionEntry 29 }

alaQoSConditionDestinationVlanStatus OBJECT-TYPE
  SYNTAX      INTEGER {
                enabled (1),
                disabled (2)
              }
  MAX-ACCESS  read-create
  STATUS      current
  DESCRIPTION "Status field indicating whether the destination VLAN
               needs to be matched(enabled) or not(disabled)."
  DEFVAL      { disabled }
  ::= { alaQoSConditionEntry 30 }

alaQoSCondition8021p OBJECT-TYPE
  SYNTAX      Integer32 (0..7)
  MAX-ACCESS  read-create
  STATUS      current
  DESCRIPTION "802.1p value to use for traffic classification"
  DEFVAL      { 0 }
  ::= { alaQoSConditionEntry 31 }

alaQoSCondition8021pStatus OBJECT-TYPE
  SYNTAX      INTEGER {
                enabled (1),
                disabled (2)
              }
  MAX-ACCESS  read-create
  STATUS      current
  DESCRIPTION "Status field indicating whether the 802.1p value
               needs to be matched(enabled) or not(disabled)."
  DEFVAL      { disabled }
  ::= { alaQoSConditionEntry 32 }

alaQoSConditionSourceIpAddr OBJECT-TYPE
  SYNTAX      IpAddress
  MAX-ACCESS  read-create
  STATUS      current
  DESCRIPTION "Source IP address to use for traffic classification"
  DEFVAL      { '00000000'h }
  ::= { alaQoSConditionEntry 33 }

alaQoSConditionSourceIpAddrStatus OBJECT-TYPE
  SYNTAX      INTEGER {
                enabled (1),
                disabled (2)
              }
  MAX-ACCESS  read-create
  STATUS      current
  DESCRIPTION "Status field indicating whether the source IP address & mask
               needs to be matched(enabled) or not(disabled)."
  DEFVAL      { disabled }
  ::= { alaQoSConditionEntry 34 }

alaQoSConditionSourceIpMask OBJECT-TYPE
  SYNTAX      IpAddress
  MAX-ACCESS  read-create
  STATUS      current
  DESCRIPTION "Source IP mask to use for traffic classification"
  DEFVAL      { 'ffffffff'h }
  ::= { alaQoSConditionEntry 35 }

alaQoSConditionSourceNetworkGroup OBJECT-TYPE
  SYNTAX      DisplayString (SIZE(0..31))
  MAX-ACCESS  read-create
  STATUS      current
  DESCRIPTION "Source network group to use for traffic classification"
  ::= { alaQoSConditionEntry 36 }

alaQoSConditionSourceNetworkGroupStatus OBJECT-TYPE
  SYNTAX      INTEGER {
                enabled (1),
                disabled (2)
              }
  MAX-ACCESS  read-create
  STATUS      current
  DESCRIPTION "Status field indicating whether the source network group
               needs to be matched(enabled) or not(disabled)."
  DEFVAL      { disabled }
  ::= { alaQoSConditionEntry 37 }

alaQoSConditionDestinationIpAddr OBJECT-TYPE
  SYNTAX      IpAddress
  MAX-ACCESS  read-create
  STATUS      current
  DESCRIPTION "Destination IP address to use for traffic classification"
  DEFVAL      { '00000000'h }
  ::= { alaQoSConditionEntry 38 }

alaQoSConditionDestinationIpAddrStatus OBJECT-TYPE
  SYNTAX      INTEGER {
                enabled (1),
                disabled (2)
              }
  MAX-ACCESS  read-create
  STATUS      current
  DESCRIPTION "Status field indicating whether the destination IP address
               & mask needs to be matched(enabled) or not(disabled)."
  DEFVAL      { disabled }
  ::= { alaQoSConditionEntry 39 }

alaQoSConditionDestinationIpMask OBJECT-TYPE
  SYNTAX      IpAddress
  MAX-ACCESS  read-create
  STATUS      current
  DESCRIPTION "Destination IP mask to use for traffic classification"
  DEFVAL      { 'ffffffff'h }
  ::= { alaQoSConditionEntry 40 }

alaQoSConditionDestinationNetworkGroup OBJECT-TYPE
  SYNTAX      DisplayString (SIZE(0..31))
  MAX-ACCESS  read-create
  STATUS      current
  DESCRIPTION "Destination network group to use for traffic classification"
  ::= { alaQoSConditionEntry 41 }

alaQoSConditionDestinationNetworkGroupStatus OBJECT-TYPE
  SYNTAX      INTEGER {
                enabled (1),
                disabled (2)
              }
  MAX-ACCESS  read-create
  STATUS      current
  DESCRIPTION "Status field indicating whether the destination network group
               needs to be matched(enabled) or not(disabled)."
  DEFVAL      { disabled }
  ::= { alaQoSConditionEntry 42 }

alaQoSConditionMulticastIpAddr OBJECT-TYPE
  SYNTAX      IpAddress
  MAX-ACCESS  read-create
  STATUS      current
  DESCRIPTION "Multicast IP address to use for traffic classification"
  DEFVAL      { '00000000'h }
  ::= { alaQoSConditionEntry 43 }

alaQoSConditionMulticastIpAddrStatus OBJECT-TYPE
  SYNTAX      INTEGER {
                enabled (1),
                disabled (2)
              }
  MAX-ACCESS  read-create
  STATUS      current
  DESCRIPTION "Status field indicating whether the multicast IP address & mask
               needs to be matched(enabled) or not(disabled)."
  DEFVAL      { disabled }
  ::= { alaQoSConditionEntry 44 }

alaQoSConditionMulticastIpMask OBJECT-TYPE
  SYNTAX      IpAddress
  MAX-ACCESS  read-create
  STATUS      current
  DESCRIPTION "Multicast IP mask to use for traffic classification"
  DEFVAL      { 'ffffffff'h }
  ::= { alaQoSConditionEntry 45 }

alaQoSConditionMulticastNetworkGroup OBJECT-TYPE
  SYNTAX      DisplayString (SIZE(0..31))
  MAX-ACCESS  read-create
  STATUS      current
  DESCRIPTION "Multicast network group to use for traffic classification"
  ::= { alaQoSConditionEntry 46 }

alaQoSConditionMulticastNetworkGroupStatus OBJECT-TYPE
  SYNTAX      INTEGER {
                enabled (1),
                disabled (2)
              }
  MAX-ACCESS  read-create
  STATUS      current
  DESCRIPTION "Status field indicating whether the multicast network group
               needs to be matched(enabled) or not(disabled)."
  DEFVAL      { disabled }
  ::= { alaQoSConditionEntry 47 }

alaQoSConditionTos OBJECT-TYPE
  SYNTAX      Integer32 (0..7)
  MAX-ACCESS  read-create
  STATUS      current
  DESCRIPTION "TOS value to use for traffic classification"
  DEFVAL      { 0 }
  ::= { alaQoSConditionEntry 48 }

alaQoSConditionTosStatus OBJECT-TYPE
  SYNTAX      INTEGER {
                enabled (1),
                disabled (2)
              }
  MAX-ACCESS  read-create
  STATUS      current
  DESCRIPTION "Status field indicating whether the TOS value & mask
               needs to be matched(enabled) or not(disabled)."
  DEFVAL      { disabled }
  ::= { alaQoSConditionEntry 49 }

alaQoSConditionTosMask OBJECT-TYPE
  SYNTAX      Integer32 (0..7)
  MAX-ACCESS  read-create
  STATUS      current
  DESCRIPTION "TOS mask to use for traffic classification"
  DEFVAL      { 7 }
  ::= { alaQoSConditionEntry 50 }

alaQoSConditionDscp OBJECT-TYPE
  SYNTAX      Integer32 (0..63)
  MAX-ACCESS  read-create
  STATUS      current
  DESCRIPTION "DSCP value to use for traffic classification"
  DEFVAL      { 0 }
  ::= { alaQoSConditionEntry 51 }

alaQoSConditionDscpStatus OBJECT-TYPE
  SYNTAX      INTEGER {
                enabled (1),
                disabled (2)
              }
  MAX-ACCESS  read-create
  STATUS      current
  DESCRIPTION "Status field indicating whether the DSCP value & mask
               needs to be matched(enabled) or not(disabled)."
  DEFVAL      { disabled }
  ::= { alaQoSConditionEntry 52 }

alaQoSConditionDscpMask OBJECT-TYPE
  SYNTAX      Integer32 (0..63)
  MAX-ACCESS  read-create
  STATUS      current
  DESCRIPTION "DSCP mask to use for traffic classification"
  DEFVAL      { 63 }
  ::= { alaQoSConditionEntry 53 }

alaQoSConditionIpProtocol OBJECT-TYPE
  SYNTAX      Integer32 (0..255)
  MAX-ACCESS  read-create
  STATUS      current
  DESCRIPTION "IP protocol to use for traffic classification."
  DEFVAL      { 0 }
  ::= { alaQoSConditionEntry 54 }

alaQoSConditionIpProtocolStatus OBJECT-TYPE
  SYNTAX      INTEGER {
                enabled (1),
                disabled (2)
              }
  MAX-ACCESS  read-create
  STATUS      current
  DESCRIPTION "Status field indicating whether the IP protocol
               needs to be matched(enabled) or not(disabled)."
  DEFVAL      { disabled }
  ::= { alaQoSConditionEntry 55 }

alaQoSConditionSourceIpPort OBJECT-TYPE
  SYNTAX      Integer32 (0..65535)
  MAX-ACCESS  read-create
  STATUS      current
  DESCRIPTION "Source IP port range start to use for traffic classification."
  ::= { alaQoSConditionEntry 56 }

alaQoSConditionSourceIpPortStatus OBJECT-TYPE
  SYNTAX      INTEGER {
                enabled (1),
                disabled (2)
              }
  MAX-ACCESS  read-create
  STATUS      current
  DESCRIPTION "Status field indicating whether the source IP port range
               needs to be matched(enabled) or not(disabled)."
  DEFVAL      { disabled }
  ::= { alaQoSConditionEntry 57 }

alaQoSConditionDestinationIpPort OBJECT-TYPE
  SYNTAX      Integer32 (0..65535)
  MAX-ACCESS  read-create
  STATUS      current
  DESCRIPTION "Destination IP port range start to use for traffic
               classification."
  ::= { alaQoSConditionEntry 58 }

alaQoSConditionDestinationIpPortStatus OBJECT-TYPE
  SYNTAX      INTEGER {
                enabled (1),
                disabled (2)
              }
  MAX-ACCESS  read-create
  STATUS      current
  DESCRIPTION "Status field indicating whether the destination IP port range
               needs to be matched(enabled) or not(disabled)."
  DEFVAL      { disabled }
  ::= { alaQoSConditionEntry 59 }

alaQoSConditionService OBJECT-TYPE
  SYNTAX      DisplayString (SIZE(0..31))
  MAX-ACCESS  read-create
  STATUS      current
  DESCRIPTION "Name of service to use for traffic classification"
  ::= { alaQoSConditionEntry 60 }

alaQoSConditionServiceStatus OBJECT-TYPE
  SYNTAX      INTEGER {
                enabled (1),
                disabled (2)
              }
  MAX-ACCESS  read-create
  STATUS      current
  DESCRIPTION "Status field indicating whether the service
               needs to be matched(enabled) or not(disabled)."
  DEFVAL      { disabled }
  ::= { alaQoSConditionEntry 61 }

alaQoSConditionServiceGroup OBJECT-TYPE
  SYNTAX      DisplayString (SIZE(0..31))
  MAX-ACCESS  read-create
  STATUS      current
  DESCRIPTION "Name of service group to use for traffic classification"
  ::= { alaQoSConditionEntry 62 }

alaQoSConditionServiceGroupStatus OBJECT-TYPE
  SYNTAX      INTEGER {
                enabled (1),
                disabled (2)
              }
  MAX-ACCESS  read-create
  STATUS      current
  DESCRIPTION "Status field indicating whether the service group
               needs to be matched(enabled) or not(disabled)."
  DEFVAL      { disabled }
  ::= { alaQoSConditionEntry 63 }

alaQoSConditionIcmpType OBJECT-TYPE
  SYNTAX      Integer32 (0..255)
  MAX-ACCESS  read-create
  STATUS      current
  DESCRIPTION "ICMP type to use for traffic classification"
  DEFVAL      { 0 }
  ::= { alaQoSConditionEntry 64 }

alaQoSConditionIcmpTypeStatus OBJECT-TYPE
  SYNTAX      INTEGER {
                enabled (1),
                disabled (2)
              }
  MAX-ACCESS  read-create
  STATUS      current
  DESCRIPTION "Status field indicating whether the ICMP type
               needs to be matched(enabled) or not(disabled)."
  DEFVAL      { disabled }
  ::= { alaQoSConditionEntry 65 }

alaQoSConditionIcmpCode OBJECT-TYPE
  SYNTAX      Integer32 (0..255)
  MAX-ACCESS  read-create
  STATUS      current
  DESCRIPTION "ICMP code to use for traffic classification"
  DEFVAL      { 0 }
  ::= { alaQoSConditionEntry 66 }

alaQoSConditionIcmpCodeStatus OBJECT-TYPE
  SYNTAX      INTEGER {
                enabled (1),
                disabled (2)
              }
  MAX-ACCESS  read-create
  STATUS      current
  DESCRIPTION "Status field indicating whether the ICMP code
               needs to be matched(enabled) or not(disabled)."
  DEFVAL      { disabled }
  ::= { alaQoSConditionEntry 67 }

alaQoSConditionDlci OBJECT-TYPE
  SYNTAX      Integer32 (0..512)
  MAX-ACCESS  read-create
  STATUS      current
  DESCRIPTION "DLCI to use to traffic classification"
  DEFVAL      { 0 }
  ::= { alaQoSConditionEntry 68 }

alaQoSConditionDlciStatus OBJECT-TYPE
  SYNTAX      INTEGER {
                enabled (1),
                disabled (2)
              }
  MAX-ACCESS  read-create
  STATUS      current
  DESCRIPTION "Status field indicating whether the DLCI
               needs to be matched(enabled) or not(disabled)."
  DEFVAL      { disabled }
  ::= { alaQoSConditionEntry 69 }

alaQoSConditionRowStatus OBJECT-TYPE
  SYNTAX      RowStatus
  MAX-ACCESS  read-create
  STATUS      current
  DESCRIPTION "Used to create/delete conditions according to the
               RowStatus convention"
  ::= { alaQoSConditionEntry 70 }

alaQoSConditionSourcePortEnd OBJECT-TYPE
  SYNTAX      Integer32 (1..52)
  MAX-ACCESS  read-create
  STATUS      current
  DESCRIPTION "Source physical port range end to use for traffic
               classification.  Must be greater than port range start to
               indicate a range.  When '1', use source port as a single port."
  DEFVAL      { 1 }
  ::= { alaQoSConditionEntry 71 }

alaQoSConditionDestinationPortEnd OBJECT-TYPE
  SYNTAX      Integer32 (1..52)
  MAX-ACCESS  read-create
  STATUS      current
  DESCRIPTION "Destination physical port range end to use for traffic
               classification.  Must be greater than port range start to
               indicate a range.  When '1', use destination port as a single
               port."
  DEFVAL      { 1 }
  ::= { alaQoSConditionEntry 72 }

alaQoSConditionSourceIpPortEnd OBJECT-TYPE
  SYNTAX      Integer32 (0..65535)
  MAX-ACCESS  read-create
  STATUS      current
  DESCRIPTION "Source IP port range end to use for traffic classification.
               Must be greater than source IP port range start to indicate a
               range.  When '0', use source IP port as a single IP port."
  ::= { alaQoSConditionEntry 73 }

alaQoSConditionDestinationIpPortEnd OBJECT-TYPE
  SYNTAX      Integer32 (0..65535)
  MAX-ACCESS  read-create
  STATUS      current
  DESCRIPTION "Destination IP port range end to use for traffic classification.
               Must be greater than destination IP port range start to indicate
               a range.  When '0', use destination IP port as a single IP port."
  ::= { alaQoSConditionEntry 74 }

alaQoSConditionSourceTcpPort OBJECT-TYPE
  SYNTAX      Integer32 (0..65535)
  MAX-ACCESS  read-create
  STATUS      current
  DESCRIPTION "Source TCP port range start to use for traffic classification."
  ::= { alaQoSConditionEntry 75 }

alaQoSConditionSourceTcpPortStatus OBJECT-TYPE
  SYNTAX      INTEGER {
                enabled (1),
                disabled (2)
              }
  MAX-ACCESS  read-create
  STATUS      current
  DESCRIPTION "Status field indicating whether the source TCP port range
               needs to be matched(enabled) or not(disabled)."
  DEFVAL      { disabled }
  ::= { alaQoSConditionEntry 76 }

alaQoSConditionSourceTcpPortEnd OBJECT-TYPE
  SYNTAX      Integer32 (0..65535)
  MAX-ACCESS  read-create
  STATUS      current
  DESCRIPTION "Source TCP port range end to use for traffic classification.
               Must be greater than source TCP port range start to indicate a
               range.  When '0', use source TCP port as a single TCP port."
  ::= { alaQoSConditionEntry 77 }

alaQoSConditionDestinationTcpPort OBJECT-TYPE
  SYNTAX      Integer32 (0..65535)
  MAX-ACCESS  read-create
  STATUS      current
  DESCRIPTION "Destination TCP port range start to use for traffic
               classification."
  ::= { alaQoSConditionEntry 78 }

alaQoSConditionDestinationTcpPortStatus OBJECT-TYPE
  SYNTAX      INTEGER {
                enabled (1),
                disabled (2)
              }
  MAX-ACCESS  read-create
  STATUS      current
  DESCRIPTION "Status field indicating whether the destination TCP port range
               needs to be matched(enabled) or not(disabled)."
  DEFVAL      { disabled }
  ::= { alaQoSConditionEntry 79 }

alaQoSConditionDestinationTcpPortEnd OBJECT-TYPE
  SYNTAX      Integer32 (0..65535)
  MAX-ACCESS  read-create
  STATUS      current
  DESCRIPTION "Destination TCP port range end to use for traffic
               classification.  Must be greater than destination TCP port range
               start to indicate a range.  When '0', use destination TCP port
               as a single TCP port."
  ::= { alaQoSConditionEntry 80 }

alaQoSConditionSourceUdpPort OBJECT-TYPE
  SYNTAX      Integer32 (0..65535)
  MAX-ACCESS  read-create
  STATUS      current
  DESCRIPTION "Source UDP port range start to use for traffic classification."
  ::= { alaQoSConditionEntry 81 }

alaQoSConditionSourceUdpPortStatus OBJECT-TYPE
  SYNTAX      INTEGER {
                enabled (1),
                disabled (2)
              }
  MAX-ACCESS  read-create
  STATUS      current
  DESCRIPTION "Status field indicating whether the source UDP port range
               needs to be matched(enabled) or not(disabled)."
  DEFVAL      { disabled }
  ::= { alaQoSConditionEntry 82 }

alaQoSConditionSourceUdpPortEnd OBJECT-TYPE
  SYNTAX      Integer32 (0..65535)
  MAX-ACCESS  read-create
  STATUS      current
  DESCRIPTION "Source UDP port range end to use for traffic classification.
               Must be greater than source UDP port range start to indicate
               a range.  When '0', use source UDP port as a single UDP port."
  ::= { alaQoSConditionEntry 83 }

alaQoSConditionDestinationUdpPort OBJECT-TYPE
  SYNTAX      Integer32 (0..65535)
  MAX-ACCESS  read-create
  STATUS      current
  DESCRIPTION "Destination UDP port range start to use for traffic
               classification."
  ::= { alaQoSConditionEntry 84 }

alaQoSConditionDestinationUdpPortStatus OBJECT-TYPE
  SYNTAX      INTEGER {
                enabled (1),
                disabled (2)
              }
  MAX-ACCESS  read-create
  STATUS      current
  DESCRIPTION "Status field indicating whether the destination UDP port range
               needs to be matched(enabled) or not(disabled)."
  DEFVAL      { disabled }
  ::= { alaQoSConditionEntry 85 }

alaQoSConditionDestinationUdpPortEnd OBJECT-TYPE
  SYNTAX      Integer32 (0..65535)
  MAX-ACCESS  read-create
  STATUS      current
  DESCRIPTION "Destination UDP port range end to use for traffic
               classification.  Must be greater than destination UDP port range
               start to indicate a range.  When '0', use destination UDP port
               as a single TCP port."
  ::= { alaQoSConditionEntry 86 }

alaQoSConditionEthertype OBJECT-TYPE
  SYNTAX      Integer32 (0..65535)
  MAX-ACCESS  read-create
  STATUS      current
  DESCRIPTION "Ethertype value to use for traffic classification"
  DEFVAL      { 0 }
  ::= { alaQoSConditionEntry 87 }

alaQoSConditionEthertypeStatus OBJECT-TYPE
  SYNTAX      INTEGER {
                enabled (1),
                disabled (2)
              }
  MAX-ACCESS  read-create
  STATUS      current
  DESCRIPTION "Status field indicating whether the ethertype value
               needs to be matched(enabled) or not(disabled)."
  DEFVAL      { disabled }
  ::= { alaQoSConditionEntry 88 }

alaQoSConditionTcpFlags OBJECT-TYPE
  SYNTAX      INTEGER {
                all (1),
                any (2)
              }
  MAX-ACCESS  read-create
  STATUS      current
  DESCRIPTION "Use any/all specifieid TCP flags for traffic classification"
  DEFVAL      { all }
  ::= { alaQoSConditionEntry 89 }

alaQoSConditionTcpFlagsStatus OBJECT-TYPE
  SYNTAX      INTEGER {
                enabled (1),
                disabled (2)
              }
  MAX-ACCESS  read-create
  STATUS      current
  DESCRIPTION "Status field indicating whether the TCP flag bits
               needs to be matched(enabled) or not(disabled)."
  DEFVAL      { disabled }
  ::= { alaQoSConditionEntry 90 }

alaQoSConditionTcpFlagsVal OBJECT-TYPE
  SYNTAX      Integer32
  MAX-ACCESS  read-create
  STATUS      current
  DESCRIPTION "TCP flags values used for traffic classification"
  ::= { alaQoSConditionEntry 91 }

alaQoSConditionTcpFlagsValStatus OBJECT-TYPE
  SYNTAX      INTEGER {
                enabled (1),
                disabled (2)
              }
  MAX-ACCESS  read-create
  STATUS      current
  DESCRIPTION "Not used"
  DEFVAL      { disabled }
  ::= { alaQoSConditionEntry 92 }

alaQoSConditionTcpFlagsMask OBJECT-TYPE
  SYNTAX      Integer32
  MAX-ACCESS  read-create
  STATUS      current
  DESCRIPTION "Mask of TCP flags bits used for traffic classification"
  ::= { alaQoSConditionEntry 93 }

alaQoSConditionTcpFlagsMaskStatus OBJECT-TYPE
  SYNTAX      INTEGER {
                enabled (1),
                disabled (2)
              }
  MAX-ACCESS  read-create
  STATUS      current
  DESCRIPTION "Not used"
  DEFVAL      { disabled }
  ::= { alaQoSConditionEntry 94 }

alaQoSConditionTcpEstablished OBJECT-TYPE
  SYNTAX      INTEGER {
                yes (1),
                no (2)
              }
  MAX-ACCESS  read-create
  STATUS      current
  DESCRIPTION "Look for established TCP sessions in classification"
  DEFVAL      { no }
  ::= { alaQoSConditionEntry 95 }

alaQoSConditionSourceIpv6Addr OBJECT-TYPE
  SYNTAX      Ipv6Address
  MAX-ACCESS  read-create
  STATUS      current
  DESCRIPTION "Source IPv6 address to use for traffic classification"
  DEFVAL      { '00000000000000000000000000000000'h }
  ::= { alaQoSConditionEntry 96 }

alaQoSConditionSourceIpv6AddrStatus OBJECT-TYPE
  SYNTAX      INTEGER {
                enabled (1),
                disabled (2)
              }
  MAX-ACCESS  read-create
  STATUS      current
  DESCRIPTION "Status field indicating whether the source IPv6 address & mask
               needs to be matched(enabled) or not(disabled)."
  DEFVAL      { disabled }
  ::= { alaQoSConditionEntry 97 }

alaQoSConditionSourceIpv6Mask OBJECT-TYPE
  SYNTAX      Ipv6Address
  MAX-ACCESS  read-create
  STATUS      current
  DESCRIPTION "Source IPv6 mask to use for traffic classification"
  DEFVAL      { 'ffffffffffffffffffffffffffffffff'h }
  ::= { alaQoSConditionEntry 98 }

alaQoSConditionDestinationIpv6Addr OBJECT-TYPE
  SYNTAX      Ipv6Address
  MAX-ACCESS  read-create
  STATUS      current
  DESCRIPTION "Destination IPv6 address to use for traffic classification"
  DEFVAL      { '00000000000000000000000000000000'h }
  ::= { alaQoSConditionEntry 99 }

alaQoSConditionDestinationIpv6AddrStatus OBJECT-TYPE
  SYNTAX      INTEGER {
                enabled (1),
                disabled (2)
              }
  MAX-ACCESS  read-create
  STATUS      current
  DESCRIPTION "Status field indicating whether the destination IPv6 address & mask
               needs to be matched(enabled) or not(disabled)."
  DEFVAL      { disabled }
  ::= { alaQoSConditionEntry 100 }

alaQoSConditionDestinationIpv6Mask OBJECT-TYPE
  SYNTAX      Ipv6Address
  MAX-ACCESS  read-create
  STATUS      current
  DESCRIPTION "Destination IPv6 mask to use for traffic classification"
  DEFVAL      { 'ffffffffffffffffffffffffffffffff'h }
  ::= { alaQoSConditionEntry 101 }

alaQoSConditionIpv6Traffic OBJECT-TYPE
  SYNTAX      INTEGER {
                yes (1),
                no (2)
              }
  MAX-ACCESS  read-create
  STATUS      current
  DESCRIPTION "classify IPV6 traffic "
  ::= { alaQoSConditionEntry 102 }

alaQoSConditionIpv6NH OBJECT-TYPE
  SYNTAX      Integer32 (0..255)
  MAX-ACCESS  read-create
  STATUS      current
  DESCRIPTION "NH value to use for traffic classification"
  DEFVAL      { 0 }
  ::= { alaQoSConditionEntry 103 }

alaQoSConditionIpv6NHStatus OBJECT-TYPE
  SYNTAX      INTEGER {
                enabled (1),
                disabled (2)
              }
  MAX-ACCESS  read-create
  STATUS      current
  DESCRIPTION "Status field indicating whether the NH value
               needs to be matched(enabled) or not(disabled)."
  DEFVAL      { disabled }
  ::= { alaQoSConditionEntry 104 }

alaQoSConditionIpv6FlowLabel OBJECT-TYPE
  SYNTAX      Integer32 (0..1048575)
  MAX-ACCESS  read-create
  STATUS      current
  DESCRIPTION "FL value to use for traffic classification"
  DEFVAL      { 0 }
  ::= { alaQoSConditionEntry 105 }

alaQoSConditionIpv6FlowLabelStatus OBJECT-TYPE
  SYNTAX      INTEGER {
                enabled (1),
                disabled (2)
              }
  MAX-ACCESS  read-create
  STATUS      current
  DESCRIPTION "Status field indicating whether the flow label value
               needs to be matched(enabled) or not(disabled)."
  DEFVAL      { disabled }
  ::= { alaQoSConditionEntry 106 }

alaQoSConditionMcastIpv6Addr OBJECT-TYPE
  SYNTAX      Ipv6Address
  MAX-ACCESS  read-create
  STATUS      current
  DESCRIPTION "Multicast IPv6 address to use for traffic classification"
  DEFVAL      { '00000000000000000000000000000000'h }
  ::= { alaQoSConditionEntry 107 }

alaQoSConditionMcastIpv6AddrStatus OBJECT-TYPE
  SYNTAX      INTEGER {
                enabled (1),
                disabled (2)
              }
  MAX-ACCESS  read-create
  STATUS      current
  DESCRIPTION "Status field indicating whether the multicast IPv6 address & mask
               needs to be matched(enabled) or not(disabled)."
  DEFVAL      { disabled }
  ::= { alaQoSConditionEntry 108 }

alaQoSConditionMcastIpv6Mask OBJECT-TYPE
  SYNTAX      Ipv6Address
  MAX-ACCESS  read-create
  STATUS      current
  DESCRIPTION "Multicast IPv6 mask to use for traffic classification"
  DEFVAL      { 'ffffffffffffffffffffffffffffffff'h }
  ::= { alaQoSConditionEntry 109 }

alaQoSConditionDscpEnd OBJECT-TYPE
  SYNTAX      Integer32 (0..63)
  MAX-ACCESS  read-create
  STATUS      current
  DESCRIPTION "DSCP value to use for traffic classification"
  DEFVAL      { 0 }
  ::= { alaQoSConditionEntry 110 }

alaQoSConditionInnerSourceVlan OBJECT-TYPE
  SYNTAX      Integer32 (0..4095)
  MAX-ACCESS  read-create
  STATUS      current
  DESCRIPTION "Customer VLAN to use for traffic classification"
  DEFVAL      { 0 }
  ::= { alaQoSConditionEntry 111 }

alaQoSConditionInnerSourceVlanStatus OBJECT-TYPE
  SYNTAX      INTEGER {
                enabled (1),
                disabled (2)
              }
  MAX-ACCESS  read-create
  STATUS      current
  DESCRIPTION "Status field indicating whether the inner VLAN
               needs to be matched(enabled) or not(disabled)."
  DEFVAL      { disabled }
  ::= { alaQoSConditionEntry 112 }

alaQoSConditionInner8021p OBJECT-TYPE
  SYNTAX      Integer32 (0..7)
  MAX-ACCESS  read-create
  STATUS      current
  DESCRIPTION "Customer 802.1p to use for traffic classification"
  DEFVAL      { 0 }
  ::= { alaQoSConditionEntry 113 }

alaQoSConditionInner8021pStatus OBJECT-TYPE
  SYNTAX      INTEGER {
                enabled (1),
                disabled (2)
              }
  MAX-ACCESS  read-create
  STATUS      current
  DESCRIPTION "Status field indicating whether the inner 802.1p
               needs to be matched(enabled) or not(disabled)."
  DEFVAL      { disabled }
  ::= { alaQoSConditionEntry 114 }

alaQoSConditionVrfName OBJECT-TYPE
  SYNTAX      DisplayString (SIZE(0..31))
  MAX-ACCESS  read-create
  STATUS      current
  DESCRIPTION "Name of Vrf to match traffic in"
  ::= { alaQoSConditionEntry 115 }

alaQoSConditionVrfNameStatus OBJECT-TYPE
  SYNTAX      INTEGER {
                enabled (1),
                disabled (2)
              }
  MAX-ACCESS  read-create
  STATUS      current
  DESCRIPTION "Status field indicating whether the traffic from a specific vrf needs to be matched(enabled) or not(disabled)."
  DEFVAL      { disabled }
  ::= { alaQoSConditionEntry 116 }

alaQoSCondition8021pEnd OBJECT-TYPE
  SYNTAX      Integer32 (0..7)
  MAX-ACCESS  read-create
  STATUS      current
  DESCRIPTION "802.1p range end value to use for traffic classification."
  DEFVAL      { 0 }
  ::= { alaQoSConditionEntry 117 }

alaQoSConditionInner8021pEnd OBJECT-TYPE
  SYNTAX      Integer32 (0..7)
  MAX-ACCESS  read-create
  STATUS      current
  DESCRIPTION "Inner 802.1p range end value to use for traffic   
               classification."
  DEFVAL      { 0 }
  ::= { alaQoSConditionEntry 118 }

alaQoSConditionSourceVlanGroup OBJECT-TYPE
  SYNTAX      DisplayString (SIZE(0..31))
  MAX-ACCESS  read-create
  STATUS      current
  DESCRIPTION "Source vlan  group to use for traffic classification"
  ::= { alaQoSConditionEntry 119 }

alaQoSConditionSourceVlanGroupStatus OBJECT-TYPE
  SYNTAX      INTEGER {
                enabled (1),
                disabled (2)
              }
  MAX-ACCESS  read-create
  STATUS      current
  DESCRIPTION "Status field indicating whether to use for traffic 
	      classification (enabled) or not (disabled) for source
	      vlan group."
  ::= { alaQoSConditionEntry 120 }

alaQoSConditionInnerSourceVlanGroup OBJECT-TYPE
  SYNTAX      DisplayString (SIZE(0..31))
  MAX-ACCESS  read-create
  STATUS      current
  DESCRIPTION "Inner Source vlan  group to use for traffic classification"
  ::= { alaQoSConditionEntry 121 }

alaQoSConditionInnerSourceVlanGroupStatus OBJECT-TYPE
  SYNTAX      INTEGER {
                enabled (1),
                disabled (2)
              }
  MAX-ACCESS  read-create
  STATUS      current
  DESCRIPTION "Status field indicating whether to use for traffic 
              classification (enabled) or not (disabled) for inner 
	      source vlan group."
  ::= { alaQoSConditionEntry 122 } 

alaQoSConditionSIP OBJECT-TYPE
  SYNTAX      INTEGER {
				audio (1),
		  		video (2),
		  		other (3)
			  }		
  MAX-ACCESS  	read-create
  STATUS      	current
  DESCRIPTION 	"SIP type to use for traffic classification"
  DEFVAL      	{ audio }
  ::= { alaQoSConditionEntry 123 }
alaQoSConditionSIPStatus OBJECT-TYPE
  SYNTAX      INTEGER {
				enabled (1),
		  		disabled (2)
			  }		
  MAX-ACCESS  	read-create
  STATUS      	current
  DESCRIPTION 	"SIP Status field indicates whether SIP is enabled or disabled 
  				for traffic classification"
  DEFVAL      	{ enabled }
  ::= { alaQoSConditionEntry 124 }

--
-- Definition of condition table
--

alaQoSAppliedConditionTable OBJECT-TYPE
  SYNTAX      SEQUENCE OF QoSAppliedConditionEntry
  MAX-ACCESS  not-accessible
  STATUS      current
  DESCRIPTION "Table of QoS AppliedCondition definitions"
  ::= { alaQoSMIBObjects 4 }

alaQoSAppliedConditionEntry OBJECT-TYPE
  SYNTAX      QoSAppliedConditionEntry
  MAX-ACCESS  not-accessible
  STATUS      current
  DESCRIPTION "Definition of QoS AppliedCondition"
  INDEX {
          alaQoSAppliedConditionName
        }
  ::= { alaQoSAppliedConditionTable 1 }

QoSAppliedConditionEntry ::=
  SEQUENCE
  {
    alaQoSAppliedConditionName                              DisplayString,
    alaQoSAppliedConditionSource                            INTEGER,
    alaQoSAppliedConditionSourceSlot                        Integer32,
    alaQoSAppliedConditionSourceSlotStatus                  INTEGER,
    alaQoSAppliedConditionSourcePort                        Integer32,
    alaQoSAppliedConditionSourcePortGroup                   DisplayString,
    alaQoSAppliedConditionSourcePortGroupStatus             INTEGER,
    alaQoSAppliedConditionDestinationSlot                   Integer32,
    alaQoSAppliedConditionDestinationSlotStatus             INTEGER,
    alaQoSAppliedConditionDestinationPort                   Integer32,
    alaQoSAppliedConditionDestinationPortGroup              DisplayString,
    alaQoSAppliedConditionDestinationPortGroupStatus        INTEGER,
    alaQoSAppliedConditionSourceInterfaceType               INTEGER,
    alaQoSAppliedConditionSourceInterfaceTypeStatus         INTEGER,
    alaQoSAppliedConditionDestinationInterfaceType          INTEGER,
    alaQoSAppliedConditionDestinationInterfaceTypeStatus    INTEGER,
    alaQoSAppliedConditionSourceMacAddr                     MacAddress,
    alaQoSAppliedConditionSourceMacAddrStatus               INTEGER,
    alaQoSAppliedConditionSourceMacMask                     MacAddress,
    alaQoSAppliedConditionSourceMacGroup                    DisplayString,
    alaQoSAppliedConditionSourceMacGroupStatus              INTEGER,
    alaQoSAppliedConditionDestinationMacAddr                MacAddress,
    alaQoSAppliedConditionDestinationMacAddrStatus          INTEGER,
    alaQoSAppliedConditionDestinationMacMask                MacAddress,
    alaQoSAppliedConditionDestinationMacGroup               DisplayString,
    alaQoSAppliedConditionDestinationMacGroupStatus         INTEGER,
    alaQoSAppliedConditionSourceVlan                        Integer32,
    alaQoSAppliedConditionSourceVlanStatus                  INTEGER,
    alaQoSAppliedConditionDestinationVlan                   Integer32,
    alaQoSAppliedConditionDestinationVlanStatus             INTEGER,
    alaQoSAppliedCondition8021p                             Integer32,
    alaQoSAppliedCondition8021pStatus                       INTEGER,
    alaQoSAppliedConditionSourceIpAddr                      IpAddress,
    alaQoSAppliedConditionSourceIpAddrStatus                INTEGER,
    alaQoSAppliedConditionSourceIpMask                      IpAddress,
    alaQoSAppliedConditionSourceNetworkGroup                DisplayString,
    alaQoSAppliedConditionSourceNetworkGroupStatus          INTEGER,
    alaQoSAppliedConditionDestinationIpAddr                 IpAddress,
    alaQoSAppliedConditionDestinationIpAddrStatus           INTEGER,
    alaQoSAppliedConditionDestinationIpMask                 IpAddress,
    alaQoSAppliedConditionDestinationNetworkGroup           DisplayString,
    alaQoSAppliedConditionDestinationNetworkGroupStatus     INTEGER,
    alaQoSAppliedConditionMulticastIpAddr                   IpAddress,
    alaQoSAppliedConditionMulticastIpAddrStatus             INTEGER,
    alaQoSAppliedConditionMulticastIpMask                   IpAddress,
    alaQoSAppliedConditionMulticastNetworkGroup             DisplayString,
    alaQoSAppliedConditionMulticastNetworkGroupStatus       INTEGER,
    alaQoSAppliedConditionTos                               Integer32,
    alaQoSAppliedConditionTosStatus                         INTEGER,
    alaQoSAppliedConditionTosMask                           Integer32,
    alaQoSAppliedConditionDscp                              Integer32,
    alaQoSAppliedConditionDscpStatus                        INTEGER,
    alaQoSAppliedConditionDscpMask                          Integer32,
    alaQoSAppliedConditionIpProtocol                        Integer32,
    alaQoSAppliedConditionIpProtocolStatus                  INTEGER,
    alaQoSAppliedConditionSourceIpPort                      Integer32,
    alaQoSAppliedConditionSourceIpPortStatus                INTEGER,
    alaQoSAppliedConditionDestinationIpPort                 Integer32,
    alaQoSAppliedConditionDestinationIpPortStatus           INTEGER,
    alaQoSAppliedConditionService                           DisplayString,
    alaQoSAppliedConditionServiceStatus                     INTEGER,
    alaQoSAppliedConditionServiceGroup                      DisplayString,
    alaQoSAppliedConditionServiceGroupStatus                INTEGER,
    alaQoSAppliedConditionIcmpType                          Integer32,
    alaQoSAppliedConditionIcmpTypeStatus                    INTEGER,
    alaQoSAppliedConditionIcmpCode                          Integer32,
    alaQoSAppliedConditionIcmpCodeStatus                    INTEGER,
    alaQoSAppliedConditionDlci                              Integer32,
    alaQoSAppliedConditionDlciStatus                        INTEGER,
    alaQoSAppliedConditionRowStatus                         RowStatus,
    alaQoSAppliedConditionSourcePortEnd                     Integer32,
    alaQoSAppliedConditionDestinationPortEnd                Integer32,
    alaQoSAppliedConditionSourceIpPortEnd                   Integer32,
    alaQoSAppliedConditionDestinationIpPortEnd              Integer32,
    alaQoSAppliedConditionSourceTcpPort                     Integer32,
    alaQoSAppliedConditionSourceTcpPortStatus               INTEGER,
    alaQoSAppliedConditionSourceTcpPortEnd                  Integer32,
    alaQoSAppliedConditionDestinationTcpPort                Integer32,
    alaQoSAppliedConditionDestinationTcpPortStatus          INTEGER,
    alaQoSAppliedConditionDestinationTcpPortEnd             Integer32,
    alaQoSAppliedConditionSourceUdpPort                     Integer32,
    alaQoSAppliedConditionSourceUdpPortStatus               INTEGER,
    alaQoSAppliedConditionSourceUdpPortEnd                  Integer32,
    alaQoSAppliedConditionDestinationUdpPort                Integer32,
    alaQoSAppliedConditionDestinationUdpPortStatus          INTEGER,
    alaQoSAppliedConditionDestinationUdpPortEnd             Integer32,
    alaQoSAppliedConditionEthertype                         Integer32,
    alaQoSAppliedConditionEthertypeStatus                   INTEGER,
    alaQoSAppliedConditionTcpFlags                          INTEGER,
    alaQoSAppliedConditionTcpFlagsStatus                    INTEGER,
    alaQoSAppliedConditionTcpFlagsVal                       Integer32,
    alaQoSAppliedConditionTcpFlagsValStatus                 INTEGER,
    alaQoSAppliedConditionTcpFlagsMask                      Integer32,
    alaQoSAppliedConditionTcpFlagsMaskStatus                INTEGER,
    alaQoSAppliedConditionTcpEstablished                    INTEGER,
    alaQoSAppliedConditionSourceIpv6Addr                    Ipv6Address,
    alaQoSAppliedConditionSourceIpv6AddrStatus              INTEGER,
    alaQoSAppliedConditionSourceIpv6Mask                    Ipv6Address,
    alaQoSAppliedConditionDestinationIpv6Addr               Ipv6Address,
    alaQoSAppliedConditionDestinationIpv6AddrStatus         INTEGER,
    alaQoSAppliedConditionDestinationIpv6Mask               Ipv6Address,
    alaQoSAppliedConditionIpv6Traffic                       INTEGER,
    alaQoSAppliedConditionIpv6NH	                    Integer32,
    alaQoSAppliedConditionIpv6NHStatus                      INTEGER,
    alaQoSAppliedConditionIpv6FlowLabel	                    Integer32,
    alaQoSAppliedConditionIpv6FlowLabelStatus               INTEGER,
    alaQoSAppliedConditionMcastIpv6Addr                     Ipv6Address,
    alaQoSAppliedConditionMcastIpv6AddrStatus               INTEGER,
    alaQoSAppliedConditionMcastIpv6Mask                     Ipv6Address,
    alaQoSAppliedConditionDscpEnd                           Integer32,
    alaQoSAppliedConditionInnerSourceVlan                   Integer32,
    alaQoSAppliedConditionInnerSourceVlanStatus             INTEGER,
    alaQoSAppliedConditionInner8021p                        Integer32,
    alaQoSAppliedConditionInner8021pStatus                  INTEGER,
    alaQoSAppliedConditionVrfName                           DisplayString,
    alaQoSAppliedConditionVrfNameStatus                     INTEGER,
    alaQoSAppliedCondition8021pEnd			    Integer32,
    alaQoSAppliedConditionInner8021pEnd			    Integer32,
    alaQoSAppliedConditionSourceVlanGroup 		    DisplayString,
    alaQoSAppliedConditionSourceVlanGroupStatus 	    INTEGER,
    alaQoSAppliedConditionInnerSourceVlanGroup 		    DisplayString,
    alaQoSAppliedConditionInnerSourceVlanGroupStatus        INTEGER,
    alaQoSAppliedConditionSIP				    INTEGER,
    alaQoSAppliedConditionSIPStatus			    INTEGER 
  }

alaQoSAppliedConditionName OBJECT-TYPE
  SYNTAX      DisplayString (SIZE(0..31))
  MAX-ACCESS  not-accessible
  STATUS      current
  DESCRIPTION "Name of condition"
  ::= { alaQoSAppliedConditionEntry 1 }

alaQoSAppliedConditionSource OBJECT-TYPE
  SYNTAX      INTEGER {
                ldap (1),
                cli (2),
                blt (3),
                api (4),
                imp (5)
              }
  MAX-ACCESS  read-only
  STATUS      current
  DESCRIPTION "What entity created the condition."
  ::= { alaQoSAppliedConditionEntry 2 }

alaQoSAppliedConditionSourceSlot OBJECT-TYPE
  SYNTAX      Integer32 (0..16)
  MAX-ACCESS  read-only
  STATUS      current
  DESCRIPTION "Source physical slot used for traffic classification
               When 0, the port identifies an aggregate"
  ::= { alaQoSAppliedConditionEntry 3 }

alaQoSAppliedConditionSourceSlotStatus OBJECT-TYPE
  SYNTAX      INTEGER {
                enabled (1),
                disabled (2)
              }
  MAX-ACCESS  read-only
  STATUS      current
  DESCRIPTION "Status field indicating whether the source physical slot and
               port range needs to be matched(enabled) or not(disabled)."
  ::= { alaQoSAppliedConditionEntry 4 }

alaQoSAppliedConditionSourcePort OBJECT-TYPE
  SYNTAX      Integer32 (1..52)
  MAX-ACCESS  read-only
  STATUS      current
  DESCRIPTION "Source physical port range start to use for
               traffic classification"
  ::= { alaQoSAppliedConditionEntry 5 }

alaQoSAppliedConditionSourcePortGroup OBJECT-TYPE
  SYNTAX      DisplayString (SIZE(0..31))
  MAX-ACCESS  read-only
  STATUS      current
  DESCRIPTION "Source physical port group to use for traffic classification"
  ::= { alaQoSAppliedConditionEntry 6 }

alaQoSAppliedConditionSourcePortGroupStatus OBJECT-TYPE
  SYNTAX      INTEGER {
                enabled (1),
                disabled (2)
              }
  MAX-ACCESS  read-only
  STATUS      current
  DESCRIPTION "Status field indicating whether the source physical port group
               needs to be matched(enabled) or not(disabled)."
  ::= { alaQoSAppliedConditionEntry 7 }

alaQoSAppliedConditionDestinationSlot OBJECT-TYPE
  SYNTAX      Integer32 (0..16)
  MAX-ACCESS  read-only
  STATUS      current
  DESCRIPTION "Destination physical slot used for traffic classification
               When 0, the port identifies an aggregate"
  ::= { alaQoSAppliedConditionEntry 8 }

alaQoSAppliedConditionDestinationSlotStatus OBJECT-TYPE
  SYNTAX      INTEGER {
                enabled (1),
                disabled (2)
              }
  MAX-ACCESS  read-only
  STATUS      current
  DESCRIPTION "Status field indicating whether the destination physical slot
               and port range needs to be matched(enabled) or not(disabled)."
  ::= { alaQoSAppliedConditionEntry 9 }

alaQoSAppliedConditionDestinationPort OBJECT-TYPE
  SYNTAX      Integer32 (1..52)
  MAX-ACCESS  read-only
  STATUS      current
  DESCRIPTION "Destination physical port range start to use for traffic
               classification"
  ::= { alaQoSAppliedConditionEntry 10 }

alaQoSAppliedConditionDestinationPortGroup OBJECT-TYPE
  SYNTAX      DisplayString (SIZE(0..31))
  MAX-ACCESS  read-only
  STATUS      current
  DESCRIPTION "Destination physical port group to use for traffic
               classification"
  ::= { alaQoSAppliedConditionEntry 11 }

alaQoSAppliedConditionDestinationPortGroupStatus OBJECT-TYPE
  SYNTAX      INTEGER {
                enabled (1),
                disabled (2)
              }
  MAX-ACCESS  read-only
  STATUS      current
  DESCRIPTION "Status field indicating whether the destination physical port
               group needs to be matched(enabled) or not(disabled)."
  ::= { alaQoSAppliedConditionEntry 12 }

alaQoSAppliedConditionSourceInterfaceType OBJECT-TYPE
  SYNTAX      INTEGER {
                ethernet (1),
                wan (2),
                ethernet10 (3),
                ethernet100 (4),
                ethernet1G (5),
                ethernet10G (6),
                aggregate (7)
              }
  MAX-ACCESS  read-only
  STATUS      current
  DESCRIPTION "Source physical interface type to use for traffic
               classification"
  ::= { alaQoSAppliedConditionEntry 13 }

alaQoSAppliedConditionSourceInterfaceTypeStatus OBJECT-TYPE
  SYNTAX      INTEGER {
                enabled (1),
                disabled (2)
              }
  MAX-ACCESS  read-only
  STATUS      current
  DESCRIPTION "Status field indicating whether the source physical
               interface type needs to be matched(enabled) or not(disabled)."
  ::= { alaQoSAppliedConditionEntry 14 }

alaQoSAppliedConditionDestinationInterfaceType OBJECT-TYPE
  SYNTAX      INTEGER {
                ethernet (1),
                wan (2),
                ethernet10 (3),
                ethernet100 (4),
                ethernet1G (5),
                ethernet10G (6),
                aggregate (7)
              }
  MAX-ACCESS  read-only
  STATUS      current
  DESCRIPTION "Destination physical interface type to use for traffic
               classification"
  ::= { alaQoSAppliedConditionEntry 15 }

alaQoSAppliedConditionDestinationInterfaceTypeStatus OBJECT-TYPE
  SYNTAX      INTEGER {
                enabled (1),
                disabled (2)
              }
  MAX-ACCESS  read-only
  STATUS      current
  DESCRIPTION "Status field indicating whether the destination physical
               interface type needs to be matched(enabled) or not(disabled)."
  ::= { alaQoSAppliedConditionEntry 16 }

alaQoSAppliedConditionSourceMacAddr OBJECT-TYPE
  SYNTAX      MacAddress
  MAX-ACCESS  read-only
  STATUS      current
  DESCRIPTION "Source MAC address to use for traffic classification"
  ::= { alaQoSAppliedConditionEntry 17 }

alaQoSAppliedConditionSourceMacAddrStatus OBJECT-TYPE
  SYNTAX      INTEGER {
                enabled (1),
                disabled (2)
              }
  MAX-ACCESS  read-only
  STATUS      current
  DESCRIPTION "Status field indicating whether the source MAC address & mask
               needs to be matched(enabled) or not(disabled)."
  ::= { alaQoSAppliedConditionEntry 18 }

alaQoSAppliedConditionSourceMacMask OBJECT-TYPE
  SYNTAX      MacAddress
  MAX-ACCESS  read-only
  STATUS      current
  DESCRIPTION "Source MAC mask to use for traffic classification"
  ::= { alaQoSAppliedConditionEntry 19 }

alaQoSAppliedConditionSourceMacGroup OBJECT-TYPE
  SYNTAX      DisplayString (SIZE(0..31))
  MAX-ACCESS  read-only
  STATUS      current
  DESCRIPTION "Source MAC group to use for traffic classification"
  ::= { alaQoSAppliedConditionEntry 20 }

alaQoSAppliedConditionSourceMacGroupStatus OBJECT-TYPE
  SYNTAX      INTEGER {
                enabled (1),
                disabled (2)
              }
  MAX-ACCESS  read-only
  STATUS      current
  DESCRIPTION "Status field indicating whether the source MAC group
               needs to be matched(enabled) or not(disabled)."
  ::= { alaQoSAppliedConditionEntry 21 }

alaQoSAppliedConditionDestinationMacAddr OBJECT-TYPE
  SYNTAX      MacAddress
  MAX-ACCESS  read-only
  STATUS      current
  DESCRIPTION "Destination MAC address to use for traffic classification"
  ::= { alaQoSAppliedConditionEntry 22 }

alaQoSAppliedConditionDestinationMacAddrStatus OBJECT-TYPE
  SYNTAX      INTEGER {
                enabled (1),
                disabled (2)
              }
  MAX-ACCESS  read-only
  STATUS      current
  DESCRIPTION "Status field indicating whether the destination MAC address
               & mask needs to be matched(enabled) or not(disabled)."
  ::= { alaQoSAppliedConditionEntry 23 }

alaQoSAppliedConditionDestinationMacMask OBJECT-TYPE
  SYNTAX      MacAddress
  MAX-ACCESS  read-only
  STATUS      current
  DESCRIPTION "Destination MAC mask to use for traffic classification"
  ::= { alaQoSAppliedConditionEntry 24 }

alaQoSAppliedConditionDestinationMacGroup OBJECT-TYPE
  SYNTAX      DisplayString (SIZE(0..31))
  MAX-ACCESS  read-only
  STATUS      current
  DESCRIPTION "Destination MAC group to use for traffic classification"
  ::= { alaQoSAppliedConditionEntry 25 }

alaQoSAppliedConditionDestinationMacGroupStatus OBJECT-TYPE
  SYNTAX      INTEGER {
                enabled (1),
                disabled (2)
              }
  MAX-ACCESS  read-only
  STATUS      current
  DESCRIPTION "Status field indicating whether the destination MAC group
               needs to be matched(enabled) or not(disabled)."
  ::= { alaQoSAppliedConditionEntry 26 }

alaQoSAppliedConditionSourceVlan OBJECT-TYPE
  SYNTAX      Integer32 (0..4095)
  MAX-ACCESS  read-only
  STATUS      current
  DESCRIPTION "Source VLAN to use for traffic classification"
  ::= { alaQoSAppliedConditionEntry 27 }

alaQoSAppliedConditionSourceVlanStatus OBJECT-TYPE
  SYNTAX      INTEGER {
                enabled (1),
                disabled (2)
              }
  MAX-ACCESS  read-only
  STATUS      current
  DESCRIPTION "Status field indicating whether the source VLAN
               needs to be matched(enabled) or not(disabled)."
  ::= { alaQoSAppliedConditionEntry 28 }

alaQoSAppliedConditionDestinationVlan OBJECT-TYPE
  SYNTAX      Integer32 (0..4095)
  MAX-ACCESS  read-only
  STATUS      current
  DESCRIPTION "Destination VLAN to use for traffic classification"
  ::= { alaQoSAppliedConditionEntry 29 }

alaQoSAppliedConditionDestinationVlanStatus OBJECT-TYPE
  SYNTAX      INTEGER {
                enabled (1),
                disabled (2)
              }
  MAX-ACCESS  read-only
  STATUS      current
  DESCRIPTION "Status field indicating whether the destination VLAN
               needs to be matched(enabled) or not(disabled)."
  ::= { alaQoSAppliedConditionEntry 30 }

alaQoSAppliedCondition8021p OBJECT-TYPE
  SYNTAX      Integer32 (0..7)
  MAX-ACCESS  read-only
  STATUS      current
  DESCRIPTION "802.1p value to use for traffic classification"
  ::= { alaQoSAppliedConditionEntry 31 }

alaQoSAppliedCondition8021pStatus OBJECT-TYPE
  SYNTAX      INTEGER {
                enabled (1),
                disabled (2)
              }
  MAX-ACCESS  read-only
  STATUS      current
  DESCRIPTION "Status field indicating whether the 802.1p value
               needs to be matched(enabled) or not(disabled)."
  ::= { alaQoSAppliedConditionEntry 32 }

alaQoSAppliedConditionSourceIpAddr OBJECT-TYPE
  SYNTAX      IpAddress
  MAX-ACCESS  read-only
  STATUS      current
  DESCRIPTION "Source IP address to use for traffic classification"
  ::= { alaQoSAppliedConditionEntry 33 }

alaQoSAppliedConditionSourceIpAddrStatus OBJECT-TYPE
  SYNTAX      INTEGER {
                enabled (1),
                disabled (2)
              }
  MAX-ACCESS  read-only
  STATUS      current
  DESCRIPTION "Status field indicating whether the source IP address & mask
               needs to be matched(enabled) or not(disabled)."
  ::= { alaQoSAppliedConditionEntry 34 }

alaQoSAppliedConditionSourceIpMask OBJECT-TYPE
  SYNTAX      IpAddress
  MAX-ACCESS  read-only
  STATUS      current
  DESCRIPTION "Source IP mask to use for traffic classification"
  ::= { alaQoSAppliedConditionEntry 35 }

alaQoSAppliedConditionSourceNetworkGroup OBJECT-TYPE
  SYNTAX      DisplayString (SIZE(0..31))
  MAX-ACCESS  read-only
  STATUS      current
  DESCRIPTION "Source network group to use for traffic classification"
  ::= { alaQoSAppliedConditionEntry 36 }

alaQoSAppliedConditionSourceNetworkGroupStatus OBJECT-TYPE
  SYNTAX      INTEGER {
                enabled (1),
                disabled (2)
              }
  MAX-ACCESS  read-only
  STATUS      current
  DESCRIPTION "Status field indicating whether the source network group
               needs to be matched(enabled) or not(disabled)."
  ::= { alaQoSAppliedConditionEntry 37 }

alaQoSAppliedConditionDestinationIpAddr OBJECT-TYPE
  SYNTAX      IpAddress
  MAX-ACCESS  read-only
  STATUS      current
  DESCRIPTION "Destination IP address to use for traffic classification"
  ::= { alaQoSAppliedConditionEntry 38 }

alaQoSAppliedConditionDestinationIpAddrStatus OBJECT-TYPE
  SYNTAX      INTEGER {
                enabled (1),
                disabled (2)
              }
  MAX-ACCESS  read-only
  STATUS      current
  DESCRIPTION "Status field indicating whether the destination IP address
               & mask needs to be matched(enabled) or not(disabled)."
  ::= { alaQoSAppliedConditionEntry 39 }

alaQoSAppliedConditionDestinationIpMask OBJECT-TYPE
  SYNTAX      IpAddress
  MAX-ACCESS  read-only
  STATUS      current
  DESCRIPTION "Destination IP mask to use for traffic classification"
  ::= { alaQoSAppliedConditionEntry 40 }

alaQoSAppliedConditionDestinationNetworkGroup OBJECT-TYPE
  SYNTAX      DisplayString (SIZE(0..31))
  MAX-ACCESS  read-only
  STATUS      current
  DESCRIPTION "Destination network group to use for traffic classification"
  ::= { alaQoSAppliedConditionEntry 41 }

alaQoSAppliedConditionDestinationNetworkGroupStatus OBJECT-TYPE
  SYNTAX      INTEGER {
                enabled (1),
                disabled (2)
              }
  MAX-ACCESS  read-only
  STATUS      current
  DESCRIPTION "Status field indicating whether the destination network group
               needs to be matched(enabled) or not(disabled)."
  ::= { alaQoSAppliedConditionEntry 42 }

alaQoSAppliedConditionMulticastIpAddr OBJECT-TYPE
  SYNTAX      IpAddress
  MAX-ACCESS  read-only
  STATUS      current
  DESCRIPTION "Multicast IP address to use for traffic classification"
  ::= { alaQoSAppliedConditionEntry 43 }

alaQoSAppliedConditionMulticastIpAddrStatus OBJECT-TYPE
  SYNTAX      INTEGER {
                enabled (1),
                disabled (2)
              }
  MAX-ACCESS  read-only
  STATUS      current
  DESCRIPTION "Status field indicating whether the multicast IP address & mask
               needs to be matched(enabled) or not(disabled)."
  ::= { alaQoSAppliedConditionEntry 44 }

alaQoSAppliedConditionMulticastIpMask OBJECT-TYPE
  SYNTAX      IpAddress
  MAX-ACCESS  read-only
  STATUS      current
  DESCRIPTION "Multicast IP mask to use for traffic classification"
  ::= { alaQoSAppliedConditionEntry 45 }

alaQoSAppliedConditionMulticastNetworkGroup OBJECT-TYPE
  SYNTAX      DisplayString (SIZE(0..31))
  MAX-ACCESS  read-only
  STATUS      current
  DESCRIPTION "Multicast network group to use for traffic classification"
  ::= { alaQoSAppliedConditionEntry 46 }

alaQoSAppliedConditionMulticastNetworkGroupStatus OBJECT-TYPE
  SYNTAX      INTEGER {
                enabled (1),
                disabled (2)
              }
  MAX-ACCESS  read-only
  STATUS      current
  DESCRIPTION "Status field indicating whether the multicast network group
               needs to be matched(enabled) or not(disabled)."
  ::= { alaQoSAppliedConditionEntry 47 }

alaQoSAppliedConditionTos OBJECT-TYPE
  SYNTAX      Integer32 (0..7)
  MAX-ACCESS  read-only
  STATUS      current
  DESCRIPTION "TOS value to use for traffic classification"
  ::= { alaQoSAppliedConditionEntry 48 }

alaQoSAppliedConditionTosStatus OBJECT-TYPE
  SYNTAX      INTEGER {
                enabled (1),
                disabled (2)
              }
  MAX-ACCESS  read-only
  STATUS      current
  DESCRIPTION "Status field indicating whether the TOS value & mask
               needs to be matched(enabled) or not(disabled)."
  ::= { alaQoSAppliedConditionEntry 49 }

alaQoSAppliedConditionTosMask OBJECT-TYPE
  SYNTAX      Integer32 (0..7)
  MAX-ACCESS  read-only
  STATUS      current
  DESCRIPTION "TOS mask to use for traffic classification"
  ::= { alaQoSAppliedConditionEntry 50 }

alaQoSAppliedConditionDscp OBJECT-TYPE
  SYNTAX      Integer32 (0..63)
  MAX-ACCESS  read-only
  STATUS      current
  DESCRIPTION "DSCP value to use for traffic classification"
  ::= { alaQoSAppliedConditionEntry 51 }

alaQoSAppliedConditionDscpStatus OBJECT-TYPE
  SYNTAX      INTEGER {
                enabled (1),
                disabled (2)
              }
  MAX-ACCESS  read-only
  STATUS      current
  DESCRIPTION "Status field indicating whether the DSCP value & mask
               needs to be matched(enabled) or not(disabled)."
  ::= { alaQoSAppliedConditionEntry 52 }

alaQoSAppliedConditionDscpMask OBJECT-TYPE
  SYNTAX      Integer32 (0..63)
  MAX-ACCESS  read-only
  STATUS      current
  DESCRIPTION "DSCP mask to use for traffic classification"
  ::= { alaQoSAppliedConditionEntry 53 }

alaQoSAppliedConditionIpProtocol OBJECT-TYPE
  SYNTAX      Integer32 (0..255)
  MAX-ACCESS  read-only
  STATUS      current
  DESCRIPTION "IP protocol to use for traffic classification."
  ::= { alaQoSAppliedConditionEntry 54 }

alaQoSAppliedConditionIpProtocolStatus OBJECT-TYPE
  SYNTAX      INTEGER {
                enabled (1),
                disabled (2)
              }
  MAX-ACCESS  read-only
  STATUS      current
  DESCRIPTION "Status field indicating whether the IP protocol
               needs to be matched(enabled) or not(disabled)."
  ::= { alaQoSAppliedConditionEntry 55 }

alaQoSAppliedConditionSourceIpPort OBJECT-TYPE
  SYNTAX      Integer32 (0..65535)
  MAX-ACCESS  read-only
  STATUS      current
  DESCRIPTION "Source IP port range start to use for traffic classification."
  ::= { alaQoSAppliedConditionEntry 56 }

alaQoSAppliedConditionSourceIpPortStatus OBJECT-TYPE
  SYNTAX      INTEGER {
                enabled (1),
                disabled (2)
              }
  MAX-ACCESS  read-only
  STATUS      current
  DESCRIPTION "Status field indicating whether the source IP port range
               needs to be matched(enabled) or not(disabled)."
  ::= { alaQoSAppliedConditionEntry 57 }

alaQoSAppliedConditionDestinationIpPort OBJECT-TYPE
  SYNTAX      Integer32 (0..65535)
  MAX-ACCESS  read-only
  STATUS      current
  DESCRIPTION "Destination IP port range start to use for traffic
               classification."
  ::= { alaQoSAppliedConditionEntry 58 }

alaQoSAppliedConditionDestinationIpPortStatus OBJECT-TYPE
  SYNTAX      INTEGER {
                enabled (1),
                disabled (2)
              }
  MAX-ACCESS  read-only
  STATUS      current
  DESCRIPTION "Status field indicating whether the destination IP port range
               needs to be matched(enabled) or not(disabled)."
  ::= { alaQoSAppliedConditionEntry 59 }

alaQoSAppliedConditionService OBJECT-TYPE
  SYNTAX      DisplayString (SIZE(0..31))
  MAX-ACCESS  read-only
  STATUS      current
  DESCRIPTION "Name of service to use for traffic classification"
  ::= { alaQoSAppliedConditionEntry 60 }

alaQoSAppliedConditionServiceStatus OBJECT-TYPE
  SYNTAX      INTEGER {
                enabled (1),
                disabled (2)
              }
  MAX-ACCESS  read-only
  STATUS      current
  DESCRIPTION "Status field indicating whether the service
               needs to be matched(enabled) or not(disabled)."
  ::= { alaQoSAppliedConditionEntry 61 }

alaQoSAppliedConditionServiceGroup OBJECT-TYPE
  SYNTAX      DisplayString (SIZE(0..31))
  MAX-ACCESS  read-only
  STATUS      current
  DESCRIPTION "Name of service group to use for traffic classification"
  ::= { alaQoSAppliedConditionEntry 62 }

alaQoSAppliedConditionServiceGroupStatus OBJECT-TYPE
  SYNTAX      INTEGER {
                enabled (1),
                disabled (2)
              }
  MAX-ACCESS  read-only
  STATUS      current
  DESCRIPTION "Status field indicating whether the service group
               needs to be matched(enabled) or not(disabled)."
  ::= { alaQoSAppliedConditionEntry 63 }

alaQoSAppliedConditionIcmpType OBJECT-TYPE
  SYNTAX      Integer32 (0..255)
  MAX-ACCESS  read-only
  STATUS      current
  DESCRIPTION "ICMP type to use for traffic classification"
  ::= { alaQoSAppliedConditionEntry 64 }

alaQoSAppliedConditionIcmpTypeStatus OBJECT-TYPE
  SYNTAX      INTEGER {
                enabled (1),
                disabled (2)
              }
  MAX-ACCESS  read-only
  STATUS      current
  DESCRIPTION "Status field indicating whether the ICMP type
               needs to be matched(enabled) or not(disabled)."
  ::= { alaQoSAppliedConditionEntry 65 }

alaQoSAppliedConditionIcmpCode OBJECT-TYPE
  SYNTAX      Integer32 (0..255)
  MAX-ACCESS  read-only
  STATUS      current
  DESCRIPTION "ICMP code to use for traffic classification"
  ::= { alaQoSAppliedConditionEntry 66 }

alaQoSAppliedConditionIcmpCodeStatus OBJECT-TYPE
  SYNTAX      INTEGER {
                enabled (1),
                disabled (2)
              }
  MAX-ACCESS  read-only
  STATUS      current
  DESCRIPTION "Status field indicating whether the ICMP code
               needs to be matched(enabled) or not(disabled)."
  ::= { alaQoSAppliedConditionEntry 67 }

alaQoSAppliedConditionDlci OBJECT-TYPE
  SYNTAX      Integer32 (0..512)
  MAX-ACCESS  read-only
  STATUS      current
  DESCRIPTION "DLCI to use to traffic classification"
  ::= { alaQoSAppliedConditionEntry 68 }

alaQoSAppliedConditionDlciStatus OBJECT-TYPE
  SYNTAX      INTEGER {
                enabled (1),
                disabled (2)
              }
  MAX-ACCESS  read-only
  STATUS      current
  DESCRIPTION "Status field indicating whether the DLCI
               needs to be matched(enabled) or not(disabled)."
  ::= { alaQoSAppliedConditionEntry 69 }

alaQoSAppliedConditionRowStatus OBJECT-TYPE
  SYNTAX      RowStatus
  MAX-ACCESS  read-only
  STATUS      current
  DESCRIPTION "Used to create/delete conditions according to the
               RowStatus convention"
  ::= { alaQoSAppliedConditionEntry 70 }

alaQoSAppliedConditionSourcePortEnd OBJECT-TYPE
  SYNTAX      Integer32 (1..52)
  MAX-ACCESS  read-only
  STATUS      current
  DESCRIPTION "Source physical port range end to use for traffic
               classification.  Must be greater than port range start to
               indicate a range.  When '1', use source port as a single port."
  ::= { alaQoSAppliedConditionEntry 71 }

alaQoSAppliedConditionDestinationPortEnd OBJECT-TYPE
  SYNTAX      Integer32 (1..52)
  MAX-ACCESS  read-only
  STATUS      current
  DESCRIPTION "Destination physical port range end to use for traffic
               classification.  Must be greater than port range start to
               indicate a range.  When '1', use destination port as a single
               port."
  ::= { alaQoSAppliedConditionEntry 72 }

alaQoSAppliedConditionSourceIpPortEnd OBJECT-TYPE
  SYNTAX      Integer32 (0..65535)
  MAX-ACCESS  read-only
  STATUS      current
  DESCRIPTION "Source IP port range end to use for traffic classification.
               Must be greater than source IP port range start to indicate a
               range.  When '0', use source IP port as a single IP port."
  ::= { alaQoSAppliedConditionEntry 73 }

alaQoSAppliedConditionDestinationIpPortEnd OBJECT-TYPE
  SYNTAX      Integer32 (0..65535)
  MAX-ACCESS  read-only
  STATUS      current
  DESCRIPTION "Destination IP port range end to use for traffic classification.
               Must be greater than destination IP port range start to indicate
               a range.  When '0', use destination IP port as a single IP port."
  ::= { alaQoSAppliedConditionEntry 74 }

alaQoSAppliedConditionSourceTcpPort OBJECT-TYPE
  SYNTAX      Integer32 (0..65535)
  MAX-ACCESS  read-only
  STATUS      current
  DESCRIPTION "Source TCP port range start to use for traffic classification."
  ::= { alaQoSAppliedConditionEntry 75 }

alaQoSAppliedConditionSourceTcpPortStatus OBJECT-TYPE
  SYNTAX      INTEGER {
                enabled (1),
                disabled (2)
              }
  MAX-ACCESS  read-only
  STATUS      current
  DESCRIPTION "Status field indicating whether the source TCP port range
               needs to be matched(enabled) or not(disabled)."
  ::= { alaQoSAppliedConditionEntry 76 }

alaQoSAppliedConditionSourceTcpPortEnd OBJECT-TYPE
  SYNTAX      Integer32 (0..65535)
  MAX-ACCESS  read-only
  STATUS      current
  DESCRIPTION "Source TCP port range end to use for traffic classification.
               Must be greater than source TCP port range start to indicate a
               range.  When '0', use source TCP port as a single TCP port."
  ::= { alaQoSAppliedConditionEntry 77 }

alaQoSAppliedConditionDestinationTcpPort OBJECT-TYPE
  SYNTAX      Integer32 (0..65535)
  MAX-ACCESS  read-only
  STATUS      current
  DESCRIPTION "Destination TCP port range start to use for traffic
               classification."
  ::= { alaQoSAppliedConditionEntry 78 }

alaQoSAppliedConditionDestinationTcpPortStatus OBJECT-TYPE
  SYNTAX      INTEGER {
                enabled (1),
                disabled (2)
              }
  MAX-ACCESS  read-only
  STATUS      current
  DESCRIPTION "Status field indicating whether the destination TCP port range
               needs to be matched(enabled) or not(disabled)."
  ::= { alaQoSAppliedConditionEntry 79 }

alaQoSAppliedConditionDestinationTcpPortEnd OBJECT-TYPE
  SYNTAX      Integer32 (0..65535)
  MAX-ACCESS  read-only
  STATUS      current
  DESCRIPTION "Destination TCP port range end to use for traffic
               classification.  Must be greater than destination TCP port range
               start to indicate a range.  When '0', use destination TCP port
               as a single TCP port."
  ::= { alaQoSAppliedConditionEntry 80 }

alaQoSAppliedConditionSourceUdpPort OBJECT-TYPE
  SYNTAX      Integer32 (0..65535)
  MAX-ACCESS  read-only
  STATUS      current
  DESCRIPTION "Source UDP port range start to use for traffic classification."
  ::= { alaQoSAppliedConditionEntry 81 }

alaQoSAppliedConditionSourceUdpPortStatus OBJECT-TYPE
  SYNTAX      INTEGER {
                enabled (1),
                disabled (2)
              }
  MAX-ACCESS  read-only
  STATUS      current
  DESCRIPTION "Status field indicating whether the source UDP port range
               needs to be matched(enabled) or not(disabled)."
  ::= { alaQoSAppliedConditionEntry 82 }

alaQoSAppliedConditionSourceUdpPortEnd OBJECT-TYPE
  SYNTAX      Integer32 (0..65535)
  MAX-ACCESS  read-only
  STATUS      current
  DESCRIPTION "Source UDP port range end to use for traffic classification.
               Must be greater than source UDP port range start to indicate
               a range.  When '0', use source UDP port as a single UDP port."
  ::= { alaQoSAppliedConditionEntry 83 }

alaQoSAppliedConditionDestinationUdpPort OBJECT-TYPE
  SYNTAX      Integer32 (0..65535)
  MAX-ACCESS  read-only
  STATUS      current
  DESCRIPTION "Destination UDP port range start to use for traffic
               classification."
  ::= { alaQoSAppliedConditionEntry 84 }

alaQoSAppliedConditionDestinationUdpPortStatus OBJECT-TYPE
  SYNTAX      INTEGER {
                enabled (1),
                disabled (2)
              }
  MAX-ACCESS  read-only
  STATUS      current
  DESCRIPTION "Status field indicating whether the destination UDP port range
               needs to be matched(enabled) or not(disabled)."
  ::= { alaQoSAppliedConditionEntry 85 }

alaQoSAppliedConditionDestinationUdpPortEnd OBJECT-TYPE
  SYNTAX      Integer32 (0..65535)
  MAX-ACCESS  read-only
  STATUS      current
  DESCRIPTION "Destination UDP port range end to use for traffic
               classification.  Must be greater than destination UDP port range
               start to indicate a range.  When '0', use destination UDP port
               as a single TCP port."
  ::= { alaQoSAppliedConditionEntry 86 }

alaQoSAppliedConditionEthertype OBJECT-TYPE
  SYNTAX      Integer32 (0..65535)
  MAX-ACCESS  read-only
  STATUS      current
  DESCRIPTION "Ethertype value to use for traffic classification"
  ::= { alaQoSAppliedConditionEntry 87 }

alaQoSAppliedConditionEthertypeStatus OBJECT-TYPE
  SYNTAX      INTEGER {
                enabled (1),
                disabled (2)
              }
  MAX-ACCESS  read-only
  STATUS      current
  DESCRIPTION "Status field indicating whether the ethertype value
               needs to be matched(enabled) or not(disabled)."
  ::= { alaQoSAppliedConditionEntry 88 }

alaQoSAppliedConditionTcpFlags OBJECT-TYPE
  SYNTAX      INTEGER {
                all (1),
                any (2)
              }
  MAX-ACCESS  read-only
  STATUS      current
  DESCRIPTION "Use any/all specifieid TCP flags for traffic classification"
  ::= { alaQoSAppliedConditionEntry 89 }

alaQoSAppliedConditionTcpFlagsStatus OBJECT-TYPE
  SYNTAX      INTEGER {
                enabled (1),
                disabled (2)
              }
  MAX-ACCESS  read-only
  STATUS      current
  DESCRIPTION "Status field indicating whether the TCP flag bits
               needs to be matched(enabled) or not(disabled)."
  ::= { alaQoSAppliedConditionEntry 90 }

alaQoSAppliedConditionTcpFlagsVal OBJECT-TYPE
  SYNTAX      Integer32
  MAX-ACCESS  read-only
  STATUS      current
  DESCRIPTION "TCP flags values used for traffic classification"
  ::= { alaQoSAppliedConditionEntry 91 }

alaQoSAppliedConditionTcpFlagsValStatus OBJECT-TYPE
  SYNTAX      INTEGER {
                enabled (1),
                disabled (2)
              }
  MAX-ACCESS  read-only
  STATUS      current
  DESCRIPTION "Not used"
  ::= { alaQoSAppliedConditionEntry 92 }

alaQoSAppliedConditionTcpFlagsMask OBJECT-TYPE
  SYNTAX      Integer32
  MAX-ACCESS  read-only
  STATUS      current
  DESCRIPTION "Mask of TCP flags bits used for traffic classification"
  ::= { alaQoSAppliedConditionEntry 93 }

alaQoSAppliedConditionTcpFlagsMaskStatus OBJECT-TYPE
  SYNTAX      INTEGER {
                enabled (1),
                disabled (2)
              }
  MAX-ACCESS  read-only
  STATUS      current
  DESCRIPTION "Not used"
  ::= { alaQoSAppliedConditionEntry 94 }

alaQoSAppliedConditionTcpEstablished OBJECT-TYPE
  SYNTAX      INTEGER {
                yes (1),
                no (2)
              }
  MAX-ACCESS  read-only
  STATUS      current
  DESCRIPTION "Look for established TCP sessions in classification"
  ::= { alaQoSAppliedConditionEntry 95 }

alaQoSAppliedConditionSourceIpv6Addr OBJECT-TYPE
  SYNTAX      Ipv6Address
  MAX-ACCESS  read-only
  STATUS      current
  DESCRIPTION "Source IPv6 address to use for traffic classification"
  ::= { alaQoSAppliedConditionEntry 96 }

alaQoSAppliedConditionSourceIpv6AddrStatus OBJECT-TYPE
  SYNTAX      INTEGER {
                enabled (1),
                disabled (2)
              }
  MAX-ACCESS  read-only
  STATUS      current
  DESCRIPTION "Status field indicating whether the source IPv6 address & mask
               needs to be matched(enabled) or not(disabled)."
  ::= { alaQoSAppliedConditionEntry 97 }

alaQoSAppliedConditionSourceIpv6Mask OBJECT-TYPE
  SYNTAX      Ipv6Address
  MAX-ACCESS  read-only
  STATUS      current
  DESCRIPTION "Source IPv6 mask to use for traffic classification"
  ::= { alaQoSAppliedConditionEntry 98 }

alaQoSAppliedConditionDestinationIpv6Addr OBJECT-TYPE
  SYNTAX      Ipv6Address
  MAX-ACCESS  read-only
  STATUS      current
  DESCRIPTION "Destination IPv6 address to use for traffic classification"
  ::= { alaQoSAppliedConditionEntry 99 }

alaQoSAppliedConditionDestinationIpv6AddrStatus OBJECT-TYPE
  SYNTAX      INTEGER {
                enabled (1),
                disabled (2)
              }
  MAX-ACCESS  read-only
  STATUS      current
  DESCRIPTION "Status field indicating whether the destination IPv6 address & mask
               needs to be matched(enabled) or not(disabled)."
  ::= { alaQoSAppliedConditionEntry 100 }

alaQoSAppliedConditionDestinationIpv6Mask OBJECT-TYPE
  SYNTAX      Ipv6Address
  MAX-ACCESS  read-only
  STATUS      current
  DESCRIPTION "Destination IPv6 mask to use for traffic classification"
  ::= { alaQoSAppliedConditionEntry 101 }

alaQoSAppliedConditionIpv6Traffic OBJECT-TYPE
  SYNTAX      INTEGER {
                yes (1),
                no (2)
              }
  MAX-ACCESS  read-only
  STATUS      current
  DESCRIPTION "classify IPV6 traffic "
  ::= { alaQoSAppliedConditionEntry 102 }

alaQoSAppliedConditionIpv6NH OBJECT-TYPE
  SYNTAX      Integer32 (0..255)
  MAX-ACCESS  read-only
  STATUS      current
  DESCRIPTION "NH value to use for traffic classification"
  DEFVAL      { 0 }
  ::= { alaQoSAppliedConditionEntry 103 }

alaQoSAppliedConditionIpv6NHStatus OBJECT-TYPE
  SYNTAX      INTEGER {
                enabled (1),
                disabled (2)
              }
  MAX-ACCESS  read-only
  STATUS      current
  DESCRIPTION "Status field indicating whether the NH value
               needs to be matched(enabled) or not(disabled)."
  DEFVAL      { disabled }
  ::= { alaQoSAppliedConditionEntry 104 }

alaQoSAppliedConditionIpv6FlowLabel OBJECT-TYPE
  SYNTAX      Integer32 (0..1048575)
  MAX-ACCESS  read-only
  STATUS      current
  DESCRIPTION "FL value to use for traffic classification"
  DEFVAL      { 0 }
  ::= { alaQoSAppliedConditionEntry 105 }

alaQoSAppliedConditionIpv6FlowLabelStatus OBJECT-TYPE
  SYNTAX      INTEGER {
                enabled (1),
                disabled (2)
              }
  MAX-ACCESS  read-only
  STATUS      current
  DESCRIPTION "Status field indicating whether the flow label value
               needs to be matched(enabled) or not(disabled)."
  DEFVAL      { disabled }
  ::= { alaQoSAppliedConditionEntry 106 }

alaQoSAppliedConditionMcastIpv6Addr OBJECT-TYPE
  SYNTAX      Ipv6Address
  MAX-ACCESS  read-create
  STATUS      current
  DESCRIPTION "Multicast IPv6 address to use for traffic classification"
  DEFVAL      { '00000000000000000000000000000000'h }
  ::= { alaQoSAppliedConditionEntry 107 }

alaQoSAppliedConditionMcastIpv6AddrStatus OBJECT-TYPE
  SYNTAX      INTEGER {
                enabled (1),
                disabled (2)
              }
  MAX-ACCESS  read-create
  STATUS      current
  DESCRIPTION "Status field indicating whether the multicast IPv6 address & mask
               needs to be matched(enabled) or not(disabled)."
  DEFVAL      { disabled }
  ::= { alaQoSAppliedConditionEntry 108 }

alaQoSAppliedConditionMcastIpv6Mask OBJECT-TYPE
  SYNTAX      Ipv6Address
  MAX-ACCESS  read-create
  STATUS      current
  DESCRIPTION "Multicast IPv6 mask to use for traffic classification"
  DEFVAL      { 'ffffffffffffffffffffffffffffffff'h }
  ::= { alaQoSAppliedConditionEntry 109 }

alaQoSAppliedConditionDscpEnd OBJECT-TYPE
  SYNTAX      Integer32 (0..63)
  MAX-ACCESS  read-only
  STATUS      current
  DESCRIPTION "DSCP value to use for traffic classification"
  ::= { alaQoSAppliedConditionEntry 110 }

alaQoSAppliedConditionInnerSourceVlan OBJECT-TYPE
  SYNTAX      Integer32 (0..4095)
  MAX-ACCESS  read-only
  STATUS      current
  DESCRIPTION "Customer VLAN to use for traffic classification"
  DEFVAL      { 0 }
  ::= { alaQoSAppliedConditionEntry 111 }

alaQoSAppliedConditionInnerSourceVlanStatus OBJECT-TYPE
  SYNTAX      INTEGER {
                enabled (1),
                disabled (2)
              }
  MAX-ACCESS  read-only
  STATUS      current
  DESCRIPTION "Status field indicating whether the inner VLAN
               needs to be matched(enabled) or not(disabled)."
  DEFVAL      { disabled }
  ::= { alaQoSAppliedConditionEntry 112 }

alaQoSAppliedConditionInner8021p OBJECT-TYPE
  SYNTAX      Integer32 (0..7)
  MAX-ACCESS  read-only
  STATUS      current
  DESCRIPTION "Customer 802.1p to use for traffic classification"
  DEFVAL      { 0 }
  ::= { alaQoSAppliedConditionEntry 113 }

alaQoSAppliedConditionInner8021pStatus OBJECT-TYPE
  SYNTAX      INTEGER {
                enabled (1),
                disabled (2)
              }
  MAX-ACCESS  read-only
  STATUS      current
  DESCRIPTION "Status field indicating whether the inner 802.1p
               needs to be matched(enabled) or not(disabled)."
  DEFVAL      { disabled }
  ::= { alaQoSAppliedConditionEntry 114 }

alaQoSAppliedConditionVrfName OBJECT-TYPE
  SYNTAX      DisplayString (SIZE(0..31))
  MAX-ACCESS  read-create
  STATUS      current
  DESCRIPTION "Name of Vrf to match traffic in"
  ::= { alaQoSAppliedConditionEntry 115 }

alaQoSAppliedConditionVrfNameStatus OBJECT-TYPE
  SYNTAX      INTEGER {
                enabled (1),
                disabled (2)
              }
  MAX-ACCESS  read-create
  STATUS      current
  DESCRIPTION "Status field indicating whether the traffic from a specific vrf needs 
  	      to be matched(enabled) or not(disabled)."
  DEFVAL      { disabled }
  ::= { alaQoSAppliedConditionEntry 116 }

alaQoSAppliedCondition8021pEnd OBJECT-TYPE
  SYNTAX      Integer32 (0..7)
  MAX-ACCESS  read-create
  STATUS      current
  DESCRIPTION "802.1p range end value to use for traffic classification."
  DEFVAL      { 0 }
  ::= { alaQoSAppliedConditionEntry 117 }

alaQoSAppliedConditionInner8021pEnd OBJECT-TYPE
  SYNTAX      Integer32 (0..7) 
  MAX-ACCESS  read-create
  STATUS      current
  DESCRIPTION "Inner 802.1p range end value to use for traffic classification."
  DEFVAL      { 0 }
  ::= { alaQoSAppliedConditionEntry 118 } 

alaQoSAppliedConditionSourceVlanGroup OBJECT-TYPE
  SYNTAX      DisplayString (SIZE(0..31))
  MAX-ACCESS  read-create
  STATUS      current
  DESCRIPTION "Source vlan  group to use for traffic classification"
  ::= { alaQoSAppliedConditionEntry 119 }

alaQoSAppliedConditionSourceVlanGroupStatus OBJECT-TYPE
  SYNTAX      INTEGER {
                enabled (1),
                disabled (2)
              }
  MAX-ACCESS  read-create
  STATUS      current
  DESCRIPTION "Status field indicating whether to use for traffic 
              classification (enabled) or not (disabled) for source
              vlan group."
  ::= { alaQoSAppliedConditionEntry 120 }

alaQoSAppliedConditionInnerSourceVlanGroup OBJECT-TYPE
  SYNTAX      DisplayString (SIZE(0..31))
  MAX-ACCESS  read-create
  STATUS      current
  DESCRIPTION "Inner Source vlan  group to use for traffic classification"
  ::= { alaQoSAppliedConditionEntry 121 }

alaQoSAppliedConditionInnerSourceVlanGroupStatus OBJECT-TYPE
  SYNTAX      INTEGER {
                enabled (1),
                disabled (2)
              }
  MAX-ACCESS  read-create
  STATUS      current
  DESCRIPTION "Status field indicating whether to use for traffic
              classification (enabled) or not (disabled) for inner
              source vlan group."
  ::= { alaQoSAppliedConditionEntry 122 }

alaQoSAppliedConditionSIP OBJECT-TYPE
  SYNTAX      INTEGER {
				audio (1),
		  		video (2),
		  		other (3)
			  }					
  MAX-ACCESS  	read-create
  STATUS      	current
  DESCRIPTION 	"SIP type to use for traffic classification"
  DEFVAL      	{ audio }
  ::= { alaQoSAppliedConditionEntry 123 }
alaQoSAppliedConditionSIPStatus OBJECT-TYPE
  SYNTAX      INTEGER {
       	        enabled (1),
		        disabled (2)
              }		
  MAX-ACCESS  	read-create
  STATUS      	current
  DESCRIPTION 	"SIP Status field indicates whether SIP is enabled or disabled 
				for traffic classification"
  DEFVAL      	{ enabled }
  ::= { alaQoSAppliedConditionEntry 124 }
--
-- Definition of service table
--

alaQoSServiceTable OBJECT-TYPE
  SYNTAX      SEQUENCE OF QoSServiceEntry
  MAX-ACCESS  not-accessible
  STATUS      current
  DESCRIPTION "Table of QoS Service definitions"
  ::= { alaQoSMIBObjects 5 }

alaQoSServiceEntry OBJECT-TYPE
  SYNTAX      QoSServiceEntry
  MAX-ACCESS  not-accessible
  STATUS      current
  DESCRIPTION "Definition of QoS Service"
  INDEX {
          alaQoSServiceName
        }
  ::= { alaQoSServiceTable 1 }

QoSServiceEntry ::=
  SEQUENCE
  {
    alaQoSServiceName                                       DisplayString,
    alaQoSServiceSource                                     INTEGER,
    alaQoSServiceProtocol                                   Integer32,
    alaQoSServiceSourceIpPort                               Integer32,
    alaQoSServiceSourceIpPortStatus                         INTEGER,
    alaQoSServiceDestinationIpPort                          Integer32,
    alaQoSServiceDestinationIpPortStatus                    INTEGER,
    alaQoSServiceRowStatus                                  RowStatus,
    alaQoSServiceSourceIpPortEnd                            Integer32,
    alaQoSServiceDestinationIpPortEnd                       Integer32,
    alaQoSServiceSourceTcpPort                              Integer32,
    alaQoSServiceSourceTcpPortStatus                        INTEGER,
    alaQoSServiceSourceTcpPortEnd                           Integer32,
    alaQoSServiceDestinationTcpPort                         Integer32,
    alaQoSServiceDestinationTcpPortStatus                   INTEGER,
    alaQoSServiceDestinationTcpPortEnd                      Integer32,
    alaQoSServiceSourceUdpPort                              Integer32,
    alaQoSServiceSourceUdpPortStatus                        INTEGER,
    alaQoSServiceSourceUdpPortEnd                           Integer32,
    alaQoSServiceDestinationUdpPort                         Integer32,
    alaQoSServiceDestinationUdpPortStatus                   INTEGER,
    alaQoSServiceDestinationUdpPortEnd                      Integer32
  }

alaQoSServiceName OBJECT-TYPE
  SYNTAX      DisplayString (SIZE(0..31))
  MAX-ACCESS  not-accessible
  STATUS      current
  DESCRIPTION "Name of the service"
  ::= { alaQoSServiceEntry 1 }

alaQoSServiceSource OBJECT-TYPE
  SYNTAX      INTEGER {
                ldap (1),
                cli (2),
                blt (3),
                api (4),
                imp (5)
              }
  MAX-ACCESS  read-create
  STATUS      current
  DESCRIPTION "What entity created the service."
  DEFVAL      { cli }
  ::= { alaQoSServiceEntry 2 }

alaQoSServiceProtocol OBJECT-TYPE
  SYNTAX      Integer32 (0..255)
  MAX-ACCESS  read-create
  STATUS      current
  DESCRIPTION "protocol field for Service"
  DEFVAL      { 0 }
  ::= { alaQoSServiceEntry 3 }

alaQoSServiceSourceIpPort OBJECT-TYPE
  SYNTAX      Integer32 (0..65535)
  MAX-ACCESS  read-create
  STATUS      current
  DESCRIPTION "Source IP port range start to use for traffic classification."
  ::= { alaQoSServiceEntry 4 }

alaQoSServiceSourceIpPortStatus OBJECT-TYPE
  SYNTAX      INTEGER {
                enabled (1),
                disabled (2)
              }
  MAX-ACCESS  read-create
  STATUS      current
  DESCRIPTION "Status field indicating whether the source IP port range
               needs to be matched(enabled) or not(disabled)."
  DEFVAL      { disabled }
  ::= { alaQoSServiceEntry 5 }

alaQoSServiceDestinationIpPort OBJECT-TYPE
  SYNTAX      Integer32 (0..65535)
  MAX-ACCESS  read-create
  STATUS      current
  DESCRIPTION "Destination IP port range start to use for traffic
               classification."
  ::= { alaQoSServiceEntry 6 }

alaQoSServiceDestinationIpPortStatus OBJECT-TYPE
  SYNTAX      INTEGER {
                enabled (1),
                disabled (2)
              }
  MAX-ACCESS  read-create
  STATUS      current
  DESCRIPTION "Status field indicating whether the destination IP port range
               needs to be matched(enabled) or not(disabled)."
  DEFVAL      { disabled }
  ::= { alaQoSServiceEntry 7 }

alaQoSServiceRowStatus OBJECT-TYPE
  SYNTAX      RowStatus
  MAX-ACCESS  read-create
  STATUS      current
  DESCRIPTION "Used to create/delete services according to the
               RowStatus convention"
  ::= { alaQoSServiceEntry 8 }

alaQoSServiceSourceIpPortEnd OBJECT-TYPE
  SYNTAX      Integer32 (0..65535)
  MAX-ACCESS  read-create
  STATUS      current
  DESCRIPTION "Source IP port range end to use for traffic classification.
               Must be greater than source IP port range start to indicate
               a range.  When '0', use source IP port as a single IP port."
  ::= { alaQoSServiceEntry 9 }

alaQoSServiceDestinationIpPortEnd OBJECT-TYPE
  SYNTAX      Integer32 (0..65535)
  MAX-ACCESS  read-create
  STATUS      current
  DESCRIPTION "Destination IP port range end to use for traffic classification.
               Must be greater than destination IP port range start to indicate
               a range.  When '0', use destination IP port as a single IP port."
  ::= { alaQoSServiceEntry 10 }

alaQoSServiceSourceTcpPort OBJECT-TYPE
  SYNTAX      Integer32 (0..65535)
  MAX-ACCESS  read-create
  STATUS      current
  DESCRIPTION "Source TCP port range start to use for traffic classification."
  ::= { alaQoSServiceEntry 11 }

alaQoSServiceSourceTcpPortStatus OBJECT-TYPE
  SYNTAX      INTEGER {
                enabled (1),
                disabled (2)
              }
  MAX-ACCESS  read-create
  STATUS      current
  DESCRIPTION "Status field indicating whether the source TCP port range
               needs to be matched(enabled) or not(disabled)."
  DEFVAL      { disabled }
  ::= { alaQoSServiceEntry 12 }

alaQoSServiceSourceTcpPortEnd OBJECT-TYPE
  SYNTAX      Integer32 (0..65535)
  MAX-ACCESS  read-create
  STATUS      current
  DESCRIPTION "Source TCP port range end to use for traffic classification.
               Must be greater than source TCP port range start to indicate a
               range.  When '0', use source TCP port as a single TCP port."
  ::= { alaQoSServiceEntry 13 }

alaQoSServiceDestinationTcpPort OBJECT-TYPE
  SYNTAX      Integer32 (0..65535)
  MAX-ACCESS  read-create
  STATUS      current
  DESCRIPTION "Destination TCP port range start to use for traffic
               classification."
  ::= { alaQoSServiceEntry 14 }

alaQoSServiceDestinationTcpPortStatus OBJECT-TYPE
  SYNTAX      INTEGER {
                enabled (1),
                disabled (2)
              }
  MAX-ACCESS  read-create
  STATUS      current
  DESCRIPTION "Status field indicating whether the destination TCP port range
               needs to be matched(enabled) or not(disabled)."
  DEFVAL      { disabled }
  ::= { alaQoSServiceEntry 15 }

alaQoSServiceDestinationTcpPortEnd OBJECT-TYPE
  SYNTAX      Integer32 (0..65535)
  MAX-ACCESS  read-create
  STATUS      current
  DESCRIPTION "Destination TCP port range end to use for traffic
               classification.  Must be greater than destination TCP port range
               start to indicate a range.  When '0', use destination TCP port as
               a single TCP port."
  ::= { alaQoSServiceEntry 16 }

alaQoSServiceSourceUdpPort OBJECT-TYPE
  SYNTAX      Integer32 (0..65535)
  MAX-ACCESS  read-create
  STATUS      current
  DESCRIPTION "Source UDP port range start to use for traffic classification."
  ::= { alaQoSServiceEntry 17 }

alaQoSServiceSourceUdpPortStatus OBJECT-TYPE
  SYNTAX      INTEGER {
                enabled (1),
                disabled (2)
              }
  MAX-ACCESS  read-create
  STATUS      current
  DESCRIPTION "Status field indicating whether the source UDP port range
               needs to be matched(enabled) or not(disabled)."
  DEFVAL      { disabled }
  ::= { alaQoSServiceEntry 18 }

alaQoSServiceSourceUdpPortEnd OBJECT-TYPE
  SYNTAX      Integer32 (0..65535)
  MAX-ACCESS  read-create
  STATUS      current
  DESCRIPTION "Source UDP port range end to use for traffic classification.
               Must be greater than source UDP port range start to indicate a
               range.  When '0', use source UDP port as a single UDP port."
  ::= { alaQoSServiceEntry 19 }

alaQoSServiceDestinationUdpPort OBJECT-TYPE
  SYNTAX      Integer32 (0..65535)
  MAX-ACCESS  read-create
  STATUS      current
  DESCRIPTION "Destination UDP port range start to use for traffic
               classification."
  ::= { alaQoSServiceEntry 20 }

alaQoSServiceDestinationUdpPortStatus OBJECT-TYPE
  SYNTAX      INTEGER {
                enabled (1),
                disabled (2)
              }
  MAX-ACCESS  read-create
  STATUS      current
  DESCRIPTION "Status field indicating whether the destination UDP port range
               needs to be matched(enabled) or not(disabled)."
  DEFVAL      { disabled }
  ::= { alaQoSServiceEntry 21 }

alaQoSServiceDestinationUdpPortEnd OBJECT-TYPE
  SYNTAX      Integer32 (0..65535)
  MAX-ACCESS  read-create
  STATUS      current
  DESCRIPTION "Destination UDP port range end to use for traffic
               classification.  Must be greater than destination UDP port range
               start to indicate a range.  When '0', use destination UDP port as
               a single UDP port."
  ::= { alaQoSServiceEntry 22 }


--
-- Definition of service table
--

alaQoSAppliedServiceTable OBJECT-TYPE
  SYNTAX      SEQUENCE OF QoSAppliedServiceEntry
  MAX-ACCESS  not-accessible
  STATUS      current
  DESCRIPTION "Table of QoS AppliedService definitions"
  ::= { alaQoSMIBObjects 6 }

alaQoSAppliedServiceEntry OBJECT-TYPE
  SYNTAX      QoSAppliedServiceEntry
  MAX-ACCESS  not-accessible
  STATUS      current
  DESCRIPTION "Definition of QoS AppliedService"
  INDEX {
          alaQoSAppliedServiceName
        }
  ::= { alaQoSAppliedServiceTable 1 }

QoSAppliedServiceEntry ::=
  SEQUENCE
  {
    alaQoSAppliedServiceName                                DisplayString,
    alaQoSAppliedServiceSource                              INTEGER,
    alaQoSAppliedServiceProtocol                            Integer32,
    alaQoSAppliedServiceSourceIpPort                        Integer32,
    alaQoSAppliedServiceSourceIpPortStatus                  INTEGER,
    alaQoSAppliedServiceDestinationIpPort                   Integer32,
    alaQoSAppliedServiceDestinationIpPortStatus             INTEGER,
    alaQoSAppliedServiceRowStatus                           RowStatus,
    alaQoSAppliedServiceSourceIpPortEnd                     Integer32,
    alaQoSAppliedServiceDestinationIpPortEnd                Integer32,
    alaQoSAppliedServiceSourceTcpPort                       Integer32,
    alaQoSAppliedServiceSourceTcpPortStatus                 INTEGER,
    alaQoSAppliedServiceSourceTcpPortEnd                    Integer32,
    alaQoSAppliedServiceDestinationTcpPort                  Integer32,
    alaQoSAppliedServiceDestinationTcpPortStatus            INTEGER,
    alaQoSAppliedServiceDestinationTcpPortEnd               Integer32,
    alaQoSAppliedServiceSourceUdpPort                       Integer32,
    alaQoSAppliedServiceSourceUdpPortStatus                 INTEGER,
    alaQoSAppliedServiceSourceUdpPortEnd                    Integer32,
    alaQoSAppliedServiceDestinationUdpPort                  Integer32,
    alaQoSAppliedServiceDestinationUdpPortStatus            INTEGER,
    alaQoSAppliedServiceDestinationUdpPortEnd               Integer32
  }

alaQoSAppliedServiceName OBJECT-TYPE
  SYNTAX      DisplayString (SIZE(0..31))
  MAX-ACCESS  not-accessible
  STATUS      current
  DESCRIPTION "Name of the service"
  ::= { alaQoSAppliedServiceEntry 1 }

alaQoSAppliedServiceSource OBJECT-TYPE
  SYNTAX      INTEGER {
                ldap (1),
                cli (2),
                blt (3),
                api (4),
                imp (5)
              }
  MAX-ACCESS  read-only
  STATUS      current
  DESCRIPTION "What entity created the service."
  ::= { alaQoSAppliedServiceEntry 2 }

alaQoSAppliedServiceProtocol OBJECT-TYPE
  SYNTAX      Integer32 (0..255)
  MAX-ACCESS  read-only
  STATUS      current
  DESCRIPTION "protocol field for AppliedService"
  ::= { alaQoSAppliedServiceEntry 3 }

alaQoSAppliedServiceSourceIpPort OBJECT-TYPE
  SYNTAX      Integer32 (0..65535)
  MAX-ACCESS  read-only
  STATUS      current
  DESCRIPTION "Source IP port range start to use for traffic classification."
  ::= { alaQoSAppliedServiceEntry 4 }

alaQoSAppliedServiceSourceIpPortStatus OBJECT-TYPE
  SYNTAX      INTEGER {
                enabled (1),
                disabled (2)
              }
  MAX-ACCESS  read-only
  STATUS      current
  DESCRIPTION "Status field indicating whether the source IP port range
               needs to be matched(enabled) or not(disabled)."
  ::= { alaQoSAppliedServiceEntry 5 }

alaQoSAppliedServiceDestinationIpPort OBJECT-TYPE
  SYNTAX      Integer32 (0..65535)
  MAX-ACCESS  read-only
  STATUS      current
  DESCRIPTION "Destination IP port range start to use for traffic
               classification."
  ::= { alaQoSAppliedServiceEntry 6 }

alaQoSAppliedServiceDestinationIpPortStatus OBJECT-TYPE
  SYNTAX      INTEGER {
                enabled (1),
                disabled (2)
              }
  MAX-ACCESS  read-only
  STATUS      current
  DESCRIPTION "Status field indicating whether the destination IP port range
               needs to be matched(enabled) or not(disabled)."
  ::= { alaQoSAppliedServiceEntry 7 }

alaQoSAppliedServiceRowStatus OBJECT-TYPE
  SYNTAX      RowStatus
  MAX-ACCESS  read-only
  STATUS      current
  DESCRIPTION "Used to create/delete services according to the
               RowStatus convention"
  ::= { alaQoSAppliedServiceEntry 8 }

alaQoSAppliedServiceSourceIpPortEnd OBJECT-TYPE
  SYNTAX      Integer32 (0..65535)
  MAX-ACCESS  read-only
  STATUS      current
  DESCRIPTION "Source IP port range end to use for traffic classification.
               Must be greater than source IP port range start to indicate
               a range.  When '0', use source IP port as a single IP port."
  ::= { alaQoSAppliedServiceEntry 9 }

alaQoSAppliedServiceDestinationIpPortEnd OBJECT-TYPE
  SYNTAX      Integer32 (0..65535)
  MAX-ACCESS  read-only
  STATUS      current
  DESCRIPTION "Destination IP port range end to use for traffic classification.
               Must be greater than destination IP port range start to indicate
               a range.  When '0', use destination IP port as a single IP port."
  ::= { alaQoSAppliedServiceEntry 10 }

alaQoSAppliedServiceSourceTcpPort OBJECT-TYPE
  SYNTAX      Integer32 (0..65535)
  MAX-ACCESS  read-only
  STATUS      current
  DESCRIPTION "Source TCP port range start to use for traffic classification."
  ::= { alaQoSAppliedServiceEntry 11 }

alaQoSAppliedServiceSourceTcpPortStatus OBJECT-TYPE
  SYNTAX      INTEGER {
                enabled (1),
                disabled (2)
              }
  MAX-ACCESS  read-only
  STATUS      current
  DESCRIPTION "Status field indicating whether the source TCP port range
               needs to be matched(enabled) or not(disabled)."
  ::= { alaQoSAppliedServiceEntry 12 }

alaQoSAppliedServiceSourceTcpPortEnd OBJECT-TYPE
  SYNTAX      Integer32 (0..65535)
  MAX-ACCESS  read-only
  STATUS      current
  DESCRIPTION "Source TCP port range end to use for traffic classification.
               Must be greater than source TCP port range start to indicate a
               range.  When '0', use source TCP port as a single TCP port."
  ::= { alaQoSAppliedServiceEntry 13 }

alaQoSAppliedServiceDestinationTcpPort OBJECT-TYPE
  SYNTAX      Integer32 (0..65535)
  MAX-ACCESS  read-only
  STATUS      current
  DESCRIPTION "Destination TCP port range start to use for traffic
               classification."
  ::= { alaQoSAppliedServiceEntry 14 }

alaQoSAppliedServiceDestinationTcpPortStatus OBJECT-TYPE
  SYNTAX      INTEGER {
                enabled (1),
                disabled (2)
              }
  MAX-ACCESS  read-only
  STATUS      current
  DESCRIPTION "Status field indicating whether the destination TCP port range
               needs to be matched(enabled) or not(disabled)."
  ::= { alaQoSAppliedServiceEntry 15 }

alaQoSAppliedServiceDestinationTcpPortEnd OBJECT-TYPE
  SYNTAX      Integer32 (0..65535)
  MAX-ACCESS  read-only
  STATUS      current
  DESCRIPTION "Destination TCP port range end to use for traffic
               classification.  Must be greater than destination TCP port range
               start to indicate a range.  When '0', use destination TCP port as
               a single TCP port."
  ::= { alaQoSAppliedServiceEntry 16 }

alaQoSAppliedServiceSourceUdpPort OBJECT-TYPE
  SYNTAX      Integer32 (0..65535)
  MAX-ACCESS  read-only
  STATUS      current
  DESCRIPTION "Source UDP port range start to use for traffic classification."
  ::= { alaQoSAppliedServiceEntry 17 }

alaQoSAppliedServiceSourceUdpPortStatus OBJECT-TYPE
  SYNTAX      INTEGER {
                enabled (1),
                disabled (2)
              }
  MAX-ACCESS  read-only
  STATUS      current
  DESCRIPTION "Status field indicating whether the source UDP port range
               needs to be matched(enabled) or not(disabled)."
  ::= { alaQoSAppliedServiceEntry 18 }

alaQoSAppliedServiceSourceUdpPortEnd OBJECT-TYPE
  SYNTAX      Integer32 (0..65535)
  MAX-ACCESS  read-only
  STATUS      current
  DESCRIPTION "Source UDP port range end to use for traffic classification.
               Must be greater than source UDP port range start to indicate a
               range.  When '0', use source UDP port as a single UDP port."
  ::= { alaQoSAppliedServiceEntry 19 }

alaQoSAppliedServiceDestinationUdpPort OBJECT-TYPE
  SYNTAX      Integer32 (0..65535)
  MAX-ACCESS  read-only
  STATUS      current
  DESCRIPTION "Destination UDP port range start to use for traffic
               classification."
  ::= { alaQoSAppliedServiceEntry 20 }

alaQoSAppliedServiceDestinationUdpPortStatus OBJECT-TYPE
  SYNTAX      INTEGER {
                enabled (1),
                disabled (2)
              }
  MAX-ACCESS  read-only
  STATUS      current
  DESCRIPTION "Status field indicating whether the destination UDP port range
               needs to be matched(enabled) or not(disabled)."
  ::= { alaQoSAppliedServiceEntry 21 }

alaQoSAppliedServiceDestinationUdpPortEnd OBJECT-TYPE
  SYNTAX      Integer32 (0..65535)
  MAX-ACCESS  read-only
  STATUS      current
  DESCRIPTION "Destination UDP port range end to use for traffic
               classification.  Must be greater than destination UDP port range
               start to indicate a range.  When '0', use destination UDP port as
               a single UDP port."
  ::= { alaQoSAppliedServiceEntry 22 }


--
-- Definition of service group table
--

alaQoSServiceGroupsTable OBJECT-TYPE
  SYNTAX      SEQUENCE OF QoSServiceGroupsEntry
  MAX-ACCESS  not-accessible
  STATUS      current
  DESCRIPTION "Table of QoS ServiceGroups definitions"
  ::= { alaQoSMIBObjects 7 }

alaQoSServiceGroupsEntry OBJECT-TYPE
  SYNTAX      QoSServiceGroupsEntry
  MAX-ACCESS  not-accessible
  STATUS      current
  DESCRIPTION "Definition of QoS ServiceGroups"
  INDEX {
          alaQoSServiceGroupsName
        }
  ::= { alaQoSServiceGroupsTable 1 }

QoSServiceGroupsEntry ::=
  SEQUENCE
  {
    alaQoSServiceGroupsName                                 DisplayString,
    alaQoSServiceGroupsSource                               INTEGER,
    alaQoSServiceGroupsStatus                               RowStatus
  }

alaQoSServiceGroupsName OBJECT-TYPE
  SYNTAX      DisplayString (SIZE(0..31))
  MAX-ACCESS  not-accessible
  STATUS      current
  DESCRIPTION "Name of service group"
  ::= { alaQoSServiceGroupsEntry 1 }

alaQoSServiceGroupsSource OBJECT-TYPE
  SYNTAX      INTEGER {
                ldap (1),
                cli (2),
                blt (3),
                api (4),
                imp (5)
              }
  MAX-ACCESS  read-create
  STATUS      current
  DESCRIPTION "What entity created the service group."
  DEFVAL      { cli }
  ::= { alaQoSServiceGroupsEntry 2 }

alaQoSServiceGroupsStatus OBJECT-TYPE
  SYNTAX      RowStatus
  MAX-ACCESS  read-create
  STATUS      current
  DESCRIPTION "Used to create/delete service groups according to the
               RowStatus convention"
  ::= { alaQoSServiceGroupsEntry 3 }


--
-- Definition of service group table
--

alaQoSAppliedServiceGroupsTable OBJECT-TYPE
  SYNTAX      SEQUENCE OF QoSAppliedServiceGroupsEntry
  MAX-ACCESS  not-accessible
  STATUS      current
  DESCRIPTION "Table of QoS AppliedServiceGroups definitions"
  ::= { alaQoSMIBObjects 8 }

alaQoSAppliedServiceGroupsEntry OBJECT-TYPE
  SYNTAX      QoSAppliedServiceGroupsEntry
  MAX-ACCESS  not-accessible
  STATUS      current
  DESCRIPTION "Definition of QoS AppliedServiceGroups"
  INDEX {
          alaQoSAppliedServiceGroupsName
        }
  ::= { alaQoSAppliedServiceGroupsTable 1 }

QoSAppliedServiceGroupsEntry ::=
  SEQUENCE
  {
    alaQoSAppliedServiceGroupsName                          DisplayString,
    alaQoSAppliedServiceGroupsSource                        INTEGER,
    alaQoSAppliedServiceGroupsStatus                        RowStatus
  }

alaQoSAppliedServiceGroupsName OBJECT-TYPE
  SYNTAX      DisplayString (SIZE(0..31))
  MAX-ACCESS  not-accessible
  STATUS      current
  DESCRIPTION "Name of service group"
  ::= { alaQoSAppliedServiceGroupsEntry 1 }

alaQoSAppliedServiceGroupsSource OBJECT-TYPE
  SYNTAX      INTEGER {
                ldap (1),
                cli (2),
                blt (3),
                api (4),
                imp (5)
              }
  MAX-ACCESS  read-only
  STATUS      current
  DESCRIPTION "What entity created the service group."
  ::= { alaQoSAppliedServiceGroupsEntry 2 }

alaQoSAppliedServiceGroupsStatus OBJECT-TYPE
  SYNTAX      RowStatus
  MAX-ACCESS  read-only
  STATUS      current
  DESCRIPTION "Used to create/delete service groups according to the
               RowStatus convention"
  ::= { alaQoSAppliedServiceGroupsEntry 3 }


--
-- Definition of service group entry table
--

alaQoSServiceGroupTable OBJECT-TYPE
  SYNTAX      SEQUENCE OF QoSServiceGroupEntry
  MAX-ACCESS  not-accessible
  STATUS      current
  DESCRIPTION "Table of QoS ServiceGroup definitions"
  ::= { alaQoSMIBObjects 9 }

alaQoSServiceGroupEntry OBJECT-TYPE
  SYNTAX      QoSServiceGroupEntry
  MAX-ACCESS  not-accessible
  STATUS      current
  DESCRIPTION "Definition of QoS ServiceGroup"
  INDEX {
          alaQoSServiceGroupsName,
          alaQoSServiceGroupServiceName
        }
  ::= { alaQoSServiceGroupTable 1 }

QoSServiceGroupEntry ::=
  SEQUENCE
  {
    alaQoSServiceGroupServiceName                           DisplayString,
    alaQoSServiceGroupStatus                                RowStatus
  }

alaQoSServiceGroupServiceName OBJECT-TYPE
  SYNTAX      DisplayString (SIZE(0..31))
  MAX-ACCESS  not-accessible
  STATUS      current
  DESCRIPTION "Name of service in service group entry"
  ::= { alaQoSServiceGroupEntry 1 }

alaQoSServiceGroupStatus OBJECT-TYPE
  SYNTAX      RowStatus
  MAX-ACCESS  read-create
  STATUS      current
  DESCRIPTION "Used to create/delete service group entries according to the
               RowStatus convention"
  ::= { alaQoSServiceGroupEntry 2 }


--
-- Definition of service group entry table
--

alaQoSAppliedServiceGroupTable OBJECT-TYPE
  SYNTAX      SEQUENCE OF QoSAppliedServiceGroupEntry
  MAX-ACCESS  not-accessible
  STATUS      current
  DESCRIPTION "Table of QoS AppliedServiceGroup definitions"
  ::= { alaQoSMIBObjects 10 }

alaQoSAppliedServiceGroupEntry OBJECT-TYPE
  SYNTAX      QoSAppliedServiceGroupEntry
  MAX-ACCESS  not-accessible
  STATUS      current
  DESCRIPTION "Definition of QoS AppliedServiceGroup"
  INDEX {
          alaQoSAppliedServiceGroupsName,
          alaQoSAppliedServiceGroupServiceName
        }
  ::= { alaQoSAppliedServiceGroupTable 1 }

QoSAppliedServiceGroupEntry ::=
  SEQUENCE
  {
    alaQoSAppliedServiceGroupServiceName                    DisplayString,
    alaQoSAppliedServiceGroupStatus                         RowStatus
  }

alaQoSAppliedServiceGroupServiceName OBJECT-TYPE
  SYNTAX      DisplayString (SIZE(0..31))
  MAX-ACCESS  not-accessible
  STATUS      current
  DESCRIPTION "Name of service in service group entry"
  ::= { alaQoSAppliedServiceGroupEntry 1 }

alaQoSAppliedServiceGroupStatus OBJECT-TYPE
  SYNTAX      RowStatus
  MAX-ACCESS  read-only
  STATUS      current
  DESCRIPTION "Used to create/delete service group entries according to the
               RowStatus convention"
  ::= { alaQoSAppliedServiceGroupEntry 2 }


--
-- Definition of network group table
--

alaQoSNetworkGroupsTable OBJECT-TYPE
  SYNTAX      SEQUENCE OF QoSNetworkGroupsEntry
  MAX-ACCESS  not-accessible
  STATUS      current
  DESCRIPTION "Table of QoS NetworkGroups definitions"
  ::= { alaQoSMIBObjects 11 }

alaQoSNetworkGroupsEntry OBJECT-TYPE
  SYNTAX      QoSNetworkGroupsEntry
  MAX-ACCESS  not-accessible
  STATUS      current
  DESCRIPTION "Definition of QoS NetworkGroups"
  INDEX {
          alaQoSNetworkGroupsName
        }
  ::= { alaQoSNetworkGroupsTable 1 }

QoSNetworkGroupsEntry ::=
  SEQUENCE
  {
    alaQoSNetworkGroupsName                                 DisplayString,
    alaQoSNetworkGroupsSource                               INTEGER,
    alaQoSNetworkGroupsStatus                               RowStatus
  }

alaQoSNetworkGroupsName OBJECT-TYPE
  SYNTAX      DisplayString (SIZE(0..31))
  MAX-ACCESS  not-accessible
  STATUS      current
  DESCRIPTION "Name of network group"
  ::= { alaQoSNetworkGroupsEntry 1 }

alaQoSNetworkGroupsSource OBJECT-TYPE
  SYNTAX      INTEGER {
                ldap (1),
                cli (2),
                blt (3),
                api (4),
                imp (5)
              }
  MAX-ACCESS  read-create
  STATUS      current
  DESCRIPTION "What entity created the network group."
  DEFVAL      { cli }
  ::= { alaQoSNetworkGroupsEntry 2 }

alaQoSNetworkGroupsStatus OBJECT-TYPE
  SYNTAX      RowStatus
  MAX-ACCESS  read-create
  STATUS      current
  DESCRIPTION "Used to create/delete network groups according to the
               RowStatus convention"
  ::= { alaQoSNetworkGroupsEntry 3 }


--
-- Definition of network group table
--

alaQoSAppliedNetworkGroupsTable OBJECT-TYPE
  SYNTAX      SEQUENCE OF QoSAppliedNetworkGroupsEntry
  MAX-ACCESS  not-accessible
  STATUS      current
  DESCRIPTION "Table of QoS AppliedNetworkGroups definitions"
  ::= { alaQoSMIBObjects 12 }

alaQoSAppliedNetworkGroupsEntry OBJECT-TYPE
  SYNTAX      QoSAppliedNetworkGroupsEntry
  MAX-ACCESS  not-accessible
  STATUS      current
  DESCRIPTION "Definition of QoS AppliedNetworkGroups"
  INDEX {
          alaQoSAppliedNetworkGroupsName
        }
  ::= { alaQoSAppliedNetworkGroupsTable 1 }

QoSAppliedNetworkGroupsEntry ::=
  SEQUENCE
  {
    alaQoSAppliedNetworkGroupsName                          DisplayString,
    alaQoSAppliedNetworkGroupsSource                        INTEGER,
    alaQoSAppliedNetworkGroupsStatus                        RowStatus
  }

alaQoSAppliedNetworkGroupsName OBJECT-TYPE
  SYNTAX      DisplayString (SIZE(0..31))
  MAX-ACCESS  not-accessible
  STATUS      current
  DESCRIPTION "Name of network group"
  ::= { alaQoSAppliedNetworkGroupsEntry 1 }

alaQoSAppliedNetworkGroupsSource OBJECT-TYPE
  SYNTAX      INTEGER {
                ldap (1),
                cli (2),
                blt (3),
                api (4),
                imp (5)
              }
  MAX-ACCESS  read-only
  STATUS      current
  DESCRIPTION "What entity created the network group."
  ::= { alaQoSAppliedNetworkGroupsEntry 2 }

alaQoSAppliedNetworkGroupsStatus OBJECT-TYPE
  SYNTAX      RowStatus
  MAX-ACCESS  read-only
  STATUS      current
  DESCRIPTION "Used to create/delete network groups according to the
               RowStatus convention"
  ::= { alaQoSAppliedNetworkGroupsEntry 3 }


--
-- Definition of network group entry table
--

alaQoSNetworkGroupTable OBJECT-TYPE
  SYNTAX      SEQUENCE OF QoSNetworkGroupEntry
  MAX-ACCESS  not-accessible
  STATUS      current
  DESCRIPTION "Table of QoS NetworkGroup definitions"
  ::= { alaQoSMIBObjects 13 }

alaQoSNetworkGroupEntry OBJECT-TYPE
  SYNTAX      QoSNetworkGroupEntry
  MAX-ACCESS  not-accessible
  STATUS      current
  DESCRIPTION "Definition of QoS NetworkGroup"
  INDEX {
          alaQoSNetworkGroupsName,
          alaQoSNetworkGroupIpAddr,
          alaQoSNetworkGroupIpMask
        }
  ::= { alaQoSNetworkGroupTable 1 }

QoSNetworkGroupEntry ::=
  SEQUENCE
  {
    alaQoSNetworkGroupIpAddr                                IpAddress,
    alaQoSNetworkGroupIpMask                                IpAddress,
    alaQoSNetworkGroupStatus                                RowStatus
  }

alaQoSNetworkGroupIpAddr OBJECT-TYPE
  SYNTAX      IpAddress
  MAX-ACCESS  not-accessible
  STATUS      current
  DESCRIPTION "IP address for network group entry."
  ::= { alaQoSNetworkGroupEntry 1 }

alaQoSNetworkGroupIpMask OBJECT-TYPE
  SYNTAX      IpAddress
  MAX-ACCESS  not-accessible
  STATUS      current
  DESCRIPTION "IP mask for network group entry."
  ::= { alaQoSNetworkGroupEntry 2 }

alaQoSNetworkGroupStatus OBJECT-TYPE
  SYNTAX      RowStatus
  MAX-ACCESS  read-create
  STATUS      current
  DESCRIPTION "Used to create/delete network group entries according to the
               RowStatus convention"
  ::= { alaQoSNetworkGroupEntry 3 }


--
-- Definition of network group entry table
--

alaQoSAppliedNetworkGroupTable OBJECT-TYPE
  SYNTAX      SEQUENCE OF QoSAppliedNetworkGroupEntry
  MAX-ACCESS  not-accessible
  STATUS      current
  DESCRIPTION "Table of QoS AppliedNetworkGroup definitions"
  ::= { alaQoSMIBObjects 14 }

alaQoSAppliedNetworkGroupEntry OBJECT-TYPE
  SYNTAX      QoSAppliedNetworkGroupEntry
  MAX-ACCESS  not-accessible
  STATUS      current
  DESCRIPTION "Definition of QoS AppliedNetworkGroup"
  INDEX {
          alaQoSAppliedNetworkGroupsName,
          alaQoSAppliedNetworkGroupIpAddr,
          alaQoSAppliedNetworkGroupIpMask
        }
  ::= { alaQoSAppliedNetworkGroupTable 1 }

QoSAppliedNetworkGroupEntry ::=
  SEQUENCE
  {
    alaQoSAppliedNetworkGroupIpAddr                         IpAddress,
    alaQoSAppliedNetworkGroupIpMask                         IpAddress,
    alaQoSAppliedNetworkGroupStatus                         RowStatus
  }

alaQoSAppliedNetworkGroupIpAddr OBJECT-TYPE
  SYNTAX      IpAddress
  MAX-ACCESS  not-accessible
  STATUS      current
  DESCRIPTION "IP address for network group entry."
  ::= { alaQoSAppliedNetworkGroupEntry 1 }

alaQoSAppliedNetworkGroupIpMask OBJECT-TYPE
  SYNTAX      IpAddress
  MAX-ACCESS  not-accessible
  STATUS      current
  DESCRIPTION "IP mask for network group entry."
  ::= { alaQoSAppliedNetworkGroupEntry 2 }

alaQoSAppliedNetworkGroupStatus OBJECT-TYPE
  SYNTAX      RowStatus
  MAX-ACCESS  read-only
  STATUS      current
  DESCRIPTION "Used to create/delete network group entries according to the
               RowStatus convention"
  ::= { alaQoSAppliedNetworkGroupEntry 3 }


--
-- Definition of mac group table
--

alaQoSMACGroupsTable OBJECT-TYPE
  SYNTAX      SEQUENCE OF QoSMACGroupsEntry
  MAX-ACCESS  not-accessible
  STATUS      current
  DESCRIPTION "Table of QoS MACGroups definitions"
  ::= { alaQoSMIBObjects 15 }

alaQoSMACGroupsEntry OBJECT-TYPE
  SYNTAX      QoSMACGroupsEntry
  MAX-ACCESS  not-accessible
  STATUS      current
  DESCRIPTION "Definition of QoS MACGroups"
  INDEX {
          alaQoSMACGroupsName
        }
  ::= { alaQoSMACGroupsTable 1 }

QoSMACGroupsEntry ::=
  SEQUENCE
  {
    alaQoSMACGroupsName                                     DisplayString,
    alaQoSMACGroupsSource                                   INTEGER,
    alaQoSMACGroupsStatus                                   RowStatus
  }

alaQoSMACGroupsName OBJECT-TYPE
  SYNTAX      DisplayString (SIZE(0..31))
  MAX-ACCESS  not-accessible
  STATUS      current
  DESCRIPTION "Name of MAC group"
  ::= { alaQoSMACGroupsEntry 1 }

alaQoSMACGroupsSource OBJECT-TYPE
  SYNTAX      INTEGER {
                ldap (1),
                cli (2),
                blt (3),
                api (4),
                imp (5)
              }
  MAX-ACCESS  read-create
  STATUS      current
  DESCRIPTION "What entity created the MAC group."
  DEFVAL      { cli }
  ::= { alaQoSMACGroupsEntry 2 }

alaQoSMACGroupsStatus OBJECT-TYPE
  SYNTAX      RowStatus
  MAX-ACCESS  read-create
  STATUS      current
  DESCRIPTION "Used to create/delete MAC groups according to the
               RowStatus convention"
  ::= { alaQoSMACGroupsEntry 3 }


--
-- Definition of mac group table
--

alaQoSAppliedMACGroupsTable OBJECT-TYPE
  SYNTAX      SEQUENCE OF QoSAppliedMACGroupsEntry
  MAX-ACCESS  not-accessible
  STATUS      current
  DESCRIPTION "Table of QoS AppliedMACGroups definitions"
  ::= { alaQoSMIBObjects 16 }

alaQoSAppliedMACGroupsEntry OBJECT-TYPE
  SYNTAX      QoSAppliedMACGroupsEntry
  MAX-ACCESS  not-accessible
  STATUS      current
  DESCRIPTION "Definition of QoS AppliedMACGroups"
  INDEX {
          alaQoSAppliedMACGroupsName
        }
  ::= { alaQoSAppliedMACGroupsTable 1 }

QoSAppliedMACGroupsEntry ::=
  SEQUENCE
  {
    alaQoSAppliedMACGroupsName                              DisplayString,
    alaQoSAppliedMACGroupsSource                            INTEGER,
    alaQoSAppliedMACGroupsStatus                            RowStatus
  }

alaQoSAppliedMACGroupsName OBJECT-TYPE
  SYNTAX      DisplayString (SIZE(0..31))
  MAX-ACCESS  not-accessible
  STATUS      current
  DESCRIPTION "Name of MAC group"
  ::= { alaQoSAppliedMACGroupsEntry 1 }

alaQoSAppliedMACGroupsSource OBJECT-TYPE
  SYNTAX      INTEGER {
                ldap (1),
                cli (2),
                blt (3),
                api (4),
                imp (5)
              }
  MAX-ACCESS  read-only
  STATUS      current
  DESCRIPTION "What entity created the MAC group."
  ::= { alaQoSAppliedMACGroupsEntry 2 }

alaQoSAppliedMACGroupsStatus OBJECT-TYPE
  SYNTAX      RowStatus
  MAX-ACCESS  read-only
  STATUS      current
  DESCRIPTION "Used to create/delete MAC groups according to the
               RowStatus convention"
  ::= { alaQoSAppliedMACGroupsEntry 3 }


--
-- Definition of MAC group entry table
--

alaQoSMACGroupTable OBJECT-TYPE
  SYNTAX      SEQUENCE OF QoSMACGroupEntry
  MAX-ACCESS  not-accessible
  STATUS      current
  DESCRIPTION "Table of QoS MACGroup definitions"
  ::= { alaQoSMIBObjects 17 }

alaQoSMACGroupEntry OBJECT-TYPE
  SYNTAX      QoSMACGroupEntry
  MAX-ACCESS  not-accessible
  STATUS      current
  DESCRIPTION "Definition of QoS MACGroup"
  INDEX {
          alaQoSMACGroupsName,
          alaQoSMACGroupMacAddr,
          alaQoSMACGroupMacMask
        }
  ::= { alaQoSMACGroupTable 1 }

QoSMACGroupEntry ::=
  SEQUENCE
  {
    alaQoSMACGroupMacAddr                                   MacAddress,
    alaQoSMACGroupMacMask                                   MacAddress,
    alaQoSMACGroupStatus                                    RowStatus
  }

alaQoSMACGroupMacAddr OBJECT-TYPE
  SYNTAX      MacAddress
  MAX-ACCESS  not-accessible
  STATUS      current
  DESCRIPTION "MAC address for MAC group entry"
  ::= { alaQoSMACGroupEntry 1 }

alaQoSMACGroupMacMask OBJECT-TYPE
  SYNTAX      MacAddress
  MAX-ACCESS  not-accessible
  STATUS      current
  DESCRIPTION "MAC mask for MAC group entry"
  ::= { alaQoSMACGroupEntry 2 }

alaQoSMACGroupStatus OBJECT-TYPE
  SYNTAX      RowStatus
  MAX-ACCESS  read-create
  STATUS      current
  DESCRIPTION "Used to create/delete MAC group entries according to the
               RowStatus convention"
  ::= { alaQoSMACGroupEntry 3 }


--
-- Definition of MAC group entry table
--

alaQoSAppliedMACGroupTable OBJECT-TYPE
  SYNTAX      SEQUENCE OF QoSAppliedMACGroupEntry
  MAX-ACCESS  not-accessible
  STATUS      current
  DESCRIPTION "Table of QoS AppliedMACGroup definitions"
  ::= { alaQoSMIBObjects 18 }

alaQoSAppliedMACGroupEntry OBJECT-TYPE
  SYNTAX      QoSAppliedMACGroupEntry
  MAX-ACCESS  not-accessible
  STATUS      current
  DESCRIPTION "Definition of QoS AppliedMACGroup"
  INDEX {
          alaQoSAppliedMACGroupsName,
          alaQoSAppliedMACGroupMacAddr,
          alaQoSAppliedMACGroupMacMask
        }
  ::= { alaQoSAppliedMACGroupTable 1 }

QoSAppliedMACGroupEntry ::=
  SEQUENCE
  {
    alaQoSAppliedMACGroupMacAddr                            MacAddress,
    alaQoSAppliedMACGroupMacMask                            MacAddress,
    alaQoSAppliedMACGroupStatus                             RowStatus
  }

alaQoSAppliedMACGroupMacAddr OBJECT-TYPE
  SYNTAX      MacAddress
  MAX-ACCESS  not-accessible
  STATUS      current
  DESCRIPTION "MAC address for MAC group entry"
  ::= { alaQoSAppliedMACGroupEntry 1 }

alaQoSAppliedMACGroupMacMask OBJECT-TYPE
  SYNTAX      MacAddress
  MAX-ACCESS  not-accessible
  STATUS      current
  DESCRIPTION "MAC mask for MAC group entry"
  ::= { alaQoSAppliedMACGroupEntry 2 }

alaQoSAppliedMACGroupStatus OBJECT-TYPE
  SYNTAX      RowStatus
  MAX-ACCESS  read-only
  STATUS      current
  DESCRIPTION "Used to create/delete MAC group entries according to the
               RowStatus convention"
  ::= { alaQoSAppliedMACGroupEntry 3 }


--
-- Definition of port group table
--

alaQoSPortGroupsTable OBJECT-TYPE
  SYNTAX      SEQUENCE OF QoSPortGroupsEntry
  MAX-ACCESS  not-accessible
  STATUS      current
  DESCRIPTION "Table of QoS PortGroups definitions"
  ::= { alaQoSMIBObjects 19 }

alaQoSPortGroupsEntry OBJECT-TYPE
  SYNTAX      QoSPortGroupsEntry
  MAX-ACCESS  not-accessible
  STATUS      current
  DESCRIPTION "Definition of QoS PortGroups"
  INDEX {
          alaQoSPortGroupsName
        }
  ::= { alaQoSPortGroupsTable 1 }

QoSPortGroupsEntry ::=
  SEQUENCE
  {
    alaQoSPortGroupsName                                    DisplayString,
    alaQoSPortGroupsSource                                  INTEGER,
    alaQoSPortGroupsStatus                                  RowStatus,
    alaQoSPortGroupsMode  	                            INTEGER
  }

alaQoSPortGroupsName OBJECT-TYPE
  SYNTAX      DisplayString (SIZE(0..31))
  MAX-ACCESS  not-accessible
  STATUS      current
  DESCRIPTION "Name of port group"
  ::= { alaQoSPortGroupsEntry 1 }

alaQoSPortGroupsSource OBJECT-TYPE
  SYNTAX      INTEGER {
                ldap (1),
                cli (2),
                blt (3),
                api (4),
                imp (5)
              }
  MAX-ACCESS  read-create
  STATUS      current
  DESCRIPTION "What entity created the port group."
  DEFVAL      { cli }
  ::= { alaQoSPortGroupsEntry 2 }

alaQoSPortGroupsStatus OBJECT-TYPE
  SYNTAX      RowStatus
  MAX-ACCESS  read-create
  STATUS      current
  DESCRIPTION "Used to create/delete port groups according to the
               RowStatus convention"
  ::= { alaQoSPortGroupsEntry 3 }

alaQoSPortGroupsMode  	OBJECT-TYPE
  SYNTAX       INTEGER {
		  split(1),
		  nonSplit(2)
	       }
  MAX-ACCESS  		read-create
  STATUS      		current
  DESCRIPTION 		"Mode for policy action on the per port basis or group basis."
  ::= { alaQoSPortGroupsEntry 4 }
--
-- Definition of port group table
--

alaQoSAppliedPortGroupsTable OBJECT-TYPE
  SYNTAX      SEQUENCE OF QoSAppliedPortGroupsEntry
  MAX-ACCESS  not-accessible
  STATUS      current
  DESCRIPTION "Table of QoS AppliedPortGroups definitions"
  ::= { alaQoSMIBObjects 20 }

alaQoSAppliedPortGroupsEntry OBJECT-TYPE
  SYNTAX      QoSAppliedPortGroupsEntry
  MAX-ACCESS  not-accessible
  STATUS      current
  DESCRIPTION "Definition of QoS AppliedPortGroups"
  INDEX {
          alaQoSAppliedPortGroupsName
        }
  ::= { alaQoSAppliedPortGroupsTable 1 }

QoSAppliedPortGroupsEntry ::=
  SEQUENCE
  {
    alaQoSAppliedPortGroupsName                             DisplayString,
    alaQoSAppliedPortGroupsSource                           INTEGER,
    alaQoSAppliedPortGroupsStatus                           RowStatus,
    alaQoSAppliedPortGroupsMode                             INTEGER
  }

alaQoSAppliedPortGroupsName OBJECT-TYPE
  SYNTAX      DisplayString (SIZE(0..31))
  MAX-ACCESS  not-accessible
  STATUS      current
  DESCRIPTION "Name of port group"
  ::= { alaQoSAppliedPortGroupsEntry 1 }

alaQoSAppliedPortGroupsSource OBJECT-TYPE
  SYNTAX      INTEGER {
                ldap (1),
                cli (2),
                blt (3),
                api (4),
                imp (5)
              }
  MAX-ACCESS  read-only
  STATUS      current
  DESCRIPTION "What entity created the port group."
  ::= { alaQoSAppliedPortGroupsEntry 2 }

alaQoSAppliedPortGroupsStatus OBJECT-TYPE
  SYNTAX      RowStatus
  MAX-ACCESS  read-only
  STATUS      current
  DESCRIPTION "Used to create/delete port groups according to the
               RowStatus convention"
  ::= { alaQoSAppliedPortGroupsEntry 3 }

alaQoSAppliedPortGroupsMode  	OBJECT-TYPE
  SYNTAX       INTEGER {
		   split(1),
		   nonSplit(2)
	       }
  MAX-ACCESS  		read-create
  STATUS      		current
  DESCRIPTION 		"Mode for policy action on the per port basis or group basis."
  ::= { alaQoSAppliedPortGroupsEntry 4 }

--
-- Definition of port group entry table
--

alaQoSPortGroupTable OBJECT-TYPE
  SYNTAX      SEQUENCE OF QoSPortGroupEntry
  MAX-ACCESS  not-accessible
  STATUS      current
  DESCRIPTION "Table of QoS PortGroup definitions"
  ::= { alaQoSMIBObjects 21 }

alaQoSPortGroupEntry OBJECT-TYPE
  SYNTAX      QoSPortGroupEntry
  MAX-ACCESS  not-accessible
  STATUS      current
  DESCRIPTION "Definition of QoS PortGroup"
  INDEX {
          alaQoSPortGroupsName,
          alaQoSPortGroupSlot,
          alaQoSPortGroupPort,
          alaQoSPortGroupPortEnd
        }
  ::= { alaQoSPortGroupTable 1 }

QoSPortGroupEntry ::=
  SEQUENCE
  {
    alaQoSPortGroupSlot                                     Integer32,
    alaQoSPortGroupPort                                     Integer32,
    alaQoSPortGroupStatus                                   RowStatus,
    alaQoSPortGroupPortEnd                                  Integer32
  }

alaQoSPortGroupSlot OBJECT-TYPE
  SYNTAX      Integer32 (1..16)
  MAX-ACCESS  not-accessible
  STATUS      current
  DESCRIPTION "Physical slot for port group entry"
  ::= { alaQoSPortGroupEntry 1 }

alaQoSPortGroupPort OBJECT-TYPE
  SYNTAX      Integer32 (1..52)
  MAX-ACCESS  not-accessible
  STATUS      current
  DESCRIPTION "Physical port range start for port group entry"
  ::= { alaQoSPortGroupEntry 2 }

alaQoSPortGroupStatus OBJECT-TYPE
  SYNTAX      RowStatus
  MAX-ACCESS  read-create
  STATUS      current
  DESCRIPTION "Used to create/delete port group entries according to the
               RowStatus convention"
  ::= { alaQoSPortGroupEntry 3 }

alaQoSPortGroupPortEnd OBJECT-TYPE
  SYNTAX      Integer32 (0..52)
  MAX-ACCESS  not-accessible
  STATUS      current
  DESCRIPTION "Physical port range end for port group entry
               Must be greater than port range start to indicate a range.
               When '1', use port as a single port."
  ::= { alaQoSPortGroupEntry 4 }


--
-- Definition of port group entry table
--

alaQoSAppliedPortGroupTable OBJECT-TYPE
  SYNTAX      SEQUENCE OF QoSAppliedPortGroupEntry
  MAX-ACCESS  not-accessible
  STATUS      current
  DESCRIPTION "Table of QoS AppliedPortGroup definitions"
  ::= { alaQoSMIBObjects 22 }

alaQoSAppliedPortGroupEntry OBJECT-TYPE
  SYNTAX      QoSAppliedPortGroupEntry
  MAX-ACCESS  not-accessible
  STATUS      current
  DESCRIPTION "Definition of QoS AppliedPortGroup"
  INDEX {
          alaQoSAppliedPortGroupsName,
          alaQoSAppliedPortGroupSlot,
          alaQoSAppliedPortGroupPort,
          alaQoSAppliedPortGroupPortEnd
        }
  ::= { alaQoSAppliedPortGroupTable 1 }

QoSAppliedPortGroupEntry ::=
  SEQUENCE
  {
    alaQoSAppliedPortGroupSlot                              Integer32,
    alaQoSAppliedPortGroupPort                              Integer32,
    alaQoSAppliedPortGroupStatus                            RowStatus,
    alaQoSAppliedPortGroupPortEnd                           Integer32
  }

alaQoSAppliedPortGroupSlot OBJECT-TYPE
  SYNTAX      Integer32 (1..16)
  MAX-ACCESS  not-accessible
  STATUS      current
  DESCRIPTION "Physical slot for port group entry"
  ::= { alaQoSAppliedPortGroupEntry 1 }

alaQoSAppliedPortGroupPort OBJECT-TYPE
  SYNTAX      Integer32 (1..52)
  MAX-ACCESS  not-accessible
  STATUS      current
  DESCRIPTION "Physical port range start for port group entry"
  ::= { alaQoSAppliedPortGroupEntry 2 }

alaQoSAppliedPortGroupStatus OBJECT-TYPE
  SYNTAX      RowStatus
  MAX-ACCESS  read-only
  STATUS      current
  DESCRIPTION "Used to create/delete port group entries according to the
               RowStatus convention"
  ::= { alaQoSAppliedPortGroupEntry 3 }

alaQoSAppliedPortGroupPortEnd OBJECT-TYPE
  SYNTAX      Integer32 (0..52)
  MAX-ACCESS  not-accessible
  STATUS      current
  DESCRIPTION "Physical port range end for port group entry
               Must be greater than port range start to indicate a range.
               When '1', use port as a single port."
  ::= { alaQoSAppliedPortGroupEntry 4 }


--
-- Definition of map group table
--

alaQoSMapGroupsTable OBJECT-TYPE
  SYNTAX      SEQUENCE OF QoSMapGroupsEntry
  MAX-ACCESS  not-accessible
  STATUS      current
  DESCRIPTION "Table of QoS MapGroups definitions"
  ::= { alaQoSMIBObjects 23 }

alaQoSMapGroupsEntry OBJECT-TYPE
  SYNTAX      QoSMapGroupsEntry
  MAX-ACCESS  not-accessible
  STATUS      current
  DESCRIPTION "Definition of QoS MapGroups"
  INDEX {
          alaQoSMapGroupsName
        }
  ::= { alaQoSMapGroupsTable 1 }

QoSMapGroupsEntry ::=
  SEQUENCE
  {
    alaQoSMapGroupsName                                     DisplayString,
    alaQoSMapGroupsSource                                   INTEGER,
    alaQoSMapGroupsStatus                                   RowStatus
  }

alaQoSMapGroupsName OBJECT-TYPE
  SYNTAX      DisplayString (SIZE(0..31))
  MAX-ACCESS  not-accessible
  STATUS      current
  DESCRIPTION "Name of map group"
  ::= { alaQoSMapGroupsEntry 1 }

alaQoSMapGroupsSource OBJECT-TYPE
  SYNTAX      INTEGER {
                ldap (1),
                cli (2),
                blt (3),
                api (4),
                imp (5)
              }
  MAX-ACCESS  read-create
  STATUS      current
  DESCRIPTION "What entity created the map group."
  DEFVAL      { cli }
  ::= { alaQoSMapGroupsEntry 2 }

alaQoSMapGroupsStatus OBJECT-TYPE
  SYNTAX      RowStatus
  MAX-ACCESS  read-create
  STATUS      current
  DESCRIPTION "Used to create/delete map groups according to the
               RowStatus convention"
  ::= { alaQoSMapGroupsEntry 3 }


--
-- Definition of map group table
--

alaQoSAppliedMapGroupsTable OBJECT-TYPE
  SYNTAX      SEQUENCE OF QoSAppliedMapGroupsEntry
  MAX-ACCESS  not-accessible
  STATUS      current
  DESCRIPTION "Table of QoS AppliedMapGroups definitions"
  ::= { alaQoSMIBObjects 24 }

alaQoSAppliedMapGroupsEntry OBJECT-TYPE
  SYNTAX      QoSAppliedMapGroupsEntry
  MAX-ACCESS  not-accessible
  STATUS      current
  DESCRIPTION "Definition of QoS AppliedMapGroups"
  INDEX {
          alaQoSAppliedMapGroupsName
        }
  ::= { alaQoSAppliedMapGroupsTable 1 }

QoSAppliedMapGroupsEntry ::=
  SEQUENCE
  {
    alaQoSAppliedMapGroupsName                              DisplayString,
    alaQoSAppliedMapGroupsSource                            INTEGER,
    alaQoSAppliedMapGroupsStatus                            RowStatus
  }

alaQoSAppliedMapGroupsName OBJECT-TYPE
  SYNTAX      DisplayString (SIZE(0..31))
  MAX-ACCESS  not-accessible
  STATUS      current
  DESCRIPTION "Name of map group"
  ::= { alaQoSAppliedMapGroupsEntry 1 }

alaQoSAppliedMapGroupsSource OBJECT-TYPE
  SYNTAX      INTEGER {
                ldap (1),
                cli (2),
                blt (3),
                api (4),
                imp (5)
              }
  MAX-ACCESS  read-only
  STATUS      current
  DESCRIPTION "What entity created the map group."
  ::= { alaQoSAppliedMapGroupsEntry 2 }

alaQoSAppliedMapGroupsStatus OBJECT-TYPE
  SYNTAX      RowStatus
  MAX-ACCESS  read-only
  STATUS      current
  DESCRIPTION "Used to create/delete map groups according to the
               RowStatus convention"
  ::= { alaQoSAppliedMapGroupsEntry 3 }


--
-- Definition of map group entry table
--

alaQoSMapGroupTable OBJECT-TYPE
  SYNTAX      SEQUENCE OF QoSMapGroupEntry
  MAX-ACCESS  not-accessible
  STATUS      current
  DESCRIPTION "Table of QoS MapGroup definitions"
  ::= { alaQoSMIBObjects 25 }

alaQoSMapGroupEntry OBJECT-TYPE
  SYNTAX      QoSMapGroupEntry
  MAX-ACCESS  not-accessible
  STATUS      current
  DESCRIPTION "Definition of QoS MapGroup"
  INDEX {
          alaQoSMapGroupsName,
          alaQoSMapGroupKey,
          alaQoSMapGroupKeyEnd,
          alaQoSMapGroupValue
        }
  ::= { alaQoSMapGroupTable 1 }

QoSMapGroupEntry ::=
  SEQUENCE
  {
    alaQoSMapGroupKey                                       Integer32,
    alaQoSMapGroupKeyEnd                                    Integer32,
    alaQoSMapGroupValue                                     Integer32,
    alaQoSMapGroupStatus                                    RowStatus
  }

alaQoSMapGroupKey OBJECT-TYPE
  SYNTAX      Integer32 (0..63)
  MAX-ACCESS  not-accessible
  STATUS      current
  DESCRIPTION "Key range start of map group entry."
  ::= { alaQoSMapGroupEntry 1 }

alaQoSMapGroupKeyEnd OBJECT-TYPE
  SYNTAX      Integer32 (0..63)
  MAX-ACCESS  not-accessible
  STATUS      current
  DESCRIPTION "Key range end for map group entries.  Key range end
               must be greater than key range start to indicate a range.
               When '0', use key range start as a single key."
  ::= { alaQoSMapGroupEntry 2 }

alaQoSMapGroupValue OBJECT-TYPE
  SYNTAX      Integer32 (0..63)
  MAX-ACCESS  not-accessible
  STATUS      current
  DESCRIPTION "Value for map group entries.  Value to stamp on traffic when
               keys in the proper range are seen."
  ::= { alaQoSMapGroupEntry 3 }

alaQoSMapGroupStatus OBJECT-TYPE
  SYNTAX      RowStatus
  MAX-ACCESS  read-create
  STATUS      current
  DESCRIPTION "Used to create/delete map group entries according to the
               RowStatus convention"
  ::= { alaQoSMapGroupEntry 4 }


--
-- Definition of map group entry table
--

alaQoSAppliedMapGroupTable OBJECT-TYPE
  SYNTAX      SEQUENCE OF QoSAppliedMapGroupEntry
  MAX-ACCESS  not-accessible
  STATUS      current
  DESCRIPTION "Table of QoS AppliedMapGroup definitions"
  ::= { alaQoSMIBObjects 26 }

alaQoSAppliedMapGroupEntry OBJECT-TYPE
  SYNTAX      QoSAppliedMapGroupEntry
  MAX-ACCESS  not-accessible
  STATUS      current
  DESCRIPTION "Definition of QoS AppliedMapGroup"
  INDEX {
          alaQoSAppliedMapGroupsName,
          alaQoSAppliedMapGroupKey,
          alaQoSAppliedMapGroupKeyEnd,
          alaQoSAppliedMapGroupValue
        }
  ::= { alaQoSAppliedMapGroupTable 1 }

QoSAppliedMapGroupEntry ::=
  SEQUENCE
  {
    alaQoSAppliedMapGroupKey                                Integer32,
    alaQoSAppliedMapGroupKeyEnd                             Integer32,
    alaQoSAppliedMapGroupValue                              Integer32,
    alaQoSAppliedMapGroupStatus                             RowStatus
  }

alaQoSAppliedMapGroupKey OBJECT-TYPE
  SYNTAX      Integer32 (0..63)
  MAX-ACCESS  not-accessible
  STATUS      current
  DESCRIPTION "Key range start of map group entry."
  ::= { alaQoSAppliedMapGroupEntry 1 }

alaQoSAppliedMapGroupKeyEnd OBJECT-TYPE
  SYNTAX      Integer32 (0..63)
  MAX-ACCESS  not-accessible
  STATUS      current
  DESCRIPTION "Key range end for map group entries.  Key range end
               must be greater than key range start to indicate a range.
               When '0', use key range start as a single key."
  ::= { alaQoSAppliedMapGroupEntry 2 }

alaQoSAppliedMapGroupValue OBJECT-TYPE
  SYNTAX      Integer32 (0..63)
  MAX-ACCESS  not-accessible
  STATUS      current
  DESCRIPTION "Value for map group entries.  Value to stamp on traffic when
               keys in the proper range are seen."
  ::= { alaQoSAppliedMapGroupEntry 3 }

alaQoSAppliedMapGroupStatus OBJECT-TYPE
  SYNTAX      RowStatus
  MAX-ACCESS  read-only
  STATUS      current
  DESCRIPTION "Used to create/delete map group entries according to the
               RowStatus convention"
  ::= { alaQoSAppliedMapGroupEntry 4 }


--
-- Definition of action table
--

alaQoSActionTable OBJECT-TYPE
  SYNTAX      SEQUENCE OF QoSActionEntry
  MAX-ACCESS  not-accessible
  STATUS      current
  DESCRIPTION "Table of QoS Action definitions"
  ::= { alaQoSMIBObjects 27 }

alaQoSActionEntry OBJECT-TYPE
  SYNTAX      QoSActionEntry
  MAX-ACCESS  not-accessible
  STATUS      current
  DESCRIPTION "Definition of QoS Action"
  INDEX {
          alaQoSActionName
        }
  ::= { alaQoSActionTable 1 }

QoSActionEntry ::=
  SEQUENCE
  {
    alaQoSActionName                                        DisplayString,
    alaQoSActionSource                                      INTEGER,
    alaQoSActionDisposition                                 INTEGER,
    alaQoSActionDropAlgorithm                               INTEGER,
    alaQoSActionWredMaximumThreshold                        Integer32,
    alaQoSActionWredMaximumThresholdStatus                  INTEGER,
    alaQoSActionWredMinimumThreshold                        Integer32,
    alaQoSActionWredMinimumThresholdStatus                  INTEGER,
    alaQoSActionWredMaximumProbability                      Integer32,
    alaQoSActionWredMaximumProbabilityStatus                INTEGER,
    alaQoSActionMinimumBandwidth                            Integer32,
    alaQoSActionMinimumBandwidthStatus                      INTEGER,
    alaQoSActionMaximumBandwidth                            Integer32,
    alaQoSActionMaximumBandwidthStatus                      INTEGER,
    alaQoSActionPeakBandwidth                               Integer32,
    alaQoSActionPeakBandwidthStatus                         INTEGER,
    alaQoSActionPriority                                    Integer32,
    alaQoSActionPriorityStatus                              INTEGER,
    alaQoSActionShared                                      INTEGER,
    alaQoSActionJitter                                      Integer32,
    alaQoSActionJitterStatus                                INTEGER,
    alaQoSActionLatency                                     Integer32,
    alaQoSActionLatencyStatus                               INTEGER,
    alaQoSActionMaximumDepth                                Integer32,
    alaQoSActionMaximumDepthStatus                          INTEGER,
    alaQoSActionMaximumBuffers                              Integer32,
    alaQoSActionMaximumBuffersStatus                        INTEGER,
    alaQoSAction8021p                                       Integer32,
    alaQoSAction8021pStatus                                 INTEGER,
    alaQoSActionTos                                         Integer32,
    alaQoSActionTosStatus                                   INTEGER,
    alaQoSActionDscp                                        Integer32,
    alaQoSActionDscpStatus                                  INTEGER,
    alaQoSActionMapFrom                                     INTEGER,
    alaQoSActionMapTo                                       INTEGER,
    alaQoSActionMapGroup                                    DisplayString,
    alaQoSActionMapGroupStatus                              INTEGER,
    alaQoSActionSourceRewriteIpAddr                         IpAddress,
    alaQoSActionSourceRewriteIpAddrStatus                   INTEGER,
    alaQoSActionSourceRewriteIpMask                         IpAddress,
    alaQoSActionSourceRewriteNetworkGroup                   DisplayString,
    alaQoSActionSourceRewriteNetworkGroupStatus             INTEGER,
    alaQoSActionDestinationRewriteIpAddr                    IpAddress,
    alaQoSActionDestinationRewriteIpAddrStatus              INTEGER,
    alaQoSActionDestinationRewriteIpMask                    IpAddress,
    alaQoSActionDestinationRewriteNetworkGroup              DisplayString,
    alaQoSActionDestinationRewriteNetworkGroupStatus        INTEGER,
    alaQoSActionLoadBalanceGroup                            DisplayString,
    alaQoSActionLoadBalanceGroupStatus                      INTEGER,
    alaQoSActionPermanentGatewayIpAddr                      IpAddress,
    alaQoSActionPermanentGatewayIpAddrStatus                INTEGER,
    alaQoSActionAlternateGatewayIpAddr                      IpAddress,
    alaQoSActionAlternateGatewayIpAddrStatus                INTEGER,
    alaQoSActionRowStatus                                   RowStatus,
    alaQoSActionMinimumDepth                                Integer32,
    alaQoSActionMinimumDepthStatus                          INTEGER,
    alaQoSActionVPNAccess                                   INTEGER,
    alaQoSActionNocache                                     INTEGER,
    alaQoSActionPortdisable                                 INTEGER,
    alaQoSActionRedirectSlot                                Integer32,
    alaQoSActionRedirectSlotStatus                          INTEGER,
    alaQoSActionRedirectPort                                Integer32,
    alaQoSActionRedirectAgg                                 Integer32,
    alaQoSActionRedirectAggStatus                           INTEGER,
    alaQoSActionMirrorSlot                                  Integer32,
    alaQoSActionMirrorPort                                  Integer32,
    alaQoSActionMirrorMode                                  INTEGER,
    alaQoSActionMirrorModeStatus                            INTEGER,
    alaQoSActionCIR                                         Integer32,
    alaQoSActionCIRStatus         			    INTEGER,
    alaQoSActionCBS                                         Integer32,
    alaQoSActionCBSStatus		                    INTEGER,
    alaQoSActionPIR                                         Integer32,
    alaQoSActionPIRStatus		                    INTEGER,
    alaQoSActionPBS                                         Integer32,
    alaQoSActionPBSStatus		          	    INTEGER,
    alaQoSActionCounterColor                                INTEGER,
    alaQoSActionRTCPMonitor                                 INTEGER,
    alaQoSActionRTCPMonitorStatus                           INTEGER,
    alaQoSActionRTCPDSCP                                    Integer32,
    alaQoSActionRTCPDSCPStatus	                            INTEGER,
    alaQoSActionTrustDSCP                                   INTEGER,
    alaQoSActionTrustDSCPStatus	                            INTEGER      				
  }

alaQoSActionName OBJECT-TYPE
  SYNTAX      DisplayString (SIZE(0..31))
  MAX-ACCESS  not-accessible
  STATUS      current
  DESCRIPTION "Name of action"
  ::= { alaQoSActionEntry 1 }

alaQoSActionSource OBJECT-TYPE
  SYNTAX      INTEGER {
                ldap (1),
                cli (2),
                blt (3),
                api (4),
                imp (5)
              }
  MAX-ACCESS  read-create
  STATUS      current
  DESCRIPTION "What entity created the action."
  DEFVAL      { cli }
  ::= { alaQoSActionEntry 2 }

alaQoSActionDisposition OBJECT-TYPE
  SYNTAX      INTEGER {
                accept (1),
                drop (2),
                deny (3)
              }
  MAX-ACCESS  read-create
  STATUS      current
  DESCRIPTION "Disposition of traffic using the action.
               Use to filter out unwanted traffic."
  DEFVAL      { accept }
  ::= { alaQoSActionEntry 3 }

alaQoSActionDropAlgorithm OBJECT-TYPE
  SYNTAX      INTEGER {
                tail (1),
                wred (2)
              }
  MAX-ACCESS  read-create
  STATUS      current
  DESCRIPTION "Which drop algorithm should be used to discard traffic when
               oversubscribed."
  DEFVAL      { tail }
  ::= { alaQoSActionEntry 4 }

alaQoSActionWredMaximumThreshold OBJECT-TYPE
  SYNTAX      Integer32
  MAX-ACCESS  read-create
  STATUS      current
  DESCRIPTION "Bandwidth at which WRED should discard most traffic."
  DEFVAL      { 0 }
  ::= { alaQoSActionEntry 5 }

alaQoSActionWredMaximumThresholdStatus OBJECT-TYPE
  SYNTAX      INTEGER {
                enabled (1),
                disabled (2)
              }
  MAX-ACCESS  read-create
  STATUS      current
  DESCRIPTION "Status field indicating whether WRED maximum threshold
               is specified(enabled) or not(disabled)."
  DEFVAL      { disabled }
  ::= { alaQoSActionEntry 6 }

alaQoSActionWredMinimumThreshold OBJECT-TYPE
  SYNTAX      Integer32
  MAX-ACCESS  read-create
  STATUS      current
  DESCRIPTION "Bandwidth at which WRED should start to discard traffic."
  DEFVAL      { 0 }
  ::= { alaQoSActionEntry 7 }

alaQoSActionWredMinimumThresholdStatus OBJECT-TYPE
  SYNTAX      INTEGER {
                enabled (1),
                disabled (2)
              }
  MAX-ACCESS  read-create
  STATUS      current
  DESCRIPTION "Status field indicating whether WRED minimum threshold
               is specified(enabled) or not(disabled)."
  DEFVAL      { disabled }
  ::= { alaQoSActionEntry 8 }

alaQoSActionWredMaximumProbability OBJECT-TYPE
  SYNTAX      Integer32
  MAX-ACCESS  read-create
  STATUS      current
  DESCRIPTION "Probabilty that traffic will be dropped at WRED
               maximum threshold."
  DEFVAL      { 0 }
  ::= { alaQoSActionEntry 9 }

alaQoSActionWredMaximumProbabilityStatus OBJECT-TYPE
  SYNTAX      INTEGER {
                enabled (1),
                disabled (2)
              }
  MAX-ACCESS  read-create
  STATUS      current
  DESCRIPTION "Status field indicating whether WRED maximum probability
               is specified(enabled) or not(disabled)."
  DEFVAL      { disabled }
  ::= { alaQoSActionEntry 10 }

alaQoSActionMinimumBandwidth OBJECT-TYPE
  SYNTAX      Integer32
  MAX-ACCESS  read-create
  STATUS      current
  DESCRIPTION "Minimum bandwidth (Kbits/sec) to guarantee for traffic"
  DEFVAL      { 0 }
  ::= { alaQoSActionEntry 11 }

alaQoSActionMinimumBandwidthStatus OBJECT-TYPE
  SYNTAX      INTEGER {
                enabled (1),
                disabled (2)
              }
  MAX-ACCESS  read-create
  STATUS      current
  DESCRIPTION "Status field indicating whether minimum bandwidth
               is specified(enabled) or not(disabled)."
  DEFVAL      { disabled }
  ::= { alaQoSActionEntry 12 }

alaQoSActionMaximumBandwidth OBJECT-TYPE
  SYNTAX      Integer32
  MAX-ACCESS  read-create
  STATUS      current
  DESCRIPTION "Maximum bandwidth (Kbits/sec) allowed for traffic"
  DEFVAL      { 0 }
  ::= { alaQoSActionEntry 13 }

alaQoSActionMaximumBandwidthStatus OBJECT-TYPE
  SYNTAX      INTEGER {
                enabled (1),
                disabled (2)
              }
  MAX-ACCESS  read-create
  STATUS      current
  DESCRIPTION "Status field indicating whether maximum bandwidth
               is specified(enabled) or not(disabled)."
  DEFVAL      { disabled }
  ::= { alaQoSActionEntry 14 }

alaQoSActionPeakBandwidth OBJECT-TYPE
  SYNTAX      Integer32
  MAX-ACCESS  read-create
  STATUS      current
  DESCRIPTION "Peak bandwidth (Kbits/sec) allowed for traffic"
  DEFVAL      { 0 }
  ::= { alaQoSActionEntry 15 }

alaQoSActionPeakBandwidthStatus OBJECT-TYPE
  SYNTAX      INTEGER {
                enabled (1),
                disabled (2)
              }
  MAX-ACCESS  read-create
  STATUS      current
  DESCRIPTION "Status field indicating whether peak bandwidth
               is specified(enabled) or not(disabled)."
  DEFVAL      { disabled }
  ::= { alaQoSActionEntry 16 }

alaQoSActionPriority OBJECT-TYPE
  SYNTAX      Integer32 (0..7)
  MAX-ACCESS  read-create
  STATUS      current
  DESCRIPTION "Internal and queueing priority to use for traffic."
  DEFVAL      { 0 }
  ::= { alaQoSActionEntry 17 }

alaQoSActionPriorityStatus OBJECT-TYPE
  SYNTAX      INTEGER {
                enabled (1),
                disabled (2)
              }
  MAX-ACCESS  read-create
  STATUS      current
  DESCRIPTION "Status field indicating whether priority
               is specified(enabled) or not(disabled)."
  DEFVAL      { disabled }
  ::= { alaQoSActionEntry 18 }

alaQoSActionShared OBJECT-TYPE
  SYNTAX      INTEGER {
                yes (1),
                no (2)
              }
  MAX-ACCESS  read-create
  STATUS      current
  DESCRIPTION "When enabled, try and share any resources
               (queues/limiters/descriptors) when more than one policy uses
               the same action."
  DEFVAL      { no }
  ::= { alaQoSActionEntry 19 }

alaQoSActionJitter OBJECT-TYPE
  SYNTAX      Integer32
  MAX-ACCESS  read-create
  STATUS      current
  DESCRIPTION "Maximum jitter to allow for traffic."
  DEFVAL      { 0 }
  ::= { alaQoSActionEntry 20 }

alaQoSActionJitterStatus OBJECT-TYPE
  SYNTAX      INTEGER {
                enabled (1),
                disabled (2)
              }
  MAX-ACCESS  read-create
  STATUS      current
  DESCRIPTION "Status field indicating whether jitter
               is specified(enabled) or not(disabled)."
  DEFVAL      { disabled }
  ::= { alaQoSActionEntry 21 }

alaQoSActionLatency OBJECT-TYPE
  SYNTAX      Integer32
  MAX-ACCESS  read-create
  STATUS      current
  DESCRIPTION "Maximum latency to allow for traffic."
  DEFVAL      { 0 }
  ::= { alaQoSActionEntry 22 }

alaQoSActionLatencyStatus OBJECT-TYPE
  SYNTAX      INTEGER {
                enabled (1),
                disabled (2)
              }
  MAX-ACCESS  read-create
  STATUS      current
  DESCRIPTION "Status field indicating whether latency
               is specified(enabled) or not(disabled)."
  DEFVAL      { disabled }
  ::= { alaQoSActionEntry 23 }

alaQoSActionMaximumDepth OBJECT-TYPE
  SYNTAX      Integer32
  MAX-ACCESS  read-create
  STATUS      current
  DESCRIPTION "Maximum depth (Kbytes) of queues for traffic.
               Used for EBS in tri-color marker applications."
  DEFVAL      { 0 }
  ::= { alaQoSActionEntry 24 }

alaQoSActionMaximumDepthStatus OBJECT-TYPE
  SYNTAX      INTEGER {
                enabled (1),
                disabled (2)
              }
  MAX-ACCESS  read-create
  STATUS      current
  DESCRIPTION "Status field indicating whether maximum depth
               is specified(enabled) or not(disabled)."
  DEFVAL      { disabled }
  ::= { alaQoSActionEntry 25 }

alaQoSActionMaximumBuffers OBJECT-TYPE
  SYNTAX      Integer32 (0..2047)
  MAX-ACCESS  read-create
  STATUS      current
  DESCRIPTION "Maxmimum buffers for queues for traffic."
  DEFVAL      { 0 }
  ::= { alaQoSActionEntry 26 }

alaQoSActionMaximumBuffersStatus OBJECT-TYPE
  SYNTAX      INTEGER {
                enabled (1),
                disabled (2)
              }
  MAX-ACCESS  read-create
  STATUS      current
  DESCRIPTION "Status field indicating whether maximum buffers
               is specified(enabled) or not(disabled)."
  DEFVAL      { disabled }
  ::= { alaQoSActionEntry 27 }

alaQoSAction8021p OBJECT-TYPE
  SYNTAX      Integer32 (0..7)
  MAX-ACCESS  read-create
  STATUS      current
  DESCRIPTION "802.1p value to stamp on traffic."
  DEFVAL      { 0 }
  ::= { alaQoSActionEntry 28 }

alaQoSAction8021pStatus OBJECT-TYPE
  SYNTAX      INTEGER {
                enabled (1),
                disabled (2)
              }
  MAX-ACCESS  read-create
  STATUS      current
  DESCRIPTION "Status field indicating whether 802.1p
               is specified(enabled) or not(disabled)."
  DEFVAL      { disabled }
  ::= { alaQoSActionEntry 29 }

alaQoSActionTos OBJECT-TYPE
  SYNTAX      Integer32 (0..7)
  MAX-ACCESS  read-create
  STATUS      current
  DESCRIPTION "TOS value to stamp on traffic. (High 3 bits of TOS byte)"
  DEFVAL      { 0 }
  ::= { alaQoSActionEntry 30 }

alaQoSActionTosStatus OBJECT-TYPE
  SYNTAX      INTEGER {
                enabled (1),
                disabled (2)
              }
  MAX-ACCESS  read-create
  STATUS      current
  DESCRIPTION "Status field indicating whether TOS
               is specified(enabled) or not(disabled)."
  DEFVAL      { disabled }
  ::= { alaQoSActionEntry 31 }

alaQoSActionDscp OBJECT-TYPE
  SYNTAX      Integer32 (0..63)
  MAX-ACCESS  read-create
  STATUS      current
  DESCRIPTION "TOS value to stamp on traffic. (High 6 bits of TOS byte)"
  DEFVAL      { 0 }
  ::= { alaQoSActionEntry 32 }

alaQoSActionDscpStatus OBJECT-TYPE
  SYNTAX      INTEGER {
                enabled (1),
                disabled (2)
              }
  MAX-ACCESS  read-create
  STATUS      current
  DESCRIPTION "Status field indicating whether DSCP
               is specified(enabled) or not(disabled)."
  DEFVAL      { disabled }
  ::= { alaQoSActionEntry 33 }

alaQoSActionMapFrom OBJECT-TYPE
  SYNTAX      INTEGER {
                b8021p (1),
                tos (2),
                dscp (3)
              }
  MAX-ACCESS  read-create
  STATUS      current
  DESCRIPTION "What field to use as key for mapping 802.1p/TOS/DSCP priorities"
  DEFVAL      { b8021p }
  ::= { alaQoSActionEntry 34 }

alaQoSActionMapTo OBJECT-TYPE
  SYNTAX      INTEGER {
                b8021p (1),
                tos (2),
                dscp (3)
              }
  MAX-ACCESS  read-create
  STATUS      current
  DESCRIPTION "What field to rewrite due to remapping 802.1p/TOS/DSCP
               priorities"
  DEFVAL      { b8021p }
  ::= { alaQoSActionEntry 35 }

alaQoSActionMapGroup OBJECT-TYPE
  SYNTAX      DisplayString (SIZE(0..31))
  MAX-ACCESS  read-create
  STATUS      current
  DESCRIPTION "Name of the map group to use when remapping 802.1p/TOS/DSCP
               priorities."
  ::= { alaQoSActionEntry 36 }

alaQoSActionMapGroupStatus OBJECT-TYPE
  SYNTAX      INTEGER {
                enabled (1),
                disabled (2)
              }
  MAX-ACCESS  read-create
  STATUS      current
  DESCRIPTION "Status field indicating whether a map group
               is specified(enabled) or not(disabled)."
  DEFVAL      { disabled }
  ::= { alaQoSActionEntry 37 }

alaQoSActionSourceRewriteIpAddr OBJECT-TYPE
  SYNTAX      IpAddress
  MAX-ACCESS  read-create
  STATUS      current
  DESCRIPTION "Source IP address to rewrite on traffic."
  DEFVAL      { '00000000'h }
  ::= { alaQoSActionEntry 38 }

alaQoSActionSourceRewriteIpAddrStatus OBJECT-TYPE
  SYNTAX      INTEGER {
                enabled (1),
                disabled (2)
              }
  MAX-ACCESS  read-create
  STATUS      current
  DESCRIPTION "Status field indicating whether source rewrite IP address & mask
               is specified(enabled) or not(disabled)."
  DEFVAL      { disabled }
  ::= { alaQoSActionEntry 39 }

alaQoSActionSourceRewriteIpMask OBJECT-TYPE
  SYNTAX      IpAddress
  MAX-ACCESS  read-create
  STATUS      current
  DESCRIPTION "Source rewrite IP mask to determine how much of
               source IP to rewrite."
  DEFVAL      { 'ffffffff'h }
  ::= { alaQoSActionEntry 40 }

alaQoSActionSourceRewriteNetworkGroup OBJECT-TYPE
  SYNTAX      DisplayString (SIZE(0..31))
  MAX-ACCESS  read-create
  STATUS      current
  DESCRIPTION "Name of network group containing source address/masks to rewrite
               on traffic.  Must be a one to on correspondence with
               source network group entries in the condition."
  ::= { alaQoSActionEntry 41 }

alaQoSActionSourceRewriteNetworkGroupStatus OBJECT-TYPE
  SYNTAX      INTEGER {
                enabled (1),
                disabled (2)
              }
  MAX-ACCESS  read-create
  STATUS      current
  DESCRIPTION "Status field indicating whether source rewrite network group
               is specified(enabled) or not(disabled)."
  DEFVAL      { disabled }
  ::= { alaQoSActionEntry 42 }

alaQoSActionDestinationRewriteIpAddr OBJECT-TYPE
  SYNTAX      IpAddress
  MAX-ACCESS  read-create
  STATUS      current
  DESCRIPTION "Destination IP address to rewrite on traffic."
  DEFVAL      { '00000000'h }
  ::= { alaQoSActionEntry 43 }

alaQoSActionDestinationRewriteIpAddrStatus OBJECT-TYPE
  SYNTAX      INTEGER {
                enabled (1),
                disabled (2)
              }
  MAX-ACCESS  read-create
  STATUS      current
  DESCRIPTION "Status field indicating whether destination rewrite IP address
               & mask is specified(enabled) or not(disabled)."
  DEFVAL      { disabled }
  ::= { alaQoSActionEntry 44 }

alaQoSActionDestinationRewriteIpMask OBJECT-TYPE
  SYNTAX      IpAddress
  MAX-ACCESS  read-create
  STATUS      current
  DESCRIPTION "Destination rewrite IP mask to determine how much of
               destination IP to rewrite."
  DEFVAL      { 'ffffffff'h }
  ::= { alaQoSActionEntry 45 }

alaQoSActionDestinationRewriteNetworkGroup OBJECT-TYPE
  SYNTAX      DisplayString (SIZE(0..31))
  MAX-ACCESS  read-create
  STATUS      current
  DESCRIPTION "Name of network group containing destination address/masks to
               rewrite on traffic.  Must be a one to on correspondence with
               destination network group entries in the condition."
  ::= { alaQoSActionEntry 46 }

alaQoSActionDestinationRewriteNetworkGroupStatus OBJECT-TYPE
  SYNTAX      INTEGER {
                enabled (1),
                disabled (2)
              }
  MAX-ACCESS  read-create
  STATUS      current
  DESCRIPTION "Status field indicating whether destination rewrite network
               group is specified(enabled) or not(disabled)."
  DEFVAL      { disabled }
  ::= { alaQoSActionEntry 47 }

alaQoSActionLoadBalanceGroup OBJECT-TYPE
  SYNTAX      DisplayString (SIZE(0..23))
  MAX-ACCESS  read-create
  STATUS      current
  DESCRIPTION "Name of load balance group to use for traffic"
  ::= { alaQoSActionEntry 48 }

alaQoSActionLoadBalanceGroupStatus OBJECT-TYPE
  SYNTAX      INTEGER {
                enabled (1),
                disabled (2)
              }
  MAX-ACCESS  read-create
  STATUS      current
  DESCRIPTION "Status field indicating whether load balanace group
               is specified(enabled) or not(disabled)."
  DEFVAL      { disabled }
  ::= { alaQoSActionEntry 49 }

alaQoSActionPermanentGatewayIpAddr OBJECT-TYPE
  SYNTAX      IpAddress
  MAX-ACCESS  read-create
  STATUS      current
  DESCRIPTION "Next hop gateway to use for traffic"
  DEFVAL      { '00000000'h }
  ::= { alaQoSActionEntry 50 }

alaQoSActionPermanentGatewayIpAddrStatus OBJECT-TYPE
  SYNTAX      INTEGER {
                enabled (1),
                disabled (2)
              }
  MAX-ACCESS  read-create
  STATUS      current
  DESCRIPTION "Status field indicating whether permanent gateway IP address
               is specified(enabled) or not(disabled)."
  DEFVAL      { disabled }
  ::= { alaQoSActionEntry 51 }

alaQoSActionAlternateGatewayIpAddr OBJECT-TYPE
  SYNTAX      IpAddress
  MAX-ACCESS  read-create
  STATUS      current
  DESCRIPTION "Next hop gateway to use for traffic that doesn't have an
               explicit route.  Use this gateway instead of default routes."
  DEFVAL      { '00000000'h }
  ::= { alaQoSActionEntry 52 }

alaQoSActionAlternateGatewayIpAddrStatus OBJECT-TYPE
  SYNTAX      INTEGER {
                enabled (1),
                disabled (2)
              }
  MAX-ACCESS  read-create
  STATUS      current
  DESCRIPTION "Status field indicating whether alternate gateway IP address
               is specified(enabled) or not(disabled)."
  DEFVAL      { disabled }
  ::= { alaQoSActionEntry 53 }

alaQoSActionRowStatus OBJECT-TYPE
  SYNTAX      RowStatus
  MAX-ACCESS  read-create
  STATUS      current
  DESCRIPTION "Used to create/delete actions according to the
               RowStatus convention"
  ::= { alaQoSActionEntry 54 }

alaQoSActionMinimumDepth OBJECT-TYPE
  SYNTAX      Integer32
  MAX-ACCESS  read-create
  STATUS      current
  DESCRIPTION "Minimum depth (Kbytes) of queues for traffic.
               Used for CBS in tri-color marker applications."
  DEFVAL      { 0 }
  ::= { alaQoSActionEntry 55 }

alaQoSActionMinimumDepthStatus OBJECT-TYPE
  SYNTAX      INTEGER {
                enabled (1),
                disabled (2)
              }
  MAX-ACCESS  read-create
  STATUS      current
  DESCRIPTION "Status field indicating whether minimum depth
               is specified(enabled) or not(disabled)."
  DEFVAL      { disabled }
  ::= { alaQoSActionEntry 56 }

alaQoSActionVPNAccess OBJECT-TYPE
  SYNTAX      INTEGER {
                protect (1),
                bypass (2),
                drop (3)
              }
  MAX-ACCESS  read-create
  STATUS      current
  DESCRIPTION "How to encrypt traffic"
  DEFVAL      { bypass }
  ::= { alaQoSActionEntry 57 }

alaQoSActionNocache OBJECT-TYPE
  SYNTAX      INTEGER {
                yes (1),
                no (2)
              }
  MAX-ACCESS  read-create
  STATUS      current
  DESCRIPTION "When enabled, don't make hardware entries for matching flows."
  DEFVAL      { no }
  ::= { alaQoSActionEntry 58 }

alaQoSActionPortdisable OBJECT-TYPE
  SYNTAX      INTEGER {
                yes (1),
                no (2)
              }
  MAX-ACCESS  read-create
  STATUS      current
  DESCRIPTION "When enabled, disable the physical source port of the traffic."
  DEFVAL      { no }
  ::= { alaQoSActionEntry 59 }

alaQoSActionRedirectSlot OBJECT-TYPE
  SYNTAX      Integer32 (0..16)
  MAX-ACCESS  read-create
  STATUS      current
  DESCRIPTION "Destination physical slot for redirected traffic"
  DEFVAL      { 1 }
  ::= { alaQoSActionEntry 60 }

alaQoSActionRedirectSlotStatus OBJECT-TYPE
  SYNTAX      INTEGER {
                enabled (1),
                disabled (2)
              }
  MAX-ACCESS  read-create
  STATUS      current
  DESCRIPTION "Status for alaQoSActionRedirectSlotStatus field"
  DEFVAL      { disabled }
  ::= { alaQoSActionEntry 61 }

alaQoSActionRedirectPort OBJECT-TYPE
  SYNTAX      Integer32 (1..52)
  MAX-ACCESS  read-create
  STATUS      current
  DESCRIPTION "Destination physical port for redirected traffic"
  DEFVAL      { 1 }
  ::= { alaQoSActionEntry 62 }

alaQoSActionRedirectAgg OBJECT-TYPE
  SYNTAX      Integer32 (0..32)
  MAX-ACCESS  read-create
  STATUS      current
  DESCRIPTION "Destination linkagg for redirected traffic"
  DEFVAL      { 0 }
  ::= { alaQoSActionEntry 63 }

alaQoSActionRedirectAggStatus OBJECT-TYPE
  SYNTAX      INTEGER {
                enabled (1),
                disabled (2)
              }
  MAX-ACCESS  read-create
  STATUS      current
  DESCRIPTION "Status for alaQoSActionRedirectAggStatus field"
  DEFVAL      { disabled }
  ::= { alaQoSActionEntry 64 }

alaQoSActionMirrorSlot OBJECT-TYPE
  SYNTAX      Integer32 (0..16)
  MAX-ACCESS  read-create
  STATUS      current
  DESCRIPTION "Destination physical slot for mirrored traffic"
  DEFVAL      { 1 }
  ::= { alaQoSActionEntry 65 }

alaQoSActionMirrorPort OBJECT-TYPE
  SYNTAX      Integer32 (1..52)
  MAX-ACCESS  read-create
  STATUS      current
  DESCRIPTION "Destination physical port for mirrored traffic"
  DEFVAL      { 1 }
  ::= { alaQoSActionEntry 66 }

alaQoSActionMirrorMode OBJECT-TYPE
  SYNTAX      INTEGER {
                ingress(1),
                egress(2),
                both(3)
              }
  MAX-ACCESS  read-create
  STATUS      current
  DESCRIPTION "Mirroring mode"
  DEFVAL      { ingress }
  ::= { alaQoSActionEntry 67 }

alaQoSActionMirrorModeStatus OBJECT-TYPE
  SYNTAX      INTEGER {
                enabled (1),
                disabled (2)
              }
  MAX-ACCESS  read-create
  STATUS      current
  DESCRIPTION "Status for alaQoSActionMirrorMode field"
  DEFVAL      { disabled }
  ::= { alaQoSActionEntry 68 }

alaQoSActionCIR OBJECT-TYPE
  SYNTAX      Integer32 
  UNITS	      "kilobits per second" 
  MAX-ACCESS  read-create
  STATUS      current
  DESCRIPTION "Committed Information Rate - bandwidth values in kilobits per second."
  DEFVAL      { 0 }
  ::= { alaQoSActionEntry 69 }

alaQoSActionCIRStatus OBJECT-TYPE
  SYNTAX      INTEGER {
                enabled (1),
                disabled (2)
              }
  MAX-ACCESS  read-create
  STATUS      current
  DESCRIPTION "Status field indicating whether CIR value is specified(enabled)
			  or not(disabled)."
  DEFVAL      { disabled }
  ::= { alaQoSActionEntry 70 }

alaQoSActionCBS OBJECT-TYPE
  SYNTAX      Integer32(0 .. 2147450880) 
  MAX-ACCESS  read-create
  STATUS      current
  DESCRIPTION "Committed Burst Size - bucket size in byte."
  DEFVAL      { 0 }
  ::= { alaQoSActionEntry 71 }

alaQoSActionCBSStatus OBJECT-TYPE
  SYNTAX      INTEGER {
                enabled (1),
                disabled (2)
              }
  MAX-ACCESS  read-create
  STATUS      current
  DESCRIPTION "Status field indicating whether CBS value is specified(enabled)
              or not(disabled)."
  DEFVAL      { disabled }
  ::= { alaQoSActionEntry 72 }

alaQoSActionPIR OBJECT-TYPE
  SYNTAX      Integer32 
  UNITS	      "kilobits per second" 
  MAX-ACCESS  read-create
  STATUS      current
  DESCRIPTION "Peak Information Rate - bandwidth values in kilobits per second."
  DEFVAL      { 0 }
  ::= { alaQoSActionEntry 73 }

alaQoSActionPIRStatus OBJECT-TYPE
  SYNTAX      INTEGER {
                enabled (1),
                disabled (2)
              }
  MAX-ACCESS  read-create
  STATUS      current
  DESCRIPTION "Status field indicating whether PIR value is specified(enabled)
              or not(disabled)."
  DEFVAL      { disabled }
  ::= { alaQoSActionEntry 74 }

alaQoSActionPBS OBJECT-TYPE
  SYNTAX      Integer32(0 .. 2147450880) 
  MAX-ACCESS  read-create
  STATUS      current
  DESCRIPTION "Peak Burst Size - bucket size in byte."
  DEFVAL      { 0 }
  ::= { alaQoSActionEntry 75 }

alaQoSActionPBSStatus OBJECT-TYPE
  SYNTAX      INTEGER {
                enabled (1),
                disabled (2)
              }
  MAX-ACCESS  read-create
  STATUS      current
  DESCRIPTION "Status field indicating whether PBS value is specified(enabled)
              or not(disabled)."
  DEFVAL      { disabled }
  ::= { alaQoSActionEntry 76 }

alaQoSActionCounterColor OBJECT-TYPE
  SYNTAX      INTEGER {
                        rednonred (1),
                        greennongreen (2),
                        greenred (3),
                        greenyellow (4),
                        redyellow (5)
		              }
  MAX-ACCESS  read-create
  STATUS      current
  DESCRIPTION "Specifies the color mode for the counters which will be used for sr/trTCM."
  DEFVAL      { redyellow }
  ::= { alaQoSActionEntry 77 }
alaQoSActionRTCPMonitor OBJECT-TYPE
  SYNTAX      INTEGER {
				enable (1),
		   		disable (2)
				}	
  MAX-ACCESS  	read-create
  STATUS      	current
  DESCRIPTION 	"RTCP Monitor status for the traffic."
  DEFVAL      	{ enable }
  ::= { alaQoSActionEntry 78 }
alaQoSActionRTCPMonitorStatus OBJECT-TYPE
  SYNTAX      INTEGER {
				enabled (1),
		   		disabled (2)
				}	
  MAX-ACCESS  	read-create
  STATUS      	current
  DESCRIPTION 	"Status of the RTCP Monitor field for the traffic."
  DEFVAL      	{ enabled }
  ::= { alaQoSActionEntry 79 }
alaQoSActionRTCPDSCP OBJECT-TYPE
  SYNTAX		Integer32
  MAX-ACCESS  	read-create
  STATUS      	current
  DESCRIPTION 	"RTCP DSCP number for the traffic."
  ::= { alaQoSActionEntry 80 }
alaQoSActionRTCPDSCPStatus OBJECT-TYPE
  SYNTAX      INTEGER {
				enabled (1),
		   		disabled (2)
				}	
  MAX-ACCESS  	read-create
  STATUS      	current
  DESCRIPTION 	"Status of the RTCP DSCP field for the traffic."
  DEFVAL      	{ enabled }
  ::= { alaQoSActionEntry 81 }
alaQoSActionTrustDSCP OBJECT-TYPE
  SYNTAX      INTEGER {
				yes (1),
		   		no (2)
				}	
  MAX-ACCESS  	read-create
  STATUS      	current
  DESCRIPTION 	"Trust DSCP status for the traffic."
  DEFVAL      	{ no }
  ::= { alaQoSActionEntry 82 }
alaQoSActionTrustDSCPStatus OBJECT-TYPE
  SYNTAX      INTEGER {
				enabled (1),
		   		disabled (2)
				}	
  MAX-ACCESS  	read-create
  STATUS      	current
  DESCRIPTION 	"Status of the Trust DSCP field for the traffic."
  DEFVAL      	{ enabled }
  ::= { alaQoSActionEntry 83 }

--
-- Definition of action table
--

alaQoSAppliedActionTable OBJECT-TYPE
  SYNTAX      SEQUENCE OF QoSAppliedActionEntry
  MAX-ACCESS  not-accessible
  STATUS      current
  DESCRIPTION "Table of QoS AppliedAction definitions"
  ::= { alaQoSMIBObjects 28 }

alaQoSAppliedActionEntry OBJECT-TYPE
  SYNTAX      QoSAppliedActionEntry
  MAX-ACCESS  not-accessible
  STATUS      current
  DESCRIPTION "Definition of QoS AppliedAction"
  INDEX {
          alaQoSAppliedActionName
        }
  ::= { alaQoSAppliedActionTable 1 }

QoSAppliedActionEntry ::=
  SEQUENCE
  {
    alaQoSAppliedActionName                                 DisplayString,
    alaQoSAppliedActionSource                               INTEGER,
    alaQoSAppliedActionDisposition                          INTEGER,
    alaQoSAppliedActionDropAlgorithm                        INTEGER,
    alaQoSAppliedActionWredMaximumThreshold                 Integer32,
    alaQoSAppliedActionWredMaximumThresholdStatus           INTEGER,
    alaQoSAppliedActionWredMinimumThreshold                 Integer32,
    alaQoSAppliedActionWredMinimumThresholdStatus           INTEGER,
    alaQoSAppliedActionWredMaximumProbability               Integer32,
    alaQoSAppliedActionWredMaximumProbabilityStatus         INTEGER,
    alaQoSAppliedActionMinimumBandwidth                     Integer32,
    alaQoSAppliedActionMinimumBandwidthStatus               INTEGER,
    alaQoSAppliedActionMaximumBandwidth                     Integer32,
    alaQoSAppliedActionMaximumBandwidthStatus               INTEGER,
    alaQoSAppliedActionPeakBandwidth                        Integer32,
    alaQoSAppliedActionPeakBandwidthStatus                  INTEGER,
    alaQoSAppliedActionPriority                             Integer32,
    alaQoSAppliedActionPriorityStatus                       INTEGER,
    alaQoSAppliedActionShared                               INTEGER,
    alaQoSAppliedActionJitter                               Integer32,
    alaQoSAppliedActionJitterStatus                         INTEGER,
    alaQoSAppliedActionLatency                              Integer32,
    alaQoSAppliedActionLatencyStatus                        INTEGER,
    alaQoSAppliedActionMaximumDepth                         Integer32,
    alaQoSAppliedActionMaximumDepthStatus                   INTEGER,
    alaQoSAppliedActionMaximumBuffers                       Integer32,
    alaQoSAppliedActionMaximumBuffersStatus                 INTEGER,
    alaQoSAppliedAction8021p                                Integer32,
    alaQoSAppliedAction8021pStatus                          INTEGER,
    alaQoSAppliedActionTos                                  Integer32,
    alaQoSAppliedActionTosStatus                            INTEGER,
    alaQoSAppliedActionDscp                                 Integer32,
    alaQoSAppliedActionDscpStatus                           INTEGER,
    alaQoSAppliedActionMapFrom                              INTEGER,
    alaQoSAppliedActionMapTo                                INTEGER,
    alaQoSAppliedActionMapGroup                             DisplayString,
    alaQoSAppliedActionMapGroupStatus                       INTEGER,
    alaQoSAppliedActionSourceRewriteIpAddr                  IpAddress,
    alaQoSAppliedActionSourceRewriteIpAddrStatus            INTEGER,
    alaQoSAppliedActionSourceRewriteIpMask                  IpAddress,
    alaQoSAppliedActionSourceRewriteNetworkGroup            DisplayString,
    alaQoSAppliedActionSourceRewriteNetworkGroupStatus      INTEGER,
    alaQoSAppliedActionDestinationRewriteIpAddr             IpAddress,
    alaQoSAppliedActionDestinationRewriteIpAddrStatus       INTEGER,
    alaQoSAppliedActionDestinationRewriteIpMask             IpAddress,
    alaQoSAppliedActionDestinationRewriteNetworkGroup       DisplayString,
    alaQoSAppliedActionDestinationRewriteNetworkGroupStatus INTEGER,
    alaQoSAppliedActionLoadBalanceGroup                     DisplayString,
    alaQoSAppliedActionLoadBalanceGroupStatus               INTEGER,
    alaQoSAppliedActionPermanentGatewayIpAddr               IpAddress,
    alaQoSAppliedActionPermanentGatewayIpAddrStatus         INTEGER,
    alaQoSAppliedActionAlternateGatewayIpAddr               IpAddress,
    alaQoSAppliedActionAlternateGatewayIpAddrStatus         INTEGER,
    alaQoSAppliedActionRowStatus                            RowStatus,
    alaQoSAppliedActionMinimumDepth                         Integer32,
    alaQoSAppliedActionMinimumDepthStatus                   INTEGER,
    alaQoSAppliedActionVPNAccess                            INTEGER,
    alaQoSAppliedActionNocache                              INTEGER,
    alaQoSAppliedActionPortdisable                          INTEGER,
    alaQoSAppliedActionRedirectSlot                         Integer32,
    alaQoSAppliedActionRedirectSlotStatus                   INTEGER,
    alaQoSAppliedActionRedirectPort                         Integer32,
    alaQoSAppliedActionRedirectAgg                          Integer32,
    alaQoSAppliedActionRedirectAggStatus                    INTEGER,
    alaQoSAppliedActionMirrorSlot                           Integer32,
    alaQoSAppliedActionMirrorPort                           Integer32,
    alaQoSAppliedActionMirrorMode                           INTEGER,
    alaQoSAppliedActionMirrorModeStatus                     INTEGER,
    alaQoSAppliedActionCIR                                  Integer32,
    alaQoSAppliedActionCIRStatus                            INTEGER,
    alaQoSAppliedActionCBS                                  Integer32,
    alaQoSAppliedActionCBSStatus			    INTEGER,
    alaQoSAppliedActionPIR                                  Integer32,
    alaQoSAppliedActionPIRStatus			    INTEGER,
    alaQoSAppliedActionPBS                                  Integer32,
    alaQoSAppliedActionPBSStatus			    INTEGER,
    alaQoSAppliedActionCounterColor                         INTEGER,
    alaQoSAppliedActionRTCPMonitor                          INTEGER,
    alaQoSAppliedActionRTCPMonitorStatus                    INTEGER,
    alaQoSAppliedActionRTCPDSCP                             Integer32,
    alaQoSAppliedActionRTCPDSCPStatus                       INTEGER,
    alaQoSAppliedActionTrustDSCP                            INTEGER,
    alaQoSAppliedActionTrustDSCPStatus                      INTEGER
  }

alaQoSAppliedActionName OBJECT-TYPE
  SYNTAX      DisplayString (SIZE(0..31))
  MAX-ACCESS  not-accessible
  STATUS      current
  DESCRIPTION "Name of action"
  ::= { alaQoSAppliedActionEntry 1 }

alaQoSAppliedActionSource OBJECT-TYPE
  SYNTAX      INTEGER {
                ldap (1),
                cli (2),
                blt (3),
                api (4),
                imp (5)
              }
  MAX-ACCESS  read-only
  STATUS      current
  DESCRIPTION "What entity created the action."
  ::= { alaQoSAppliedActionEntry 2 }

alaQoSAppliedActionDisposition OBJECT-TYPE
  SYNTAX      INTEGER {
                accept (1),
                drop (2),
                deny (3)
              }
  MAX-ACCESS  read-only
  STATUS      current
  DESCRIPTION "Disposition of traffic using the action.
               Use to filter out unwanted traffic."
  ::= { alaQoSAppliedActionEntry 3 }

alaQoSAppliedActionDropAlgorithm OBJECT-TYPE
  SYNTAX      INTEGER {
                tail (1),
                wred (2)
              }
  MAX-ACCESS  read-only
  STATUS      current
  DESCRIPTION "Which drop algorithm should be used to discard traffic when
               oversubscribed."
  ::= { alaQoSAppliedActionEntry 4 }

alaQoSAppliedActionWredMaximumThreshold OBJECT-TYPE
  SYNTAX      Integer32
  MAX-ACCESS  read-only
  STATUS      current
  DESCRIPTION "Bandwidth at which WRED should discard most traffic."
  ::= { alaQoSAppliedActionEntry 5 }

alaQoSAppliedActionWredMaximumThresholdStatus OBJECT-TYPE
  SYNTAX      INTEGER {
                enabled (1),
                disabled (2)
              }
  MAX-ACCESS  read-only
  STATUS      current
  DESCRIPTION "Status field indicating whether WRED maximum threshold
               is specified(enabled) or not(disabled)."
  ::= { alaQoSAppliedActionEntry 6 }

alaQoSAppliedActionWredMinimumThreshold OBJECT-TYPE
  SYNTAX      Integer32
  MAX-ACCESS  read-only
  STATUS      current
  DESCRIPTION "Bandwidth at which WRED should start to discard traffic."
  ::= { alaQoSAppliedActionEntry 7 }

alaQoSAppliedActionWredMinimumThresholdStatus OBJECT-TYPE
  SYNTAX      INTEGER {
                enabled (1),
                disabled (2)
              }
  MAX-ACCESS  read-only
  STATUS      current
  DESCRIPTION "Status field indicating whether WRED minimum threshold
               is specified(enabled) or not(disabled)."
  ::= { alaQoSAppliedActionEntry 8 }

alaQoSAppliedActionWredMaximumProbability OBJECT-TYPE
  SYNTAX      Integer32
  MAX-ACCESS  read-only
  STATUS      current
  DESCRIPTION "Probabilty that traffic will be dropped at WRED
               maximum threshold."
  ::= { alaQoSAppliedActionEntry 9 }

alaQoSAppliedActionWredMaximumProbabilityStatus OBJECT-TYPE
  SYNTAX      INTEGER {
                enabled (1),
                disabled (2)
              }
  MAX-ACCESS  read-only
  STATUS      current
  DESCRIPTION "Status field indicating whether WRED maximum probability
               is specified(enabled) or not(disabled)."
  ::= { alaQoSAppliedActionEntry 10 }

alaQoSAppliedActionMinimumBandwidth OBJECT-TYPE
  SYNTAX      Integer32
  MAX-ACCESS  read-only
  STATUS      current
  DESCRIPTION "Minimum bandwidth (Kbits/sec) to guarantee for traffic"
  ::= { alaQoSAppliedActionEntry 11 }

alaQoSAppliedActionMinimumBandwidthStatus OBJECT-TYPE
  SYNTAX      INTEGER {
                enabled (1),
                disabled (2)
              }
  MAX-ACCESS  read-only
  STATUS      current
  DESCRIPTION "Status field indicating whether minimum bandwidth
               is specified(enabled) or not(disabled)."
  ::= { alaQoSAppliedActionEntry 12 }

alaQoSAppliedActionMaximumBandwidth OBJECT-TYPE
  SYNTAX      Integer32
  MAX-ACCESS  read-only
  STATUS      current
  DESCRIPTION "Maximum bandwidth (Kbits/sec) allowed for traffic"
  ::= { alaQoSAppliedActionEntry 13 }

alaQoSAppliedActionMaximumBandwidthStatus OBJECT-TYPE
  SYNTAX      INTEGER {
                enabled (1),
                disabled (2)
              }
  MAX-ACCESS  read-only
  STATUS      current
  DESCRIPTION "Status field indicating whether maximum bandwidth
               is specified(enabled) or not(disabled)."
  ::= { alaQoSAppliedActionEntry 14 }

alaQoSAppliedActionPeakBandwidth OBJECT-TYPE
  SYNTAX      Integer32
  MAX-ACCESS  read-only
  STATUS      current
  DESCRIPTION "Peak bandwidth (Kbits/sec) allowed for traffic"
  ::= { alaQoSAppliedActionEntry 15 }

alaQoSAppliedActionPeakBandwidthStatus OBJECT-TYPE
  SYNTAX      INTEGER {
                enabled (1),
                disabled (2)
              }
  MAX-ACCESS  read-only
  STATUS      current
  DESCRIPTION "Status field indicating whether peak bandwidth
               is specified(enabled) or not(disabled)."
  ::= { alaQoSAppliedActionEntry 16 }

alaQoSAppliedActionPriority OBJECT-TYPE
  SYNTAX      Integer32 (0..7)
  MAX-ACCESS  read-only
  STATUS      current
  DESCRIPTION "Internal and queueing priority to use for traffic."
  ::= { alaQoSAppliedActionEntry 17 }

alaQoSAppliedActionPriorityStatus OBJECT-TYPE
  SYNTAX      INTEGER {
                enabled (1),
                disabled (2)
              }
  MAX-ACCESS  read-only
  STATUS      current
  DESCRIPTION "Status field indicating whether priority
               is specified(enabled) or not(disabled)."
  ::= { alaQoSAppliedActionEntry 18 }

alaQoSAppliedActionShared OBJECT-TYPE
  SYNTAX      INTEGER {
                yes (1),
                no (2)
              }
  MAX-ACCESS  read-only
  STATUS      current
  DESCRIPTION "When enabled, try and share any resources
               (queues/limiters/descriptors) when more than one policy uses
               the same action."
  ::= { alaQoSAppliedActionEntry 19 }

alaQoSAppliedActionJitter OBJECT-TYPE
  SYNTAX      Integer32
  MAX-ACCESS  read-only
  STATUS      current
  DESCRIPTION "Maximum jitter to allow for traffic."
  ::= { alaQoSAppliedActionEntry 20 }

alaQoSAppliedActionJitterStatus OBJECT-TYPE
  SYNTAX      INTEGER {
                enabled (1),
                disabled (2)
              }
  MAX-ACCESS  read-only
  STATUS      current
  DESCRIPTION "Status field indicating whether jitter
               is specified(enabled) or not(disabled)."
  ::= { alaQoSAppliedActionEntry 21 }

alaQoSAppliedActionLatency OBJECT-TYPE
  SYNTAX      Integer32
  MAX-ACCESS  read-only
  STATUS      current
  DESCRIPTION "Maximum latency to allow for traffic."
  ::= { alaQoSAppliedActionEntry 22 }

alaQoSAppliedActionLatencyStatus OBJECT-TYPE
  SYNTAX      INTEGER {
                enabled (1),
                disabled (2)
              }
  MAX-ACCESS  read-only
  STATUS      current
  DESCRIPTION "Status field indicating whether latency
               is specified(enabled) or not(disabled)."
  ::= { alaQoSAppliedActionEntry 23 }

alaQoSAppliedActionMaximumDepth OBJECT-TYPE
  SYNTAX      Integer32
  MAX-ACCESS  read-only
  STATUS      current
  DESCRIPTION "Maximum depth (Kbytes) of queues for traffic.
               Used for EBS in tri-color marker applications."
  ::= { alaQoSAppliedActionEntry 24 }

alaQoSAppliedActionMaximumDepthStatus OBJECT-TYPE
  SYNTAX      INTEGER {
                enabled (1),
                disabled (2)
              }
  MAX-ACCESS  read-only
  STATUS      current
  DESCRIPTION "Status field indicating whether maximum depth
               is specified(enabled) or not(disabled)."
  ::= { alaQoSAppliedActionEntry 25 }

alaQoSAppliedActionMaximumBuffers OBJECT-TYPE
  SYNTAX      Integer32 (0..2047)
  MAX-ACCESS  read-only
  STATUS      current
  DESCRIPTION "Maxmimum buffers for queues for traffic."
  ::= { alaQoSAppliedActionEntry 26 }

alaQoSAppliedActionMaximumBuffersStatus OBJECT-TYPE
  SYNTAX      INTEGER {
                enabled (1),
                disabled (2)
              }
  MAX-ACCESS  read-only
  STATUS      current
  DESCRIPTION "Status field indicating whether maximum buffers
               is specified(enabled) or not(disabled)."
  ::= { alaQoSAppliedActionEntry 27 }

alaQoSAppliedAction8021p OBJECT-TYPE
  SYNTAX      Integer32 (0..7)
  MAX-ACCESS  read-only
  STATUS      current
  DESCRIPTION "802.1p value to stamp on traffic."
  ::= { alaQoSAppliedActionEntry 28 }

alaQoSAppliedAction8021pStatus OBJECT-TYPE
  SYNTAX      INTEGER {
                enabled (1),
                disabled (2)
              }
  MAX-ACCESS  read-only
  STATUS      current
  DESCRIPTION "Status field indicating whether 802.1p
               is specified(enabled) or not(disabled)."
  ::= { alaQoSAppliedActionEntry 29 }

alaQoSAppliedActionTos OBJECT-TYPE
  SYNTAX      Integer32 (0..7)
  MAX-ACCESS  read-only
  STATUS      current
  DESCRIPTION "TOS value to stamp on traffic. (High 3 bits of TOS byte)"
  ::= { alaQoSAppliedActionEntry 30 }

alaQoSAppliedActionTosStatus OBJECT-TYPE
  SYNTAX      INTEGER {
                enabled (1),
                disabled (2)
              }
  MAX-ACCESS  read-only
  STATUS      current
  DESCRIPTION "Status field indicating whether TOS
               is specified(enabled) or not(disabled)."
  ::= { alaQoSAppliedActionEntry 31 }

alaQoSAppliedActionDscp OBJECT-TYPE
  SYNTAX      Integer32 (0..63)
  MAX-ACCESS  read-only
  STATUS      current
  DESCRIPTION "TOS value to stamp on traffic. (High 6 bits of TOS byte)"
  ::= { alaQoSAppliedActionEntry 32 }

alaQoSAppliedActionDscpStatus OBJECT-TYPE
  SYNTAX      INTEGER {
                enabled (1),
                disabled (2)
              }
  MAX-ACCESS  read-only
  STATUS      current
  DESCRIPTION "Status field indicating whether DSCP
               is specified(enabled) or not(disabled)."
  ::= { alaQoSAppliedActionEntry 33 }

alaQoSAppliedActionMapFrom OBJECT-TYPE
  SYNTAX      INTEGER {
                b8021p (1),
                tos (2),
                dscp (3)
              }
  MAX-ACCESS  read-only
  STATUS      current
  DESCRIPTION "What field to use as key for mapping 802.1p/TOS/DSCP priorities"
  ::= { alaQoSAppliedActionEntry 34 }

alaQoSAppliedActionMapTo OBJECT-TYPE
  SYNTAX      INTEGER {
                b8021p (1),
                tos (2),
                dscp (3)
              }
  MAX-ACCESS  read-only
  STATUS      current
  DESCRIPTION "What field to rewrite due to remapping 802.1p/TOS/DSCP
               priorities"
  ::= { alaQoSAppliedActionEntry 35 }

alaQoSAppliedActionMapGroup OBJECT-TYPE
  SYNTAX      DisplayString (SIZE(0..31))
  MAX-ACCESS  read-only
  STATUS      current
  DESCRIPTION "Name of the map group to use when remapping 802.1p/TOS/DSCP
               priorities."
  ::= { alaQoSAppliedActionEntry 36 }

alaQoSAppliedActionMapGroupStatus OBJECT-TYPE
  SYNTAX      INTEGER {
                enabled (1),
                disabled (2)
              }
  MAX-ACCESS  read-only
  STATUS      current
  DESCRIPTION "Status field indicating whether a map group
               is specified(enabled) or not(disabled)."
  ::= { alaQoSAppliedActionEntry 37 }

alaQoSAppliedActionSourceRewriteIpAddr OBJECT-TYPE
  SYNTAX      IpAddress
  MAX-ACCESS  read-only
  STATUS      current
  DESCRIPTION "Source IP address to rewrite on traffic."
  ::= { alaQoSAppliedActionEntry 38 }

alaQoSAppliedActionSourceRewriteIpAddrStatus OBJECT-TYPE
  SYNTAX      INTEGER {
                enabled (1),
                disabled (2)
              }
  MAX-ACCESS  read-only
  STATUS      current
  DESCRIPTION "Status field indicating whether source rewrite IP address & mask
               is specified(enabled) or not(disabled)."
  ::= { alaQoSAppliedActionEntry 39 }

alaQoSAppliedActionSourceRewriteIpMask OBJECT-TYPE
  SYNTAX      IpAddress
  MAX-ACCESS  read-only
  STATUS      current
  DESCRIPTION "Source rewrite IP mask to determine how much of
               source IP to rewrite."
  ::= { alaQoSAppliedActionEntry 40 }

alaQoSAppliedActionSourceRewriteNetworkGroup OBJECT-TYPE
  SYNTAX      DisplayString (SIZE(0..31))
  MAX-ACCESS  read-only
  STATUS      current
  DESCRIPTION "Name of network group containing source address/masks to rewrite
               on traffic.  Must be a one to on correspondence with
               source network group entries in the condition."
  ::= { alaQoSAppliedActionEntry 41 }

alaQoSAppliedActionSourceRewriteNetworkGroupStatus OBJECT-TYPE
  SYNTAX      INTEGER {
                enabled (1),
                disabled (2)
              }
  MAX-ACCESS  read-only
  STATUS      current
  DESCRIPTION "Status field indicating whether source rewrite network group
               is specified(enabled) or not(disabled)."
  ::= { alaQoSAppliedActionEntry 42 }

alaQoSAppliedActionDestinationRewriteIpAddr OBJECT-TYPE
  SYNTAX      IpAddress
  MAX-ACCESS  read-only
  STATUS      current
  DESCRIPTION "Destination IP address to rewrite on traffic."
  ::= { alaQoSAppliedActionEntry 43 }

alaQoSAppliedActionDestinationRewriteIpAddrStatus OBJECT-TYPE
  SYNTAX      INTEGER {
                enabled (1),
                disabled (2)
              }
  MAX-ACCESS  read-only
  STATUS      current
  DESCRIPTION "Status field indicating whether destination rewrite IP address
               & mask is specified(enabled) or not(disabled)."
  ::= { alaQoSAppliedActionEntry 44 }

alaQoSAppliedActionDestinationRewriteIpMask OBJECT-TYPE
  SYNTAX      IpAddress
  MAX-ACCESS  read-only
  STATUS      current
  DESCRIPTION "Destination rewrite IP mask to determine how much of
               destination IP to rewrite."
  ::= { alaQoSAppliedActionEntry 45 }

alaQoSAppliedActionDestinationRewriteNetworkGroup OBJECT-TYPE
  SYNTAX      DisplayString (SIZE(0..31))
  MAX-ACCESS  read-only
  STATUS      current
  DESCRIPTION "Name of network group containing destination address/masks to
               rewrite on traffic.  Must be a one to on correspondence with
               destination network group entries in the condition."
  ::= { alaQoSAppliedActionEntry 46 }

alaQoSAppliedActionDestinationRewriteNetworkGroupStatus OBJECT-TYPE
  SYNTAX      INTEGER {
                enabled (1),
                disabled (2)
              }
  MAX-ACCESS  read-only
  STATUS      current
  DESCRIPTION "Status field indicating whether destination rewrite network
               group is specified(enabled) or not(disabled)."
  ::= { alaQoSAppliedActionEntry 47 }

alaQoSAppliedActionLoadBalanceGroup OBJECT-TYPE
  SYNTAX      DisplayString (SIZE(0..23))
  MAX-ACCESS  read-only
  STATUS      current
  DESCRIPTION "Name of load balance group to use for traffic"
  ::= { alaQoSAppliedActionEntry 48 }

alaQoSAppliedActionLoadBalanceGroupStatus OBJECT-TYPE
  SYNTAX      INTEGER {
                enabled (1),
                disabled (2)
              }
  MAX-ACCESS  read-only
  STATUS      current
  DESCRIPTION "Status field indicating whether load balanace group
               is specified(enabled) or not(disabled)."
  ::= { alaQoSAppliedActionEntry 49 }

alaQoSAppliedActionPermanentGatewayIpAddr OBJECT-TYPE
  SYNTAX      IpAddress
  MAX-ACCESS  read-only
  STATUS      current
  DESCRIPTION "Next hop gateway to use for traffic"
  ::= { alaQoSAppliedActionEntry 50 }

alaQoSAppliedActionPermanentGatewayIpAddrStatus OBJECT-TYPE
  SYNTAX      INTEGER {
                enabled (1),
                disabled (2)
              }
  MAX-ACCESS  read-only
  STATUS      current
  DESCRIPTION "Status field indicating whether permanent gateway IP address
               is specified(enabled) or not(disabled)."
  ::= { alaQoSAppliedActionEntry 51 }

alaQoSAppliedActionAlternateGatewayIpAddr OBJECT-TYPE
  SYNTAX      IpAddress
  MAX-ACCESS  read-only
  STATUS      current
  DESCRIPTION "Next hop gateway to use for traffic that doesn't have an
               explicit route.  Use this gateway instead of default routes."
  ::= { alaQoSAppliedActionEntry 52 }

alaQoSAppliedActionAlternateGatewayIpAddrStatus OBJECT-TYPE
  SYNTAX      INTEGER {
                enabled (1),
                disabled (2)
              }
  MAX-ACCESS  read-only
  STATUS      current
  DESCRIPTION "Status field indicating whether alternate gateway IP address
               is specified(enabled) or not(disabled)."
  ::= { alaQoSAppliedActionEntry 53 }

alaQoSAppliedActionRowStatus OBJECT-TYPE
  SYNTAX      RowStatus
  MAX-ACCESS  read-only
  STATUS      current
  DESCRIPTION "Used to create/delete actions according to the
               RowStatus convention"
  ::= { alaQoSAppliedActionEntry 54 }

alaQoSAppliedActionMinimumDepth OBJECT-TYPE
  SYNTAX      Integer32
  MAX-ACCESS  read-only
  STATUS      current
  DESCRIPTION "Minimum depth (Kbytes) of queues for traffic.
               Used for CBS in tri-color marker applications."
  ::= { alaQoSAppliedActionEntry 55 }

alaQoSAppliedActionMinimumDepthStatus OBJECT-TYPE
  SYNTAX      INTEGER {
                enabled (1),
                disabled (2)
              }
  MAX-ACCESS  read-only
  STATUS      current
  DESCRIPTION "Status field indicating whether minimum depth
               is specified(enabled) or not(disabled)."
  ::= { alaQoSAppliedActionEntry 56 }

alaQoSAppliedActionVPNAccess OBJECT-TYPE
  SYNTAX      INTEGER {
                protect (1),
                bypass (2),
                drop (3)
              }
  MAX-ACCESS  read-only
  STATUS      current
  DESCRIPTION "How to encrypt traffic"
  ::= { alaQoSAppliedActionEntry 57 }

alaQoSAppliedActionNocache OBJECT-TYPE
  SYNTAX      INTEGER {
                yes (1),
                no (2)
              }
  MAX-ACCESS  read-only
  STATUS      current
  DESCRIPTION "When enabled, don't make hardware entries for matching flows."
  ::= { alaQoSAppliedActionEntry 58 }

alaQoSAppliedActionPortdisable OBJECT-TYPE
  SYNTAX      INTEGER {
                yes (1),
                no (2)
              }
  MAX-ACCESS  read-only
  STATUS      current
  DESCRIPTION "When enabled, disable the physical source port of the traffic."
  ::= { alaQoSAppliedActionEntry 59 }

alaQoSAppliedActionRedirectSlot OBJECT-TYPE
  SYNTAX      Integer32 (0..16)
  MAX-ACCESS  read-only
  STATUS      current
  DESCRIPTION "Destination physical slot for redirected traffic"
  ::= { alaQoSAppliedActionEntry 60 }

alaQoSAppliedActionRedirectSlotStatus OBJECT-TYPE
  SYNTAX      INTEGER {
                enabled (1),
                disabled (2)
              }
  MAX-ACCESS  read-only
  STATUS      current
  DESCRIPTION "Status for alaQoSAppliedActionRedirectSlotStatus field"
  ::= { alaQoSAppliedActionEntry 61 }

alaQoSAppliedActionRedirectPort OBJECT-TYPE
  SYNTAX      Integer32 (1..52)
  MAX-ACCESS  read-only
  STATUS      current
  DESCRIPTION "Destination physical port for redirected traffic"
  ::= { alaQoSAppliedActionEntry 62 }

alaQoSAppliedActionRedirectAgg OBJECT-TYPE
  SYNTAX      Integer32 (0..32)
  MAX-ACCESS  read-only
  STATUS      current
  DESCRIPTION "Destination linkagg for redirected traffic"
  ::= { alaQoSAppliedActionEntry 63 }

alaQoSAppliedActionRedirectAggStatus OBJECT-TYPE
  SYNTAX      INTEGER {
                enabled (1),
                disabled (2)
              }
  MAX-ACCESS  read-only
  STATUS      current
  DESCRIPTION "Status for alaQoSAppliedActionRedirectAggStatus field"
  ::= { alaQoSAppliedActionEntry 64 }

alaQoSAppliedActionMirrorSlot OBJECT-TYPE
  SYNTAX      Integer32 (0..16)
  MAX-ACCESS  read-only
  STATUS      current
  DESCRIPTION "Destination physical slot for mirrored traffic"
  ::= { alaQoSAppliedActionEntry 65 }

alaQoSAppliedActionMirrorPort OBJECT-TYPE
  SYNTAX      Integer32 (1..52)
  MAX-ACCESS  read-only
  STATUS      current
  DESCRIPTION "Destination physical port for mirrored traffic"
  ::= { alaQoSAppliedActionEntry 66 }

alaQoSAppliedActionMirrorMode OBJECT-TYPE
  SYNTAX      INTEGER {
                ingress(1),
                egress(2),
                both(3)
              }
  MAX-ACCESS  read-only
  STATUS      current
  DESCRIPTION "Mirroring mode"
  DEFVAL      { ingress }
  ::= { alaQoSAppliedActionEntry 67 }

alaQoSAppliedActionMirrorModeStatus OBJECT-TYPE
  SYNTAX      INTEGER {
                enabled (1),
                disabled (2)
              }
  MAX-ACCESS  read-only
  STATUS      current
  DESCRIPTION "Status for alaQoSAppliedActionMirrorMode field"
  ::= { alaQoSAppliedActionEntry 68 }

alaQoSAppliedActionCIR OBJECT-TYPE
  SYNTAX      Integer32
  UNITS       "kilobits per second" 
  MAX-ACCESS  read-create
  STATUS      current
  DESCRIPTION "Committed Information Rate - bandwidth values in kilobits per second."
  DEFVAL      { 0 }
  ::= { alaQoSAppliedActionEntry 69 }

alaQoSAppliedActionCIRStatus OBJECT-TYPE
  SYNTAX      INTEGER {
                enabled (1),
                disabled (2)
              }
  MAX-ACCESS  read-create
  STATUS      current
  DESCRIPTION "Status field indicating whether CIR value is specified(enabled)
              or not(disabled)."
  DEFVAL      { disabled }
  ::= { alaQoSAppliedActionEntry 70 }

alaQoSAppliedActionCBS OBJECT-TYPE
  SYNTAX      Integer32(0 .. 2147450880)
  MAX-ACCESS  read-create
  STATUS      current
  DESCRIPTION "Committed Burst Size - bucket size in byte." 
  DEFVAL      { 0 }
  ::= { alaQoSAppliedActionEntry 71 }

alaQoSAppliedActionCBSStatus OBJECT-TYPE
  SYNTAX      INTEGER {
                enabled (1),
                disabled (2)
              }
  MAX-ACCESS  read-create
  STATUS      current
  DESCRIPTION "Status field indicating whether CBS value is specified(enabled)
              or not(disabled)."
  DEFVAL      { disabled }
  ::= { alaQoSAppliedActionEntry 72 }

alaQoSAppliedActionPIR OBJECT-TYPE
  SYNTAX      Integer32
  UNITS       "kilobits per second" 
  MAX-ACCESS  read-create
  STATUS      current
  DESCRIPTION "Peak Information Rate - bandwidth values in kilobits per second."
  DEFVAL      { 0 }
  ::= { alaQoSAppliedActionEntry 73 }

alaQoSAppliedActionPIRStatus OBJECT-TYPE
  SYNTAX      INTEGER {
                enabled (1),
                disabled (2)
              }
  MAX-ACCESS  read-create
  STATUS      current
  DESCRIPTION "Status field indicating whether PIR value is specified(enabled)
              or not(disabled)."
  DEFVAL      { disabled }
  ::= { alaQoSAppliedActionEntry 74 }

alaQoSAppliedActionPBS OBJECT-TYPE
  SYNTAX      Integer32(0 .. 2147450880)
  MAX-ACCESS  read-create
  STATUS      current
  DESCRIPTION "Peak Burst Size - bucket size in byte."
  DEFVAL      { 0 }
  ::= { alaQoSAppliedActionEntry 75 }

alaQoSAppliedActionPBSStatus OBJECT-TYPE
  SYNTAX      INTEGER {
                enabled (1),
                disabled (2)
              }
  MAX-ACCESS  read-create
  STATUS      current
  DESCRIPTION "Status field indicating whether PBS value is specified(enabled)
              or not(disabled)."
  DEFVAL      { disabled }
  ::= { alaQoSAppliedActionEntry 76 }

alaQoSAppliedActionCounterColor OBJECT-TYPE
  SYNTAX      INTEGER {
	                    rednonred (1),
	                    greennongreen (2),
	                    greenred (3),
	                    greenyellow (4),
	                    redyellow (5)
                      }
  MAX-ACCESS  read-create
  STATUS      current
  DESCRIPTION "Specifies the color mode for the counters which will be used for sr/trTCM."
  DEFVAL      { redyellow }
  ::= { alaQoSAppliedActionEntry 77 }
alaQoSAppliedActionRTCPMonitor OBJECT-TYPE
  SYNTAX      INTEGER {
				enable (1),
		   		disable (2)
				}	
  MAX-ACCESS  	read-create
  STATUS      	current
  DESCRIPTION 	"RTCP Monitor status for the traffic."
  DEFVAL      	{ enable }
  ::= { alaQoSAppliedActionEntry 78 }
alaQoSAppliedActionRTCPMonitorStatus OBJECT-TYPE
  SYNTAX      INTEGER {
				enable (1),
		   		disable (2)
				}	
  MAX-ACCESS  	read-create
  STATUS      	current
  DESCRIPTION 	"Status of the RTCP Monitor field for the traffic."
  DEFVAL      	{ enable }
  ::= { alaQoSAppliedActionEntry 79 }
alaQoSAppliedActionRTCPDSCP OBJECT-TYPE
  SYNTAX		Integer32
  MAX-ACCESS  	read-create
  STATUS      	current
  DESCRIPTION 	"RTCP DSCP number for the traffic."
  ::= { alaQoSAppliedActionEntry 80 }
alaQoSAppliedActionRTCPDSCPStatus OBJECT-TYPE
  SYNTAX      INTEGER {
				enable (1),
		   		disable (2)
				}	
  MAX-ACCESS  	read-create
  STATUS      	current
  DESCRIPTION 	"Status of the RTCP DSCP field for the traffic."
  ::= { alaQoSAppliedActionEntry 81 }
alaQoSAppliedActionTrustDSCP OBJECT-TYPE
  SYNTAX      INTEGER {
				yes (1),
		   		no (2)
				}	
  MAX-ACCESS  	read-create
  STATUS      	current
  DESCRIPTION 	"Trust DSCP status for the traffic."
  DEFVAL      	{ no }
  ::= { alaQoSAppliedActionEntry 82 }
alaQoSAppliedActionTrustDSCPStatus OBJECT-TYPE
  SYNTAX      INTEGER {
				enable (1),
		   		disable (2)
				}	
  MAX-ACCESS  	read-create
  STATUS      	current
  DESCRIPTION 	"Status of the Trust DSCP field for the traffic."
  DEFVAL      	{ enable }
  ::= { alaQoSAppliedActionEntry 83 }

--
-- Definition of port table
--

alaQoSPortTable OBJECT-TYPE
  SYNTAX      SEQUENCE OF QoSPortEntry
  MAX-ACCESS  not-accessible
  STATUS      current
  DESCRIPTION "Table of QoS Port definitions"
  ::= { alaQoSMIBObjects 29 }

alaQoSPortEntry OBJECT-TYPE
  SYNTAX      QoSPortEntry
  MAX-ACCESS  not-accessible
  STATUS      current
  DESCRIPTION "Definition of QoS Port"
  INDEX {
          alaQoSPortSlot,
          alaQoSPortPort
        }
  ::= { alaQoSPortTable 1 }

QoSPortEntry ::=
  SEQUENCE
  {
    alaQoSPortSlot                                          Integer32,
    alaQoSPortPort                                          Integer32,
    alaQoSPortEnabled                                       INTEGER,
    alaQoSPortAppliedEnabled                                INTEGER,
    alaQoSPortInterfaceType                                 INTEGER,
    alaQoSPortTrusted                                       INTEGER,
    alaQoSPortDefault8021p                                  Integer32,
    alaQoSPortDefaultDSCP                                   Integer32,
    alaQoSPortMaximumReservedBandwidth                      Integer32,
    alaQoSPortMaximumReservedBandwidthStatus                INTEGER,
    alaQoSPortAppliedMaximumReservedBandwidth               Integer32,
    alaQoSPortAppliedMaximumReservedBandwidthStatus         INTEGER,
    alaQoSPortMaximumSignalledBandwidth                     Integer32,
    alaQoSPortMaximumSignalledBandwidthStatus               INTEGER,
    alaQoSPortAppliedMaximumSignalledBandwidth              Integer32,
    alaQoSPortAppliedMaximumSignalledBandwidthStatus        INTEGER,
    alaQoSPortDefaultQueues                                 Integer32,
    alaQoSPortAppliedDefaultQueues                          Integer32,
    alaQoSPortMaximumDefaultBandwidth                       Integer32,
    alaQoSPortMaximumDefaultBandwidthStatus                 INTEGER,
    alaQoSPortAppliedMaximumDefaultBandwidth                Integer32,
    alaQoSPortAppliedMaximumDefaultBandwidthStatus          INTEGER,
    alaQoSPortMaximumDefaultDepth                           Integer32,
    alaQoSPortMaximumDefaultDepthStatus                     INTEGER,
    alaQoSPortAppliedMaximumDefaultDepth                    Integer32,
    alaQoSPortAppliedMaximumDefaultDepthStatus              INTEGER,
    alaQoSPortMaximumDefaultBuffers                         Integer32,
    alaQoSPortMaximumDefaultBuffersStatus                   INTEGER,
    alaQoSPortAppliedMaximumDefaultBuffers                  Integer32,
    alaQoSPortAppliedMaximumDefaultBuffersStatus            INTEGER,
    alaQoSPortReset                                         INTEGER,
    alaQoSPortPhysicalBandwidth                             Integer32,
    alaQoSPortReservedBandwidth                             Integer32,
    alaQoSPortSignalledBandwidth                            Integer32,
    alaQoSPortCurrentBandwidth                              Integer32,
    alaQoSPortDefaultQidLow                                 Integer32,
    alaQoSPortDefaultQidMedium                              Integer32,
    alaQoSPortDefaultQidHigh                                Integer32,
    alaQoSPortDefaultQidUrgent                              Integer32,
    alaQoSPortFloodQid                                      Integer32,
    alaQoSPortQueues                                        Integer32,
    alaQoSPortQueuesCreated                                 Integer32,
    alaQoSPortQueuesFailed                                  Integer32,
    alaQoSPortQueuesPreempted                               Integer32,
    alaQoSPortRowStatus                                     RowStatus,
    alaQoSPortFirPrio0EnqBytes                              Counter64,
    alaQoSPortFirPrio0DeqBytes                              Counter64,
    alaQoSPortFirPrio0EnqPkts                               Counter64,
    alaQoSPortFirPrio0DeqPkts                               Counter64,
    alaQoSPortFirPrio0QidDiscardPkts                        Counter64,
    alaQoSPortFirPrio0WredDiscardPkts                       Counter64,
    alaQoSPortFirPrio0OverflowDiscardPkts                   Counter64,
    alaQoSPortFirPrio1EnqBytes                              Counter64,
    alaQoSPortFirPrio1DeqBytes                              Counter64,
    alaQoSPortFirPrio1EnqPkts                               Counter64,
    alaQoSPortFirPrio1DeqPkts                               Counter64,
    alaQoSPortFirPrio1QidDiscardPkts                        Counter64,
    alaQoSPortFirPrio1WredDiscardPkts                       Counter64,
    alaQoSPortFirPrio1OverflowDiscardPkts                   Counter64,
    alaQoSPortFirPrio2EnqBytes                              Counter64,
    alaQoSPortFirPrio2DeqBytes                              Counter64,
    alaQoSPortFirPrio2EnqPkts                               Counter64,
    alaQoSPortFirPrio2DeqPkts                               Counter64,
    alaQoSPortFirPrio2QidDiscardPkts                        Counter64,
    alaQoSPortFirPrio2WredDiscardPkts                       Counter64,
    alaQoSPortFirPrio2OverflowDiscardPkts                   Counter64,
    alaQoSPortFirPrio3EnqBytes                              Counter64,
    alaQoSPortFirPrio3DeqBytes                              Counter64,
    alaQoSPortFirPrio3EnqPkts                               Counter64,
    alaQoSPortFirPrio3DeqPkts                               Counter64,
    alaQoSPortFirPrio3QidDiscardPkts                        Counter64,
    alaQoSPortFirPrio3WredDiscardPkts                       Counter64,
    alaQoSPortFirPrio3OverflowDiscardPkts                   Counter64,
    alaQoSPortDefaultClassification                         INTEGER,
    alaQoSPortLowPriorityWeight                             Integer32,
    alaQoSPortMediumPriorityWeight                          Integer32,
    alaQoSPortHighPriorityWeight                            Integer32,
    alaQoSPortUrgentPriorityWeight                          Integer32,
    alaQoSPortMaximumBandwidth                              Integer32,
    alaQoSPortMaximumBandwidthStatus                        INTEGER,
    alaQoSPortEnqueuingThresholdP0Lower                     Integer32,
    alaQoSPortEnqueuingThresholdP0Upper                     Integer32,
    alaQoSPortEnqueuingThresholdP1Lower                     Integer32,
    alaQoSPortEnqueuingThresholdP1Upper                     Integer32,
    alaQoSPortEnqueuingThresholdP2Lower                     Integer32,
    alaQoSPortEnqueuingThresholdP2Upper                     Integer32,
    alaQoSPortEnqueuingThresholdP3Lower                     Integer32,
    alaQoSPortEnqueuingThresholdP3Upper                     Integer32,
    alaQoSPortEnqueuingThresholdStatus                      INTEGER,
    alaQoSPortHighDensity                                   INTEGER,
    alaQoSPortServicingMode                                 INTEGER, 
    alaQoSPortFreeFFPRules                                  Integer32,
    alaQoSPortUsedFFPRules                                  Integer32,
    alaQoSPortFreeFFPMasks                                  Integer32,
    alaQoSPortUsedFFPMasks                                  Integer32,
    alaQoSPortSpoofedCount                                  Integer32,
    alaQoSPortNonSpoofedCount                               Integer32,
    alaQoSPortQ4PriorityWeight                              Integer32,
    alaQoSPortQ5PriorityWeight                              Integer32,
    alaQoSPortQ6PriorityWeight                              Integer32,
    alaQoSPortQ7PriorityWeight                              Integer32,
    alaQoSPortCOS0MaximumBandwidth                          Integer32,
    alaQoSPortCOS0MaximumBandwidthStatus                    INTEGER,
    alaQoSPortCOS1MaximumBandwidth                          Integer32,
    alaQoSPortCOS1MaximumBandwidthStatus                    INTEGER,
    alaQoSPortCOS2MaximumBandwidth                          Integer32,
    alaQoSPortCOS2MaximumBandwidthStatus                    INTEGER,
    alaQoSPortCOS3MaximumBandwidth                          Integer32,
    alaQoSPortCOS3MaximumBandwidthStatus                    INTEGER,
    alaQoSPortCOS4MaximumBandwidth                          Integer32,
    alaQoSPortCOS4MaximumBandwidthStatus                    INTEGER,
    alaQoSPortCOS5MaximumBandwidth                          Integer32,
    alaQoSPortCOS5MaximumBandwidthStatus                    INTEGER,
    alaQoSPortCOS6MaximumBandwidth                          Integer32,
    alaQoSPortCOS6MaximumBandwidthStatus                    INTEGER,
    alaQoSPortCOS7MaximumBandwidth                          Integer32,
    alaQoSPortCOS7MaximumBandwidthStatus                    INTEGER,
    alaQoSPortCOS0MinimumBandwidth                          Integer32,
    alaQoSPortCOS0MinimumBandwidthStatus                    INTEGER,
    alaQoSPortCOS1MinimumBandwidth                          Integer32,
    alaQoSPortCOS1MinimumBandwidthStatus                    INTEGER,
    alaQoSPortCOS2MinimumBandwidth                          Integer32,
    alaQoSPortCOS2MinimumBandwidthStatus                    INTEGER,
    alaQoSPortCOS3MinimumBandwidth                          Integer32,
    alaQoSPortCOS3MinimumBandwidthStatus                    INTEGER,
    alaQoSPortCOS4MinimumBandwidth                          Integer32,
    alaQoSPortCOS4MinimumBandwidthStatus                    INTEGER,
    alaQoSPortCOS5MinimumBandwidth                          Integer32,
    alaQoSPortCOS5MinimumBandwidthStatus                    INTEGER,
    alaQoSPortCOS6MinimumBandwidth                          Integer32,
    alaQoSPortCOS6MinimumBandwidthStatus                    INTEGER,
    alaQoSPortCOS7MinimumBandwidth                          Integer32,
    alaQoSPortCOS7MinimumBandwidthStatus                    INTEGER,
    alaQoSPortMaximumIngBandwidth                           Integer32,
    alaQoSPortMaximumIngBandwidthStatus                     INTEGER,
    alaQoSPortDEIMarking 				                    INTEGER,
    alaQoSPortMonitor                                       INTEGER,
    alaQoSPortDEIMapping				                    INTEGER
  }

alaQoSPortSlot OBJECT-TYPE
  SYNTAX      Integer32 (0..16)
  MAX-ACCESS  not-accessible
  STATUS      current
  DESCRIPTION "Physical slot port resides on"
  ::= { alaQoSPortEntry 1 }

alaQoSPortPort OBJECT-TYPE
  SYNTAX      Integer32 (0..52)
  MAX-ACCESS  not-accessible
  STATUS      current
  DESCRIPTION "Physical port number"
  ::= { alaQoSPortEntry 2 }

alaQoSPortEnabled OBJECT-TYPE
  SYNTAX      INTEGER {
                enable (1),
                disable (2)
              }
  MAX-ACCESS  read-create
  STATUS      current
  DESCRIPTION "Pending QoS enable status for the physical port
               Does not take effect until an 'Apply' command is issued"
  DEFVAL      { enable }
  ::= { alaQoSPortEntry 3 }

alaQoSPortAppliedEnabled OBJECT-TYPE
  SYNTAX      INTEGER {
                enable (1),
                disable (2)
              }
  MAX-ACCESS  read-only
  STATUS      current
  DESCRIPTION "Current QoS enable status for the physical port
"
  ::= { alaQoSPortEntry 4 }

alaQoSPortInterfaceType OBJECT-TYPE
  SYNTAX      INTEGER {
                ethernet (1),
                wan (2),
                ethernet10 (3),
                ethernet100 (4),
                ethernet1G (5),
                ethernet10G (6),
                aggregate (7)
              }
  MAX-ACCESS  read-only
  STATUS      current
  DESCRIPTION "The type of interface QoS matches for this physical port"
  ::= { alaQoSPortEntry 5 }

alaQoSPortTrusted OBJECT-TYPE
  SYNTAX      INTEGER {
                yes (1),
                no (2)
              }
  MAX-ACCESS  read-create
  STATUS      current
  DESCRIPTION "Status of trusting 802.1p/TOS/DSCP values.
               When trusted, 802.1p/DSCP values in the packet are passed
               through the switch.  When untrusted, 802.1p/DSCP values are set
               to the port defaults."
  DEFVAL      { no }
  ::= { alaQoSPortEntry 6 }

alaQoSPortDefault8021p OBJECT-TYPE
  SYNTAX      Integer32 (0..7)
  MAX-ACCESS  read-create
  STATUS      current
  DESCRIPTION "802.1p priority value to use for untagged frames arriving on
               the port and tagged frames when the port is untrusted."
  DEFVAL      { 0 }
  ::= { alaQoSPortEntry 7 }

alaQoSPortDefaultDSCP OBJECT-TYPE
  SYNTAX      Integer32 (0..63)
  MAX-ACCESS  read-create
  STATUS      current
  DESCRIPTION "DSCP value to stamp in frames arriving on the port when the port
               is untrusted"
  DEFVAL      { 0 }
  ::= { alaQoSPortEntry 8 }

alaQoSPortMaximumReservedBandwidth OBJECT-TYPE
  SYNTAX      Integer32
  MAX-ACCESS  read-create
  STATUS      current
  DESCRIPTION "Pending maximum reservable bandwidth on the port.
               Policies can reserve up to this much bandwidth.
               Does not take effect until an 'Apply' is issued"
  DEFVAL      { 0 }
  ::= { alaQoSPortEntry 9 }

alaQoSPortMaximumReservedBandwidthStatus OBJECT-TYPE
  SYNTAX      INTEGER {
                enabled (1),
                disabled (2)
              }
  MAX-ACCESS  read-create
  STATUS      current
  DESCRIPTION "Pending status field indicating whether to enforce
               maximum reservable bandwidth on next 'Apply'"
  DEFVAL      { disabled }
  ::= { alaQoSPortEntry 10 }

alaQoSPortAppliedMaximumReservedBandwidth OBJECT-TYPE
  SYNTAX      Integer32
  MAX-ACCESS  read-only
  STATUS      current
  DESCRIPTION "Current maximum reservable bandwidth on the port.
               Policies can reserve up to this much bandwidth.
"
  ::= { alaQoSPortEntry 11 }

alaQoSPortAppliedMaximumReservedBandwidthStatus OBJECT-TYPE
  SYNTAX      INTEGER {
                enabled (1),
                disabled (2)
              }
  MAX-ACCESS  read-only
  STATUS      current
  DESCRIPTION "Current status field indicating whether to enforce
               maximum reservable bandwidth."
  DEFVAL      { disabled }
  ::= { alaQoSPortEntry 12 }

alaQoSPortMaximumSignalledBandwidth OBJECT-TYPE
  SYNTAX      Integer32
  MAX-ACCESS  read-create
  STATUS      current
  DESCRIPTION "Pending maximum signalled bandwidth on the port.
               Signalling protocols can reserve up to this much bandwidth.
               Does not take effect until an 'Apply' is issued"
  DEFVAL      { 0 }
  ::= { alaQoSPortEntry 13 }

alaQoSPortMaximumSignalledBandwidthStatus OBJECT-TYPE
  SYNTAX      INTEGER {
                enabled (1),
                disabled (2)
              }
  MAX-ACCESS  read-create
  STATUS      current
  DESCRIPTION "Pending status field indicating whether to enforce
               maximum signalled bandwidth on next 'Apply'"
  DEFVAL      { disabled }
  ::= { alaQoSPortEntry 14 }

alaQoSPortAppliedMaximumSignalledBandwidth OBJECT-TYPE
  SYNTAX      Integer32
  MAX-ACCESS  read-only
  STATUS      current
  DESCRIPTION "Current maximum signalled bandwidth on the port.
               Signalling protocols can reserve up to this much bandwidth.
"
  ::= { alaQoSPortEntry 15 }

alaQoSPortAppliedMaximumSignalledBandwidthStatus OBJECT-TYPE
  SYNTAX      INTEGER {
                enabled (1),
                disabled (2)
              }
  MAX-ACCESS  read-only
  STATUS      current
  DESCRIPTION "Current status field indicating whether to enforce
               maximum signalled bandwidth."
  DEFVAL      { disabled }
  ::= { alaQoSPortEntry 16 }

alaQoSPortDefaultQueues OBJECT-TYPE
  SYNTAX      Integer32 (8..8)
  MAX-ACCESS  read-create
  STATUS      current
  DESCRIPTION "Pending number of default queues for the port
               Overrides any switch-wide default queue setting"
  DEFVAL      { 8 }
  ::= { alaQoSPortEntry 17 }

alaQoSPortAppliedDefaultQueues OBJECT-TYPE
  SYNTAX      Integer32 (8..8)
  MAX-ACCESS  read-only
  STATUS      current
  DESCRIPTION "Current number of default queues for the port
               Overrides any switch-wide default queue setting"
  ::= { alaQoSPortEntry 18 }

alaQoSPortMaximumDefaultBandwidth OBJECT-TYPE
  SYNTAX      Integer32
  MAX-ACCESS  read-create
  STATUS      current
  DESCRIPTION "Pending maximum default bandwidth (Kbits/sec).
               Maximum rate for default queues on this port
               Does not take effect until an 'Apply' command is issued"
  DEFVAL      { 0 }
  ::= { alaQoSPortEntry 19 }

alaQoSPortMaximumDefaultBandwidthStatus OBJECT-TYPE
  SYNTAX      INTEGER {
                enabled (1),
                disabled (2)
              }
  MAX-ACCESS  read-create
  STATUS      current
  DESCRIPTION "Pending status field indicating whether to enforce
               maximum default bandwidth on next 'Apply'"
  DEFVAL      { disabled }
  ::= { alaQoSPortEntry 20 }

alaQoSPortAppliedMaximumDefaultBandwidth OBJECT-TYPE
  SYNTAX      Integer32
  MAX-ACCESS  read-only
  STATUS      current
  DESCRIPTION "Current maximum default bandwidth (Kbits/sec).
               Maximum rate for default queues this port
"
  ::= { alaQoSPortEntry 21 }

alaQoSPortAppliedMaximumDefaultBandwidthStatus OBJECT-TYPE
  SYNTAX      INTEGER {
                enabled (1),
                disabled (2)
              }
  MAX-ACCESS  read-only
  STATUS      current
  DESCRIPTION "Current status field indicating whether to enforce
               maximum default bandwidth."
  DEFVAL      { disabled }
  ::= { alaQoSPortEntry 22 }

alaQoSPortMaximumDefaultDepth OBJECT-TYPE
  SYNTAX      Integer32
  MAX-ACCESS  read-create
  STATUS      current
  DESCRIPTION "Pending maximum depth of egress queues (Kbytes).
               Maximum depth of queues on this port
               Does not take effect until an 'Apply' command is issued"
  DEFVAL      { 0 }
  ::= { alaQoSPortEntry 23 }

alaQoSPortMaximumDefaultDepthStatus OBJECT-TYPE
  SYNTAX      INTEGER {
                enabled (1),
                disabled (2)
              }
  MAX-ACCESS  read-create
  STATUS      current
  DESCRIPTION "Pending status field indicating whether to enforce
               maximum depth on next 'Apply'"
  DEFVAL      { disabled }
  ::= { alaQoSPortEntry 24 }

alaQoSPortAppliedMaximumDefaultDepth OBJECT-TYPE
  SYNTAX      Integer32
  MAX-ACCESS  read-only
  STATUS      current
  DESCRIPTION "Current maximum depth of egress queues (Kbytes).
               Maximum depth of queues on this port
"
  ::= { alaQoSPortEntry 25 }

alaQoSPortAppliedMaximumDefaultDepthStatus OBJECT-TYPE
  SYNTAX      INTEGER {
                enabled (1),
                disabled (2)
              }
  MAX-ACCESS  read-only
  STATUS      current
  DESCRIPTION "Current status field indicating whether to enforce
               maximum depth."
  DEFVAL      { disabled }
  ::= { alaQoSPortEntry 26 }

alaQoSPortMaximumDefaultBuffers OBJECT-TYPE
  SYNTAX      Integer32
  MAX-ACCESS  read-create
  STATUS      current
  DESCRIPTION "Pending maximum buffers for egress queues.
               Maximum number of buffers for queues on this port
               Does not take effect until an 'Apply' command is issued"
  DEFVAL      { 0 }
  ::= { alaQoSPortEntry 27 }

alaQoSPortMaximumDefaultBuffersStatus OBJECT-TYPE
  SYNTAX      INTEGER {
                enabled (1),
                disabled (2)
              }
  MAX-ACCESS  read-create
  STATUS      current
  DESCRIPTION "Pending status field indicating whether to enforce
               maximum buffers on next 'Apply'"
  DEFVAL      { disabled }
  ::= { alaQoSPortEntry 28 }

alaQoSPortAppliedMaximumDefaultBuffers OBJECT-TYPE
  SYNTAX      Integer32
  MAX-ACCESS  read-only
  STATUS      current
  DESCRIPTION "Current maximum buffers for egress queues.
               Maximum number of buffers for queues on this port
"
  ::= { alaQoSPortEntry 29 }

alaQoSPortAppliedMaximumDefaultBuffersStatus OBJECT-TYPE
  SYNTAX      INTEGER {
                enabled (1),
                disabled (2)
              }
  MAX-ACCESS  read-only
  STATUS      current
  DESCRIPTION "Current status field indicating whether to enforce
               maximum buffers."
  DEFVAL      { disabled }
  ::= { alaQoSPortEntry 30 }

alaQoSPortReset OBJECT-TYPE
  SYNTAX      INTEGER {
                yes (1),
                no (2)
              }
  MAX-ACCESS  read-create
  STATUS      current
  DESCRIPTION "Reset all QoS parameters to default values"
  DEFVAL      { no }
  ::= { alaQoSPortEntry 31 }

alaQoSPortPhysicalBandwidth OBJECT-TYPE
  SYNTAX      Integer32
  MAX-ACCESS  read-only
  STATUS      current
  DESCRIPTION "Physical bandwidth of port (Kbit/sec)"
  ::= { alaQoSPortEntry 32 }

alaQoSPortReservedBandwidth OBJECT-TYPE
  SYNTAX      Integer32
  MAX-ACCESS  read-only
  STATUS      current
  DESCRIPTION "Bandwidth reserved by policies on port (Kbit/sec)"
  ::= { alaQoSPortEntry 33 }

alaQoSPortSignalledBandwidth OBJECT-TYPE
  SYNTAX      Integer32
  MAX-ACCESS  read-only
  STATUS      current
  DESCRIPTION "Bandwidth reserved by signalling on port (Kbit/sec)"
  ::= { alaQoSPortEntry 34 }

alaQoSPortCurrentBandwidth OBJECT-TYPE
  SYNTAX      Integer32
  MAX-ACCESS  read-only
  STATUS      current
  DESCRIPTION "Current measured bandwidth of port (Kbits/sec)"
  ::= { alaQoSPortEntry 35 }

alaQoSPortDefaultQidLow OBJECT-TYPE
  SYNTAX      Integer32
  MAX-ACCESS  read-only
  STATUS      current
  DESCRIPTION "Default low queue ID"
  ::= { alaQoSPortEntry 36 }

alaQoSPortDefaultQidMedium OBJECT-TYPE
  SYNTAX      Integer32
  MAX-ACCESS  read-only
  STATUS      current
  DESCRIPTION "Default medium queue ID"
  ::= { alaQoSPortEntry 37 }

alaQoSPortDefaultQidHigh OBJECT-TYPE
  SYNTAX      Integer32
  MAX-ACCESS  read-only
  STATUS      current
  DESCRIPTION "Default high queue ID"
  ::= { alaQoSPortEntry 38 }

alaQoSPortDefaultQidUrgent OBJECT-TYPE
  SYNTAX      Integer32
  MAX-ACCESS  read-only
  STATUS      current
  DESCRIPTION "Default urgent queue ID"
  ::= { alaQoSPortEntry 39 }

alaQoSPortFloodQid OBJECT-TYPE
  SYNTAX      Integer32
  MAX-ACCESS  read-only
  STATUS      current
  DESCRIPTION "ID of the flood queue"
  ::= { alaQoSPortEntry 40 }

alaQoSPortQueues OBJECT-TYPE
  SYNTAX      Integer32
  MAX-ACCESS  read-only
  STATUS      current
  DESCRIPTION "Number of queues currently on the port"
  ::= { alaQoSPortEntry 41 }

alaQoSPortQueuesCreated OBJECT-TYPE
  SYNTAX      Integer32
  MAX-ACCESS  read-only
  STATUS      current
  DESCRIPTION "Number of queue requests on the port"
  ::= { alaQoSPortEntry 42 }

alaQoSPortQueuesFailed OBJECT-TYPE
  SYNTAX      Integer32
  MAX-ACCESS  read-only
  STATUS      current
  DESCRIPTION "Number of queue requests that failed on the port"
  ::= { alaQoSPortEntry 43 }

alaQoSPortQueuesPreempted OBJECT-TYPE
  SYNTAX      Integer32
  MAX-ACCESS  read-only
  STATUS      current
  DESCRIPTION "Number of queues preempted on the port"
  ::= { alaQoSPortEntry 44 }

alaQoSPortRowStatus OBJECT-TYPE
  SYNTAX      RowStatus
  MAX-ACCESS  read-create
  STATUS      current
  DESCRIPTION "Used to create/delete ports according to the
               RowStatus convention"
  ::= { alaQoSPortEntry 45 }

alaQoSPortFirPrio0EnqBytes OBJECT-TYPE
  SYNTAX      Counter64
  MAX-ACCESS  read-only
  STATUS      current
  DESCRIPTION "Firenze priority 0 enqueue byte count"
  ::= { alaQoSPortEntry 46 }

alaQoSPortFirPrio0DeqBytes OBJECT-TYPE
  SYNTAX      Counter64
  MAX-ACCESS  read-only
  STATUS      current
  DESCRIPTION "Firenze priority 0 dequeue byte count"
  ::= { alaQoSPortEntry 47 }

alaQoSPortFirPrio0EnqPkts OBJECT-TYPE
  SYNTAX      Counter64
  MAX-ACCESS  read-only
  STATUS      current
  DESCRIPTION "Firenze priority 0 enqueue packet count"
  ::= { alaQoSPortEntry 48 }

alaQoSPortFirPrio0DeqPkts OBJECT-TYPE
  SYNTAX      Counter64
  MAX-ACCESS  read-only
  STATUS      current
  DESCRIPTION "Firenze priority 0 dequeue packet count"
  ::= { alaQoSPortEntry 49 }

alaQoSPortFirPrio0QidDiscardPkts OBJECT-TYPE
  SYNTAX      Counter64
  MAX-ACCESS  read-only
  STATUS      current
  DESCRIPTION "Firenze priority 0 QID discard packet count"
  ::= { alaQoSPortEntry 50 }

alaQoSPortFirPrio0WredDiscardPkts OBJECT-TYPE
  SYNTAX      Counter64
  MAX-ACCESS  read-only
  STATUS      current
  DESCRIPTION "Firenze priority 0 WRED discard packet count"
  ::= { alaQoSPortEntry 51 }

alaQoSPortFirPrio0OverflowDiscardPkts OBJECT-TYPE
  SYNTAX      Counter64
  MAX-ACCESS  read-only
  STATUS      current
  DESCRIPTION "Firenze priority 0 overflow discard packet count"
  ::= { alaQoSPortEntry 52 }

alaQoSPortFirPrio1EnqBytes OBJECT-TYPE
  SYNTAX      Counter64
  MAX-ACCESS  read-only
  STATUS      current
  DESCRIPTION "Firenze priority 1 enqueue byte count"
  ::= { alaQoSPortEntry 53 }

alaQoSPortFirPrio1DeqBytes OBJECT-TYPE
  SYNTAX      Counter64
  MAX-ACCESS  read-only
  STATUS      current
  DESCRIPTION "Firenze priority 1 dequeue byte count"
  ::= { alaQoSPortEntry 54 }

alaQoSPortFirPrio1EnqPkts OBJECT-TYPE
  SYNTAX      Counter64
  MAX-ACCESS  read-only
  STATUS      current
  DESCRIPTION "Firenze priority 1 enqueue packet count"
  ::= { alaQoSPortEntry 55 }

alaQoSPortFirPrio1DeqPkts OBJECT-TYPE
  SYNTAX      Counter64
  MAX-ACCESS  read-only
  STATUS      current
  DESCRIPTION "Firenze priority 1 dequeue packet count"
  ::= { alaQoSPortEntry 56 }

alaQoSPortFirPrio1QidDiscardPkts OBJECT-TYPE
  SYNTAX      Counter64
  MAX-ACCESS  read-only
  STATUS      current
  DESCRIPTION "Firenze priority 1 QID discard packet count"
  ::= { alaQoSPortEntry 57 }

alaQoSPortFirPrio1WredDiscardPkts OBJECT-TYPE
  SYNTAX      Counter64
  MAX-ACCESS  read-only
  STATUS      current
  DESCRIPTION "Firenze priority 1 WRED discard packet count"
  ::= { alaQoSPortEntry 58 }

alaQoSPortFirPrio1OverflowDiscardPkts OBJECT-TYPE
  SYNTAX      Counter64
  MAX-ACCESS  read-only
  STATUS      current
  DESCRIPTION "Firenze priority 1 overflow discard packet count"
  ::= { alaQoSPortEntry 59 }

alaQoSPortFirPrio2EnqBytes OBJECT-TYPE
  SYNTAX      Counter64
  MAX-ACCESS  read-only
  STATUS      current
  DESCRIPTION "Firenze priority 2 enqueue byte count"
  ::= { alaQoSPortEntry 60 }

alaQoSPortFirPrio2DeqBytes OBJECT-TYPE
  SYNTAX      Counter64
  MAX-ACCESS  read-only
  STATUS      current
  DESCRIPTION "Firenze priority 2 dequeue byte count"
  ::= { alaQoSPortEntry 61 }

alaQoSPortFirPrio2EnqPkts OBJECT-TYPE
  SYNTAX      Counter64
  MAX-ACCESS  read-only
  STATUS      current
  DESCRIPTION "Firenze priority 2 enqueue packet count"
  ::= { alaQoSPortEntry 62 }

alaQoSPortFirPrio2DeqPkts OBJECT-TYPE
  SYNTAX      Counter64
  MAX-ACCESS  read-only
  STATUS      current
  DESCRIPTION "Firenze priority 2 dequeue packet count"
  ::= { alaQoSPortEntry 63 }

alaQoSPortFirPrio2QidDiscardPkts OBJECT-TYPE
  SYNTAX      Counter64
  MAX-ACCESS  read-only
  STATUS      current
  DESCRIPTION "Firenze priority 2 QID discard packet count"
  ::= { alaQoSPortEntry 64 }

alaQoSPortFirPrio2WredDiscardPkts OBJECT-TYPE
  SYNTAX      Counter64
  MAX-ACCESS  read-only
  STATUS      current
  DESCRIPTION "Firenze priority 2 WRED discard packet count"
  ::= { alaQoSPortEntry 65 }

alaQoSPortFirPrio2OverflowDiscardPkts OBJECT-TYPE
  SYNTAX      Counter64
  MAX-ACCESS  read-only
  STATUS      current
  DESCRIPTION "Firenze priority 2 overflow discard packet count"
  ::= { alaQoSPortEntry 66 }

alaQoSPortFirPrio3EnqBytes OBJECT-TYPE
  SYNTAX      Counter64
  MAX-ACCESS  read-only
  STATUS      current
  DESCRIPTION "Firenze priority 3 enqueue byte count"
  ::= { alaQoSPortEntry 67 }

alaQoSPortFirPrio3DeqBytes OBJECT-TYPE
  SYNTAX      Counter64
  MAX-ACCESS  read-only
  STATUS      current
  DESCRIPTION "Firenze priority 3 dequeue byte count"
  ::= { alaQoSPortEntry 68 }

alaQoSPortFirPrio3EnqPkts OBJECT-TYPE
  SYNTAX      Counter64
  MAX-ACCESS  read-only
  STATUS      current
  DESCRIPTION "Firenze priority 3 enqueue packet count"
  ::= { alaQoSPortEntry 69 }

alaQoSPortFirPrio3DeqPkts OBJECT-TYPE
  SYNTAX      Counter64
  MAX-ACCESS  read-only
  STATUS      current
  DESCRIPTION "Firenze priority 3 dequeue packet count"
  ::= { alaQoSPortEntry 70 }

alaQoSPortFirPrio3QidDiscardPkts OBJECT-TYPE
  SYNTAX      Counter64
  MAX-ACCESS  read-only
  STATUS      current
  DESCRIPTION "Firenze priority 3 QID discard packet count"
  ::= { alaQoSPortEntry 71 }

alaQoSPortFirPrio3WredDiscardPkts OBJECT-TYPE
  SYNTAX      Counter64
  MAX-ACCESS  read-only
  STATUS      current
  DESCRIPTION "Firenze priority 3 WRED discard packet count"
  ::= { alaQoSPortEntry 72 }

alaQoSPortFirPrio3OverflowDiscardPkts OBJECT-TYPE
  SYNTAX      Counter64
  MAX-ACCESS  read-only
  STATUS      current
  DESCRIPTION "Firenze priority 3 overflow discard packet count"
  ::= { alaQoSPortEntry 73 }

alaQoSPortDefaultClassification OBJECT-TYPE
  SYNTAX      INTEGER {
                b8021p (1),
                tos (2),
                dscp (3)
              }
  MAX-ACCESS  read-create
  STATUS      current
  DESCRIPTION "Ingress traffic classification parameter for Firenze port
               What field to interpret as priority for WRED"
  DEFVAL      { tos }
  ::= { alaQoSPortEntry 74 }

alaQoSPortLowPriorityWeight OBJECT-TYPE
  SYNTAX      Integer32 (0..15)
  MAX-ACCESS  read-create
  STATUS      current
  DESCRIPTION "Weight to use for low priority egress queue on fixed queue blades."
  DEFVAL      { 1 }
  ::= { alaQoSPortEntry 75 }

alaQoSPortMediumPriorityWeight OBJECT-TYPE
  SYNTAX      Integer32 (0..15)
  MAX-ACCESS  read-create
  STATUS      current
  DESCRIPTION "Weight to use for medium priority egress queue on fixed queue blades."
  DEFVAL      { 1 }
  ::= { alaQoSPortEntry 76 }

alaQoSPortHighPriorityWeight OBJECT-TYPE
  SYNTAX      Integer32 (0..15)
  MAX-ACCESS  read-create
  STATUS      current
  DESCRIPTION "Weight to use for high priority egress queue on fixed queue blades."
  DEFVAL      { 1 }
  ::= { alaQoSPortEntry 77 }

alaQoSPortUrgentPriorityWeight OBJECT-TYPE
  SYNTAX      Integer32 (0..15)
  MAX-ACCESS  read-create
  STATUS      current
  DESCRIPTION "Weight to use for urgent priority egress queue on fixed queue blades."
  DEFVAL      { 1 }
  ::= { alaQoSPortEntry 78 }

alaQoSPortMaximumBandwidth OBJECT-TYPE
  SYNTAX      Integer32
  MAX-ACCESS  read-create
  STATUS      current
  DESCRIPTION "Maximum egress bandwidth (Kbits/sec).
               Maximum rate to send traffic out this port"
  DEFVAL      { 0 }
  ::= { alaQoSPortEntry 79 }

alaQoSPortMaximumBandwidthStatus OBJECT-TYPE
  SYNTAX      INTEGER {
                enabled (1),
                disabled (2)
              }
  MAX-ACCESS  read-create
  STATUS      current
  DESCRIPTION "Status field indicating whether to enforce
               maximum bandwidth on port."
  DEFVAL      { disabled }
  ::= { alaQoSPortEntry 80 }

alaQoSPortEnqueuingThresholdP0Lower OBJECT-TYPE
  SYNTAX      Integer32 (0..4095)
  MAX-ACCESS  read-create
  STATUS      current
  DESCRIPTION "Priority 0 FIFO lower threshold for high density module"
  DEFVAL      { 10 }
  ::= { alaQoSPortEntry 81 }

alaQoSPortEnqueuingThresholdP0Upper OBJECT-TYPE
  SYNTAX      Integer32 (0..4095)
  MAX-ACCESS  read-create
  STATUS      current
  DESCRIPTION "Priority 0 FIFO upper threshold for high density module"
  DEFVAL      { 30 }
  ::= { alaQoSPortEntry 82 }

alaQoSPortEnqueuingThresholdP1Lower OBJECT-TYPE
  SYNTAX      Integer32 (0..4095)
  MAX-ACCESS  read-create
  STATUS      current
  DESCRIPTION "Priority 1 FIFO lower threshold for high density module"
  DEFVAL      { 10 }
  ::= { alaQoSPortEntry 83 }

alaQoSPortEnqueuingThresholdP1Upper OBJECT-TYPE
  SYNTAX      Integer32 (0..4095)
  MAX-ACCESS  read-create
  STATUS      current
  DESCRIPTION "Priority 1 FIFO upper threshold for high density module"
  DEFVAL      { 35 }
  ::= { alaQoSPortEntry 84 }

alaQoSPortEnqueuingThresholdP2Lower OBJECT-TYPE
  SYNTAX      Integer32 (0..4095)
  MAX-ACCESS  read-create
  STATUS      current
  DESCRIPTION "Priority 2 FIFO lower threshold for high density module"
  DEFVAL      { 10 }
  ::= { alaQoSPortEntry 85 }

alaQoSPortEnqueuingThresholdP2Upper OBJECT-TYPE
  SYNTAX      Integer32 (0..4095)
  MAX-ACCESS  read-create
  STATUS      current
  DESCRIPTION "Priority 2 FIFO upper threshold for high density module"
  DEFVAL      { 40 }
  ::= { alaQoSPortEntry 86 }

alaQoSPortEnqueuingThresholdP3Lower OBJECT-TYPE
  SYNTAX      Integer32 (0..4095)
  MAX-ACCESS  read-create
  STATUS      current
  DESCRIPTION "Priority 3 FIFO lower threshold for high density module"
  DEFVAL      { 260 }
  ::= { alaQoSPortEntry 87 }

alaQoSPortEnqueuingThresholdP3Upper OBJECT-TYPE
  SYNTAX      Integer32 (0..4095)
  MAX-ACCESS  read-create
  STATUS      current
  DESCRIPTION "Priority 3 FIFO upper threshold for high density module"
  DEFVAL      { 575 }
  ::= { alaQoSPortEntry 88 }

alaQoSPortEnqueuingThresholdStatus OBJECT-TYPE
  SYNTAX      INTEGER {
                enabled (1),
                disabled (2)
              }
  MAX-ACCESS  read-create
  STATUS      current
  DESCRIPTION "Status field indicating whether enqueuing thresholds need
               to be enforced on high density module."
  DEFVAL      { disabled }
  ::= { alaQoSPortEntry 89 }

alaQoSPortHighDensity OBJECT-TYPE
  SYNTAX      INTEGER {
                yes (1),
                no (2)
              }
  MAX-ACCESS  read-only
  STATUS      current
  DESCRIPTION "Indicates whether this is a high-density port or not."
  ::= { alaQoSPortEntry 90 }
  

alaQoSPortServicingMode OBJECT-TYPE
  SYNTAX      INTEGER {
                default (0),
                strictpriority (1),
                prioritywrr (2),
                wrr (3),
                drr (4)
              }
  MAX-ACCESS  read-create
  STATUS      current
  DESCRIPTION "Servicing mode for the port"
  DEFVAL      { default }
  ::= { alaQoSPortEntry 91 }

alaQoSPortFreeFFPRules OBJECT-TYPE
  SYNTAX      Integer32
  MAX-ACCESS  read-only
  STATUS      current
  DESCRIPTION "Number of Free FPP rule entries"
  ::= { alaQoSPortEntry 92 }

alaQoSPortUsedFFPRules OBJECT-TYPE
  SYNTAX      Integer32
  MAX-ACCESS  read-only
  STATUS      current
  DESCRIPTION "Number of Used FPP rule entries"
  ::= { alaQoSPortEntry 93 }

alaQoSPortFreeFFPMasks OBJECT-TYPE
  SYNTAX      Integer32
  MAX-ACCESS  read-only
  STATUS      current
  DESCRIPTION "Number of Free FPP mask entries"
  ::= { alaQoSPortEntry 94 }

alaQoSPortUsedFFPMasks OBJECT-TYPE
  SYNTAX      Integer32
  MAX-ACCESS  read-only
  STATUS      current
  DESCRIPTION "Number of Free FPP mask enries"
  ::= { alaQoSPortEntry 95 }

alaQoSPortSpoofedCount OBJECT-TYPE
  SYNTAX      Integer32
  MAX-ACCESS  read-only
  STATUS      current
  DESCRIPTION "Spoofed packet count"
  ::= { alaQoSPortEntry 96 }

alaQoSPortNonSpoofedCount OBJECT-TYPE
  SYNTAX      Integer32
  MAX-ACCESS  read-only
  STATUS      current
  DESCRIPTION "Non-spoofed packet count"
  ::= { alaQoSPortEntry 97 }

alaQoSPortQ4PriorityWeight OBJECT-TYPE
  SYNTAX      Integer32 (0..15)
  MAX-ACCESS  read-create
  STATUS      current
  DESCRIPTION "Weight to use for cos queue 4."
  DEFVAL      { 1 }
  ::= { alaQoSPortEntry 98 }

alaQoSPortQ5PriorityWeight OBJECT-TYPE
  SYNTAX      Integer32 (0..15)
  MAX-ACCESS  read-create
  STATUS      current
  DESCRIPTION "Weight to use for cos queue 5."
  DEFVAL      { 1 }
  ::= { alaQoSPortEntry 99 }

alaQoSPortQ6PriorityWeight OBJECT-TYPE
  SYNTAX      Integer32 (0..15)
  MAX-ACCESS  read-create
  STATUS      current
  DESCRIPTION "Weight to use for cos queue 6."
  DEFVAL      { 1 }
  ::= { alaQoSPortEntry 100 }

alaQoSPortQ7PriorityWeight OBJECT-TYPE
  SYNTAX      Integer32 (0..15)
  MAX-ACCESS  read-create
  STATUS      current
  DESCRIPTION "Weight to use for cos queue 7."
  DEFVAL      { 1 }
  ::= { alaQoSPortEntry 101 }

alaQoSPortCOS0MaximumBandwidth OBJECT-TYPE
  SYNTAX      Integer32
  MAX-ACCESS  read-create
  STATUS      current
  DESCRIPTION "Maximum egress bandwidth (Kbits/sec).
               Maximum rate to send traffic out this queue"
  DEFVAL      { 0 }
  ::= { alaQoSPortEntry 102 }

alaQoSPortCOS0MaximumBandwidthStatus OBJECT-TYPE
  SYNTAX      INTEGER {
                enabled (1),
                disabled (2)
              }
  MAX-ACCESS  read-create
  STATUS      current
  DESCRIPTION "Status field indicating whether to enforce
               maximum bandwidth on queue."
  DEFVAL      { disabled }
  ::= { alaQoSPortEntry 103 }

alaQoSPortCOS1MaximumBandwidth OBJECT-TYPE
  SYNTAX      Integer32
  MAX-ACCESS  read-create
  STATUS      current
  DESCRIPTION "Maximum egress bandwidth (Kbits/sec).
               Maximum rate to send traffic out this queue"
  DEFVAL      { 0 }
  ::= { alaQoSPortEntry 104 }

alaQoSPortCOS1MaximumBandwidthStatus OBJECT-TYPE
  SYNTAX      INTEGER {
                enabled (1),
                disabled (2)
              }
  MAX-ACCESS  read-create
  STATUS      current
  DESCRIPTION "Status field indicating whether to enforce
               maximum bandwidth on queue."
  DEFVAL      { disabled }
  ::= { alaQoSPortEntry 105 }

alaQoSPortCOS2MaximumBandwidth OBJECT-TYPE
  SYNTAX      Integer32
  MAX-ACCESS  read-create
  STATUS      current
  DESCRIPTION "Maximum egress bandwidth (Kbits/sec).
               Maximum rate to send traffic out this queue"
  DEFVAL      { 0 }
  ::= { alaQoSPortEntry 106 }

alaQoSPortCOS2MaximumBandwidthStatus OBJECT-TYPE
  SYNTAX      INTEGER {
                enabled (1),
                disabled (2)
              }
  MAX-ACCESS  read-create
  STATUS      current
  DESCRIPTION "Status field indicating whether to enforce
               maximum bandwidth on queue."
  DEFVAL      { disabled }
  ::= { alaQoSPortEntry 107 }

alaQoSPortCOS3MaximumBandwidth OBJECT-TYPE
  SYNTAX      Integer32
  MAX-ACCESS  read-create
  STATUS      current
  DESCRIPTION "Maximum egress bandwidth (Kbits/sec).
               Maximum rate to send traffic out this queue"
  DEFVAL      { 0 }
  ::= { alaQoSPortEntry 108 }

alaQoSPortCOS3MaximumBandwidthStatus OBJECT-TYPE
  SYNTAX      INTEGER {
                enabled (1),
                disabled (2)
              }
  MAX-ACCESS  read-create
  STATUS      current
  DESCRIPTION "Status field indicating whether to enforce
               maximum bandwidth on queue."
  DEFVAL      { disabled }
  ::= { alaQoSPortEntry 109 }

alaQoSPortCOS4MaximumBandwidth OBJECT-TYPE
  SYNTAX      Integer32
  MAX-ACCESS  read-create
  STATUS      current
  DESCRIPTION "Maximum egress bandwidth (Kbits/sec).
               Maximum rate to send traffic out this queue"
  DEFVAL      { 0 }
  ::= { alaQoSPortEntry 110 }

alaQoSPortCOS4MaximumBandwidthStatus OBJECT-TYPE
  SYNTAX      INTEGER {
                enabled (1),
                disabled (2)
              }
  MAX-ACCESS  read-create
  STATUS      current
  DESCRIPTION "Status field indicating whether to enforce
               maximum bandwidth on queue."
  DEFVAL      { disabled }
  ::= { alaQoSPortEntry 111 }

alaQoSPortCOS5MaximumBandwidth OBJECT-TYPE
  SYNTAX      Integer32
  MAX-ACCESS  read-create
  STATUS      current
  DESCRIPTION "Maximum egress bandwidth (Kbits/sec).
               Maximum rate to send traffic out this queue"
  DEFVAL      { 0 }
  ::= { alaQoSPortEntry 112 }

alaQoSPortCOS5MaximumBandwidthStatus OBJECT-TYPE
  SYNTAX      INTEGER {
                enabled (1),
                disabled (2)
              }
  MAX-ACCESS  read-create
  STATUS      current
  DESCRIPTION "Status field indicating whether to enforce
               maximum bandwidth on queue."
  DEFVAL      { disabled }
  ::= { alaQoSPortEntry 113 }

alaQoSPortCOS6MaximumBandwidth OBJECT-TYPE
  SYNTAX      Integer32
  MAX-ACCESS  read-create
  STATUS      current
  DESCRIPTION "Maximum egress bandwidth (Kbits/sec).
               Maximum rate to send traffic out this queue"
  DEFVAL      { 0 }
  ::= { alaQoSPortEntry 114 }

alaQoSPortCOS6MaximumBandwidthStatus OBJECT-TYPE
  SYNTAX      INTEGER {
                enabled (1),
                disabled (2)
              }
  MAX-ACCESS  read-create
  STATUS      current
  DESCRIPTION "Status field indicating whether to enforce
               maximum bandwidth on queue."
  DEFVAL      { disabled }
  ::= { alaQoSPortEntry 115 }

alaQoSPortCOS7MaximumBandwidth OBJECT-TYPE
  SYNTAX      Integer32
  MAX-ACCESS  read-create
  STATUS      current
  DESCRIPTION "Maximum egress bandwidth (Kbits/sec).
               Maximum rate to send traffic out this queue"
  DEFVAL      { 0 }
  ::= { alaQoSPortEntry 116 }

alaQoSPortCOS7MaximumBandwidthStatus OBJECT-TYPE
  SYNTAX      INTEGER {
                enabled (1),
                disabled (2)
              }
  MAX-ACCESS  read-create
  STATUS      current
  DESCRIPTION "Status field indicating whether to enforce
               maximum bandwidth on queue."
  DEFVAL      { disabled }
  ::= { alaQoSPortEntry 117 }

alaQoSPortCOS0MinimumBandwidth OBJECT-TYPE
  SYNTAX      Integer32
  MAX-ACCESS  read-create
  STATUS      current
  DESCRIPTION "Minimum egress bandwidth (Kbits/sec).
               Minimum rate to send traffic out this queue"
  DEFVAL      { 0 }
  ::= { alaQoSPortEntry 118 }

alaQoSPortCOS0MinimumBandwidthStatus OBJECT-TYPE
  SYNTAX      INTEGER {
                enabled (1),
                disabled (2)
              }
  MAX-ACCESS  read-create
  STATUS      current
  DESCRIPTION "Status field indicating whether to enforce
               minimum bandwidth on queue."
  DEFVAL      { disabled }
  ::= { alaQoSPortEntry 119 }

alaQoSPortCOS1MinimumBandwidth OBJECT-TYPE
  SYNTAX      Integer32
  MAX-ACCESS  read-create
  STATUS      current
  DESCRIPTION "Minimum egress bandwidth (Kbits/sec).
               Minimum rate to send traffic out this queue"
  DEFVAL      { 0 }
  ::= { alaQoSPortEntry 120 }

alaQoSPortCOS1MinimumBandwidthStatus OBJECT-TYPE
  SYNTAX      INTEGER {
                enabled (1),
                disabled (2)
              }
  MAX-ACCESS  read-create
  STATUS      current
  DESCRIPTION "Status field indicating whether to enforce
               minimum bandwidth on queue."
  DEFVAL      { disabled }
  ::= { alaQoSPortEntry 121 }

alaQoSPortCOS2MinimumBandwidth OBJECT-TYPE
  SYNTAX      Integer32
  MAX-ACCESS  read-create
  STATUS      current
  DESCRIPTION "Minimum egress bandwidth (Kbits/sec).
               Minimum rate to send traffic out this queue"
  DEFVAL      { 0 }
  ::= { alaQoSPortEntry 122 }

alaQoSPortCOS2MinimumBandwidthStatus OBJECT-TYPE
  SYNTAX      INTEGER {
                enabled (1),
                disabled (2)
              }
  MAX-ACCESS  read-create
  STATUS      current
  DESCRIPTION "Status field indicating whether to enforce
               minimum bandwidth on queue."
  DEFVAL      { disabled }
  ::= { alaQoSPortEntry 123 }

alaQoSPortCOS3MinimumBandwidth OBJECT-TYPE
  SYNTAX      Integer32
  MAX-ACCESS  read-create
  STATUS      current
  DESCRIPTION "Minimum egress bandwidth (Kbits/sec).
               Minimum rate to send traffic out this queue"
  DEFVAL      { 0 }
  ::= { alaQoSPortEntry 124 }

alaQoSPortCOS3MinimumBandwidthStatus OBJECT-TYPE
  SYNTAX      INTEGER {
                enabled (1),
                disabled (2)
              }
  MAX-ACCESS  read-create
  STATUS      current
  DESCRIPTION "Status field indicating whether to enforce
               minimum bandwidth on queue."
  DEFVAL      { disabled }
  ::= { alaQoSPortEntry 125 }

alaQoSPortCOS4MinimumBandwidth OBJECT-TYPE
  SYNTAX      Integer32
  MAX-ACCESS  read-create
  STATUS      current
  DESCRIPTION "Minimum egress bandwidth (Kbits/sec).
               Minimum rate to send traffic out this queue"
  DEFVAL      { 0 }
  ::= { alaQoSPortEntry 126 }

alaQoSPortCOS4MinimumBandwidthStatus OBJECT-TYPE
  SYNTAX      INTEGER {
                enabled (1),
                disabled (2)
              }
  MAX-ACCESS  read-create
  STATUS      current
  DESCRIPTION "Status field indicating whether to enforce
               minimum bandwidth on queue."
  DEFVAL      { disabled }
  ::= { alaQoSPortEntry 127 }

alaQoSPortCOS5MinimumBandwidth OBJECT-TYPE
  SYNTAX      Integer32
  MAX-ACCESS  read-create
  STATUS      current
  DESCRIPTION "Minimum egress bandwidth (Kbits/sec).
               Minimum rate to send traffic out this queue"
  DEFVAL      { 0 }
  ::= { alaQoSPortEntry 128 }

alaQoSPortCOS5MinimumBandwidthStatus OBJECT-TYPE
  SYNTAX      INTEGER {
                enabled (1),
                disabled (2)
              }
  MAX-ACCESS  read-create
  STATUS      current
  DESCRIPTION "Status field indicating whether to enforce
               minimum bandwidth on queue."
  DEFVAL      { disabled }
  ::= { alaQoSPortEntry 129 }

alaQoSPortCOS6MinimumBandwidth OBJECT-TYPE
  SYNTAX      Integer32
  MAX-ACCESS  read-create
  STATUS      current
  DESCRIPTION "Minimum egress bandwidth (Kbits/sec).
               Minimum rate to send traffic out this queue"
  DEFVAL      { 0 }
  ::= { alaQoSPortEntry 130 }

alaQoSPortCOS6MinimumBandwidthStatus OBJECT-TYPE
  SYNTAX      INTEGER {
                enabled (1),
                disabled (2)
              }
  MAX-ACCESS  read-create
  STATUS      current
  DESCRIPTION "Status field indicating whether to enforce
               minimum bandwidth on queue."
  DEFVAL      { disabled }
  ::= { alaQoSPortEntry 131 }

alaQoSPortCOS7MinimumBandwidth OBJECT-TYPE
  SYNTAX      Integer32
  MAX-ACCESS  read-create
  STATUS      current
  DESCRIPTION "Minimum egress bandwidth (Kbits/sec).
               Minimum rate to send traffic out this queue"
  DEFVAL      { 0 }
  ::= { alaQoSPortEntry 132 }

alaQoSPortCOS7MinimumBandwidthStatus OBJECT-TYPE
  SYNTAX      INTEGER {
                enabled (1),
                disabled (2)
              }
  MAX-ACCESS  read-create
  STATUS      current
  DESCRIPTION "Status field indicating whether to enforce
               minimum bandwidth on queue."
  DEFVAL      { disabled }
  ::= { alaQoSPortEntry 133 }

alaQoSPortMaximumIngBandwidth OBJECT-TYPE
  SYNTAX      Integer32
  MAX-ACCESS  read-create
  STATUS      current
  DESCRIPTION "Maximum igress bandwidth (Kbits/sec).
               Maximum rate to recieve traffic in on this port"
  DEFVAL      { 0 }
  ::= { alaQoSPortEntry 134 }

alaQoSPortMaximumIngBandwidthStatus OBJECT-TYPE
  SYNTAX      INTEGER {
                enabled (1),
                disabled (2)
              }
  MAX-ACCESS  read-create
  STATUS      current
  DESCRIPTION "Status field indicating whether to enforce
               maximum bandwidth on port."
  DEFVAL      { disabled }
  ::= { alaQoSPortEntry 135 }

alaQoSPortDEIMarking OBJECT-TYPE
  SYNTAX      INTEGER {
                enabled (1),
                disabled (2)
              }
  MAX-ACCESS  read-create
  STATUS      current
  DESCRIPTION "This object specifies if, in egress traffic, the DEI/CFI bit 
	      will be set or not for the traffic which is not conformant to 
              SLA (Yellow color packets).

	      enabled(1)  -- the DEI/CFI bit will be set in egress traffic.
	      disabled(2) -- the DEI/CFI bit will not be set in egress traffic."
  DEFVAL      { disabled }
  ::= { alaQoSPortEntry 136 }

alaQoSPortMonitor OBJECT-TYPE
  SYNTAX      INTEGER {
                enabled (1),
                disabled (2)
              }
  MAX-ACCESS  read-create
  STATUS      current
  DESCRIPTION "This object is used to monitor a slot/port on which user is interested
	      to get the cos egress statistics.
	
	      enabled(1)  -- monitor the slot/port to gather per port cos egress
			     statistics.
	      disabled(2) -- reset the previously monitored slot/port."
   DEFVAL      { disabled }
  ::= { alaQoSPortEntry 137 }

alaQoSPortDEIMapping OBJECT-TYPE
  SYNTAX      INTEGER {
                enabled (1),
                disabled (2)
              }
  MAX-ACCESS  read-create
  STATUS      current
  DESCRIPTION "This object specifies if, in ingress traffic, the DEI/CFI bit
              will be set or not for the traffic which is not conformant to
              SLA (Yellow color packets).

              enabled(1)  -- the DEI/CFI bit will be set in ingress  traffic.
              disabled(2) -- the DEI/CFI bit will not be set in ingress traffic."
  DEFVAL      { disabled }
  ::= { alaQoSPortEntry 138 }

--
-- Definition of config table
--

alaQoSConfig OBJECT IDENTIFIER ::= { alaQoSMIBObjects 30 }

alaQoSConfigEnabled OBJECT-TYPE
  SYNTAX      INTEGER {
                enable (1),
                disable (2)
              }
  MAX-ACCESS  read-write
  STATUS      current
  DESCRIPTION "Is QoS enabled on the switch"
  ::= { alaQoSConfig 1 }

alaQoSConfigDefaultQueues OBJECT-TYPE
  SYNTAX      Integer32 (2..8)
  MAX-ACCESS  read-write
  STATUS      current
  DESCRIPTION "Pending number of default queues to create for each port.
               Can be overridden on a port by port basis.  Does not take affect
               until an 'Apply' command is issued."
  ::= { alaQoSConfig 2 }

alaQoSConfigAppliedDefaultQueues OBJECT-TYPE
  SYNTAX      Integer32 (2..8)
  MAX-ACCESS  read-only
  STATUS      current
  DESCRIPTION "Number of default queues configured at last 'Apply' command."
  ::= { alaQoSConfig 3 }

alaQoSConfigTrustPorts OBJECT-TYPE
  SYNTAX      INTEGER {
                yes (1),
                no (2)
              }
  MAX-ACCESS  read-write
  STATUS      current
  DESCRIPTION "Flag to indicate whether to trust the 802.1p/TOS values on
               incoming traffic by default.  Can be overridden on a port by
               port basis."
  ::= { alaQoSConfig 4 }

alaQoSConfigFlowTimeout OBJECT-TYPE
  SYNTAX      Integer32 (2..3600)
  MAX-ACCESS  read-write
  STATUS      current
  DESCRIPTION "Pending flow timeout (seconds).  Flows are removed from
               hardware/software if no traffic is seen for this many seconds.
               Does not take effect until an 'Apply' command is issued"
  ::= { alaQoSConfig 5 }

alaQoSConfigAppliedFlowTimeout OBJECT-TYPE
  SYNTAX      Integer32 (2..3600)
  MAX-ACCESS  read-only
  STATUS      current
  DESCRIPTION "Current flow timeout (seconds).  Flows are removed from
               hardware/software if no traffic is seen for this many seconds."
  ::= { alaQoSConfig 6 }

alaQoSConfigFragmentTimeout OBJECT-TYPE
  SYNTAX      Integer32 (2..60)
  MAX-ACCESS  read-write
  STATUS      current
  DESCRIPTION "Pending fragment timeout (seconds).  Packet fragments are
               remembered for this many seconds.
               Does not take effect until an 'Apply' command is issued"
  ::= { alaQoSConfig 7 }

alaQoSConfigAppliedFragmentTimeout OBJECT-TYPE
  SYNTAX      Integer32 (2..60)
  MAX-ACCESS  read-only
  STATUS      current
  DESCRIPTION "Current fragment timeout (seconds).  Packet fragments are
               remembered for this many seconds."
  ::= { alaQoSConfig 8 }

alaQoSConfigReflexiveTimeout OBJECT-TYPE
  SYNTAX      Integer32 (10..3000)
  MAX-ACCESS  read-write
  STATUS      current
  DESCRIPTION "Pending reflexive timeout (seconds).  Anticipate reverse flows
               for reflexive and NAT connections for this long until we see a
               response.
               Does not take effect until an 'Apply' command is issued"
  ::= { alaQoSConfig 9 }

alaQoSConfigAppliedReflfexiveTimeout OBJECT-TYPE
  SYNTAX      Integer32 (10..3000)
  MAX-ACCESS  read-only
  STATUS      current
  DESCRIPTION "Current reflexive timeout (seconds).  Anticipate reverse flows
               for reflexive and NAT connections for this long until we see a
               response.
"
  ::= { alaQoSConfig 10 }

alaQoSConfigNatTimeout OBJECT-TYPE
  SYNTAX      Integer32 (10..200000)
  MAX-ACCESS  read-write
  STATUS      current
  DESCRIPTION "Pending nat timeout (seconds).  Once traffic is seen in both
               directions for anticipated flows, length of time to remember the
               flow without seeing traffic in either direction.
               Does not take effect until an 'Apply' command is issued"
  ::= { alaQoSConfig 11 }

alaQoSConfigAppliedNatTimeout OBJECT-TYPE
  SYNTAX      Integer32 (10..200000)
  MAX-ACCESS  read-only
  STATUS      current
  DESCRIPTION "Current nat timeout (seconds).  Once traffic is seen in both
               directions for anticipated flows, length of time to remember the
               flow without seeing traffic in either direction."
  ::= { alaQoSConfig 12 }

alaQoSConfigClassifyl3Bridged OBJECT-TYPE
  SYNTAX      INTEGER {
                yes (1),
                no (2)
              }
  MAX-ACCESS  read-write
  STATUS      current
  DESCRIPTION "Pending indicator for looking at L3/L4 parameters of bridged
               traffic.  Does not take effect until an 'Apply' command is
               issued."
  ::= { alaQoSConfig 13 }

alaQoSConfigAppliedClassifyl3Bridged OBJECT-TYPE
  SYNTAX      INTEGER {
                yes (1),
                no (2)
              }
  MAX-ACCESS  read-only
  STATUS      current
  DESCRIPTION "Current indicator for looking at L3/L4 parameters of bridged
               traffic."
  ::= { alaQoSConfig 14 }

alaQoSConfigClassifyFragments OBJECT-TYPE
  SYNTAX      INTEGER {
                yes (1),
                no (2)
              }
  MAX-ACCESS  read-write
  STATUS      current
  DESCRIPTION "Pending indicator for classifying fragmented traffic at L4
               Does not take effect until an 'Apply' command is issued"
  ::= { alaQoSConfig 15 }

alaQoSConfigAppliedClassifyFragments OBJECT-TYPE
  SYNTAX      INTEGER {
                yes (1),
                no (2)
              }
  MAX-ACCESS  read-only
  STATUS      current
  DESCRIPTION "Current indicator for classifying fragmented traffic at L4
               Does not take effect until an 'Apply' command is issued"
  ::= { alaQoSConfig 16 }

alaQoSConfigDefaultBridgedDisposition OBJECT-TYPE
  SYNTAX      INTEGER {
                accept (1),
                drop (2),
                deny (3)
              }
  MAX-ACCESS  read-write
  STATUS      current
  DESCRIPTION "Pending disposition of bridged traffic that doesn't match a
               policy.  Does not take effect until an 'Apply' command is issued."
  ::= { alaQoSConfig 17 }

alaQoSConfigAppliedDefaultBridgedDisposition OBJECT-TYPE
  SYNTAX      INTEGER {
                accept (1),
                drop (2),
                deny (3)
              }
  MAX-ACCESS  read-only
  STATUS      current
  DESCRIPTION "Current disposition of bridged traffic that doesn't match a
               policy."
  ::= { alaQoSConfig 18 }

alaQoSConfigDefaultRoutedDisposition OBJECT-TYPE
  SYNTAX      INTEGER {
                accept (1),
                drop (2),
                deny (3)
              }
  MAX-ACCESS  read-write
  STATUS      current
  DESCRIPTION "Pending disposition of routed traffic that doesn't match a
               policy.  Does not take effect until an 'Apply' command is issued."
  ::= { alaQoSConfig 19 }

alaQoSConfigAppliedDefaultRoutedDisposition OBJECT-TYPE
  SYNTAX      INTEGER {
                accept (1),
                drop (2),
                deny (3)
              }
  MAX-ACCESS  read-only
  STATUS      current
  DESCRIPTION "Current disposition of routed traffic that doesn't match a policy
"
  ::= { alaQoSConfig 20 }

alaQoSConfigDefaultMulticastDisposition OBJECT-TYPE
  SYNTAX      INTEGER {
                accept (1),
                drop (2),
                deny (3)
              }
  MAX-ACCESS  read-write
  STATUS      current
  DESCRIPTION "Pending disposition of IGMP requests that don't match a policy
               Does not take effect until an 'Apply' command is issued"
  ::= { alaQoSConfig 21 }

alaQoSConfigAppliedDefaultMulticastDisposition OBJECT-TYPE
  SYNTAX      INTEGER {
                accept (1),
                drop (2),
                deny (3)
              }
  MAX-ACCESS  read-only
  STATUS      current
  DESCRIPTION "Current disposition of IGMP requests that don't match a policy
"
  ::= { alaQoSConfig 22 }

alaQoSConfigStatsInterval OBJECT-TYPE
  SYNTAX      Integer32 (10..3600)
  MAX-ACCESS  read-write
  STATUS      current
  DESCRIPTION "Interval in seconds for how often statistics are updated"
  ::= { alaQoSConfig 23 }

alaQoSConfigLogLines OBJECT-TYPE
  SYNTAX      Integer32 (0..1024)
  MAX-ACCESS  read-write
  STATUS      current
  DESCRIPTION "Number of log lines to maintain in the QoS log"
  ::= { alaQoSConfig 24 }

alaQoSConfigLogLevel OBJECT-TYPE
  SYNTAX      Integer32 (2..9)
  MAX-ACCESS  read-write
  STATUS      current
  DESCRIPTION "The level of logging desired.  The higher the level, the more
               verbose the logging"
  ::= { alaQoSConfig 25 }

alaQoSConfigLogConsole OBJECT-TYPE
  SYNTAX      INTEGER {
                yes (1),
                no (2)
              }
  MAX-ACCESS  read-write
  STATUS      current
  DESCRIPTION "Whether QoS log events are logged to the console"
  ::= { alaQoSConfig 26 }

alaQoSConfigForwardLog OBJECT-TYPE
  SYNTAX      INTEGER {
                yes (1),
                no (2)
              }
  MAX-ACCESS  read-write
  STATUS      current
  DESCRIPTION "Whether QoS forwards logging events to PolicyManager"
  ::= { alaQoSConfig 27 }

alaQoSConfigClearLog OBJECT-TYPE
  SYNTAX      INTEGER {
                yes (1),
                no (2)
              }
  MAX-ACCESS  read-write
  STATUS      current
  DESCRIPTION "Clear the QoS log"
  ::= { alaQoSConfig 28 }

alaQoSConfigApply OBJECT-TYPE
  SYNTAX      INTEGER {
                yes (1),
                no (2)
              }
  MAX-ACCESS  read-write
  STATUS      current
  DESCRIPTION "Set to apply all pending QoS configuration/policy changes"
  ::= { alaQoSConfig 29 }

alaQoSConfigRevert OBJECT-TYPE
  SYNTAX      INTEGER {
                yes (1),
                no (2)
              }
  MAX-ACCESS  read-write
  STATUS      current
  DESCRIPTION "Set to revert all pending QoS configuration/policy changes"
  ::= { alaQoSConfig 30 }

alaQoSConfigReset OBJECT-TYPE
  SYNTAX      INTEGER {
                yes (1),
                no (2)
              }
  MAX-ACCESS  read-write
  STATUS      current
  DESCRIPTION "Set to reset global QoS configuration parameters to their
               default values"
  ::= { alaQoSConfig 31 }

alaQoSConfigStatsReset OBJECT-TYPE
  SYNTAX      INTEGER {
                yes (1),
                no (2)
              }
  MAX-ACCESS  read-write
  STATUS      current
  DESCRIPTION "Set to reset global QoS statistics counters"
  ::= { alaQoSConfig 32 }

alaQoSConfigFlush OBJECT-TYPE
  SYNTAX      INTEGER {
                yes (1),
                no (2)
              }
  MAX-ACCESS  read-write
  STATUS      current
  DESCRIPTION "Flush all pending policy objects"
  ::= { alaQoSConfig 33 }

alaQoSConfigDebug OBJECT-TYPE
  SYNTAX      Integer32
  MAX-ACCESS  read-write
  STATUS      current
  DESCRIPTION "Possible debug flags for QoS"
  ::= { alaQoSConfig 34 }

alaQoSConfigServicingMode OBJECT-TYPE
  SYNTAX      INTEGER {
                strictpriority (1),
                prioritywrr (2),
                wrr (3),
                drr (4)
              }
  MAX-ACCESS  read-create
  STATUS      current
  DESCRIPTION "Servicing mode for the system"
  ::= { alaQoSConfig 35 }

alaQoSConfigLowPriorityWeight OBJECT-TYPE
  SYNTAX      Integer32 (0..15)
  MAX-ACCESS  read-create
  STATUS      current
  DESCRIPTION "Weight to use for low priority queue(0) on fixed queue blades"
  ::= { alaQoSConfig 36 }

alaQoSConfigMediumPriorityWeight OBJECT-TYPE
  SYNTAX      Integer32 (0..15)
  MAX-ACCESS  read-create
  STATUS      current
  DESCRIPTION "Weight to use for medium priority queue(1) on fixed queue blades"
  ::= { alaQoSConfig 37 }

alaQoSConfigHighPriorityWeight OBJECT-TYPE
  SYNTAX      Integer32 (0..15)
  MAX-ACCESS  read-create
  STATUS      current
  DESCRIPTION "Weight to use for high priority queue(2) on fixed queue blades"
  ::= { alaQoSConfig 38 }

alaQoSConfigUrgentPriorityWeight OBJECT-TYPE
  SYNTAX      Integer32 (0..15)
  MAX-ACCESS  read-create
  STATUS      current
  DESCRIPTION "Weight to use for urgent priority queue(3) on fixed queue blades"
  ::= { alaQoSConfig 39 }

alaQoSConfigQ4PriorityWeight OBJECT-TYPE
  SYNTAX      Integer32 (0..15)
  MAX-ACCESS  read-create
  STATUS      current
  DESCRIPTION "Weight to use for COS 4 priority queue(4) on fixed queue blades"
  ::= { alaQoSConfig 40 }

alaQoSConfigQ5PriorityWeight OBJECT-TYPE
  SYNTAX      Integer32 (0..15)
  MAX-ACCESS  read-create
  STATUS      current
  DESCRIPTION "Weight to use for COS 5 priority queue(5) on fixed queue blades"
  ::= { alaQoSConfig 41 }

alaQoSConfigQ6PriorityWeight OBJECT-TYPE
  SYNTAX      Integer32 (0..15)
  MAX-ACCESS  read-create
  STATUS      current
  DESCRIPTION "Weight to use for COS 6 priority queue(6) on fixed queue blades"
  ::= { alaQoSConfig 42 }

alaQoSConfigQ7PriorityWeight OBJECT-TYPE
  SYNTAX      Integer32 (0..15)
  MAX-ACCESS  read-create
  STATUS      current
  DESCRIPTION "Weight to use for COS 7 priority queue(7) on fixed queue blades"
  ::= { alaQoSConfig 43 }

alaQoSConfigUserportFilter OBJECT-TYPE
  SYNTAX      Integer32
  MAX-ACCESS  read-create
  STATUS      current
  DESCRIPTION "Events/protocols to filter on a Userport.  Event bits values are:
                  spoof = 1
                  bpdu = 2
                  bgp = 4
                  ospf = 8
                  rip = 16
                  vrrp = 32
		  dhcp-server = 64
                  pim = 128
                  dvmrp = 256
                  is-is = 512
                  dnsreply = 1024"
  ::= { alaQoSConfig 44 }

alaQoSConfigAppliedUserportFilter OBJECT-TYPE
  SYNTAX      Integer32
  MAX-ACCESS  read-only
  STATUS      current
  DESCRIPTION "Events/protocols to filter on a Userport.  Event bits values are:
                  spoof = 1
                  bpdu = 2
                  bgp = 4
                  ospf = 8
                  rip = 16
                  vrrp = 32
		  dhcp-server = 64
                  pim = 128
                  dvmrp = 256
                  is-is = 512
                  dnsreply = 1024"
  ::= { alaQoSConfig 45 }

alaQoSConfigUserportShutdown OBJECT-TYPE
  SYNTAX      Integer32
  MAX-ACCESS  read-create
  STATUS      current
  DESCRIPTION "Events/protocols that trigger admin down of a Userport.
               Event bits values are:
                  spoof = 1
                  bpdu = 2
                  bgp = 4
                  ospf = 8
                  rip = 16
                  vrrp = 32
		  dhcp-server = 64
                  pim = 128
                  dvmrp = 256
                  is-is = 512
                  dnsreply = 1024"
  ::= { alaQoSConfig 46 }

alaQoSConfigAppliedUserportShutdown OBJECT-TYPE
  SYNTAX      Integer32
  MAX-ACCESS  read-only
  STATUS      current
  DESCRIPTION "Events/protocols that trigger admin down of a Userport.
               Event bits values are:
                  spoof = 1
                  bpdu = 2
                  bgp = 4
                  ospf = 8
                  rip = 16
                  vrrp = 32
		  dhcp-server = 64
                  pim = 128
                  dvmrp = 256
                  is-is = 512
                  dnsreply = 1024"
  ::= { alaQoSConfig 47 }

alaQoSConfigAutoNMS OBJECT-TYPE
  SYNTAX      INTEGER {
                yes (1),
                no (2)
              }
  MAX-ACCESS  read-write
  STATUS      current
  DESCRIPTION "Flag to indicate whether to Prioritize NMS traffic by default."
  ::= { alaQoSConfig 48 }

alaQoSConfigAutoPhones OBJECT-TYPE
  SYNTAX      INTEGER {
                pri0 (0),
                pri1 (1),
                pri2 (2),
                pri3 (3),
                pri4 (4),
                pri5 (5),
                pri6 (6),
                pri7 (7),
                trusted (8),
                disable (9)
              }
  MAX-ACCESS  read-write
  STATUS      current
  DESCRIPTION "Auto configure CSBU Phones 
              pri0-7 - will replace the priority.
              trusted - will allow priority from the orginator to be used.
              disable - will unconfigure to feature."
  ::= { alaQoSConfig 49 }

alaQoSConfigQMPage OBJECT-TYPE
  SYNTAX      INTEGER {
                yes (1),
                no (2)
              }
  MAX-ACCESS  read-write
  STATUS      current
  DESCRIPTION "Flag to indicate whether to send back a quarantined page when a client is quarantined but a remediation URL is not specified."
  ::= { alaQoSConfig 50 }

alaQoSConfigQMMACGroup OBJECT-TYPE
  SYNTAX	DisplayString (SIZE(0..31))
  MAX-ACCESS	read-write
  STATUS	current
  DESCRIPTION "Group name for quarantine manager quarantined MACs."
  ::= { alaQoSConfig 51 } 

alaQoSConfigQMPath OBJECT-TYPE
  SYNTAX	DisplayString (SIZE(0..255))
  MAX-ACCESS	read-write
  STATUS	current
  DESCRIPTION "Default path for remediation server redirect."
  ::= { alaQoSConfig 52 } 

alaQoSConfigDEIMapping OBJECT-TYPE
  SYNTAX      INTEGER {
                enabled (1),
                disabled (2)
              }
  MAX-ACCESS  read-create
  STATUS      current
  DESCRIPTION "This object specifies, in ingress traffic, the DEI/CFI bit is mapped
              or not to internal drop precedence or yellow color.

              enabled(1)  -- the DEI/CFI bit is mapped to internal drop precedence or yellow
                             color if that bit is set.
              disabled(2) -- the DEI/CFI bit is not mapped to drop precedence or yellow
                             color."
  DEFVAL      { disabled }
  ::= { alaQoSConfig 53 }

alaQoSConfigDEIMarking OBJECT-TYPE
  SYNTAX      INTEGER {
                enabled (1),
                disabled (2)
              }
  MAX-ACCESS  read-create
  STATUS      current
  DESCRIPTION "This object specifies, in egress traffic, the DEI/CFI bit is mapped
              or not to internal drop precedence or yellow color.

	      enabled(1) --  the DEI/CFI bit is mapped to internal drop precedence or yellow
			     color if that bit is set.
	      disabled(2) -- the DEI/CFI bit is not mapped to drop precedence or yellow
			     color."
  DEFVAL      { disabled }
  ::= { alaQoSConfig 54 }

alaQoSConfigStatsResetEgress OBJECT-TYPE
  SYNTAX      INTEGER {
                yes (1),
                no (2)
              }
  MAX-ACCESS  read-write
  STATUS      current
  DESCRIPTION "Set to reset global Egress QoS statistics counters"
  ::= { alaQoSConfig 55 }

alaQoSConfigForceYellowPriority  OBJECT-TYPE
SYNTAX      INTEGER {
                pri0 (0),
                pri1 (1),
                pri2 (2),
                pri3 (3),
                pri4 (4),
                pri5 (5),
                pri6 (6),
                pri7 (7),
                disable (8)
              }
  MAX-ACCESS  read-write
  STATUS      current
  DESCRIPTION "Change the Priority for Yellow Traffic 
              pri0-7 - will replace the priority.
              disable - will unconfigure to feature."
  DEFVAL 	{ pri0 }
  ::= { alaQoSConfig 56 }

alaQoSConfigMulticastRateLimit OBJECT-TYPE
  SYNTAX      INTEGER {
             pps128 (1),
             pps256 (2),
             pps512 (3),
             pps1024 (4)
}
 MAX-ACCESS  read-write
 STATUS      current
 DESCRIPTION "Used to set rate Limit in case of Qos debug"
 ::= { alaQoSConfig 57 }

alaQoSConfigForceYellowDSCP OBJECT-TYPE
SYNTAX      INTEGER {
                pri0 (0),
                pri1 (1),
                pri2 (2),
                pri3 (3),
                pri4 (4),
                pri5 (5),
                pri6 (6),
                pri7 (7),
                pri8 (8),
                pri9 (9),
                pri10 (10),
                pri11 (11),
                pri12 (12),
                pri13 (13),
                pri14 (14),
                pri15 (15),
                pri16 (16),
                pri17 (17),
                pri18 (18),
                pri19 (19),
                pri20 (20),
                pri21 (21),
                pri22 (22),
                pri23 (23),
                pri24 (24),
                pri25 (25),
                pri26 (26),
                pri27 (27),
                pri28 (28),
                pri29 (29),
                pri30 (30),
                pri31 (31),
                pri32 (32),
                pri33 (33),
                pri34 (34),
                pri35 (35),
                pri36 (36),
                pri37 (37),
                pri38 (38),
                pri39 (39),
                pri40 (40),
                pri51 (51),
                pri52 (52),
                pri53 (53),
                pri54 (54),
                pri55 (55),
                pri56 (56),
                pri57 (57),
                pri58 (58),
                pri59 (59),
                pri60 (60),
                pri61 (61),
                pri62 (62),
                pri63 (63),
                disable (64)
              }
 
  MAX-ACCESS  read-write
  STATUS      current
  DESCRIPTION "Change the DSCP value for Yellow Traffic
              pri0-63 - will replace the priority.
              disable - will unconfigure the feature."
  DEFVAL        { pri0 }
  ::= { alaQoSConfig 59 }

alaQoSConfigUserportLinkShutdown OBJECT-TYPE
   SYNTAX      Integer32
   MAX-ACCESS  read-create
   STATUS      current
   DESCRIPTION "Events/protocols that trigger link shut down of a Userport.
				Event bits values are:
				spoof = 1
				bpdu = 2
				bgp = 4
				ospf = 8
				rip = 16
				vrrp = 32
				dhcp-server = 64
				pim = 128
				dvmrp = 256
				is-is = 512
				dnsreply = 1024"
  ::= { alaQoSConfig 61 }

alaQoSConfigAppliedUserportLinkShutdown OBJECT-TYPE
  SYNTAX      Integer32
  MAX-ACCESS  read-only
  STATUS      current
  DESCRIPTION "Events/protocols that trigger Link shut down of a Userport.
                Event bits values are:
                spoof = 1
                bpdu = 2
                bgp = 4
                ospf = 8
                rip = 16
                vrrp = 32
                dhcp-server = 64
                pim = 128
                dvmrp = 256
                is-is = 512
                dnsreply = 1024"

  ::= { alaQoSConfig 62 }

alaQoSConfigNATFlush OBJECT-TYPE   
  SYNTAX      INTEGER {   
                yes (1),   
                no (2)   
              }   
  MAX-ACCESS  read-write   
  STATUS      current   
  DESCRIPTION "Flush all NAT Flow entries"   
  ::= { alaQoSConfig 63 } 
  

alaQoSConfigForceYellowUserPriority OBJECT-TYPE
SYNTAX      INTEGER {
                pri0 (0),
                pri1 (1),
                pri2 (2),
                pri3 (3),
                pri4 (4),
                pri5 (5),
                pri6 (6),
                pri7 (7),
                disable (8)
              }
  MAX-ACCESS  read-write
  STATUS      current
  DESCRIPTION "Change the 8021P Priority for Yellow Traffic
              pri0-7 - will replace the priority.
              disable - will unconfigure the feature."
  DEFVAL        { pri0 }
  ::= { alaQoSConfig 64 }
  
--
-- Definition of queue table
--

alaQoSQueueTable OBJECT-TYPE
  SYNTAX      SEQUENCE OF QoSQueueEntry
  MAX-ACCESS  not-accessible
  STATUS      current
  DESCRIPTION "Table of QoS Queue definitions"
  ::= { alaQoSMIBObjects 32 }

alaQoSQueueEntry OBJECT-TYPE
  SYNTAX      QoSQueueEntry
  MAX-ACCESS  not-accessible
  STATUS      current
  DESCRIPTION "Definition of QoS Queue"
  INDEX {
          alaQoSQueueId
        }
  ::= { alaQoSQueueTable 1 }

QoSQueueEntry ::=
  SEQUENCE
  {
    alaQoSQueueId                                           Integer32,
    alaQoSQueueSlot                                         Integer32,
    alaQoSQueuePort                                         Integer32,
    alaQoSQueuePortId                                       Integer32,
    alaQoSQueueType                                         INTEGER,
    alaQoSQueuePriority                                     Integer32,
    alaQoSQueueMinimumBandwidth                             Integer32,
    alaQoSQueueMaximumBandwidth                             Integer32,
    alaQoSQueueAverageBandwidth                             Integer32,
    alaQoSQueueMinimumDepth                                 Integer32,
    alaQoSQueueMaximumDepth                                 Integer32,
    alaQoSQueueMaximumBuffers                               Integer32,
    alaQoSQueue8021p                                        Integer32,
    alaQoSQueuePacketsSent                                  Integer32,
    alaQoSQueuePacketsDropped                               Integer32,
    alaQoSQueueMaxLength                                    Integer32,
    alaQoSQueueAverageLength                                Integer32,
    alaQoSQueueCurrentLength                                Integer32,
    alaQoSQueueAction                                       DisplayString
  }

alaQoSQueueId OBJECT-TYPE
  SYNTAX      Integer32(0..2147483647)
  MAX-ACCESS  not-accessible
  STATUS      current
  DESCRIPTION "Internal queue identifier"
  ::= { alaQoSQueueEntry 1 }

alaQoSQueueSlot OBJECT-TYPE
  SYNTAX      Integer32 (0..255)
  MAX-ACCESS  read-only
  STATUS      current
  DESCRIPTION "Physical slot queue is destined to"
  ::= { alaQoSQueueEntry 2 }

alaQoSQueuePort OBJECT-TYPE
  SYNTAX      Integer32 (0..255)
  MAX-ACCESS  read-only
  STATUS      current
  DESCRIPTION "Physical port queue is destined to"
  ::= { alaQoSQueueEntry 3 }

alaQoSQueuePortId OBJECT-TYPE
  SYNTAX      Integer32 (0..65535)
  MAX-ACCESS  read-only
  STATUS      current
  DESCRIPTION "Internal global port id of destination port"
  ::= { alaQoSQueueEntry 4 }

alaQoSQueueType OBJECT-TYPE
  SYNTAX      INTEGER {
                mammoth (1),
                priority (2),
                spwrr (3),
                wrr (4),
                drr (5)
              }
  MAX-ACCESS  read-only
  STATUS      current
  DESCRIPTION "Type of queueing done on this queue"
  ::= { alaQoSQueueEntry 5 }

alaQoSQueuePriority OBJECT-TYPE
  SYNTAX      Integer32 (0..255)
  MAX-ACCESS  read-only
  STATUS      current
  DESCRIPTION "Queueing priority for the queue"
  ::= { alaQoSQueueEntry 6 }

alaQoSQueueMinimumBandwidth OBJECT-TYPE
  SYNTAX      Integer32
  MAX-ACCESS  read-only
  STATUS      current
  DESCRIPTION "Minimum bandwidth (Kbits/sec) given to the queue"
  ::= { alaQoSQueueEntry 7 }

alaQoSQueueMaximumBandwidth OBJECT-TYPE
  SYNTAX      Integer32
  MAX-ACCESS  read-only
  STATUS      current
  DESCRIPTION "Maximum bandwidth (Kbits/sec) given to the queue"
  ::= { alaQoSQueueEntry 8 }

alaQoSQueueAverageBandwidth OBJECT-TYPE
  SYNTAX      Integer32
  MAX-ACCESS  read-only
  STATUS      current
  DESCRIPTION "Average measured bandwidth (Kbits/sec) for the queue"
  ::= { alaQoSQueueEntry 9 }

alaQoSQueueMinimumDepth OBJECT-TYPE
  SYNTAX      Integer32
  MAX-ACCESS  read-only
  STATUS      current
  DESCRIPTION "Minimum depth (Kbytes) of the queue"
  ::= { alaQoSQueueEntry 10 }

alaQoSQueueMaximumDepth OBJECT-TYPE
  SYNTAX      Integer32
  MAX-ACCESS  read-only
  STATUS      current
  DESCRIPTION "Maximum depth (Kbytes) of the queue"
  ::= { alaQoSQueueEntry 11 }

alaQoSQueueMaximumBuffers OBJECT-TYPE
  SYNTAX      Integer32 (0..65535)
  MAX-ACCESS  read-only
  STATUS      current
  DESCRIPTION "Maximum number of buffers for the queue"
  ::= { alaQoSQueueEntry 12 }

alaQoSQueue8021p OBJECT-TYPE
  SYNTAX      Integer32 (0..255)
  MAX-ACCESS  read-only
  STATUS      current
  DESCRIPTION "802.1p value queue places on traffic"
  ::= { alaQoSQueueEntry 13 }

alaQoSQueuePacketsSent OBJECT-TYPE
  SYNTAX      Integer32
  MAX-ACCESS  read-only
  STATUS      current
  DESCRIPTION "Number of packets sent through the queue"
  ::= { alaQoSQueueEntry 14 }

alaQoSQueuePacketsDropped OBJECT-TYPE
  SYNTAX      Integer32
  MAX-ACCESS  read-only
  STATUS      current
  DESCRIPTION "Number of packets dropped trying to queue into this queue"
  ::= { alaQoSQueueEntry 15 }

alaQoSQueueMaxLength OBJECT-TYPE
  SYNTAX      Integer32
  MAX-ACCESS  read-only
  STATUS      current
  DESCRIPTION "Maximum measured length the queue has reached in buffers"
  ::= { alaQoSQueueEntry 16 }

alaQoSQueueAverageLength OBJECT-TYPE
  SYNTAX      Integer32
  MAX-ACCESS  read-only
  STATUS      current
  DESCRIPTION "Average measured length of the queue in buffers"
  ::= { alaQoSQueueEntry 17 }

alaQoSQueueCurrentLength OBJECT-TYPE
  SYNTAX      Integer32
  MAX-ACCESS  read-only
  STATUS      current
  DESCRIPTION "Current measured length of the queue in buffers"
  ::= { alaQoSQueueEntry 18 }

alaQoSQueueAction OBJECT-TYPE
  SYNTAX      DisplayString (SIZE(0..31))
  MAX-ACCESS  read-only
  STATUS      current
  DESCRIPTION "Name of the action this queue was created from"
  ::= { alaQoSQueueEntry 19 }


--
-- Definition of statistics table
--

alaQoSStats OBJECT IDENTIFIER ::= { alaQoSMIBObjects 31 }

alaQoSStatsL2Events OBJECT-TYPE
  SYNTAX      Counter32
  MAX-ACCESS  read-only
  STATUS      current
  DESCRIPTION "Number of L2 classification events"
  ::= { alaQoSStats 1 }

alaQoSStatsL2Matches OBJECT-TYPE
  SYNTAX      Counter32
  MAX-ACCESS  read-only
  STATUS      current
  DESCRIPTION "Number of L2 classifications matching a policy"
  ::= { alaQoSStats 2 }

alaQoSStatsL2Drops OBJECT-TYPE
  SYNTAX      Counter32
  MAX-ACCESS  read-only
  STATUS      current
  DESCRIPTION "Number of L2 classifications matching a drop policy"
  ::= { alaQoSStats 3 }

alaQoSStatsL3IngressEvents OBJECT-TYPE
  SYNTAX      Counter32
  MAX-ACCESS  read-only
  STATUS      current
  DESCRIPTION "Number of L3/L4 ingress classification events"
  ::= { alaQoSStats 4 }

alaQoSStatsL3IngressMatches OBJECT-TYPE
  SYNTAX      Counter32
  MAX-ACCESS  read-only
  STATUS      current
  DESCRIPTION "Number of L3 ingress classifications matching a policy"
  ::= { alaQoSStats 5 }

alaQoSStatsL3IngressDrops OBJECT-TYPE
  SYNTAX      Counter32
  MAX-ACCESS  read-only
  STATUS      current
  DESCRIPTION "Number of L3 ingress classifications matching a drop policy"
  ::= { alaQoSStats 6 }

alaQoSStatsL3EgressEvents OBJECT-TYPE
  SYNTAX      Counter32
  MAX-ACCESS  read-only
  STATUS      current
  DESCRIPTION "Number of L3/L4 egress classification events"
  ::= { alaQoSStats 7 }

alaQoSStatsL3EgressMatches OBJECT-TYPE
  SYNTAX      Counter32
  MAX-ACCESS  read-only
  STATUS      current
  DESCRIPTION "Number of L3 egress classifications matching a policy"
  ::= { alaQoSStats 8 }

alaQoSStatsL3EgressDrops OBJECT-TYPE
  SYNTAX      Counter32
  MAX-ACCESS  read-only
  STATUS      current
  DESCRIPTION "Number of L3 egress classifications matching a drop policy"
  ::= { alaQoSStats 9 }

alaQoSStatsMulticastEvents OBJECT-TYPE
  SYNTAX      Counter32
  MAX-ACCESS  read-only
  STATUS      current
  DESCRIPTION "Number of IGMP classification events"
  ::= { alaQoSStats 10 }

alaQoSStatsMulticastMatches OBJECT-TYPE
  SYNTAX      Counter32
  MAX-ACCESS  read-only
  STATUS      current
  DESCRIPTION "Number of IGMP classifications matching a policy"
  ::= { alaQoSStats 11 }

alaQoSStatsMulticastDrops OBJECT-TYPE
  SYNTAX      Counter32
  MAX-ACCESS  read-only
  STATUS      current
  DESCRIPTION "Number of IGMP classifications matching a drop policy"
  ::= { alaQoSStats 12 }

alaQoSStatsFragments OBJECT-TYPE
  SYNTAX      Counter32
  MAX-ACCESS  read-only
  STATUS      current
  DESCRIPTION "Number of fragments processed by QoS"
  ::= { alaQoSStats 13 }

alaQoSStatsBadFragments OBJECT-TYPE
  SYNTAX      Counter32
  MAX-ACCESS  read-only
  STATUS      current
  DESCRIPTION "Number of illegal (offset = 1) fragments"
  ::= { alaQoSStats 14 }

alaQoSStatsUnknownFragments OBJECT-TYPE
  SYNTAX      Counter32
  MAX-ACCESS  read-only
  STATUS      current
  DESCRIPTION "Number of out of order fragment pieces"
  ::= { alaQoSStats 15 }

alaQoSStatsReflexiveFlows OBJECT-TYPE
  SYNTAX      Counter32
  MAX-ACCESS  read-only
  STATUS      current
  DESCRIPTION "Number of reflexive flow entries"
  ::= { alaQoSStats 16 }

alaQoSStatsReflexiveCorrections OBJECT-TYPE
  SYNTAX      Counter32
  MAX-ACCESS  read-only
  STATUS      current
  DESCRIPTION "Number of reflexive flow corrections"
  ::= { alaQoSStats 17 }

alaQoSStatsLoadBalanceFlows OBJECT-TYPE
  SYNTAX      Counter32
  MAX-ACCESS  read-only
  STATUS      current
  DESCRIPTION "Number of server load balanced flow entries"
  ::= { alaQoSStats 18 }

alaQoSStatsClassifierMaxNodes OBJECT-TYPE
  SYNTAX      Counter32
  MAX-ACCESS  read-only
  STATUS      current
  DESCRIPTION "Highest number of nodes in classifier tree"
  ::= { alaQoSStats 19 }

alaQoSStatsClassifierMaxDepth OBJECT-TYPE
  SYNTAX      Counter32
  MAX-ACCESS  read-only
  STATUS      current
  DESCRIPTION "Length of longest path in classifier tree"
  ::= { alaQoSStats 20 }

alaQoSStatsFlowLookups OBJECT-TYPE
  SYNTAX      Counter32
  MAX-ACCESS  read-only
  STATUS      current
  DESCRIPTION "Number of flow table lookups"
  ::= { alaQoSStats 21 }

alaQoSStatsFlowHits OBJECT-TYPE
  SYNTAX      Counter32
  MAX-ACCESS  read-only
  STATUS      current
  DESCRIPTION "Number of flow table lookup hits"
  ::= { alaQoSStats 22 }

alaQoSStatsSentNIMessages OBJECT-TYPE
  SYNTAX      Counter32
  MAX-ACCESS  read-only
  STATUS      current
  DESCRIPTION "Number of messages sent to NIs"
  ::= { alaQoSStats 23 }

alaQoSStatsReceivedNIMessages OBJECT-TYPE
  SYNTAX      Counter32
  MAX-ACCESS  read-only
  STATUS      current
  DESCRIPTION "Number of messages received from NIs"
  ::= { alaQoSStats 24 }

alaQoSStatsFailedNIMessages OBJECT-TYPE
  SYNTAX      Counter32
  MAX-ACCESS  read-only
  STATUS      current
  DESCRIPTION "Number of failed message attemptes to NIs"
  ::= { alaQoSStats 25 }

alaQoSStatsSpoofedEvents OBJECT-TYPE
  SYNTAX      Counter32
  MAX-ACCESS  read-only
  STATUS      current
  DESCRIPTION "Total Number of spoofed events"
  ::= { alaQoSStats 26 }

alaQoSStatsNonSpoofedEvents OBJECT-TYPE
  SYNTAX      Counter32
  MAX-ACCESS  read-only
  STATUS      current
  DESCRIPTION "Total number of non-spoofed events"
  ::= { alaQoSStats 27 }

alaQoSStatsDropServicesEvents OBJECT-TYPE
  SYNTAX      Counter32
  MAX-ACCESS  read-only
  STATUS      current
  DESCRIPTION "Total number of packets matching the DropServices group"
  ::= { alaQoSStats 28 }

--
-- Definition of slice table
--

alaQoSSlotTable OBJECT-TYPE
  SYNTAX      SEQUENCE OF QoSSlotEntry
  MAX-ACCESS  not-accessible
  STATUS      current
  DESCRIPTION "Table of QoS Slot definitions"
  ::= { alaQoSMIBObjects 33 }

alaQoSSlotEntry OBJECT-TYPE
  SYNTAX      QoSSlotEntry
  MAX-ACCESS  not-accessible
  STATUS      current
  DESCRIPTION "Definition of QoS Slot"
  INDEX {
          alaQoSSlotSlot,
          alaQoSSlotSlice
        }
  ::= { alaQoSSlotTable 1 }

QoSSlotEntry ::=
  SEQUENCE
  {
    alaQoSSlotSlot                                          Integer32,
    alaQoSSlotSlice                                         Integer32,
    alaQoSSlotType                                          INTEGER,
    alaQoSSlotMaxBuffers                                    Integer32,
    alaQoSSlotFreeBuffers1                                  Integer32,
    alaQoSSlotFreeBuffers2                                  Integer32,
    alaQoSSlotThreshold1Low                                 Integer32,
    alaQoSSlotThreshold1Medium                              Integer32,
    alaQoSSlotThreshold1High                                Integer32,
    alaQoSSlotThreshold1Urgent                              Integer32,
    alaQoSSlotThreshold2Low                                 Integer32,
    alaQoSSlotThreshold2Medium                              Integer32,
    alaQoSSlotThreshold2High                                Integer32,
    alaQoSSlotThreshold2Urgent                              Integer32,
    alaQoSSlotBuffersDenied                                 Integer32,
    alaQoSSlotBuffersDeniedAverage                          Integer32,
    alaQoSSlotBuffersDropped                                Integer32,
    alaQoSSlotBuffersDroppedAverage                         Integer32,
    alaQoSSlotWredThresholdP0Lower                          Integer32,
    alaQoSSlotWredThresholdP0Upper                          Integer32,
    alaQoSSlotWredThresholdP1Lower                          Integer32,
    alaQoSSlotWredThresholdP1Upper                          Integer32,
    alaQoSSlotWredThresholdP2Lower                          Integer32,
    alaQoSSlotWredThresholdP2Upper                          Integer32,
    alaQoSSlotWredThresholdP3Lower                          Integer32,
    alaQoSSlotWredThresholdP3Upper                          Integer32,
    alaQoSSlotWredAverageCounterWeight                      Integer32,
    alaQoSSlotWredThresholdStatus                           INTEGER,
    alaQoSSlotCbqThresholdMode                              INTEGER,
    alaQoSSlotCbqThresholdP1                                Integer32,
    alaQoSSlotCbqThresholdP2                                Integer32,
    alaQoSSlotCbqThresholdP3                                Integer32,
    alaQoSSlotHighDensity                                   INTEGER
  }

alaQoSSlotSlot OBJECT-TYPE
  SYNTAX      Integer32 (1..16)
  MAX-ACCESS  not-accessible
  STATUS      current
  DESCRIPTION "Physical slot number"
  ::= { alaQoSSlotEntry 1 }

alaQoSSlotSlice OBJECT-TYPE
  SYNTAX      Integer32 (0..4)
  MAX-ACCESS  not-accessible
  STATUS      current
  DESCRIPTION "Physical device number on slot"
  ::= { alaQoSSlotEntry 2 }

alaQoSSlotType OBJECT-TYPE
  SYNTAX      INTEGER {
                mammoth (1),
                kodiak (2),
                mailbox (3),
                coronado (4),
                ixe2424 (5),
                kite (6),
                fuji (7)
              }
  MAX-ACCESS  read-only
  STATUS      current
  DESCRIPTION "Type of hardware in this slot/slice"
  ::= { alaQoSSlotEntry 3 }

alaQoSSlotMaxBuffers OBJECT-TYPE
  SYNTAX      Integer32
  MAX-ACCESS  read-only
  STATUS      current
  DESCRIPTION "Maximum total buffers on this slot/slice"
  ::= { alaQoSSlotEntry 4 }

alaQoSSlotFreeBuffers1 OBJECT-TYPE
  SYNTAX      Integer32
  MAX-ACCESS  read-only
  STATUS      current
  DESCRIPTION "Current free buffers in list 1"
  ::= { alaQoSSlotEntry 5 }

alaQoSSlotFreeBuffers2 OBJECT-TYPE
  SYNTAX      Integer32
  MAX-ACCESS  read-only
  STATUS      current
  DESCRIPTION "Current free buffers in list 2"
  ::= { alaQoSSlotEntry 6 }

alaQoSSlotThreshold1Low OBJECT-TYPE
  SYNTAX      Integer32
  MAX-ACCESS  read-only
  STATUS      current
  DESCRIPTION "Buffer are not given to low priority traffic from list 1
               when free buffers in list 1 is less than this threshold."
  ::= { alaQoSSlotEntry 7 }

alaQoSSlotThreshold1Medium OBJECT-TYPE
  SYNTAX      Integer32
  MAX-ACCESS  read-only
  STATUS      current
  DESCRIPTION "Buffer are not given to medium priority traffic from list 1
               when free buffers in list 1 is less than this threshold."
  ::= { alaQoSSlotEntry 8 }

alaQoSSlotThreshold1High OBJECT-TYPE
  SYNTAX      Integer32
  MAX-ACCESS  read-only
  STATUS      current
  DESCRIPTION "Buffer are not given to high priority traffic from list 1
               when free buffers in list 1 is less than this threshold."
  ::= { alaQoSSlotEntry 9 }

alaQoSSlotThreshold1Urgent OBJECT-TYPE
  SYNTAX      Integer32
  MAX-ACCESS  read-only
  STATUS      current
  DESCRIPTION "Buffer are not given to urgent priority traffic from list 1
               when free buffers in list 1 is less than this threshold."
  ::= { alaQoSSlotEntry 10 }

alaQoSSlotThreshold2Low OBJECT-TYPE
  SYNTAX      Integer32
  MAX-ACCESS  read-only
  STATUS      current
  DESCRIPTION "Buffer are not given to low priority traffic from list 2
               when free buffers in list 2 is less than this threshold."
  ::= { alaQoSSlotEntry 11 }

alaQoSSlotThreshold2Medium OBJECT-TYPE
  SYNTAX      Integer32
  MAX-ACCESS  read-only
  STATUS      current
  DESCRIPTION "Buffer are not given to medium priority traffic from list 2
               when free buffers in list 2 is less than this threshold."
  ::= { alaQoSSlotEntry 12 }

alaQoSSlotThreshold2High OBJECT-TYPE
  SYNTAX      Integer32
  MAX-ACCESS  read-only
  STATUS      current
  DESCRIPTION "Buffer are not given to high priority traffic from list 2
               when free buffers in list 2 is less than this threshold."
  ::= { alaQoSSlotEntry 13 }

alaQoSSlotThreshold2Urgent OBJECT-TYPE
  SYNTAX      Integer32
  MAX-ACCESS  read-only
  STATUS      current
  DESCRIPTION "Buffer are not given to urgent priority traffic from list 2
               when free buffers in list 2 is less than this threshold."
  ::= { alaQoSSlotEntry 14 }

alaQoSSlotBuffersDenied OBJECT-TYPE
  SYNTAX      Integer32
  MAX-ACCESS  read-only
  STATUS      current
  DESCRIPTION "Buffers denied on this slot"
  ::= { alaQoSSlotEntry 15 }

alaQoSSlotBuffersDeniedAverage OBJECT-TYPE
  SYNTAX      Integer32
  MAX-ACCESS  read-only
  STATUS      current
  DESCRIPTION "Average number of denied buffers over time"
  ::= { alaQoSSlotEntry 16 }

alaQoSSlotBuffersDropped OBJECT-TYPE
  SYNTAX      Integer32
  MAX-ACCESS  read-only
  STATUS      current
  DESCRIPTION "Buffers dropped on this slot"
  ::= { alaQoSSlotEntry 17 }

alaQoSSlotBuffersDroppedAverage OBJECT-TYPE
  SYNTAX      Integer32
  MAX-ACCESS  read-only
  STATUS      current
  DESCRIPTION "Average number of dropped buffers over time"
  ::= { alaQoSSlotEntry 18 }

alaQoSSlotWredThresholdP0Lower OBJECT-TYPE
  SYNTAX      Integer32 (0..4095)
  MAX-ACCESS  read-create
  STATUS      current
  DESCRIPTION "Priority 0 WRED lower threshold for high density module"
  DEFVAL      { 4095 }
  ::= { alaQoSSlotEntry 19 }

alaQoSSlotWredThresholdP0Upper OBJECT-TYPE
  SYNTAX      Integer32 (0..4095)
  MAX-ACCESS  read-create
  STATUS      current
  DESCRIPTION "Priority 0 WRED upper threshold for high density module"
  DEFVAL      { 4095 }
  ::= { alaQoSSlotEntry 20 }

alaQoSSlotWredThresholdP1Lower OBJECT-TYPE
  SYNTAX      Integer32 (0..4095)
  MAX-ACCESS  read-create
  STATUS      current
  DESCRIPTION "Priority 1 WRED lower threshold for high density module"
  DEFVAL      { 4095 }
  ::= { alaQoSSlotEntry 21 }

alaQoSSlotWredThresholdP1Upper OBJECT-TYPE
  SYNTAX      Integer32 (0..4095)
  MAX-ACCESS  read-create
  STATUS      current
  DESCRIPTION "Priority 1 WRED upper threshold for high density module"
  DEFVAL      { 4095 }
  ::= { alaQoSSlotEntry 22 }

alaQoSSlotWredThresholdP2Lower OBJECT-TYPE
  SYNTAX      Integer32 (0..4095)
  MAX-ACCESS  read-create
  STATUS      current
  DESCRIPTION "Priority 2 WRED lower threshold for high density module"
  DEFVAL      { 4095 }
  ::= { alaQoSSlotEntry 23 }

alaQoSSlotWredThresholdP2Upper OBJECT-TYPE
  SYNTAX      Integer32 (0..4095)
  MAX-ACCESS  read-create
  STATUS      current
  DESCRIPTION "Priority 2 WRED upper threshold for high density module"
  DEFVAL      { 4095 }
  ::= { alaQoSSlotEntry 24 }

alaQoSSlotWredThresholdP3Lower OBJECT-TYPE
  SYNTAX      Integer32 (0..4095)
  MAX-ACCESS  read-create
  STATUS      current
  DESCRIPTION "Priority 3 WRED lower threshold for high density module"
  DEFVAL      { 4095 }
  ::= { alaQoSSlotEntry 25 }

alaQoSSlotWredThresholdP3Upper OBJECT-TYPE
  SYNTAX      Integer32 (0..4095)
  MAX-ACCESS  read-create
  STATUS      current
  DESCRIPTION "Priority 3 WRED upper threshold for high density module"
  DEFVAL      { 4095 }
  ::= { alaQoSSlotEntry 26 }

alaQoSSlotWredAverageCounterWeight OBJECT-TYPE
  SYNTAX      Integer32 (0..7)
  MAX-ACCESS  read-create
  STATUS      current
  DESCRIPTION "The weight used in the WRED algorithm.  It is used as a
               negative power of 2"
  DEFVAL      { 4 }
  ::= { alaQoSSlotEntry 27 }

alaQoSSlotWredThresholdStatus OBJECT-TYPE
  SYNTAX      INTEGER {
                enabled (1),
                disabled (2)
              }
  MAX-ACCESS  read-create
  STATUS      current
  DESCRIPTION "Status field indicating whether WRED maximum thresholds
               are specified(enable) or not(disable)."
  DEFVAL      { disabled }
  ::= { alaQoSSlotEntry 28 }

alaQoSSlotCbqThresholdMode OBJECT-TYPE
  SYNTAX      INTEGER {
                prioritywrr (1),
                wrr (2),
                strictpriority (3)
              }
  MAX-ACCESS  read-create
  STATUS      current
  DESCRIPTION "Servicing mode for the CBQ thresholds for high density modules"
  DEFVAL      { prioritywrr }
  ::= { alaQoSSlotEntry 29 }

alaQoSSlotCbqThresholdP1 OBJECT-TYPE
  SYNTAX      Integer32 (0..4095)
  MAX-ACCESS  read-create
  STATUS      current
  DESCRIPTION "Priority 1 CBQ threshold for high density module"
  ::= { alaQoSSlotEntry 30 }

alaQoSSlotCbqThresholdP2 OBJECT-TYPE
  SYNTAX      Integer32 (0..4095)
  MAX-ACCESS  read-create
  STATUS      current
  DESCRIPTION "Priority 2 CBQ threshold for high density module"
  ::= { alaQoSSlotEntry 31 }

alaQoSSlotCbqThresholdP3 OBJECT-TYPE
  SYNTAX      Integer32 (0..4095)
  MAX-ACCESS  read-create
  STATUS      current
  DESCRIPTION "Priority 3 CBQ threshold for high density module"
  ::= { alaQoSSlotEntry 32 }

alaQoSSlotHighDensity OBJECT-TYPE
  SYNTAX      INTEGER {
                yes (1),
                no (2)
              }
  MAX-ACCESS  read-only
  STATUS      current
  DESCRIPTION "Indicates whether this is a high-density slice or not."
  ::= { alaQoSSlotEntry 33 }


--
-- Definition of classify table
--

alaQoSClassify OBJECT IDENTIFIER ::= { alaQoSMIBObjects 34 }

alaQoSClassifyClassify OBJECT-TYPE
  SYNTAX      INTEGER {
                l2 (1),
                l3 (2),
                multicast (3)
              }
  MAX-ACCESS  read-write
  STATUS      current
  DESCRIPTION "Which classification routine to run on the sample packet"
  ::= { alaQoSClassify 1 }

alaQoSClassifyApplied OBJECT-TYPE
  SYNTAX      INTEGER {
                yes (1),
                no (2)
              }
  MAX-ACCESS  read-write
  STATUS      current
  DESCRIPTION "What set of policies QoS uses when testing the classifier.
               When yes(1) the applied policies are used.
               When no(2) the pending policies are used."
  ::= { alaQoSClassify 2 }

alaQoSClassifySourceSlot OBJECT-TYPE
  SYNTAX      Integer32 (0..16)
  MAX-ACCESS  read-write
  STATUS      current
  DESCRIPTION "Source physical slot to submit when testing classifier."
  ::= { alaQoSClassify 3 }

alaQoSClassifySourcePort OBJECT-TYPE
  SYNTAX      Integer32 (0..52)
  MAX-ACCESS  read-write
  STATUS      current
  DESCRIPTION "Source physical port to submit when testing classifier."
  ::= { alaQoSClassify 4 }

alaQoSClassifySourceInterfaceType OBJECT-TYPE
  SYNTAX      INTEGER {
                any (0),
                ethernet (1),
                wan (2),
                ethernet10 (3),
                ethernet100 (4),
                ethernet1G (5),
                ethernet10G (6),
                aggregate (7)
              }
  MAX-ACCESS  read-write
  STATUS      current
  DESCRIPTION "Source interface type to submit when testing classifier."
  ::= { alaQoSClassify 5 }

alaQoSClassifyDestinationSlot OBJECT-TYPE
  SYNTAX      Integer32 (0..16)
  MAX-ACCESS  read-write
  STATUS      current
  DESCRIPTION "Destination physical slot to submit when testing classifier."
  ::= { alaQoSClassify 6 }

alaQoSClassifyDestinationPort OBJECT-TYPE
  SYNTAX      Integer32 (0..52)
  MAX-ACCESS  read-write
  STATUS      current
  DESCRIPTION "Destination physical port to submit when testing classifier."
  ::= { alaQoSClassify 7 }

alaQoSClassifyDestinationInterfaceType OBJECT-TYPE
  SYNTAX      INTEGER {
                any (0),
                ethernet (1),
                wan (2),
                ethernet10 (3),
                ethernet100 (4),
                ethernet1G (5),
                ethernet10G (6),
                aggregate (7)
              }
  MAX-ACCESS  read-write
  STATUS      current
  DESCRIPTION "Destination interface type to submit when testing classifier."
  ::= { alaQoSClassify 8 }

alaQoSClassifySourceMac OBJECT-TYPE
  SYNTAX      MacAddress
  MAX-ACCESS  read-write
  STATUS      current
  DESCRIPTION "Source MAC address to submit when testing classifier."
  ::= { alaQoSClassify 9 }

alaQoSClassifyDestinationMac OBJECT-TYPE
  SYNTAX      MacAddress
  MAX-ACCESS  read-write
  STATUS      current
  DESCRIPTION "Destination MAC address to submit when testing classifier."
  ::= { alaQoSClassify 10 }

alaQoSClassifySourceVlan OBJECT-TYPE
  SYNTAX      Integer32 (0..65535)
  MAX-ACCESS  read-write
  STATUS      current
  DESCRIPTION "Source VLAN to submit when testing classifier."
  ::= { alaQoSClassify 11 }

alaQoSClassifyDestinationVlan OBJECT-TYPE
  SYNTAX      Integer32 (0..65535)
  MAX-ACCESS  read-write
  STATUS      current
  DESCRIPTION "Destination VLAN to submit when testing classifier."
  ::= { alaQoSClassify 12 }

alaQoSClassify8021p OBJECT-TYPE
  SYNTAX      Integer32 (0..7)
  MAX-ACCESS  read-write
  STATUS      current
  DESCRIPTION "802.1p value to submit when testing classifier."
  ::= { alaQoSClassify 13 }

alaQoSClassifySourceIp OBJECT-TYPE
  SYNTAX      IpAddress
  MAX-ACCESS  read-write
  STATUS      current
  DESCRIPTION "Source IP address to submit when testing classifier."
  ::= { alaQoSClassify 14 }

alaQoSClassifyDestinationIp OBJECT-TYPE
  SYNTAX      IpAddress
  MAX-ACCESS  read-write
  STATUS      current
  DESCRIPTION "Destination IP address to submit when testing classifier."
  ::= { alaQoSClassify 15 }

alaQoSClassifyMulticastIp OBJECT-TYPE
  SYNTAX      IpAddress
  MAX-ACCESS  read-write
  STATUS      current
  DESCRIPTION "Multicast IP address to submit when testing classifier."
  ::= { alaQoSClassify 16 }

alaQoSClassifyTos OBJECT-TYPE
  SYNTAX      Integer32 (0..7)
  MAX-ACCESS  read-write
  STATUS      current
  DESCRIPTION "TOS value to submit when testing classifier."
  ::= { alaQoSClassify 17 }

alaQoSClassifyDscp OBJECT-TYPE
  SYNTAX      Integer32 (0..63)
  MAX-ACCESS  read-write
  STATUS      current
  DESCRIPTION "DSCP value to submit when testing classifier."
  ::= { alaQoSClassify 18 }

alaQoSClassifyIpProtocol OBJECT-TYPE
  SYNTAX      Integer32 (0..255)
  MAX-ACCESS  read-write
  STATUS      current
  DESCRIPTION "IP protocol value to submit when testing classifier."
  ::= { alaQoSClassify 19 }

alaQoSClassifySourceIpPort OBJECT-TYPE
  SYNTAX      Integer32 (0..65535)
  MAX-ACCESS  read-write
  STATUS      current
  DESCRIPTION "Source IP port to submit when testing classifier."
  ::= { alaQoSClassify 20 }

alaQoSClassifyDestinationIpPort OBJECT-TYPE
  SYNTAX      Integer32 (0..65535)
  MAX-ACCESS  read-write
  STATUS      current
  DESCRIPTION "Destination IP port to submit when testing classifier."
  ::= { alaQoSClassify 21 }

alaQoSClassifyExecute OBJECT-TYPE
  SYNTAX      INTEGER {
                yes (1),
                no (2)
              }
  MAX-ACCESS  read-write
  STATUS      current
  DESCRIPTION "Writing to this field tells QoS to run the classifier on the
               current packet headers.  The classifier stores the results in
               result fields.  The next 'set' to the table will clear all fields
               before actually performing the set."
  ::= { alaQoSClassify 22 }

alaQoSClassifyL2SourceResultRule OBJECT-TYPE
  SYNTAX      DisplayString (SIZE(0..31))
  MAX-ACCESS  read-only
  STATUS      current
  DESCRIPTION "Matching rule for L2 (source)"
  ::= { alaQoSClassify 23 }

alaQoSClassifyL2SourceResultDisposition OBJECT-TYPE
  SYNTAX      INTEGER {
                accept (1),
                drop (2),
                deny (3)
              }
  MAX-ACCESS  read-only
  STATUS      current
  DESCRIPTION "Result disposition for L2 (source)"
  ::= { alaQoSClassify 24 }

alaQoSClassifyL2DestinationResultRule OBJECT-TYPE
  SYNTAX      DisplayString (SIZE(0..31))
  MAX-ACCESS  read-only
  STATUS      current
  DESCRIPTION "Matching rule for L2 (destination)"
  ::= { alaQoSClassify 25 }

alaQoSClassifyL2DestinationResultDisposition OBJECT-TYPE
  SYNTAX      INTEGER {
                accept (1),
                drop (2),
                deny (3)
              }
  MAX-ACCESS  read-only
  STATUS      current
  DESCRIPTION "Result disposition for L2 (destination)"
  ::= { alaQoSClassify 26 }

alaQoSClassifyL3ResultRule OBJECT-TYPE
  SYNTAX      DisplayString (SIZE(0..31))
  MAX-ACCESS  read-only
  STATUS      current
  DESCRIPTION "Matching rule for L3"
  ::= { alaQoSClassify 27 }

alaQoSClassifyL3ResultDisposition OBJECT-TYPE
  SYNTAX      INTEGER {
                accept (1),
                drop (2),
                deny (3)
              }
  MAX-ACCESS  read-only
  STATUS      current
  DESCRIPTION "Result disposition for L3"
  ::= { alaQoSClassify 28 }

alaQoSClassifyIGMPResultRule OBJECT-TYPE
  SYNTAX      DisplayString (SIZE(0..31))
  MAX-ACCESS  read-only
  STATUS      current
  DESCRIPTION "Matching rule for IGMP request"
  ::= { alaQoSClassify 29 }

alaQoSClassifyIGMPResultDisposition OBJECT-TYPE
  SYNTAX      INTEGER {
                accept (1),
                drop (2),
                deny (3)
              }
  MAX-ACCESS  read-only
  STATUS      current
  DESCRIPTION "Result disposition for IGMP"
  ::= { alaQoSClassify 30 }

alaQoSClassifyMulticastResultRule OBJECT-TYPE
  SYNTAX      DisplayString (SIZE(0..31))
  MAX-ACCESS  read-only
  STATUS      current
  DESCRIPTION "Matching rule for multicast"
  ::= { alaQoSClassify 31 }

alaQoSClassifyMulticastResultDisposition OBJECT-TYPE
  SYNTAX      INTEGER {
                accept (1),
                drop (2),
                deny (3)
              }
  MAX-ACCESS  read-only
  STATUS      current
  DESCRIPTION "Result disposition for multicast"
  ::= { alaQoSClassify 32 }


--
-- Definition of user cams table
--

alaQoSSlotProtocolTable OBJECT-TYPE
  SYNTAX      SEQUENCE OF QoSSlotProtocolEntry
  MAX-ACCESS  not-accessible
  STATUS      current
  DESCRIPTION "Table of QoS SlotProtocol definitions"
  ::= { alaQoSMIBObjects 35 }

alaQoSSlotProtocolEntry OBJECT-TYPE
  SYNTAX      QoSSlotProtocolEntry
  MAX-ACCESS  not-accessible
  STATUS      current
  DESCRIPTION "Definition of QoS SlotProtocol"
  INDEX {
          alaQoSSlotSlot,
          alaQoSSlotSlice,
          alaQoSSlotProtocolId
        }
  ::= { alaQoSSlotProtocolTable 1 }

QoSSlotProtocolEntry ::=
  SEQUENCE
  {
    alaQoSSlotProtocolId                                    INTEGER,
    alaQoSSlotProtocolEthertype                             Integer32,
    alaQoSSlotProtocolDsap                                  Integer32,
    alaQoSSlotProtocolSsap                                  Integer32,
    alaQoSSlotProtocol8023Enabled                           INTEGER,
    alaQoSSlotProtocolType                                  INTEGER,
    alaQoSSlotProtocolRowStatus                             RowStatus
  }

alaQoSSlotProtocolId OBJECT-TYPE
  SYNTAX      INTEGER {
                user1 (1),
                user2 (2),
                user3 (3),
                user4 (4),
                unknown (5)
              }
  MAX-ACCESS  not-accessible
  STATUS      current
  DESCRIPTION "Used on high density module classification in the MAC.
               This is the protocol ID used between the CAM and
               priority descriptors."
  ::= { alaQoSSlotProtocolEntry 1 }

alaQoSSlotProtocolEthertype OBJECT-TYPE
  SYNTAX      Integer32 (0..65535)
  MAX-ACCESS  read-create
  STATUS      current
  DESCRIPTION "Used on high density module classification in the MAC.
               This is the Ethernet type used between the CAM for
               classification."
  DEFVAL      { 0 }
  ::= { alaQoSSlotProtocolEntry 2 }

alaQoSSlotProtocolDsap OBJECT-TYPE
  SYNTAX      Integer32 (0..255)
  MAX-ACCESS  read-create
  STATUS      current
  DESCRIPTION "Used on high density module classification in the MAC.
               This is the destination SAP in an 802.3 packet."
  DEFVAL      { 0 }
  ::= { alaQoSSlotProtocolEntry 3 }

alaQoSSlotProtocolSsap OBJECT-TYPE
  SYNTAX      Integer32 (0..255)
  MAX-ACCESS  read-create
  STATUS      current
  DESCRIPTION "Used on high density module classification in the MAC.
               This is the source SAP in an 802.3 packet."
  DEFVAL      { 0 }
  ::= { alaQoSSlotProtocolEntry 4 }

alaQoSSlotProtocol8023Enabled OBJECT-TYPE
  SYNTAX      INTEGER {
                enable (1),
                disable (2)
              }
  MAX-ACCESS  read-create
  STATUS      current
  DESCRIPTION "Used on high density module classification in the MAC.
               This will enable 802.3 checking on the CAM entry."
  DEFVAL      { disable }
  ::= { alaQoSSlotProtocolEntry 5 }

alaQoSSlotProtocolType OBJECT-TYPE
  SYNTAX      INTEGER {
                priority (1),
                fallback (2)
              }
  MAX-ACCESS  read-create
  STATUS      current
  DESCRIPTION "Used on high density module classification in the MAC.
               This positions the CAM entry in the list.  Priority will
               put the entries in the front of the CAM, giving it priority.
               fallback will put the entry at the end."
  DEFVAL      { fallback }
  ::= { alaQoSSlotProtocolEntry 6 }

alaQoSSlotProtocolRowStatus OBJECT-TYPE
  SYNTAX      RowStatus
  MAX-ACCESS  read-create
  STATUS      current
  DESCRIPTION "Used to create/delete slot protoocols according to the
               RowStatus convention"
  ::= { alaQoSSlotProtocolEntry 7 }


--
-- Definition of user pdis table
--

alaQoSPortProtocolTable OBJECT-TYPE
  SYNTAX      SEQUENCE OF QoSPortProtocolEntry
  MAX-ACCESS  not-accessible
  STATUS      current
  DESCRIPTION "Table of QoS PortProtocol definitions"
  ::= { alaQoSMIBObjects 36 }

alaQoSPortProtocolEntry OBJECT-TYPE
  SYNTAX      QoSPortProtocolEntry
  MAX-ACCESS  not-accessible
  STATUS      current
  DESCRIPTION "Definition of QoS PortProtocol"
  INDEX {
          alaQoSPortSlot,
          alaQoSPortPort,
          alaQoSPortProtocolId
        }
  ::= { alaQoSPortProtocolTable 1 }

QoSPortProtocolEntry ::=
  SEQUENCE
  {
    alaQoSPortProtocolId                                    INTEGER,
    alaQoSPortProtocolClassification                        INTEGER,
    alaQoSPortProtocolPriorityP0                            Integer32,
    alaQoSPortProtocolPriorityP1                            Integer32,
    alaQoSPortProtocolPriorityP2                            Integer32,
    alaQoSPortProtocolPriorityP3                            Integer32,
    alaQoSPortProtocolPriorityP4                            Integer32,
    alaQoSPortProtocolPriorityP5                            Integer32,
    alaQoSPortProtocolPriorityP6                            Integer32,
    alaQoSPortProtocolPriorityP7                            Integer32,
    alaQoSPortProtocolRowStatus                             RowStatus
  }

alaQoSPortProtocolId OBJECT-TYPE
  SYNTAX      INTEGER {
                bpdu (1),
                lcpsnap (2),
                lcpeth (3),
                ipv4 (4),
                arp (5),
                rarp (6),
                ipv6 (7),
                ipx (8),
                apple (9),
                sna (10),
                decnet (11),
                user1 (12),
                user2 (13),
                user3 (14),
                user4 (15)
              }
  MAX-ACCESS  not-accessible
  STATUS      current
  DESCRIPTION "Used on high density module classification in the MAC.  This
               is the protocol id that needs to be changed."
  ::= { alaQoSPortProtocolEntry 1 }

alaQoSPortProtocolClassification OBJECT-TYPE
  SYNTAX      INTEGER {
                b8021p (1),
                tos (2),
                dscp (3)
              }
  MAX-ACCESS  read-create
  STATUS      current
  DESCRIPTION "Used on high density module classification in the MAC. This
               determines what type of classification is used to find
               priority."
  DEFVAL      { b8021p }
  ::= { alaQoSPortProtocolEntry 2 }

alaQoSPortProtocolPriorityP0 OBJECT-TYPE
  SYNTAX      Integer32 (0..3)
  MAX-ACCESS  read-create
  STATUS      current
  DESCRIPTION "Used on high density module classification in the MAC. This
               is the new priority for P0 to be mapped to."
  DEFVAL      { 0 }
  ::= { alaQoSPortProtocolEntry 3 }

alaQoSPortProtocolPriorityP1 OBJECT-TYPE
  SYNTAX      Integer32 (0..3)
  MAX-ACCESS  read-create
  STATUS      current
  DESCRIPTION "Used on high density module classification in the MAC. This
               is the new priority for P1 to be mapped to."
  DEFVAL      { 0 }
  ::= { alaQoSPortProtocolEntry 4 }

alaQoSPortProtocolPriorityP2 OBJECT-TYPE
  SYNTAX      Integer32 (0..3)
  MAX-ACCESS  read-create
  STATUS      current
  DESCRIPTION "Used on high density module classification in the MAC. This
               is the new priority for P2 to be mapped to."
  DEFVAL      { 1 }
  ::= { alaQoSPortProtocolEntry 5 }

alaQoSPortProtocolPriorityP3 OBJECT-TYPE
  SYNTAX      Integer32 (0..3)
  MAX-ACCESS  read-create
  STATUS      current
  DESCRIPTION "Used on high density module classification in the MAC. This
               is the new priority for P3 to be mapped to."
  DEFVAL      { 1 }
  ::= { alaQoSPortProtocolEntry 6 }

alaQoSPortProtocolPriorityP4 OBJECT-TYPE
  SYNTAX      Integer32 (0..3)
  MAX-ACCESS  read-create
  STATUS      current
  DESCRIPTION "Used on high density module classification in the MAC. This
               is the new priority for P4 to be mapped to."
  DEFVAL      { 2 }
  ::= { alaQoSPortProtocolEntry 7 }

alaQoSPortProtocolPriorityP5 OBJECT-TYPE
  SYNTAX      Integer32 (0..3)
  MAX-ACCESS  read-create
  STATUS      current
  DESCRIPTION "Used on high density module classification in the MAC. This
               is the new priority for P5 to be mapped to."
  DEFVAL      { 2 }
  ::= { alaQoSPortProtocolEntry 8 }

alaQoSPortProtocolPriorityP6 OBJECT-TYPE
  SYNTAX      Integer32 (0..3)
  MAX-ACCESS  read-create
  STATUS      current
  DESCRIPTION "Used on high density module classification in the MAC. This
               is the new priority for P6 to be mapped to."
  DEFVAL      { 3 }
  ::= { alaQoSPortProtocolEntry 9 }

alaQoSPortProtocolPriorityP7 OBJECT-TYPE
  SYNTAX      Integer32 (0..3)
  MAX-ACCESS  read-create
  STATUS      current
  DESCRIPTION "Used on high density module classification in the MAC. This
               is the new priority for P7 to be mapped to."
  DEFVAL      { 3 }
  ::= { alaQoSPortProtocolEntry 10 }

alaQoSPortProtocolRowStatus OBJECT-TYPE
  SYNTAX      RowStatus
  MAX-ACCESS  read-create
  STATUS      current
  DESCRIPTION "Used to create/delete rows according to RowStatus convention"
  ::= { alaQoSPortProtocolEntry 11 }


--
-- Definition of dscp table
--

alaQoSSlotDscpTable OBJECT-TYPE
  SYNTAX      SEQUENCE OF QoSSlotDscpEntry
  MAX-ACCESS  not-accessible
  STATUS      current
  DESCRIPTION "Table of QoS SlotDscp definitions"
  ::= { alaQoSMIBObjects 37 }

alaQoSSlotDscpEntry OBJECT-TYPE
  SYNTAX      QoSSlotDscpEntry
  MAX-ACCESS  not-accessible
  STATUS      current
  DESCRIPTION "Definition of QoS SlotDscp"
  INDEX {
          alaQoSSlotSlot,
          alaQoSSlotSlice,
          alaQoSSlotDscpIndex
        }
  ::= { alaQoSSlotDscpTable 1 }

QoSSlotDscpEntry ::=
  SEQUENCE
  {
    alaQoSSlotDscpIndex                                     Integer32,
    alaQoSSlotDscpPriority                                  Integer32
  }

alaQoSSlotDscpIndex OBJECT-TYPE
  SYNTAX      Integer32 (0..63)
  MAX-ACCESS  not-accessible
  STATUS      current
  DESCRIPTION "Used on high density module classification in the MAC
               This is the index into the DSCP table to access."
  ::= { alaQoSSlotDscpEntry 1 }

alaQoSSlotDscpPriority OBJECT-TYPE
  SYNTAX      Integer32 (0..3)
  MAX-ACCESS  read-create
  STATUS      current
  DESCRIPTION "Used on high density module classification in the MAC.
               This is the priority of the index of the DSCP table."
  ::= { alaQoSSlotDscpEntry 2 }


--
-- Definition of cams table
--

alaQoSSlotPcamTable OBJECT-TYPE
  SYNTAX      SEQUENCE OF QoSSlotPcamEntry
  MAX-ACCESS  not-accessible
  STATUS      current
  DESCRIPTION "Table of QoS SlotPcam definitions"
  ::= { alaQoSMIBObjects 38 }

alaQoSSlotPcamEntry OBJECT-TYPE
  SYNTAX      QoSSlotPcamEntry
  MAX-ACCESS  not-accessible
  STATUS      current
  DESCRIPTION "Definition of QoS SlotPcam"
  INDEX {
          alaQoSSlotSlot,
          alaQoSSlotSlice,
          alaQoSSlotPcamId
        }
  ::= { alaQoSSlotPcamTable 1 }

QoSSlotPcamEntry ::=
  SEQUENCE
  {
    alaQoSSlotPcamId                                        Integer32,
    alaQoSSlotPcamEthertype                                 Integer32,
    alaQoSSlotPcamDsap                                      Integer32,
    alaQoSSlotPcamSsap                                      Integer32,
    alaQoSSlotPcam8023Enabled                               INTEGER,
    alaQoSSlotPcamProtocolNumber                            Integer32,
    alaQoSSlotPcamEnableEntry                               INTEGER,
    alaQoSSlotPcamEnable8023                                INTEGER,
    alaQoSSlotPcamEnableDsap                                INTEGER,
    alaQoSSlotPcamEnableSsap                                INTEGER,
    alaQoSSlotPcamEnableEthertype                           INTEGER
  }

alaQoSSlotPcamId OBJECT-TYPE
  SYNTAX      Integer32 (0..24)
  MAX-ACCESS  not-accessible
  STATUS      current
  DESCRIPTION "Used on high density module classification in the MAC.
               This is the index used in the PCAM."
  ::= { alaQoSSlotPcamEntry 1 }

alaQoSSlotPcamEthertype OBJECT-TYPE
  SYNTAX      Integer32 (0..65535)
  MAX-ACCESS  read-only
  STATUS      current
  DESCRIPTION "Used on high density module classification in the MAC.
               This is the Ethernet type in the CAM."
  ::= { alaQoSSlotPcamEntry 2 }

alaQoSSlotPcamDsap OBJECT-TYPE
  SYNTAX      Integer32 (0..255)
  MAX-ACCESS  read-only
  STATUS      current
  DESCRIPTION "Used on high density module classification in the MAC.
               This is the destination SAP in an 802.3 packet."
  ::= { alaQoSSlotPcamEntry 3 }

alaQoSSlotPcamSsap OBJECT-TYPE
  SYNTAX      Integer32 (0..255)
  MAX-ACCESS  read-only
  STATUS      current
  DESCRIPTION "Used on high density module classification in the MAC.
               This is the source SAP in an 802.3 packet."
  ::= { alaQoSSlotPcamEntry 4 }

alaQoSSlotPcam8023Enabled OBJECT-TYPE
  SYNTAX      INTEGER {
                yes (1),
                no (2)
              }
  MAX-ACCESS  read-only
  STATUS      current
  DESCRIPTION "Used on high density module classification in the MAC.
               This will enable 802.3 checking on the CAM entry."
  ::= { alaQoSSlotPcamEntry 5 }

alaQoSSlotPcamProtocolNumber OBJECT-TYPE
  SYNTAX      Integer32 (0..255)
  MAX-ACCESS  read-only
  STATUS      current
  DESCRIPTION "Used on high density module classification in the MAC.
               This identifies the protocol number of the CAM entry."
  ::= { alaQoSSlotPcamEntry 6 }

alaQoSSlotPcamEnableEntry OBJECT-TYPE
  SYNTAX      INTEGER {
                yes (1),
                no (2)
              }
  MAX-ACCESS  read-only
  STATUS      current
  DESCRIPTION "Used on high density module to enable the pcam entry."
  ::= { alaQoSSlotPcamEntry 7 }

alaQoSSlotPcamEnable8023 OBJECT-TYPE
  SYNTAX      INTEGER {
                yes (1),
                no (2)
              }
  MAX-ACCESS  read-only
  STATUS      current
  DESCRIPTION "Used on high density module to indiciate if 802.3
               is enabled in the pcam entry."
  ::= { alaQoSSlotPcamEntry 8 }

alaQoSSlotPcamEnableDsap OBJECT-TYPE
  SYNTAX      INTEGER {
                yes (1),
                no (2)
              }
  MAX-ACCESS  read-only
  STATUS      current
  DESCRIPTION "Used on high density module to indiciate if DSAP
               is enabled in the pcam entry."
  ::= { alaQoSSlotPcamEntry 9 }

alaQoSSlotPcamEnableSsap OBJECT-TYPE
  SYNTAX      INTEGER {
                yes (1),
                no (2)
              }
  MAX-ACCESS  read-only
  STATUS      current
  DESCRIPTION "Used on high density module to indiciate if SSAP
               is enabled in the pcam entry."
  ::= { alaQoSSlotPcamEntry 10 }

alaQoSSlotPcamEnableEthertype OBJECT-TYPE
  SYNTAX      INTEGER {
                yes (1),
                no (2)
              }
  MAX-ACCESS  read-only
  STATUS      current
  DESCRIPTION "Used on high density module to indiciate if Ethertype
               is enabled in the pcam entry."
  ::= { alaQoSSlotPcamEntry 11 }


--
-- Definition of pdi table
--

alaQoSPortPdiTable OBJECT-TYPE
  SYNTAX      SEQUENCE OF QoSPortPdiEntry
  MAX-ACCESS  not-accessible
  STATUS      current
  DESCRIPTION "Table of QoS PortPdi definitions"
  ::= { alaQoSMIBObjects 39 }

alaQoSPortPdiEntry OBJECT-TYPE
  SYNTAX      QoSPortPdiEntry
  MAX-ACCESS  not-accessible
  STATUS      current
  DESCRIPTION "Definition of QoS PortPdi"
  INDEX {
          alaQoSPortSlot,
          alaQoSPortPort,
          alaQoSPortPdiId
        }
  ::= { alaQoSPortPdiTable 1 }

QoSPortPdiEntry ::=
  SEQUENCE
  {
    alaQoSPortPdiId                                         Integer32,
    alaQoSPortPdiPriorityType                               Integer32,
    alaQoSPortPdiPriorityP0                                 Integer32,
    alaQoSPortPdiPriorityP1                                 Integer32,
    alaQoSPortPdiPriorityP2                                 Integer32,
    alaQoSPortPdiPriorityP3                                 Integer32,
    alaQoSPortPdiPriorityP4                                 Integer32,
    alaQoSPortPdiPriorityP5                                 Integer32,
    alaQoSPortPdiPriorityP6                                 Integer32,
    alaQoSPortPdiPriorityP7                                 Integer32
  }

alaQoSPortPdiId OBJECT-TYPE
  SYNTAX      Integer32 (0..16)
  MAX-ACCESS  not-accessible
  STATUS      current
  DESCRIPTION "Used on high density module classification in the MAC.
               This is the index used in the PDI."
  ::= { alaQoSPortPdiEntry 1 }

alaQoSPortPdiPriorityType OBJECT-TYPE
  SYNTAX      Integer32 (0..255)
  MAX-ACCESS  read-only
  STATUS      current
  DESCRIPTION "Used on high density module classification in the MAC.
               This is the classification type on the port."
  ::= { alaQoSPortPdiEntry 2 }

alaQoSPortPdiPriorityP0 OBJECT-TYPE
  SYNTAX      Integer32 (0..255)
  MAX-ACCESS  read-only
  STATUS      current
  DESCRIPTION "Used on high density module classification in the MAC.
               This is the internal priority mapping for a P0 packet."
  ::= { alaQoSPortPdiEntry 3 }

alaQoSPortPdiPriorityP1 OBJECT-TYPE
  SYNTAX      Integer32 (0..255)
  MAX-ACCESS  read-only
  STATUS      current
  DESCRIPTION "Used on high density module classification in the MAC.
               This is the internal priority mapping for a P1 packet."
  ::= { alaQoSPortPdiEntry 4 }

alaQoSPortPdiPriorityP2 OBJECT-TYPE
  SYNTAX      Integer32 (0..255)
  MAX-ACCESS  read-only
  STATUS      current
  DESCRIPTION "Used on high density module classification in the MAC.
               This is the internal priority mapping for a P2 packet."
  ::= { alaQoSPortPdiEntry 5 }

alaQoSPortPdiPriorityP3 OBJECT-TYPE
  SYNTAX      Integer32 (0..255)
  MAX-ACCESS  read-only
  STATUS      current
  DESCRIPTION "Used on high density module classification in the MAC.
               This is the internal priority mapping for a P3 packet."
  ::= { alaQoSPortPdiEntry 6 }

alaQoSPortPdiPriorityP4 OBJECT-TYPE
  SYNTAX      Integer32 (0..255)
  MAX-ACCESS  read-only
  STATUS      current
  DESCRIPTION "Used on high density module classification in the MAC.
               This is the internal priority mapping for a P4 packet."
  ::= { alaQoSPortPdiEntry 7 }

alaQoSPortPdiPriorityP5 OBJECT-TYPE
  SYNTAX      Integer32 (0..255)
  MAX-ACCESS  read-only
  STATUS      current
  DESCRIPTION "Used on high density module classification in the MAC.
               This is the internal priority mapping for a P5 packet."
  ::= { alaQoSPortPdiEntry 8 }

alaQoSPortPdiPriorityP6 OBJECT-TYPE
  SYNTAX      Integer32 (0..255)
  MAX-ACCESS  read-only
  STATUS      current
  DESCRIPTION "Used on high density module classification in the MAC.
               This is the internal priority mapping for a P6 packet."
  ::= { alaQoSPortPdiEntry 9 }

alaQoSPortPdiPriorityP7 OBJECT-TYPE
  SYNTAX      Integer32 (0..255)
  MAX-ACCESS  read-only
  STATUS      current
  DESCRIPTION "Used on high density module classification in the MAC.
               This is the internal priority mapping for a P7 packet."
  ::= { alaQoSPortPdiEntry 10 }


--
-- Definition of validity period table
--

alaQoSValidityPeriodTable OBJECT-TYPE
  SYNTAX      SEQUENCE OF QoSValidityPeriodEntry
  MAX-ACCESS  not-accessible
  STATUS      current
  DESCRIPTION "Table of QoS ValidityPeriod definitions"
  ::= { alaQoSMIBObjects 40 }

alaQoSValidityPeriodEntry OBJECT-TYPE
  SYNTAX      QoSValidityPeriodEntry
  MAX-ACCESS  not-accessible
  STATUS      current
  DESCRIPTION "Definition of QoS ValidityPeriod"
  INDEX {
          alaQoSValidityPeriodName
        }
  ::= { alaQoSValidityPeriodTable 1 }

QoSValidityPeriodEntry ::=
  SEQUENCE
  {
    alaQoSValidityPeriodName                                DisplayString,
    alaQoSValidityPeriodSource                              INTEGER,
    alaQoSValidityPeriodDays                                Integer32,
    alaQoSValidityPeriodDaysStatus                          INTEGER,
    alaQoSValidityPeriodMonths                              Integer32,
    alaQoSValidityPeriodMonthsStatus                        INTEGER,
    alaQoSValidityPeriodHour                                DisplayString,
    alaQoSValidityPeriodHourStatus                          INTEGER,
    alaQoSValidityPeriodEndHour                             DisplayString,
    alaQoSValidityPeriodInterval                            DisplayString,
    alaQoSValidityPeriodIntervalStatus                      INTEGER,
    alaQoSValidityPeriodEndInterval                         DisplayString,
    alaQoSValidityPeriodRowStatus                           RowStatus
  }

alaQoSValidityPeriodName OBJECT-TYPE
  SYNTAX      DisplayString (SIZE(0..31))
  MAX-ACCESS  not-accessible
  STATUS      current
  DESCRIPTION "Name of validity period"
  ::= { alaQoSValidityPeriodEntry 1 }

alaQoSValidityPeriodSource OBJECT-TYPE
  SYNTAX      INTEGER {
                ldap (1),
                cli (2),
                blt (3),
                api (4),
                imp (5)
              }
  MAX-ACCESS  read-create
  STATUS      current
  DESCRIPTION "What entity created the validity period."
  DEFVAL      { cli }
  ::= { alaQoSValidityPeriodEntry 2 }

alaQoSValidityPeriodDays OBJECT-TYPE
  SYNTAX      Integer32
  MAX-ACCESS  read-create
  STATUS      current
  DESCRIPTION "Bitfield for each day of the week this validity period
               is active.  Monday is least significant, Sunday
               is most significant."
  ::= { alaQoSValidityPeriodEntry 3 }

alaQoSValidityPeriodDaysStatus OBJECT-TYPE
  SYNTAX      INTEGER {
                enabled (1),
                disabled (2)
              }
  MAX-ACCESS  read-create
  STATUS      current
  DESCRIPTION "Status field indicating whether the validity period
               has specific active days of the month."
  DEFVAL      { disabled }
  ::= { alaQoSValidityPeriodEntry 4 }

alaQoSValidityPeriodMonths OBJECT-TYPE
  SYNTAX      Integer32
  MAX-ACCESS  read-create
  STATUS      current
  DESCRIPTION "Bitfield for each month this validity period
               is active.  January is least significant. Decemeber
               is most significant."
  ::= { alaQoSValidityPeriodEntry 5 }

alaQoSValidityPeriodMonthsStatus OBJECT-TYPE
  SYNTAX      INTEGER {
                enabled (1),
                disabled (2)
              }
  MAX-ACCESS  read-create
  STATUS      current
  DESCRIPTION "Status field indicating whether the validity period
               has specific active days of the week."
  DEFVAL      { disabled }
  ::= { alaQoSValidityPeriodEntry 6 }

alaQoSValidityPeriodHour OBJECT-TYPE
  SYNTAX      DisplayString (SIZE(0..7))
  MAX-ACCESS  read-create
  STATUS      current
  DESCRIPTION "Time of day this period becomes active.
               Format is 'hh:mm'"
  ::= { alaQoSValidityPeriodEntry 7 }

alaQoSValidityPeriodHourStatus OBJECT-TYPE
  SYNTAX      INTEGER {
                enabled (1),
                disabled (2)
              }
  MAX-ACCESS  read-create
  STATUS      current
  DESCRIPTION "Status field indicating whether the validity period
               has specific active hours of the day."
  DEFVAL      { disabled }
  ::= { alaQoSValidityPeriodEntry 8 }

alaQoSValidityPeriodEndHour OBJECT-TYPE
  SYNTAX      DisplayString (SIZE(0..7))
  MAX-ACCESS  read-create
  STATUS      current
  DESCRIPTION "Time of day this period becomes inactive.
               Format is 'hh:mm'"
  ::= { alaQoSValidityPeriodEntry 9 }

alaQoSValidityPeriodInterval OBJECT-TYPE
  SYNTAX      DisplayString (SIZE(0..19))
  MAX-ACCESS  read-create
  STATUS      current
  DESCRIPTION "Date/time when the validity period begins.
               Format is 'mm/dd/yyyy hh:mm'"
  ::= { alaQoSValidityPeriodEntry 10 }

alaQoSValidityPeriodIntervalStatus OBJECT-TYPE
  SYNTAX      INTEGER {
                enabled (1),
                disabled (2)
              }
  MAX-ACCESS  read-create
  STATUS      current
  DESCRIPTION "Status field indicating whether the validity period
               has a specific active date-time interval."
  DEFVAL      { disabled }
  ::= { alaQoSValidityPeriodEntry 11 }

alaQoSValidityPeriodEndInterval OBJECT-TYPE
  SYNTAX      DisplayString (SIZE(0..19))
  MAX-ACCESS  read-create
  STATUS      current
  DESCRIPTION "Date/time when the validity period ends.
               Format is 'mm/dd/yyyy hh:mm'"
  ::= { alaQoSValidityPeriodEntry 12 }

alaQoSValidityPeriodRowStatus OBJECT-TYPE
  SYNTAX      RowStatus
  MAX-ACCESS  read-create
  STATUS      current
  DESCRIPTION "Used to create/delete validity periods according
               to the RowStatus convention"
  ::= { alaQoSValidityPeriodEntry 13 }


--
-- Definition of validity period table
--

alaQoSAppliedValidityPeriodTable OBJECT-TYPE
  SYNTAX      SEQUENCE OF QoSAppliedValidityPeriodEntry
  MAX-ACCESS  not-accessible
  STATUS      current
  DESCRIPTION "Table of QoS AppliedValidityPeriod definitions"
  ::= { alaQoSMIBObjects 41 }

alaQoSAppliedValidityPeriodEntry OBJECT-TYPE
  SYNTAX      QoSAppliedValidityPeriodEntry
  MAX-ACCESS  not-accessible
  STATUS      current
  DESCRIPTION "Definition of QoS AppliedValidityPeriod"
  INDEX {
          alaQoSAppliedValidityPeriodName
        }
  ::= { alaQoSAppliedValidityPeriodTable 1 }

QoSAppliedValidityPeriodEntry ::=
  SEQUENCE
  {
    alaQoSAppliedValidityPeriodName                         DisplayString,
    alaQoSAppliedValidityPeriodSource                       INTEGER,
    alaQoSAppliedValidityPeriodDays                         Integer32,
    alaQoSAppliedValidityPeriodDaysStatus                   INTEGER,
    alaQoSAppliedValidityPeriodMonths                       Integer32,
    alaQoSAppliedValidityPeriodMonthsStatus                 INTEGER,
    alaQoSAppliedValidityPeriodHour                         DisplayString,
    alaQoSAppliedValidityPeriodHourStatus                   INTEGER,
    alaQoSAppliedValidityPeriodEndHour                      DisplayString,
    alaQoSAppliedValidityPeriodInterval                     DisplayString,
    alaQoSAppliedValidityPeriodIntervalStatus               INTEGER,
    alaQoSAppliedValidityPeriodEndInterval                  DisplayString,
    alaQoSAppliedValidityPeriodRowStatus                    RowStatus
  }

alaQoSAppliedValidityPeriodName OBJECT-TYPE
  SYNTAX      DisplayString (SIZE(0..31))
  MAX-ACCESS  not-accessible
  STATUS      current
  DESCRIPTION "Name of validity period"
  ::= { alaQoSAppliedValidityPeriodEntry 1 }

alaQoSAppliedValidityPeriodSource OBJECT-TYPE
  SYNTAX      INTEGER {
                ldap (1),
                cli (2),
                blt (3),
                api (4),
                imp (5)
              }
  MAX-ACCESS  read-only
  STATUS      current
  DESCRIPTION "What entity created the validity period."
  ::= { alaQoSAppliedValidityPeriodEntry 2 }

alaQoSAppliedValidityPeriodDays OBJECT-TYPE
  SYNTAX      Integer32
  MAX-ACCESS  read-only
  STATUS      current
  DESCRIPTION "Bitfield for each day of the week this validity period
               is active.  Monday is least significant, Sunday
               is most significant."
  ::= { alaQoSAppliedValidityPeriodEntry 3 }

alaQoSAppliedValidityPeriodDaysStatus OBJECT-TYPE
  SYNTAX      INTEGER {
                enabled (1),
                disabled (2)
              }
  MAX-ACCESS  read-only
  STATUS      current
  DESCRIPTION "Status field indicating whether the validity period
               has specific active days of the month."
  ::= { alaQoSAppliedValidityPeriodEntry 4 }

alaQoSAppliedValidityPeriodMonths OBJECT-TYPE
  SYNTAX      Integer32
  MAX-ACCESS  read-only
  STATUS      current
  DESCRIPTION "Bitfield for each month this validity period
               is active.  January is least significant. Decemeber
               is most significant."
  ::= { alaQoSAppliedValidityPeriodEntry 5 }

alaQoSAppliedValidityPeriodMonthsStatus OBJECT-TYPE
  SYNTAX      INTEGER {
                enabled (1),
                disabled (2)
              }
  MAX-ACCESS  read-only
  STATUS      current
  DESCRIPTION "Status field indicating whether the validity period
               has specific active days of the week."
  ::= { alaQoSAppliedValidityPeriodEntry 6 }

alaQoSAppliedValidityPeriodHour OBJECT-TYPE
  SYNTAX      DisplayString (SIZE(0..7))
  MAX-ACCESS  read-only
  STATUS      current
  DESCRIPTION "Time of day this period becomes active.
               Format is 'hh:mm'"
  ::= { alaQoSAppliedValidityPeriodEntry 7 }

alaQoSAppliedValidityPeriodHourStatus OBJECT-TYPE
  SYNTAX      INTEGER {
                enabled (1),
                disabled (2)
              }
  MAX-ACCESS  read-only
  STATUS      current
  DESCRIPTION "Status field indicating whether the validity period
               has specific active hours of the day."
  ::= { alaQoSAppliedValidityPeriodEntry 8 }

alaQoSAppliedValidityPeriodEndHour OBJECT-TYPE
  SYNTAX      DisplayString (SIZE(0..7))
  MAX-ACCESS  read-only
  STATUS      current
  DESCRIPTION "Time of day this period becomes inactive.
               Format is 'hh:mm'"
  ::= { alaQoSAppliedValidityPeriodEntry 9 }

alaQoSAppliedValidityPeriodInterval OBJECT-TYPE
  SYNTAX      DisplayString (SIZE(0..19))
  MAX-ACCESS  read-only
  STATUS      current
  DESCRIPTION "Date/time when the validity period begins.
               Format is 'mm/dd/yyyy hh:mm'"
  ::= { alaQoSAppliedValidityPeriodEntry 10 }

alaQoSAppliedValidityPeriodIntervalStatus OBJECT-TYPE
  SYNTAX      INTEGER {
                enabled (1),
                disabled (2)
              }
  MAX-ACCESS  read-only
  STATUS      current
  DESCRIPTION "Status field indicating whether the validity period
               has a specific active date-time interval."
  ::= { alaQoSAppliedValidityPeriodEntry 11 }

alaQoSAppliedValidityPeriodEndInterval OBJECT-TYPE
  SYNTAX      DisplayString (SIZE(0..19))
  MAX-ACCESS  read-only
  STATUS      current
  DESCRIPTION "Date/time when the validity period ends.
               Format is 'mm/dd/yyyy hh:mm'"
  ::= { alaQoSAppliedValidityPeriodEntry 12 }

alaQoSAppliedValidityPeriodRowStatus OBJECT-TYPE
  SYNTAX      RowStatus
  MAX-ACCESS  read-only
  STATUS      current
  DESCRIPTION "Used to create/delete validity periods according
               to the RowStatus convention"
  ::= { alaQoSAppliedValidityPeriodEntry 13 }


--
-- Definition of import table
--

alaQoSImportTable OBJECT-TYPE
  SYNTAX      SEQUENCE OF QoSImportEntry
  MAX-ACCESS  not-accessible
  STATUS      current
  DESCRIPTION "Table of QoS Import definitions"
  ::= { alaQoSMIBObjects 42 }

alaQoSImportEntry OBJECT-TYPE
  SYNTAX      QoSImportEntry
  MAX-ACCESS  not-accessible
  STATUS      current
  DESCRIPTION "Definition of QoS Import"
  INDEX {
          alaQoSImportIndex,
          alaQoSImportText
        }
  ::= { alaQoSImportTable 1 }

QoSImportEntry ::=
  SEQUENCE
  {
    alaQoSImportIndex                                       Integer32,
    alaQoSImportText                                        DisplayString,
    alaQoSImportPrecedence                                  Integer32,
    alaQoSImportPrefix                                      DisplayString,
    alaQoSImportSlot                                        Integer32,
    alaQoSImportPort                                        Integer32,
    alaQoSImportPortend                                     Integer32,
    alaQoSImportPortgroup                                   DisplayString,
    alaQoSImportRowStatus                                   RowStatus
  }

alaQoSImportIndex OBJECT-TYPE
  SYNTAX      Integer32 (0..2147483647)
  MAX-ACCESS  not-accessible
  STATUS      current
  DESCRIPTION "Index of entry in import list"
  ::= { alaQoSImportEntry 1 }

alaQoSImportText OBJECT-TYPE
  SYNTAX      DisplayString (SIZE(0..63))
  MAX-ACCESS  not-accessible
  STATUS      current
  DESCRIPTION "Text or filename to import"
  ::= { alaQoSImportEntry 2 }

alaQoSImportPrecedence OBJECT-TYPE
  SYNTAX      Integer32 (0..65535)
  MAX-ACCESS  read-create
  STATUS      current
  DESCRIPTION "Precedence to use for policies imported from file"
  DEFVAL      { 0 }
  ::= { alaQoSImportEntry 3 }

alaQoSImportPrefix OBJECT-TYPE
  SYNTAX      DisplayString (SIZE(0..11))
  MAX-ACCESS  read-create
  STATUS      current
  DESCRIPTION "Prefix for policy names that are imported"
  ::= { alaQoSImportEntry 4 }

alaQoSImportSlot OBJECT-TYPE
  SYNTAX      Integer32 (0..52)
  MAX-ACCESS  read-create
  STATUS      current
  DESCRIPTION "Slot on which to apply imported policy(s)"
  DEFVAL      { 0 }
  ::= { alaQoSImportEntry 5 }

alaQoSImportPort OBJECT-TYPE
  SYNTAX      Integer32 (0..16)
  MAX-ACCESS  read-create
  STATUS      current
  DESCRIPTION "Starting port on which to apply imported policy(s)"
  DEFVAL      { 0 }
  ::= { alaQoSImportEntry 6 }

alaQoSImportPortend OBJECT-TYPE
  SYNTAX      Integer32 (0..16)
  MAX-ACCESS  read-create
  STATUS      current
  DESCRIPTION "Ending port on which to apply imported policy(s)"
  DEFVAL      { 0 }
  ::= { alaQoSImportEntry 7 }

alaQoSImportPortgroup OBJECT-TYPE
  SYNTAX      DisplayString (SIZE(0..31))
  MAX-ACCESS  read-create
  STATUS      current
  DESCRIPTION "Portgroup on which to apply imported policy(s)"
  ::= { alaQoSImportEntry 8 }

alaQoSImportRowStatus OBJECT-TYPE
  SYNTAX      RowStatus
  MAX-ACCESS  read-create
  STATUS      current
  DESCRIPTION "Used to create/delete imports according to the
               RowStatus convention"
  ::= { alaQoSImportEntry 9 }


--
-- Definition of import table
--

alaQoSAppliedImportTable OBJECT-TYPE
  SYNTAX      SEQUENCE OF QoSAppliedImportEntry
  MAX-ACCESS  not-accessible
  STATUS      current
  DESCRIPTION "Table of QoS AppliedImport definitions"
  ::= { alaQoSMIBObjects 43 }

alaQoSAppliedImportEntry OBJECT-TYPE
  SYNTAX      QoSAppliedImportEntry
  MAX-ACCESS  not-accessible
  STATUS      current
  DESCRIPTION "Definition of QoS AppliedImport"
  INDEX {
          alaQoSAppliedImportIndex,
          alaQoSAppliedImportText
        }
  ::= { alaQoSAppliedImportTable 1 }

QoSAppliedImportEntry ::=
  SEQUENCE
  {
    alaQoSAppliedImportIndex                                Integer32,
    alaQoSAppliedImportText                                 DisplayString,
    alaQoSAppliedImportPrecedence                           Integer32,
    alaQoSAppliedImportPrefix                               DisplayString,
    alaQoSAppliedImportSlot                                 Integer32,
    alaQoSAppliedImportPort                                 Integer32,
    alaQoSAppliedImportPortend                              Integer32,
    alaQoSAppliedImportPortgroup                            DisplayString,
    alaQoSAppliedImportRowStatus                            RowStatus
  }

alaQoSAppliedImportIndex OBJECT-TYPE
  SYNTAX      Integer32  (0..2147483647)
  MAX-ACCESS  not-accessible
  STATUS      current
  DESCRIPTION "Index of entry in import list"
  ::= { alaQoSAppliedImportEntry 1 }

alaQoSAppliedImportText OBJECT-TYPE
  SYNTAX      DisplayString (SIZE(0..63))
  MAX-ACCESS  not-accessible
  STATUS      current
  DESCRIPTION "Text or filename to import"
  ::= { alaQoSAppliedImportEntry 2 }

alaQoSAppliedImportPrecedence OBJECT-TYPE
  SYNTAX      Integer32 (0..65535)
  MAX-ACCESS  read-only
  STATUS      current
  DESCRIPTION "Precedence to use for policies imported from file"
  ::= { alaQoSAppliedImportEntry 3 }

alaQoSAppliedImportPrefix OBJECT-TYPE
  SYNTAX      DisplayString (SIZE(0..11))
  MAX-ACCESS  read-only
  STATUS      current
  DESCRIPTION "Prefix for policy names that are imported"
  ::= { alaQoSAppliedImportEntry 4 }

alaQoSAppliedImportSlot OBJECT-TYPE
  SYNTAX      Integer32 (0..52)
  MAX-ACCESS  read-only
  STATUS      current
  DESCRIPTION "Slot on which to apply imported policy(s)"
  ::= { alaQoSAppliedImportEntry 5 }

alaQoSAppliedImportPort OBJECT-TYPE
  SYNTAX      Integer32 (0..16)
  MAX-ACCESS  read-only
  STATUS      current
  DESCRIPTION "Starting port on which to apply imported policy(s)"
  ::= { alaQoSAppliedImportEntry 6 }

alaQoSAppliedImportPortend OBJECT-TYPE
  SYNTAX      Integer32 (0..16)
  MAX-ACCESS  read-only
  STATUS      current
  DESCRIPTION "Ending port on which to apply imported policy(s)"
  ::= { alaQoSAppliedImportEntry 7 }

alaQoSAppliedImportPortgroup OBJECT-TYPE
  SYNTAX      DisplayString (SIZE(0..31))
  MAX-ACCESS  read-only
  STATUS      current
  DESCRIPTION "Portgroup on which to apply imported policy(s)"
  ::= { alaQoSAppliedImportEntry 8 }

alaQoSAppliedImportRowStatus OBJECT-TYPE
  SYNTAX      RowStatus
  MAX-ACCESS  read-only
  STATUS      current
  DESCRIPTION "Used to create/delete imports according to the
               RowStatus convention"
  ::= { alaQoSAppliedImportEntry 9 }

--
-- Definition of Rule group table
--

alaQoSRuleGroupsTable OBJECT-TYPE
  SYNTAX      SEQUENCE OF QoSRuleGroupsEntry
  MAX-ACCESS  not-accessible
  STATUS      current
  DESCRIPTION "Table of QoS RuleGroups definitions"
  ::= { alaQoSMIBObjects 44 }

alaQoSRuleGroupsEntry OBJECT-TYPE
  SYNTAX      QoSRuleGroupsEntry
  MAX-ACCESS  not-accessible
  STATUS      current
  DESCRIPTION "Definition of QoS RuleGroups"
  INDEX {
          alaQoSRuleGroupsName
        }
  ::= { alaQoSRuleGroupsTable 1 }

QoSRuleGroupsEntry ::=
  SEQUENCE
  {
    alaQoSRuleGroupsName                                 DisplayString,
    alaQoSRuleGroupsSource                               INTEGER,
    alaQoSRuleGroupsType                                 INTEGER,
    alaQoSRuleGroupsEnabled                              INTEGER,
    alaQoSRuleGroupsStatus                               RowStatus
 }

alaQoSRuleGroupsName OBJECT-TYPE
  SYNTAX      DisplayString (SIZE(0..31))
  MAX-ACCESS  not-accessible
  STATUS      current
  DESCRIPTION "Name of rule group"
  ::= { alaQoSRuleGroupsEntry 1 }

alaQoSRuleGroupsSource OBJECT-TYPE
  SYNTAX      INTEGER {
                ldap (1),
                cli (2),
                blt (3),
                api (4),
                imp (5)
              }
  MAX-ACCESS  read-create
  STATUS      current
  DESCRIPTION "What entity created the rule group."
  DEFVAL      { cli }
  ::= { alaQoSRuleGroupsEntry 2 }

alaQoSRuleGroupsType OBJECT-TYPE
  SYNTAX      INTEGER {
		default (1),
		unp (2),
		vrf (3),
		ingress (4),
		egress (5),
		slb (6)
              }
  MAX-ACCESS  read-create
  STATUS      current
  DESCRIPTION "Type of rule group."
  DEFVAL      { unp }
  ::= { alaQoSRuleGroupsEntry 3 }

alaQoSRuleGroupsEnabled OBJECT-TYPE
  SYNTAX      INTEGER {
                enable (1),
                disable (2)
              }
  MAX-ACCESS  read-create
  STATUS      current
  DESCRIPTION "Is this rule grop enabled or not"
  DEFVAL      { enable }
  ::= { alaQoSRuleGroupsEntry 4 }

alaQoSRuleGroupsStatus OBJECT-TYPE
  SYNTAX      RowStatus
  MAX-ACCESS  read-create
  STATUS      current
  DESCRIPTION "Used to create/delete rule groups according to the
               RowStatus convention"
  ::= { alaQoSRuleGroupsEntry 5 }

--
-- Definition of rule group table
--

alaQoSAppliedRuleGroupsTable OBJECT-TYPE
  SYNTAX      SEQUENCE OF QoSAppliedRuleGroupsEntry
  MAX-ACCESS  not-accessible
  STATUS      current
  DESCRIPTION "Table of QoS AppliedRuleGroups definitions"
  ::= { alaQoSMIBObjects 45 }

alaQoSAppliedRuleGroupsEntry OBJECT-TYPE
  SYNTAX      QoSAppliedRuleGroupsEntry
  MAX-ACCESS  not-accessible
  STATUS      current
  DESCRIPTION "Definition of QoS AppliedRuleGroups"
  INDEX {
          alaQoSAppliedRuleGroupsName
        }
  ::= { alaQoSAppliedRuleGroupsTable 1 }

QoSAppliedRuleGroupsEntry ::=
  SEQUENCE
  {
    alaQoSAppliedRuleGroupsName                          DisplayString,
    alaQoSAppliedRuleGroupsSource                        INTEGER,
    alaQoSAppliedRuleGroupsType                          INTEGER,
    alaQoSAppliedRuleGroupsEnabled                       INTEGER,
    alaQoSAppliedRuleGroupsStatus                        RowStatus
 }

alaQoSAppliedRuleGroupsName OBJECT-TYPE
  SYNTAX      DisplayString (SIZE(0..31))
  MAX-ACCESS  not-accessible
  STATUS      current
  DESCRIPTION "Name of rule group"
  ::= { alaQoSAppliedRuleGroupsEntry 1 }

alaQoSAppliedRuleGroupsSource OBJECT-TYPE
  SYNTAX      INTEGER {
                ldap (1),
                cli (2),
                blt (3),
                api (4),
                imp (5)
              }
  MAX-ACCESS  read-create
  STATUS      current
  DESCRIPTION "What entity created the service group."
  DEFVAL      { cli }
  ::= { alaQoSAppliedRuleGroupsEntry 2 }

alaQoSAppliedRuleGroupsType OBJECT-TYPE
  SYNTAX      INTEGER {
								defualt (1),
								unp (2),
                vrf (3),
								ingress (4),
								egress (5),
								slb (6)
              }
  MAX-ACCESS  read-only
  STATUS      current
  DESCRIPTION "What entity created the rule group."
  ::= { alaQoSAppliedRuleGroupsEntry 3 }

alaQoSAppliedRuleGroupsEnabled OBJECT-TYPE
  SYNTAX      INTEGER {
                enable (1),
                disable (2)
              }
  MAX-ACCESS  read-create
  STATUS      current
  DESCRIPTION "Is this rule grop enabled or not"
  ::= { alaQoSAppliedRuleGroupsEntry 4 }

alaQoSAppliedRuleGroupsStatus OBJECT-TYPE
  SYNTAX      RowStatus
  MAX-ACCESS  read-only
  STATUS      current
  DESCRIPTION "Used to create/delete rule groups according to the
               RowStatus convention"
  ::= { alaQoSAppliedRuleGroupsEntry 5 }

--
-- Definition of rule group entry table
--

alaQoSRuleGroupTable OBJECT-TYPE
  SYNTAX      SEQUENCE OF QoSRuleGroupEntry
  MAX-ACCESS  not-accessible
  STATUS      current
  DESCRIPTION "Table of QoS RuleGroup definitions"
  ::= { alaQoSMIBObjects 46 }

alaQoSRuleGroupEntry OBJECT-TYPE
  SYNTAX      QoSRuleGroupEntry
  MAX-ACCESS  not-accessible
  STATUS      current
  DESCRIPTION "Definition of QoS RuleGroup"
  INDEX {
          alaQoSRuleGroupsName,
          alaQoSRuleGroupRuleName
        }
  ::= { alaQoSRuleGroupTable 1 }

QoSRuleGroupEntry ::=
  SEQUENCE
  {
    alaQoSRuleGroupRuleName                           DisplayString,
    alaQoSRuleGroupMatches                            Counter32,
    alaQoSRuleGroupCountType                          INTEGER,
    alaQoSRuleGroupPacketCount                        Counter64,
    alaQoSRuleGroupByteCount                          Counter64,
    alaQoSRuleGroupStatus                             RowStatus,
    alaQoSRuleGroupPacketRate                         Counter64,
    alaQoSRuleGroupBitRate                           Counter64,
    alaQoSRuleGroupAccPacketCount                     Counter64, 
    alaQoSRuleGroupAccByteCount                          Counter64
}

alaQoSRuleGroupRuleName OBJECT-TYPE
  SYNTAX      DisplayString (SIZE(0..31))
  MAX-ACCESS  not-accessible
  STATUS      current
  DESCRIPTION "Name of rule in rule group entry"
  ::= { alaQoSRuleGroupEntry 1 }

alaQoSRuleGroupMatches OBJECT-TYPE
  SYNTAX      Counter32
  MAX-ACCESS  read-only
  STATUS      current
  DESCRIPTION "Number of times this rule has been matched."
  ::= { alaQoSRuleGroupEntry 2 }
	
alaQoSRuleGroupCountType OBJECT-TYPE
  SYNTAX      INTEGER {
                packets (1),
                bytes (2)
              }
  MAX-ACCESS  read-create
  STATUS      current
  DESCRIPTION "Which rule statistics counters to update if not all are available"
  DEFVAL      { packets }
  ::= { alaQoSRuleGroupEntry 3 }
	
alaQoSRuleGroupPacketCount OBJECT-TYPE
  SYNTAX      Counter64
  MAX-ACCESS  read-only
  STATUS      current
  DESCRIPTION "Counter for packets patching this rule"
  ::= { alaQoSRuleGroupEntry 4 }

alaQoSRuleGroupByteCount OBJECT-TYPE
  SYNTAX      Counter64
  MAX-ACCESS  read-only
  STATUS      current
  DESCRIPTION "Counter for bytes matching this rule"
  ::= { alaQoSRuleGroupEntry 5 }
	
alaQoSRuleGroupStatus OBJECT-TYPE
  SYNTAX      RowStatus
  MAX-ACCESS  read-create
  STATUS      current
  DESCRIPTION "Used to create/delete rule group entries according to the
               RowStatus convention"
  ::= { alaQoSRuleGroupEntry 6 }



alaQoSRuleGroupPacketRate OBJECT-TYPE
 SYNTAX      Counter64 
 MAX-ACCESS  read-only
 STATUS      current
 DESCRIPTION "Packets mathcing the rule per second ."
 ::= {alaQoSRuleGroupEntry 7}


alaQoSRuleGroupBitRate OBJECT-TYPE
 SYNTAX      Counter64  
 MAX-ACCESS  read-only
 STATUS      current 
 DESCRIPTION "Bytes mathcing the rule per second ."
 ::= {alaQoSRuleGroupEntry 8} 

alaQoSRuleGroupAccPacketCount OBJECT-TYPE
 SYNTAX      Counter64
 MAX-ACCESS  read-only
 STATUS      current
 DESCRIPTION "Counter for packets matching this rule"
 ::= { alaQoSRuleGroupEntry 9 }  
 
 alaQoSRuleGroupAccByteCount OBJECT-TYPE
 SYNTAX      Counter64
 MAX-ACCESS  read-only
 STATUS      current
 DESCRIPTION "Counter for bytes matching this rule"
 ::= { alaQoSRuleGroupEntry 10 }

--
-- Definition of rule group entry table
--

alaQoSAppliedRuleGroupTable OBJECT-TYPE
  SYNTAX      SEQUENCE OF QoSAppliedRuleGroupEntry
  MAX-ACCESS  not-accessible
  STATUS      current
  DESCRIPTION "Table of QoS AppliedRuleGroup definitions"
  ::= { alaQoSMIBObjects 47 }

alaQoSAppliedRuleGroupEntry OBJECT-TYPE
  SYNTAX      QoSAppliedRuleGroupEntry
  MAX-ACCESS  not-accessible
  STATUS      current
  DESCRIPTION "Definition of QoS AppliedRuleGroup"
  INDEX {
          alaQoSAppliedRuleGroupsName,
          alaQoSAppliedRuleGroupRuleName
        }
  ::= { alaQoSAppliedRuleGroupTable 1 }

QoSAppliedRuleGroupEntry ::=
  SEQUENCE
  {
    alaQoSAppliedRuleGroupRuleName                    DisplayString,
    alaQoSAppliedRuleGroupMatches                     Counter32,
    alaQoSAppliedRuleGroupCountType                   INTEGER,
    alaQoSAppliedRuleGroupPacketCount                 Counter64,
    alaQoSAppliedRuleGroupByteCount                   Counter64,
    alaQoSAppliedRuleGroupStatus                      RowStatus,
    alaQosAppliedRuleGroupPacketRate		        Counter64,
    alaQosAppliedRuleGroupBitRate		              Counter64,
    alaQoSAppliedRuleGroupAccPacketCount                  Counter64,
    alaQoSAppliedRuleGroupAccByteCount                   Counter64

  }

alaQoSAppliedRuleGroupRuleName OBJECT-TYPE
  SYNTAX      DisplayString (SIZE(0..31))
  MAX-ACCESS  not-accessible
  STATUS      current
  DESCRIPTION "Name of rule in rule group entry"
  ::= { alaQoSAppliedRuleGroupEntry 1 }

alaQoSAppliedRuleGroupMatches OBJECT-TYPE
  SYNTAX      Counter32
  MAX-ACCESS  read-only
  STATUS      current
  DESCRIPTION "Number of times this rule has been matched."
  ::= { alaQoSAppliedRuleGroupEntry 2 }
	
alaQoSAppliedRuleGroupCountType OBJECT-TYPE
  SYNTAX      INTEGER {
                packets (1),
                bytes (2)
              }
  MAX-ACCESS  read-create
  STATUS      current
  DESCRIPTION "Which rule statistics counters to update if not all are available"
  DEFVAL      { packets }
  ::= { alaQoSAppliedRuleGroupEntry 3 }

alaQoSAppliedRuleGroupPacketCount OBJECT-TYPE
  SYNTAX      Counter64
  MAX-ACCESS  read-only
  STATUS      current
  DESCRIPTION "Counter for packets patching this rule"
  ::= { alaQoSAppliedRuleGroupEntry 4 }

alaQoSAppliedRuleGroupByteCount OBJECT-TYPE
  SYNTAX      Counter64
  MAX-ACCESS  read-only
  STATUS      current
  DESCRIPTION "Counter for bytes matching this rule"
  ::= { alaQoSAppliedRuleGroupEntry 5 }
	
alaQoSAppliedRuleGroupStatus OBJECT-TYPE
  SYNTAX      RowStatus
  MAX-ACCESS  read-only
  STATUS      current
  DESCRIPTION "Used to create/delete rule group entries according to the
               RowStatus convention"
  ::= { alaQoSAppliedRuleGroupEntry 6 }

alaQosAppliedRuleGroupPacketRate OBJECT-TYPE
  SYNTAX      Counter64
  MAX-ACCESS  read-only
  STATUS      current
  DESCRIPTION "Shows the packet rate for policy list"
  ::= { alaQoSAppliedRuleGroupEntry 7 }

alaQosAppliedRuleGroupBitRate OBJECT-TYPE
  SYNTAX      Counter64
  MAX-ACCESS  read-only
  STATUS      current
  DESCRIPTION "Shows the bit rate for policy list"
  ::= { alaQoSAppliedRuleGroupEntry 8 }

alaQoSAppliedRuleGroupAccPacketCount OBJECT-TYPE
SYNTAX      Counter64
MAX-ACCESS  read-only
STATUS      current
DESCRIPTION "Counter for packets matching this rule"
::= { alaQoSAppliedRuleGroupEntry 9 }

alaQoSAppliedRuleGroupAccByteCount OBJECT-TYPE
SYNTAX      Counter64
MAX-ACCESS  read-only
STATUS      current
DESCRIPTION "Counter for bytes matching this rule"
::= { alaQoSAppliedRuleGroupEntry 10 }


alaQoSVlanGroupsTable OBJECT-TYPE
  SYNTAX      SEQUENCE OF QoSVlanGroupsEntry
  MAX-ACCESS  not-accessible
  STATUS      current
  DESCRIPTION "Table of QoS Vlan Groups definitions"
  ::= { alaQoSMIBObjects 48 }

alaQoSVlanGroupsEntry OBJECT-TYPE
  SYNTAX      QoSVlanGroupsEntry
  MAX-ACCESS  not-accessible
  STATUS      current
  DESCRIPTION "Definition of QoS Vlan Groups"
  INDEX {
          alaQoSVlanGroupsName
        }
  ::= { alaQoSVlanGroupsTable 1 }

QoSVlanGroupsEntry ::=
  SEQUENCE
  {
    alaQoSVlanGroupsName                                    DisplayString,
    alaQoSVlanGroupsSource                                  INTEGER,
    alaQoSVlanGroupsStatus                                  RowStatus
  }

alaQoSVlanGroupsName OBJECT-TYPE
  SYNTAX      DisplayString (SIZE(0..31))
  MAX-ACCESS  not-accessible
  STATUS      current
  DESCRIPTION "Name of Vlan group"
  ::= { alaQoSVlanGroupsEntry 1 }

alaQoSVlanGroupsSource OBJECT-TYPE
  SYNTAX      INTEGER {
                ldap (1),
                cli (2),
                blt (3),
                api (4),
                imp (5)
              }
  MAX-ACCESS  read-create
  STATUS      current
  DESCRIPTION "What entity created the Vlan group."
  DEFVAL      { cli }
  ::= { alaQoSVlanGroupsEntry 2 }

alaQoSVlanGroupsStatus OBJECT-TYPE
  SYNTAX      RowStatus
  MAX-ACCESS  read-create
  STATUS      current
  DESCRIPTION "Used to create/delete Vlan groups according to the
               RowStatus convention"
  ::= { alaQoSVlanGroupsEntry 3 }

-- Applied Object syntax

alaQoSAppliedVlanGroupsTable OBJECT-TYPE
  SYNTAX      SEQUENCE OF QoSAppliedVlanGroupsEntry
  MAX-ACCESS  not-accessible
  STATUS      current
  DESCRIPTION "Table of QoS Applied Vlan Groups definitions"
  ::= { alaQoSMIBObjects 49 }

alaQoSAppliedVlanGroupsEntry OBJECT-TYPE
  SYNTAX      QoSAppliedVlanGroupsEntry
  MAX-ACCESS  not-accessible
  STATUS      current
  DESCRIPTION "Definition of QoS Applied Vlan Groups"
  INDEX {
          alaQoSAppliedVlanGroupsName
        }
  ::= { alaQoSAppliedVlanGroupsTable 1 }

QoSAppliedVlanGroupsEntry ::=
  SEQUENCE
  {
    alaQoSAppliedVlanGroupsName          			DisplayString,
    alaQoSAppliedVlanGroupsSource                       INTEGER,
    alaQoSAppliedVlanGroupsStatus                       RowStatus
  }

alaQoSAppliedVlanGroupsName OBJECT-TYPE
  SYNTAX      DisplayString (SIZE(0..31))
  MAX-ACCESS  not-accessible
  STATUS      current
  DESCRIPTION "Name of Applied Vlan group"
  ::= { alaQoSAppliedVlanGroupsEntry 1 }

alaQoSAppliedVlanGroupsSource OBJECT-TYPE
  SYNTAX      INTEGER {
                ldap (1),
                cli (2),
                blt (3),
                api (4),
                imp (5)
              }
  MAX-ACCESS  read-create
  STATUS      current
  DESCRIPTION "What entity created the Vlan group."
  DEFVAL      { cli }
  ::= { alaQoSAppliedVlanGroupsEntry 2 }

alaQoSAppliedVlanGroupsStatus OBJECT-TYPE
  SYNTAX      RowStatus
  MAX-ACCESS  read-create
  STATUS      current
  DESCRIPTION "Used to create/delete Vlan groups according to the
               RowStatus convention"
  ::= { alaQoSAppliedVlanGroupsEntry 3 }



-- Definition of Vlan group entry table

alaQoSVlanGroupTable OBJECT-TYPE
  SYNTAX      SEQUENCE OF QoSVlanGroupEntry
  MAX-ACCESS  not-accessible
  STATUS      current
  DESCRIPTION "Table of QoS Vlan Group definitions"
  ::= { alaQoSMIBObjects 50 }

alaQoSVlanGroupEntry OBJECT-TYPE
  SYNTAX      QoSVlanGroupEntry
  MAX-ACCESS  not-accessible
  STATUS      current
  DESCRIPTION "Definition of QoS Vlan Group"
  INDEX {
          alaQoSVlanGroupsName,
 alaQoSVlanGroupVlan,
 alaQoSVlanGroupVlanEnd
        }
  ::= { alaQoSVlanGroupTable 1 }

QoSVlanGroupEntry ::=
  SEQUENCE
  {
    alaQoSVlanGroupVlan                                     Integer32,
    alaQoSVlanGroupVlanEnd                                  Integer32,
    alaQoSVlanGroupStatus                                   RowStatus
  }

alaQoSVlanGroupVlan OBJECT-TYPE
  SYNTAX      Integer32 (0..4095)
  MAX-ACCESS  not-accessible
  STATUS      current
  DESCRIPTION "Vlan range start for vlan group entry"
  ::= { alaQoSVlanGroupEntry 1 }

alaQoSVlanGroupVlanEnd OBJECT-TYPE
  SYNTAX      Integer32 (0..4095)
  MAX-ACCESS  not-accessible
  STATUS      current
  DESCRIPTION "Vlan range end for vlan group entry"
  ::= { alaQoSVlanGroupEntry 2 }


alaQoSVlanGroupStatus OBJECT-TYPE
  SYNTAX      RowStatus
  MAX-ACCESS  read-create
  STATUS      current
  DESCRIPTION "Used to create/delete vlan group entries according to the
               RowStatus convention"
  ::= { alaQoSVlanGroupEntry 3 }



-- Definition of Applied vlan group entry table

alaQoSAppliedVlanGroupTable OBJECT-TYPE
  SYNTAX      SEQUENCE OF QoSAppliedVlanGroupEntry
  MAX-ACCESS  not-accessible
  STATUS      current
  DESCRIPTION "Table of QoS Applied Vlan Group definitions"
  ::= { alaQoSMIBObjects 51 }

alaQoSAppliedVlanGroupEntry OBJECT-TYPE
  SYNTAX      QoSAppliedVlanGroupEntry
  MAX-ACCESS  not-accessible
  STATUS      current
  DESCRIPTION "Definition of QoS Applied Vlan Group"
  INDEX {
          alaQoSAppliedVlanGroupsName,
	  alaQoSAppliedVlanGroupVlan,
 	  alaQoSAppliedVlanGroupVlanEnd
        }
  ::= { alaQoSAppliedVlanGroupTable 1 }

QoSAppliedVlanGroupEntry ::=
  SEQUENCE
  {
    alaQoSAppliedVlanGroupVlan                              Integer32,
    alaQoSAppliedVlanGroupVlanEnd                           Integer32,
    alaQoSAppliedVlanGroupStatus                            RowStatus
  }

alaQoSAppliedVlanGroupVlan OBJECT-TYPE
  SYNTAX      Integer32 (0..4095)
  MAX-ACCESS  not-accessible
  STATUS      current
  DESCRIPTION "Vlan range start for vlan group entry"
  ::= { alaQoSAppliedVlanGroupEntry 1 }

alaQoSAppliedVlanGroupVlanEnd OBJECT-TYPE
  SYNTAX      Integer32 (0..4095)
  MAX-ACCESS  not-accessible
  STATUS      current
  DESCRIPTION "Vlan range end for vlan group entry"
  ::= { alaQoSAppliedVlanGroupEntry 2 }

alaQoSAppliedVlanGroupStatus OBJECT-TYPE
  SYNTAX      RowStatus
  MAX-ACCESS  read-create
  STATUS      current
  DESCRIPTION "Used to create/delete vlan group entries according
               to the RowStatus convention"
  ::= { alaQoSAppliedVlanGroupEntry 3 }

alaQoSHwLoopbackProfileTable OBJECT-TYPE   
  SYNTAX      SEQUENCE OF QoSHwLoopbackProfileEntry   
  MAX-ACCESS  not-accessible   
  STATUS      current   
  DESCRIPTION "Table of QoS Hw Loopback Profiles"   
  ::= { alaQoSMIBObjects 52 }   
   
alaQoSHwLoopbackProfileEntry OBJECT-TYPE   
  SYNTAX      QoSHwLoopbackProfileEntry   
  MAX-ACCESS  not-accessible   
  STATUS      current   
  DESCRIPTION "Definition of QoS Hw Loopback Profiles "   
  INDEX {   
          alaQoSHwLoopbackProfileName   
          }   
  ::= { alaQoSHwLoopbackProfileTable 1 }   
   
QoSHwLoopbackProfileEntry ::=   
  SEQUENCE   
  {   
    alaQoSHwLoopbackProfileName                    DisplayString,   
    alaQoSHwLoopbackSourceMac                           MacAddress,   
    alaQoSHwLoopbackDestinationMac               MacAddress,   
    alaQoSHwLoopbackVlan                       Integer32,   
    alaQoSHwLoopbackPort                                   InterfaceIndex,           
    alaQoSHwLoopbackType                               INTEGER,   
    alaQoSHwLoopbackProfileStatus                     INTEGER,   
    alaQoSHwLoopbackProfileRowStatus                  RowStatus,
    alaQosHwLoopbackSapId                             Integer32     
  }   
   
alaQoSHwLoopbackProfileName OBJECT-TYPE   
  SYNTAX      DisplayString (SIZE(1..31))   
  MAX-ACCESS  not-accessible   
  STATUS      current   
  DESCRIPTION "Name of Profile Name"   
  ::= { alaQoSHwLoopbackProfileEntry 1 }   
     
alaQoSHwLoopbackSourceMac OBJECT-TYPE   
  SYNTAX      MacAddress   
  MAX-ACCESS  read-create   
  STATUS      current   
  DESCRIPTION "Source MAC address to use for Hardware Loopback   
  profile configuration"   
  DEFVAL      { '000000000000'h }   
  ::= { alaQoSHwLoopbackProfileEntry 2 }   
   
alaQoSHwLoopbackDestinationMac OBJECT-TYPE   
  SYNTAX      MacAddress   
  MAX-ACCESS  read-create   
  STATUS      current   
  DESCRIPTION "Destination MAC address to use for Hardware Loopback   
  profile configuration"   
  DEFVAL      { '000000000000'h }   
  ::= { alaQoSHwLoopbackProfileEntry 3 }   
   
alaQoSHwLoopbackVlan OBJECT-TYPE   
  SYNTAX       Integer32 (0..4094)   
  MAX-ACCESS   read-create   
  STATUS       current   
  DESCRIPTION  "Vlan used in Hardware Loopback Profile Config"   
  ::= { alaQoSHwLoopbackProfileEntry 4 }   
   
alaQoSHwLoopbackPort OBJECT-TYPE   
  SYNTAX       InterfaceIndex    
  MAX-ACCESS   read-create   
  STATUS       current   
  DESCRIPTION  "Loopback Port ifindex used in Hardware Loopback Profile Config"   
  ::= { alaQoSHwLoopbackProfileEntry 5 }   
   
alaQoSHwLoopbackType OBJECT-TYPE   
  SYNTAX       INTEGER {   
  inward (1),   
  outward (2)   
  }   
  MAX-ACCESS   read-create   
  STATUS       current   
  DESCRIPTION  "The type of Hardware Profile Config, inward and outward"   
  ::= { alaQoSHwLoopbackProfileEntry 6 }   
   
alaQoSHwLoopbackProfileStatus OBJECT-TYPE   
  SYNTAX       INTEGER {   
  config (0),
  start (1),   
  stop (2)   
  }   
  MAX-ACCESS   read-create   
  STATUS       current   
  DESCRIPTION  "The status of the Hardware Profile Config"   
  ::= { alaQoSHwLoopbackProfileEntry 7 }   

alaQoSHwLoopbackProfileRowStatus OBJECT-TYPE   
  SYNTAX      RowStatus   
  MAX-ACCESS  read-create   
  STATUS      current   
  DESCRIPTION "Used to create/delete the Profile Config"   
  ::= { alaQoSHwLoopbackProfileEntry 8 }   

alaQosHwLoopbackSapId OBJECT-TYPE
  SYNTAX Integer32
  MAX-ACCESS  read-create
  STATUS  current
  DESCRIPTION
  "A Number given to uniquely identify the SAP."
  ::= { alaQoSHwLoopbackProfileEntry 9 }

-----------------------------------
-- Definition of queue  Stats table
-----------------------------------

alaQoSQueueStatsTable OBJECT-TYPE
  SYNTAX      SEQUENCE OF QoSQueueStatsEntry
  MAX-ACCESS  not-accessible
  STATUS      current
  DESCRIPTION "Table of QoS Queue Stats definitions"
  ::= { alaQoSMIBObjects 53 }

alaQoSQueueStatsEntry OBJECT-TYPE
  SYNTAX      QoSQueueStatsEntry
  MAX-ACCESS  not-accessible
  STATUS      current
  DESCRIPTION "Definition of QoS Queue Stats "
  INDEX {
          alaQoSQueueStatsId
        }
  ::= { alaQoSQueueStatsTable 1 }

QoSQueueStatsEntry ::=
  SEQUENCE
  {
    alaQoSQueueStatsId                                         	Integer32,
    alaQoSQueueStatsSlot                                       	Integer32,
    alaQoSQueueStatsPort                                        Integer32,
    alaQoSQueueStatsTransmitQueue                               Integer32 ,
    alaQoSQueueStatsPriority                                    INTEGER ,	
    alaQoSQueueStatsPacketsSent                                 Counter32,
    alaQoSQueueStatsPacketsDropped             	                Counter32,
    alaQoSQueueStatsBytesSent                                   Counter64,
    alaQoSQueueStatsBytesDropped                                Counter64,
    alaQoSQueueStatsRateSent                                    Counter64,
    alaQoSQueueStatsRateDropped                                 Counter64
  }

alaQoSQueueStatsId OBJECT-TYPE
  SYNTAX      Integer32 (0..2147483647)
  MAX-ACCESS  not-accessible
  STATUS      current
  DESCRIPTION "Internal queue identifier"
  ::= { alaQoSQueueStatsEntry 1 }

alaQoSQueueStatsSlot OBJECT-TYPE
  SYNTAX      Integer32 (0..255)
  MAX-ACCESS  read-only
  STATUS      current
  DESCRIPTION "Physical slot queue is destined to"
  ::= { alaQoSQueueStatsEntry 2 }

alaQoSQueueStatsPort OBJECT-TYPE
  SYNTAX      Integer32 (0..255)
  MAX-ACCESS  read-only
  STATUS      current
  DESCRIPTION "Physical port queue is destined to"
  ::= { alaQoSQueueStatsEntry 3 }

alaQoSQueueStatsTransmitQueue OBJECT-TYPE
  SYNTAX      Integer32 (0..7)
  MAX-ACCESS  read-only
  STATUS      current
  DESCRIPTION " Transmit queue number"
  ::= { alaQoSQueueStatsEntry 4 }

alaQoSQueueStatsPriority OBJECT-TYPE
  SYNTAX      INTEGER {
                high (1),
                low (2)
              }
  MAX-ACCESS  read-only
  STATUS      current
  DESCRIPTION " Transmit priority  for the queue"
  ::= { alaQoSQueueStatsEntry 5 }
  
alaQoSQueueStatsPacketsSent OBJECT-TYPE
  SYNTAX      Counter32
  MAX-ACCESS  read-only

  STATUS      current
  DESCRIPTION "Number of packets sent through the queue"
  ::= { alaQoSQueueStatsEntry 6}

alaQoSQueueStatsPacketsDropped OBJECT-TYPE
  SYNTAX      Counter32
  MAX-ACCESS  read-only
  STATUS      current
  DESCRIPTION "Number of packets dropped trying to queue into this queue"
  ::= { alaQoSQueueStatsEntry 7}

alaQoSQueueStatsBytesSent OBJECT-TYPE
  SYNTAX      Counter64
  MAX-ACCESS  read-only
  STATUS      current
  DESCRIPTION "Number of bytes sent through the queue"
  ::= { alaQoSQueueStatsEntry 8}

alaQoSQueueStatsBytesDropped OBJECT-TYPE
  SYNTAX      Counter64
  MAX-ACCESS  read-only
  STATUS      current
  DESCRIPTION "Number of bytes dropped trying to queue into this queue"
  ::= { alaQoSQueueStatsEntry 9}
  
alaQoSQueueStatsRateSent OBJECT-TYPE
  SYNTAX      Counter64
  MAX-ACCESS  read-only
  STATUS      current
  DESCRIPTION "Rate(Mbits/sec) sent through the queue"
  ::= { alaQoSQueueStatsEntry 10}

alaQoSQueueStatsRateDropped OBJECT-TYPE
  SYNTAX      Counter64
  MAX-ACCESS  read-only
  STATUS      current
  DESCRIPTION "Rate(Mbits/sec) dropped trying to queue into this queue"
  ::= { alaQoSQueueStatsEntry 11}  

alaQoSMIBConformance OBJECT-IDENTITY
  STATUS      current
  DESCRIPTION "Branch for QoS Managed Conformance Information."
  ::= { alaQoSMIB 2 }

alaQoSMIBGroups OBJECT-IDENTITY
  STATUS      current
  DESCRIPTION "Branch for QoS Units of Conformance."
  ::= { alaQoSMIBConformance 1 }

alaQoSMIBCompliances OBJECT-IDENTITY
  STATUS      current
  DESCRIPTION "Branch for QoS Compliance Statements."
  ::= { alaQoSMIBConformance 2 }

alaQoSMIBRuleObjects OBJECT-GROUP
  OBJECTS {
    alaQoSRuleEnabled,
    alaQoSRuleSource,
    alaQoSRulePrecedence,
    alaQoSRuleCondition,
    alaQoSRuleAction,
    alaQoSRuleReflexive,
    alaQoSRuleSave,
    alaQoSRuleLog,
    alaQoSRuleMatches,
    alaQoSRuleEnforced,
    alaQoSRuleActive,
    alaQoSRuleRowStatus,
    alaQoSRuleValidityPeriod,
    alaQoSRuleValidityPeriodStatus,
    alaQoSRuleLogInterval,
    alaQoSRuleCountType,
    alaQoSRulePacketCount,
    alaQoSRuleByteCount,
    alaQoSRuleExcessPacketCount,
    alaQoSRuleExcessByteCount,
    alaQoSRuleType,
    alaQoSRuleTrapEvents,
    alaQoSRuleDefaultList,
    alaQoSRuleGreenCount,
    alaQoSRuleYellowCount,
    alaQoSRuleRedCount,
    alaQoSRuleNonGreenCount,
    alaQoSRuleNonRedCount,
    alaQoSRuleAccounting,
    alaQoSRulePacketRate,
    alaQoSRuleAccPacketCount,
    alaQoSRuleAccByteCount,
    alaQoSRuleBitRate
  }
  STATUS      current
  DESCRIPTION "Collections of objects providing information for Rules"
  ::= { alaQoSMIBGroups 1 }

alaQoSMIBAppliedRuleObjects OBJECT-GROUP
  OBJECTS {
    alaQoSAppliedRuleEnabled,
    alaQoSAppliedRuleSource,
    alaQoSAppliedRulePrecedence,
    alaQoSAppliedRuleCondition,
    alaQoSAppliedRuleAction,
    alaQoSAppliedRuleReflexive,
    alaQoSAppliedRuleSave,
    alaQoSAppliedRuleLog,
    alaQoSAppliedRuleMatches,
    alaQoSAppliedRuleEnforced,
    alaQoSAppliedRuleActive,
    alaQoSAppliedRuleRowStatus,
    alaQoSAppliedRuleValidityPeriod,
    alaQoSAppliedRuleValidityPeriodStatus,
    alaQoSAppliedRuleLogInterval,
    alaQoSAppliedRuleCountType,
    alaQoSAppliedRulePacketCount,
    alaQoSAppliedRuleByteCount,
    alaQoSAppliedRuleExcessPacketCount,
    alaQoSAppliedRuleExcessByteCount,
    alaQoSAppliedRuleType,
    alaQoSAppliedRuleTrapEvents,
    alaQoSAppliedRuleDefaultList,
    alaQoSAppliedRuleGreenCount,
    alaQoSAppliedRuleYellowCount,
    alaQoSAppliedRuleRedCount,
    alaQoSAppliedRuleNonGreenCount,
    alaQoSAppliedRuleNonRedCount,
    alaQoSAppliedRuleAccounting,
    alaQoSAppliedRulePacketRate,
    alaQoSAppliedRuleAccPacketCount,
    alaQoSAppliedRuleAccByteCount,
    alaQoSAppliedRuleBitRate
  }
  STATUS      current
  DESCRIPTION "Collections of objects providing information
               for applied Rules"
  ::= { alaQoSMIBGroups 2 }

alaQoSMIBConditionObjects OBJECT-GROUP
  OBJECTS {
    alaQoSConditionSource,
    alaQoSConditionSourceSlot,
    alaQoSConditionSourceSlotStatus,
    alaQoSConditionSourcePort,
    alaQoSConditionSourcePortGroup,
    alaQoSConditionSourcePortGroupStatus,
    alaQoSConditionDestinationSlot,
    alaQoSConditionDestinationSlotStatus,
    alaQoSConditionDestinationPort,
    alaQoSConditionDestinationPortGroup,
    alaQoSConditionDestinationPortGroupStatus,
    alaQoSConditionSourceInterfaceType,
    alaQoSConditionSourceInterfaceTypeStatus,
    alaQoSConditionDestinationInterfaceType,
    alaQoSConditionDestinationInterfaceTypeStatus,
    alaQoSConditionSourceMacAddr,
    alaQoSConditionSourceMacAddrStatus,
    alaQoSConditionSourceMacMask,
    alaQoSConditionSourceMacGroup,
    alaQoSConditionSourceMacGroupStatus,
    alaQoSConditionDestinationMacAddr,
    alaQoSConditionDestinationMacAddrStatus,
    alaQoSConditionDestinationMacMask,
    alaQoSConditionDestinationMacGroup,
    alaQoSConditionDestinationMacGroupStatus,
    alaQoSConditionSourceVlan,
    alaQoSConditionSourceVlanStatus,
    alaQoSConditionDestinationVlan,
    alaQoSConditionDestinationVlanStatus,
    alaQoSCondition8021p,
    alaQoSCondition8021pStatus,
    alaQoSConditionSourceIpAddr,
    alaQoSConditionSourceIpAddrStatus,
    alaQoSConditionSourceIpMask,
    alaQoSConditionSourceNetworkGroup,
    alaQoSConditionSourceNetworkGroupStatus,
    alaQoSConditionDestinationIpAddr,
    alaQoSConditionDestinationIpAddrStatus,
    alaQoSConditionDestinationIpMask,
    alaQoSConditionDestinationNetworkGroup,
    alaQoSConditionDestinationNetworkGroupStatus,
    alaQoSConditionMulticastIpAddr,
    alaQoSConditionMulticastIpAddrStatus,
    alaQoSConditionMulticastIpMask,
    alaQoSConditionMulticastNetworkGroup,
    alaQoSConditionMulticastNetworkGroupStatus,
    alaQoSConditionTos,
    alaQoSConditionTosStatus,
    alaQoSConditionTosMask,
    alaQoSConditionDscp,
    alaQoSConditionDscpStatus,
    alaQoSConditionDscpMask,
    alaQoSConditionIpProtocol,
    alaQoSConditionIpProtocolStatus,
    alaQoSConditionSourceIpPort,
    alaQoSConditionSourceIpPortStatus,
    alaQoSConditionDestinationIpPort,
    alaQoSConditionDestinationIpPortStatus,
    alaQoSConditionService,
    alaQoSConditionServiceStatus,
    alaQoSConditionServiceGroup,
    alaQoSConditionServiceGroupStatus,
    alaQoSConditionIcmpType,
    alaQoSConditionIcmpTypeStatus,
    alaQoSConditionIcmpCode,
    alaQoSConditionIcmpCodeStatus,
    alaQoSConditionDlci,
    alaQoSConditionDlciStatus,
    alaQoSConditionRowStatus,
    alaQoSConditionSourcePortEnd,
    alaQoSConditionDestinationPortEnd,
    alaQoSConditionSourceIpPortEnd,
    alaQoSConditionDestinationIpPortEnd,
    alaQoSConditionSourceTcpPort,
    alaQoSConditionSourceTcpPortStatus,
    alaQoSConditionSourceTcpPortEnd,
    alaQoSConditionDestinationTcpPort,
    alaQoSConditionDestinationTcpPortStatus,
    alaQoSConditionDestinationTcpPortEnd,
    alaQoSConditionSourceUdpPort,
    alaQoSConditionSourceUdpPortStatus,
    alaQoSConditionSourceUdpPortEnd,
    alaQoSConditionDestinationUdpPort,
    alaQoSConditionDestinationUdpPortStatus,
    alaQoSConditionDestinationUdpPortEnd,
    alaQoSConditionEthertype,
    alaQoSConditionEthertypeStatus,
    alaQoSConditionTcpFlags,
    alaQoSConditionTcpFlagsStatus,
    alaQoSConditionTcpFlagsVal,
    alaQoSConditionTcpFlagsValStatus,
    alaQoSConditionTcpFlagsMask,
    alaQoSConditionTcpFlagsMaskStatus,
    alaQoSConditionTcpEstablished,
    alaQoSConditionSourceIpv6Addr,
    alaQoSConditionSourceIpv6AddrStatus,
    alaQoSConditionSourceIpv6Mask,
    alaQoSConditionDestinationIpv6Addr,
    alaQoSConditionDestinationIpv6AddrStatus,
    alaQoSConditionDestinationIpv6Mask,
    alaQoSConditionIpv6Traffic,
    alaQoSConditionIpv6NH,
    alaQoSConditionIpv6NHStatus,
    alaQoSConditionIpv6FlowLabel,
    alaQoSConditionIpv6FlowLabelStatus,
    alaQoSConditionMcastIpv6Addr,          
    alaQoSConditionMcastIpv6AddrStatus,
    alaQoSConditionMcastIpv6Mask,
    alaQoSConditionDscpEnd,
    alaQoSConditionInnerSourceVlan,
    alaQoSConditionInnerSourceVlanStatus,
    alaQoSConditionInner8021p,
    alaQoSConditionInner8021pStatus,
    alaQoSConditionVrfName,
    alaQoSConditionVrfNameStatus,
    alaQoSCondition8021pEnd,
    alaQoSConditionInner8021pEnd,
    alaQoSConditionSourceVlanGroup,
    alaQoSConditionSourceVlanGroupStatus,
    alaQoSConditionInnerSourceVlanGroup,
    alaQoSConditionInnerSourceVlanGroupStatus
  }

  STATUS      current
  DESCRIPTION "Collections of objects providing information for Conditions"
  ::= { alaQoSMIBGroups 3 }

alaQoSMIBAppliedConditionObjects OBJECT-GROUP
  OBJECTS {
    alaQoSAppliedConditionSource,
    alaQoSAppliedConditionSourceSlot,
    alaQoSAppliedConditionSourceSlotStatus,
    alaQoSAppliedConditionSourcePort,
    alaQoSAppliedConditionSourcePortGroup,
    alaQoSAppliedConditionSourcePortGroupStatus,
    alaQoSAppliedConditionDestinationSlot,
    alaQoSAppliedConditionDestinationSlotStatus,
    alaQoSAppliedConditionDestinationPort,
    alaQoSAppliedConditionDestinationPortGroup,
    alaQoSAppliedConditionDestinationPortGroupStatus,
    alaQoSAppliedConditionSourceInterfaceType,
    alaQoSAppliedConditionSourceInterfaceTypeStatus,
    alaQoSAppliedConditionDestinationInterfaceType,
    alaQoSAppliedConditionDestinationInterfaceTypeStatus,
    alaQoSAppliedConditionSourceMacAddr,
    alaQoSAppliedConditionSourceMacAddrStatus,
    alaQoSAppliedConditionSourceMacMask,
    alaQoSAppliedConditionSourceMacGroup,
    alaQoSAppliedConditionSourceMacGroupStatus,
    alaQoSAppliedConditionDestinationMacAddr,
    alaQoSAppliedConditionDestinationMacAddrStatus,
    alaQoSAppliedConditionDestinationMacMask,
    alaQoSAppliedConditionDestinationMacGroup,
    alaQoSAppliedConditionDestinationMacGroupStatus,
    alaQoSAppliedConditionSourceVlan,
    alaQoSAppliedConditionSourceVlanStatus,
    alaQoSAppliedConditionDestinationVlan,
    alaQoSAppliedConditionDestinationVlanStatus,
    alaQoSAppliedCondition8021p,
    alaQoSAppliedCondition8021pStatus,
    alaQoSAppliedConditionSourceIpAddr,
    alaQoSAppliedConditionSourceIpAddrStatus,
    alaQoSAppliedConditionSourceIpMask,
    alaQoSAppliedConditionSourceNetworkGroup,
    alaQoSAppliedConditionSourceNetworkGroupStatus,
    alaQoSAppliedConditionDestinationIpAddr,
    alaQoSAppliedConditionDestinationIpAddrStatus,
    alaQoSAppliedConditionDestinationIpMask,
    alaQoSAppliedConditionDestinationNetworkGroup,
    alaQoSAppliedConditionDestinationNetworkGroupStatus,
    alaQoSAppliedConditionMulticastIpAddr,
    alaQoSAppliedConditionMulticastIpAddrStatus,
    alaQoSAppliedConditionMulticastIpMask,
    alaQoSAppliedConditionMulticastNetworkGroup,
    alaQoSAppliedConditionMulticastNetworkGroupStatus,
    alaQoSAppliedConditionTos,
    alaQoSAppliedConditionTosStatus,
    alaQoSAppliedConditionTosMask,
    alaQoSAppliedConditionDscp,
    alaQoSAppliedConditionDscpStatus,
    alaQoSAppliedConditionDscpMask,
    alaQoSAppliedConditionIpProtocol,
    alaQoSAppliedConditionIpProtocolStatus,
    alaQoSAppliedConditionSourceIpPort,
    alaQoSAppliedConditionSourceIpPortStatus,
    alaQoSAppliedConditionDestinationIpPort,
    alaQoSAppliedConditionDestinationIpPortStatus,
    alaQoSAppliedConditionService,
    alaQoSAppliedConditionServiceStatus,
    alaQoSAppliedConditionServiceGroup,
    alaQoSAppliedConditionServiceGroupStatus,
    alaQoSAppliedConditionIcmpType,
    alaQoSAppliedConditionIcmpTypeStatus,
    alaQoSAppliedConditionIcmpCode,
    alaQoSAppliedConditionIcmpCodeStatus,
    alaQoSAppliedConditionDlci,
    alaQoSAppliedConditionDlciStatus,
    alaQoSAppliedConditionRowStatus,
    alaQoSAppliedConditionSourcePortEnd,
    alaQoSAppliedConditionDestinationPortEnd,
    alaQoSAppliedConditionSourceIpPortEnd,
    alaQoSAppliedConditionDestinationIpPortEnd,
    alaQoSAppliedConditionSourceTcpPort,
    alaQoSAppliedConditionSourceTcpPortStatus,
    alaQoSAppliedConditionSourceTcpPortEnd,
    alaQoSAppliedConditionDestinationTcpPort,
    alaQoSAppliedConditionDestinationTcpPortStatus,
    alaQoSAppliedConditionDestinationTcpPortEnd,
    alaQoSAppliedConditionSourceUdpPort,
    alaQoSAppliedConditionSourceUdpPortStatus,
    alaQoSAppliedConditionSourceUdpPortEnd,
    alaQoSAppliedConditionDestinationUdpPort,
    alaQoSAppliedConditionDestinationUdpPortStatus,
    alaQoSAppliedConditionDestinationUdpPortEnd,
    alaQoSAppliedConditionEthertype,
    alaQoSAppliedConditionEthertypeStatus,
    alaQoSAppliedConditionTcpFlags,
    alaQoSAppliedConditionTcpFlagsStatus,
    alaQoSAppliedConditionTcpFlagsVal,
    alaQoSAppliedConditionTcpFlagsValStatus,
    alaQoSAppliedConditionTcpFlagsMask,
    alaQoSAppliedConditionTcpFlagsMaskStatus,
    alaQoSAppliedConditionTcpEstablished,
    alaQoSAppliedConditionSourceIpv6Addr,
    alaQoSAppliedConditionSourceIpv6AddrStatus,
    alaQoSAppliedConditionSourceIpv6Mask,
    alaQoSAppliedConditionDestinationIpv6Addr,
    alaQoSAppliedConditionDestinationIpv6AddrStatus,
    alaQoSAppliedConditionDestinationIpv6Mask,
    alaQoSAppliedConditionIpv6Traffic,
    alaQoSAppliedConditionIpv6NH,
    alaQoSAppliedConditionIpv6NHStatus,
    alaQoSAppliedConditionIpv6FlowLabel,
    alaQoSAppliedConditionIpv6FlowLabelStatus,
    alaQoSAppliedConditionMcastIpv6Addr,          
    alaQoSAppliedConditionMcastIpv6AddrStatus,
    alaQoSAppliedConditionMcastIpv6Mask,
    alaQoSAppliedConditionDscpEnd,
    alaQoSAppliedConditionInnerSourceVlan,
    alaQoSAppliedConditionInnerSourceVlanStatus,
    alaQoSAppliedConditionInner8021p,
    alaQoSAppliedConditionInner8021pStatus,
    alaQoSAppliedConditionVrfName,
    alaQoSAppliedConditionVrfNameStatus,
    alaQoSAppliedCondition8021pEnd,
    alaQoSAppliedConditionInner8021pEnd,
    alaQoSAppliedConditionSourceVlanGroup,
    alaQoSAppliedConditionSourceVlanGroupStatus,
    alaQoSAppliedConditionInnerSourceVlanGroup,
    alaQoSAppliedConditionInnerSourceVlanGroupStatus
  }
  STATUS      current
  DESCRIPTION "Collections of objects providing information
               for applied Conditions"
  ::= { alaQoSMIBGroups 4 }

alaQoSMIBServiceObjects OBJECT-GROUP
  OBJECTS {
    alaQoSServiceSource,
    alaQoSServiceProtocol,
    alaQoSServiceSourceIpPort,
    alaQoSServiceSourceIpPortStatus,
    alaQoSServiceDestinationIpPort,
    alaQoSServiceDestinationIpPortStatus,
    alaQoSServiceRowStatus,
    alaQoSServiceSourceIpPortEnd,
    alaQoSServiceDestinationIpPortEnd,
    alaQoSServiceSourceTcpPort,
    alaQoSServiceSourceTcpPortStatus,
    alaQoSServiceSourceTcpPortEnd,
    alaQoSServiceDestinationTcpPort,
    alaQoSServiceDestinationTcpPortStatus,
    alaQoSServiceDestinationTcpPortEnd,
    alaQoSServiceSourceUdpPort,
    alaQoSServiceSourceUdpPortStatus,
    alaQoSServiceSourceUdpPortEnd,
    alaQoSServiceDestinationUdpPort,
    alaQoSServiceDestinationUdpPortStatus,
    alaQoSServiceDestinationUdpPortEnd
  }
  STATUS      current
  DESCRIPTION "Collections of objects providing information for Services"
  ::= { alaQoSMIBGroups 5 }

alaQoSMIBAppliedServiceObjects OBJECT-GROUP
  OBJECTS {
    alaQoSAppliedServiceSource,
    alaQoSAppliedServiceProtocol,
    alaQoSAppliedServiceSourceIpPort,
    alaQoSAppliedServiceSourceIpPortStatus,
    alaQoSAppliedServiceDestinationIpPort,
    alaQoSAppliedServiceDestinationIpPortStatus,
    alaQoSAppliedServiceRowStatus,
    alaQoSAppliedServiceSourceIpPortEnd,
    alaQoSAppliedServiceDestinationIpPortEnd,
    alaQoSAppliedServiceSourceTcpPort,
    alaQoSAppliedServiceSourceTcpPortStatus,
    alaQoSAppliedServiceSourceTcpPortEnd,
    alaQoSAppliedServiceDestinationTcpPort,
    alaQoSAppliedServiceDestinationTcpPortStatus,
    alaQoSAppliedServiceDestinationTcpPortEnd,
    alaQoSAppliedServiceSourceUdpPort,
    alaQoSAppliedServiceSourceUdpPortStatus,
    alaQoSAppliedServiceSourceUdpPortEnd,
    alaQoSAppliedServiceDestinationUdpPort,
    alaQoSAppliedServiceDestinationUdpPortStatus,
    alaQoSAppliedServiceDestinationUdpPortEnd
  }
  STATUS      current
  DESCRIPTION "Collections of objects providing information
               for applied Services"
  ::= { alaQoSMIBGroups 6 }

alaQoSMIBServiceGroupsObjects OBJECT-GROUP
  OBJECTS {
    alaQoSServiceGroupsSource,
    alaQoSServiceGroupsStatus
  }
  STATUS      current
  DESCRIPTION "Collections of objects providing information for ServiceGroupss"
  ::= { alaQoSMIBGroups 7 }

alaQoSMIBAppliedServiceGroupsObjects OBJECT-GROUP
  OBJECTS {
    alaQoSAppliedServiceGroupsSource,
    alaQoSAppliedServiceGroupsStatus
  }
  STATUS      current
  DESCRIPTION "Collections of objects providing information
               for applied ServiceGroupss"
  ::= { alaQoSMIBGroups 8 }

alaQoSMIBServiceGroupObjects OBJECT-GROUP
  OBJECTS {
    alaQoSServiceGroupStatus
  }
  STATUS      current
  DESCRIPTION "Collections of objects providing information for ServiceGroups"
  ::= { alaQoSMIBGroups 9 }

alaQoSMIBAppliedServiceGroupObjects OBJECT-GROUP
  OBJECTS {
    alaQoSAppliedServiceGroupStatus
  }
  STATUS      current
  DESCRIPTION "Collections of objects providing information
               for applied ServiceGroups"
  ::= { alaQoSMIBGroups 10 }

alaQoSMIBNetworkGroupsObjects OBJECT-GROUP
  OBJECTS {
    alaQoSNetworkGroupsSource,
    alaQoSNetworkGroupsStatus
  }
  STATUS      current
  DESCRIPTION "Collections of objects providing information for NetworkGroupss"
  ::= { alaQoSMIBGroups 11 }

alaQoSMIBAppliedNetworkGroupsObjects OBJECT-GROUP
  OBJECTS {
    alaQoSAppliedNetworkGroupsSource,
    alaQoSAppliedNetworkGroupsStatus
  }
  STATUS      current
  DESCRIPTION "Collections of objects providing information
               for applied NetworkGroupss"
  ::= { alaQoSMIBGroups 12 }

alaQoSMIBNetworkGroupObjects OBJECT-GROUP
  OBJECTS {
    alaQoSNetworkGroupStatus
  }
  STATUS      current
  DESCRIPTION "Collections of objects providing information for NetworkGroups"
  ::= { alaQoSMIBGroups 13 }

alaQoSMIBAppliedNetworkGroupObjects OBJECT-GROUP
  OBJECTS {
    alaQoSAppliedNetworkGroupStatus
  }
  STATUS      current
  DESCRIPTION "Collections of objects providing information
               for applied NetworkGroups"
  ::= { alaQoSMIBGroups 14 }

alaQoSMIBMACGroupsObjects OBJECT-GROUP
  OBJECTS {
    alaQoSMACGroupsSource,
    alaQoSMACGroupsStatus
  }
  STATUS      current
  DESCRIPTION "Collections of objects providing information for MACGroupss"
  ::= { alaQoSMIBGroups 15 }

alaQoSMIBAppliedMACGroupsObjects OBJECT-GROUP
  OBJECTS {
    alaQoSAppliedMACGroupsSource,
    alaQoSAppliedMACGroupsStatus
  }
  STATUS      current
  DESCRIPTION "Collections of objects providing information
               for applied MACGroupss"
  ::= { alaQoSMIBGroups 16 }

alaQoSMIBMACGroupObjects OBJECT-GROUP
  OBJECTS {
    alaQoSMACGroupStatus
  }
  STATUS      current
  DESCRIPTION "Collections of objects providing information for MACGroups"
  ::= { alaQoSMIBGroups 17 }

alaQoSMIBAppliedMACGroupObjects OBJECT-GROUP
  OBJECTS {
    alaQoSAppliedMACGroupStatus
  }
  STATUS      current
  DESCRIPTION "Collections of objects providing information
               for applied MACGroups"
  ::= { alaQoSMIBGroups 18 }

alaQoSMIBPortGroupsObjects OBJECT-GROUP
  OBJECTS {
    alaQoSPortGroupsSource,
    alaQoSPortGroupsStatus
  }
  STATUS      current
  DESCRIPTION "Collections of objects providing information for PortGroupss"
  ::= { alaQoSMIBGroups 19 }

alaQoSMIBAppliedPortGroupsObjects OBJECT-GROUP
  OBJECTS {
    alaQoSAppliedPortGroupsSource,
    alaQoSAppliedPortGroupsStatus
  }
  STATUS      current
  DESCRIPTION "Collections of objects providing information
               for applied PortGroupss"
  ::= { alaQoSMIBGroups 20 }

alaQoSMIBPortGroupObjects OBJECT-GROUP
  OBJECTS {
    alaQoSPortGroupStatus
  }
  STATUS      current
  DESCRIPTION "Collections of objects providing information for PortGroups"
  ::= { alaQoSMIBGroups 21 }

alaQoSMIBAppliedPortGroupObjects OBJECT-GROUP
  OBJECTS {
    alaQoSAppliedPortGroupStatus
  }
  STATUS      current
  DESCRIPTION "Collections of objects providing information
               for applied PortGroups"
  ::= { alaQoSMIBGroups 22 }

alaQoSMIBMapGroupsObjects OBJECT-GROUP
  OBJECTS {
    alaQoSMapGroupsSource,
    alaQoSMapGroupsStatus
  }
  STATUS      current
  DESCRIPTION "Collections of objects providing information for MapGroupss"
  ::= { alaQoSMIBGroups 23 }

alaQoSMIBAppliedMapGroupsObjects OBJECT-GROUP
  OBJECTS {
    alaQoSAppliedMapGroupsSource,
    alaQoSAppliedMapGroupsStatus
  }
  STATUS      current
  DESCRIPTION "Collections of objects providing information
               for applied MapGroupss"
  ::= { alaQoSMIBGroups 24 }

alaQoSMIBMapGroupObjects OBJECT-GROUP
  OBJECTS {
    alaQoSMapGroupStatus
  }
  STATUS      current
  DESCRIPTION "Collections of objects providing information for MapGroups"
  ::= { alaQoSMIBGroups 25 }

alaQoSMIBAppliedMapGroupObjects OBJECT-GROUP
  OBJECTS {
    alaQoSAppliedMapGroupStatus
  }
  STATUS      current
  DESCRIPTION "Collections of objects providing information
               for applied MapGroups"
  ::= { alaQoSMIBGroups 26 }

alaQoSMIBActionObjects OBJECT-GROUP
  OBJECTS {
    alaQoSActionSource,
    alaQoSActionDisposition,
    alaQoSActionDropAlgorithm,
    alaQoSActionWredMaximumThreshold,
    alaQoSActionWredMaximumThresholdStatus,
    alaQoSActionWredMinimumThreshold,
    alaQoSActionWredMinimumThresholdStatus,
    alaQoSActionWredMaximumProbability,
    alaQoSActionWredMaximumProbabilityStatus,
    alaQoSActionMinimumBandwidth,
    alaQoSActionMinimumBandwidthStatus,
    alaQoSActionMaximumBandwidth,
    alaQoSActionMaximumBandwidthStatus,
    alaQoSActionPeakBandwidth,
    alaQoSActionPeakBandwidthStatus,
    alaQoSActionPriority,
    alaQoSActionPriorityStatus,
    alaQoSActionShared,
    alaQoSActionJitter,
    alaQoSActionJitterStatus,
    alaQoSActionLatency,
    alaQoSActionLatencyStatus,
    alaQoSActionMaximumDepth,
    alaQoSActionMaximumDepthStatus,
    alaQoSActionMaximumBuffers,
    alaQoSActionMaximumBuffersStatus,
    alaQoSAction8021p,
    alaQoSAction8021pStatus,
    alaQoSActionTos,
    alaQoSActionTosStatus,
    alaQoSActionDscp,
    alaQoSActionDscpStatus,
    alaQoSActionMapFrom,
    alaQoSActionMapTo,
    alaQoSActionMapGroup,
    alaQoSActionMapGroupStatus,
    alaQoSActionSourceRewriteIpAddr,
    alaQoSActionSourceRewriteIpAddrStatus,
    alaQoSActionSourceRewriteIpMask,
    alaQoSActionSourceRewriteNetworkGroup,
    alaQoSActionSourceRewriteNetworkGroupStatus,
    alaQoSActionDestinationRewriteIpAddr,
    alaQoSActionDestinationRewriteIpAddrStatus,
    alaQoSActionDestinationRewriteIpMask,
    alaQoSActionDestinationRewriteNetworkGroup,
    alaQoSActionDestinationRewriteNetworkGroupStatus,
    alaQoSActionLoadBalanceGroup,
    alaQoSActionLoadBalanceGroupStatus,
    alaQoSActionPermanentGatewayIpAddr,
    alaQoSActionPermanentGatewayIpAddrStatus,
    alaQoSActionAlternateGatewayIpAddr,
    alaQoSActionAlternateGatewayIpAddrStatus,
    alaQoSActionRowStatus,
    alaQoSActionMinimumDepth,
    alaQoSActionMinimumDepthStatus,
    alaQoSActionVPNAccess,
    alaQoSActionNocache,
    alaQoSActionPortdisable,
    alaQoSActionRedirectSlot,
    alaQoSActionRedirectSlotStatus,
    alaQoSActionRedirectPort,
    alaQoSActionRedirectAgg,
    alaQoSActionRedirectAggStatus,
    alaQoSActionMirrorSlot,
    alaQoSActionMirrorPort,
    alaQoSActionMirrorMode,
    alaQoSActionMirrorModeStatus,
    alaQoSActionCIR,
    alaQoSActionCIRStatus,
    alaQoSActionCBS,
    alaQoSActionCBSStatus,
    alaQoSActionPIR,
    alaQoSActionPIRStatus,
    alaQoSActionPBS,
    alaQoSActionPBSStatus,
    alaQoSActionCounterColor
  }
  STATUS      current
  DESCRIPTION "Collections of objects providing information for Actions"
  ::= { alaQoSMIBGroups 27 }

alaQoSMIBAppliedActionObjects OBJECT-GROUP
  OBJECTS {
    alaQoSAppliedActionSource,
    alaQoSAppliedActionDisposition,
    alaQoSAppliedActionDropAlgorithm,
    alaQoSAppliedActionWredMaximumThreshold,
    alaQoSAppliedActionWredMaximumThresholdStatus,
    alaQoSAppliedActionWredMinimumThreshold,
    alaQoSAppliedActionWredMinimumThresholdStatus,
    alaQoSAppliedActionWredMaximumProbability,
    alaQoSAppliedActionWredMaximumProbabilityStatus,
    alaQoSAppliedActionMinimumBandwidth,
    alaQoSAppliedActionMinimumBandwidthStatus,
    alaQoSAppliedActionMaximumBandwidth,
    alaQoSAppliedActionMaximumBandwidthStatus,
    alaQoSAppliedActionPeakBandwidth,
    alaQoSAppliedActionPeakBandwidthStatus,
    alaQoSAppliedActionPriority,
    alaQoSAppliedActionPriorityStatus,
    alaQoSAppliedActionShared,
    alaQoSAppliedActionJitter,
    alaQoSAppliedActionJitterStatus,
    alaQoSAppliedActionLatency,
    alaQoSAppliedActionLatencyStatus,
    alaQoSAppliedActionMaximumDepth,
    alaQoSAppliedActionMaximumDepthStatus,
    alaQoSAppliedActionMaximumBuffers,
    alaQoSAppliedActionMaximumBuffersStatus,
    alaQoSAppliedAction8021p,
    alaQoSAppliedAction8021pStatus,
    alaQoSAppliedActionTos,
    alaQoSAppliedActionTosStatus,
    alaQoSAppliedActionDscp,
    alaQoSAppliedActionDscpStatus,
    alaQoSAppliedActionMapFrom,
    alaQoSAppliedActionMapTo,
    alaQoSAppliedActionMapGroup,
    alaQoSAppliedActionMapGroupStatus,
    alaQoSAppliedActionSourceRewriteIpAddr,
    alaQoSAppliedActionSourceRewriteIpAddrStatus,
    alaQoSAppliedActionSourceRewriteIpMask,
    alaQoSAppliedActionSourceRewriteNetworkGroup,
    alaQoSAppliedActionSourceRewriteNetworkGroupStatus,
    alaQoSAppliedActionDestinationRewriteIpAddr,
    alaQoSAppliedActionDestinationRewriteIpAddrStatus,
    alaQoSAppliedActionDestinationRewriteIpMask,
    alaQoSAppliedActionDestinationRewriteNetworkGroup,
    alaQoSAppliedActionDestinationRewriteNetworkGroupStatus,
    alaQoSAppliedActionLoadBalanceGroup,
    alaQoSAppliedActionLoadBalanceGroupStatus,
    alaQoSAppliedActionPermanentGatewayIpAddr,
    alaQoSAppliedActionPermanentGatewayIpAddrStatus,
    alaQoSAppliedActionAlternateGatewayIpAddr,
    alaQoSAppliedActionAlternateGatewayIpAddrStatus,
    alaQoSAppliedActionRowStatus,
    alaQoSAppliedActionMinimumDepth,
    alaQoSAppliedActionMinimumDepthStatus,
    alaQoSAppliedActionVPNAccess,
    alaQoSAppliedActionNocache,
    alaQoSAppliedActionPortdisable,
    alaQoSAppliedActionRedirectSlot,
    alaQoSAppliedActionRedirectSlotStatus,
    alaQoSAppliedActionRedirectPort,
    alaQoSAppliedActionRedirectAgg,
    alaQoSAppliedActionRedirectAggStatus,
    alaQoSAppliedActionMirrorSlot,
    alaQoSAppliedActionMirrorPort,
    alaQoSAppliedActionMirrorMode,
    alaQoSAppliedActionMirrorModeStatus,
    alaQoSAppliedActionCIR,
    alaQoSAppliedActionCIRStatus,
    alaQoSAppliedActionCBS,
    alaQoSAppliedActionCBSStatus,
    alaQoSAppliedActionPIR,
    alaQoSAppliedActionPIRStatus,
    alaQoSAppliedActionPBS,
    alaQoSAppliedActionPBSStatus,
    alaQoSAppliedActionCounterColor
  }
  STATUS      current
  DESCRIPTION "Collections of objects providing information
               for applied Actions"
  ::= { alaQoSMIBGroups 28 }

alaQoSMIBPortObjects OBJECT-GROUP
  OBJECTS {
    alaQoSPortEnabled,
    alaQoSPortAppliedEnabled,
    alaQoSPortInterfaceType,
    alaQoSPortTrusted,
    alaQoSPortDefault8021p,
    alaQoSPortDefaultDSCP,
    alaQoSPortMaximumReservedBandwidth,
    alaQoSPortMaximumReservedBandwidthStatus,
    alaQoSPortAppliedMaximumReservedBandwidth,
    alaQoSPortAppliedMaximumReservedBandwidthStatus,
    alaQoSPortMaximumSignalledBandwidth,
    alaQoSPortMaximumSignalledBandwidthStatus,
    alaQoSPortAppliedMaximumSignalledBandwidth,
    alaQoSPortAppliedMaximumSignalledBandwidthStatus,
    alaQoSPortDefaultQueues,
    alaQoSPortAppliedDefaultQueues,
    alaQoSPortMaximumDefaultBandwidth,
    alaQoSPortMaximumDefaultBandwidthStatus,
    alaQoSPortAppliedMaximumDefaultBandwidth,
    alaQoSPortAppliedMaximumDefaultBandwidthStatus,
    alaQoSPortMaximumDefaultDepth,
    alaQoSPortMaximumDefaultDepthStatus,
    alaQoSPortAppliedMaximumDefaultDepth,
    alaQoSPortAppliedMaximumDefaultDepthStatus,
    alaQoSPortMaximumDefaultBuffers,
    alaQoSPortMaximumDefaultBuffersStatus,
    alaQoSPortAppliedMaximumDefaultBuffers,
    alaQoSPortAppliedMaximumDefaultBuffersStatus,
    alaQoSPortReset,
    alaQoSPortPhysicalBandwidth,
    alaQoSPortReservedBandwidth,
    alaQoSPortSignalledBandwidth,
    alaQoSPortCurrentBandwidth,
    alaQoSPortDefaultQidLow,
    alaQoSPortDefaultQidMedium,
    alaQoSPortDefaultQidHigh,
    alaQoSPortDefaultQidUrgent,
    alaQoSPortFloodQid,
    alaQoSPortQueues,
    alaQoSPortQueuesCreated,
    alaQoSPortQueuesFailed,
    alaQoSPortQueuesPreempted,
    alaQoSPortRowStatus,
    alaQoSPortFirPrio0EnqBytes,
    alaQoSPortFirPrio0DeqBytes,
    alaQoSPortFirPrio0EnqPkts,
    alaQoSPortFirPrio0DeqPkts,
    alaQoSPortFirPrio0QidDiscardPkts,
    alaQoSPortFirPrio0WredDiscardPkts,
    alaQoSPortFirPrio0OverflowDiscardPkts,
    alaQoSPortFirPrio1EnqBytes,
    alaQoSPortFirPrio1DeqBytes,
    alaQoSPortFirPrio1EnqPkts,
    alaQoSPortFirPrio1DeqPkts,
    alaQoSPortFirPrio1QidDiscardPkts,
    alaQoSPortFirPrio1WredDiscardPkts,
    alaQoSPortFirPrio1OverflowDiscardPkts,
    alaQoSPortFirPrio2EnqBytes,
    alaQoSPortFirPrio2DeqBytes,
    alaQoSPortFirPrio2EnqPkts,
    alaQoSPortFirPrio2DeqPkts,
    alaQoSPortFirPrio2QidDiscardPkts,
    alaQoSPortFirPrio2WredDiscardPkts,
    alaQoSPortFirPrio2OverflowDiscardPkts,
    alaQoSPortFirPrio3EnqBytes,
    alaQoSPortFirPrio3DeqBytes,
    alaQoSPortFirPrio3EnqPkts,
    alaQoSPortFirPrio3DeqPkts,
    alaQoSPortFirPrio3QidDiscardPkts,
    alaQoSPortFirPrio3WredDiscardPkts,
    alaQoSPortFirPrio3OverflowDiscardPkts,
    alaQoSPortDefaultClassification,
    alaQoSPortLowPriorityWeight,
    alaQoSPortMediumPriorityWeight,
    alaQoSPortHighPriorityWeight,
    alaQoSPortUrgentPriorityWeight,
    alaQoSPortMaximumBandwidth,
    alaQoSPortMaximumBandwidthStatus,
    alaQoSPortEnqueuingThresholdP0Lower,
    alaQoSPortEnqueuingThresholdP0Upper,
    alaQoSPortEnqueuingThresholdP1Lower,
    alaQoSPortEnqueuingThresholdP1Upper,
    alaQoSPortEnqueuingThresholdP2Lower,
    alaQoSPortEnqueuingThresholdP2Upper,
    alaQoSPortEnqueuingThresholdP3Lower,
    alaQoSPortEnqueuingThresholdP3Upper,
    alaQoSPortEnqueuingThresholdStatus,
    alaQoSPortServicingMode,
    alaQoSPortHighDensity,
    alaQoSPortFreeFFPRules,
    alaQoSPortUsedFFPRules,
    alaQoSPortFreeFFPMasks,
    alaQoSPortUsedFFPMasks,
    alaQoSPortSpoofedCount,
    alaQoSPortNonSpoofedCount,
    alaQoSPortQ4PriorityWeight,
    alaQoSPortQ5PriorityWeight,
    alaQoSPortQ6PriorityWeight,
    alaQoSPortQ7PriorityWeight,
    alaQoSPortCOS0MaximumBandwidth,
    alaQoSPortCOS0MaximumBandwidthStatus,
    alaQoSPortCOS1MaximumBandwidth,
    alaQoSPortCOS1MaximumBandwidthStatus,
    alaQoSPortCOS2MaximumBandwidth,
    alaQoSPortCOS2MaximumBandwidthStatus,
    alaQoSPortCOS3MaximumBandwidth,
    alaQoSPortCOS3MaximumBandwidthStatus,
    alaQoSPortCOS4MaximumBandwidth,
    alaQoSPortCOS4MaximumBandwidthStatus,
    alaQoSPortCOS5MaximumBandwidth,
    alaQoSPortCOS5MaximumBandwidthStatus,
    alaQoSPortCOS6MaximumBandwidth,
    alaQoSPortCOS6MaximumBandwidthStatus,
    alaQoSPortCOS7MaximumBandwidth,
    alaQoSPortCOS7MaximumBandwidthStatus,
    alaQoSPortCOS0MinimumBandwidth,
    alaQoSPortCOS0MinimumBandwidthStatus,
    alaQoSPortCOS1MinimumBandwidth,
    alaQoSPortCOS1MinimumBandwidthStatus,
    alaQoSPortCOS2MinimumBandwidth,
    alaQoSPortCOS2MinimumBandwidthStatus,
    alaQoSPortCOS3MinimumBandwidth,
    alaQoSPortCOS3MinimumBandwidthStatus,
    alaQoSPortCOS4MinimumBandwidth,
    alaQoSPortCOS4MinimumBandwidthStatus,
    alaQoSPortCOS5MinimumBandwidth,
    alaQoSPortCOS5MinimumBandwidthStatus,
    alaQoSPortCOS6MinimumBandwidth,
    alaQoSPortCOS6MinimumBandwidthStatus,
    alaQoSPortCOS7MinimumBandwidth,
    alaQoSPortCOS7MinimumBandwidthStatus,
    alaQoSPortMaximumIngBandwidth,
    alaQoSPortMaximumIngBandwidthStatus,
    alaQoSPortDEIMarking,
    alaQoSPortMonitor,
    alaQoSPortDEIMapping 
  }
  STATUS      current
  DESCRIPTION "Collections of objects providing information for Ports"
  ::= { alaQoSMIBGroups 29 }

alaQoSMIBConfigObjects OBJECT-GROUP
  OBJECTS {
    alaQoSConfigEnabled,
    alaQoSConfigDefaultQueues,
    alaQoSConfigAppliedDefaultQueues,
    alaQoSConfigTrustPorts,
    alaQoSConfigFlowTimeout,
    alaQoSConfigAppliedFlowTimeout,
    alaQoSConfigFragmentTimeout,
    alaQoSConfigAppliedFragmentTimeout,
    alaQoSConfigReflexiveTimeout,
    alaQoSConfigAppliedReflfexiveTimeout,
    alaQoSConfigNatTimeout,
    alaQoSConfigAppliedNatTimeout,
    alaQoSConfigClassifyl3Bridged,
    alaQoSConfigAppliedClassifyl3Bridged,
    alaQoSConfigClassifyFragments,
    alaQoSConfigAppliedClassifyFragments,
    alaQoSConfigDefaultBridgedDisposition,
    alaQoSConfigAppliedDefaultBridgedDisposition,
    alaQoSConfigDefaultRoutedDisposition,
    alaQoSConfigAppliedDefaultRoutedDisposition,
    alaQoSConfigDefaultMulticastDisposition,
    alaQoSConfigAppliedDefaultMulticastDisposition,
    alaQoSConfigStatsInterval,
    alaQoSConfigLogLines,
    alaQoSConfigLogLevel,
    alaQoSConfigLogConsole,
    alaQoSConfigForwardLog,
    alaQoSConfigClearLog,
    alaQoSConfigApply,
    alaQoSConfigRevert,
    alaQoSConfigReset,
    alaQoSConfigStatsReset,
    alaQoSConfigFlush,
    alaQoSConfigNATFlush,
    alaQoSConfigDebug,
    alaQoSConfigServicingMode,
    alaQoSConfigLowPriorityWeight,
    alaQoSConfigMediumPriorityWeight,
    alaQoSConfigHighPriorityWeight,
    alaQoSConfigUrgentPriorityWeight,
    alaQoSConfigQ4PriorityWeight,
    alaQoSConfigQ5PriorityWeight,
    alaQoSConfigQ6PriorityWeight,
    alaQoSConfigQ7PriorityWeight,
    alaQoSConfigUserportFilter,
    alaQoSConfigAppliedUserportFilter,
    alaQoSConfigUserportShutdown,
    alaQoSConfigAppliedUserportShutdown,
    alaQoSConfigAutoNMS,
    alaQoSConfigAutoPhones,
    alaQoSConfigQMPage,
    alaQoSConfigQMMACGroup,
    alaQoSConfigQMPath,
    alaQoSConfigDEIMapping,
    alaQoSConfigDEIMarking,
    alaQoSConfigStatsResetEgress,
    alaQoSConfigForceYellowPriority,
    alaQoSConfigUserportLinkShutdown,
    alaQoSConfigAppliedUserportLinkShutdown,
    alaQoSConfigForceYellowUserPriority,
    alaQoSConfigForceYellowDSCP
  }
  STATUS      current
  DESCRIPTION "Collections of objects providing information for Configs"
  ::= { alaQoSMIBGroups 30 }

alaQoSMIBStatsObjects OBJECT-GROUP
  OBJECTS {
    alaQoSStatsL2Events,
    alaQoSStatsL2Matches,
    alaQoSStatsL2Drops,
    alaQoSStatsL3IngressEvents,
    alaQoSStatsL3IngressMatches,
    alaQoSStatsL3IngressDrops,
    alaQoSStatsL3EgressEvents,
    alaQoSStatsL3EgressMatches,
    alaQoSStatsL3EgressDrops,
    alaQoSStatsMulticastEvents,
    alaQoSStatsMulticastMatches,
    alaQoSStatsMulticastDrops,
    alaQoSStatsFragments,
    alaQoSStatsBadFragments,
    alaQoSStatsUnknownFragments,
    alaQoSStatsReflexiveFlows,
    alaQoSStatsReflexiveCorrections,
    alaQoSStatsLoadBalanceFlows,
    alaQoSStatsClassifierMaxNodes,
    alaQoSStatsClassifierMaxDepth,
    alaQoSStatsFlowLookups,
    alaQoSStatsFlowHits,
    alaQoSStatsSentNIMessages,
    alaQoSStatsReceivedNIMessages,
    alaQoSStatsFailedNIMessages,
    alaQoSStatsSpoofedEvents,
    alaQoSStatsNonSpoofedEvents,
    alaQoSStatsDropServicesEvents		
  }
  STATUS      current
  DESCRIPTION "Collections of objects providing information for Statss"
  ::= { alaQoSMIBGroups 31 }

alaQoSMIBQueueObjects OBJECT-GROUP
  OBJECTS {
    alaQoSQueueSlot,
    alaQoSQueuePort,
    alaQoSQueuePortId,
    alaQoSQueueType,
    alaQoSQueuePriority,
    alaQoSQueueMinimumBandwidth,
    alaQoSQueueMaximumBandwidth,
    alaQoSQueueAverageBandwidth,
    alaQoSQueueMinimumDepth,
    alaQoSQueueMaximumDepth,
    alaQoSQueueMaximumBuffers,
    alaQoSQueue8021p,
    alaQoSQueuePacketsSent,
    alaQoSQueuePacketsDropped,
    alaQoSQueueMaxLength,
    alaQoSQueueAverageLength,
    alaQoSQueueCurrentLength,
    alaQoSQueueAction
  }
  STATUS      current
  DESCRIPTION "Collections of objects providing information for Queues"
  ::= { alaQoSMIBGroups 32 }

alaQoSMIBSlotObjects OBJECT-GROUP
  OBJECTS {
    alaQoSSlotType,
    alaQoSSlotMaxBuffers,
    alaQoSSlotFreeBuffers1,
    alaQoSSlotFreeBuffers2,
    alaQoSSlotThreshold1Low,
    alaQoSSlotThreshold1Medium,
    alaQoSSlotThreshold1High,
    alaQoSSlotThreshold1Urgent,
    alaQoSSlotThreshold2Low,
    alaQoSSlotThreshold2Medium,
    alaQoSSlotThreshold2High,
    alaQoSSlotThreshold2Urgent,
    alaQoSSlotBuffersDenied,
    alaQoSSlotBuffersDeniedAverage,
    alaQoSSlotBuffersDropped,
    alaQoSSlotBuffersDroppedAverage,
    alaQoSSlotWredThresholdP0Lower,
    alaQoSSlotWredThresholdP0Upper,
    alaQoSSlotWredThresholdP1Lower,
    alaQoSSlotWredThresholdP1Upper,
    alaQoSSlotWredThresholdP2Lower,
    alaQoSSlotWredThresholdP2Upper,
    alaQoSSlotWredThresholdP3Lower,
    alaQoSSlotWredThresholdP3Upper,
    alaQoSSlotWredAverageCounterWeight,
    alaQoSSlotWredThresholdStatus,
    alaQoSSlotCbqThresholdMode,
    alaQoSSlotCbqThresholdP1,
    alaQoSSlotCbqThresholdP2,
    alaQoSSlotCbqThresholdP3,
    alaQoSSlotHighDensity
  }
  STATUS      current
  DESCRIPTION "Collections of objects providing information for Slots"
  ::= { alaQoSMIBGroups 33 }

alaQoSMIBClassifyObjects OBJECT-GROUP
  OBJECTS {
    alaQoSClassifyExecute,
    alaQoSClassifyL2SourceResultRule,
    alaQoSClassifyL2SourceResultDisposition,
    alaQoSClassifyL2DestinationResultRule,
    alaQoSClassifyL2DestinationResultDisposition,
    alaQoSClassifyL3ResultRule,
    alaQoSClassifyL3ResultDisposition,
    alaQoSClassifyIGMPResultRule,
    alaQoSClassifyIGMPResultDisposition,
    alaQoSClassifyMulticastResultRule,
    alaQoSClassifyMulticastResultDisposition
  }
  STATUS      current
  DESCRIPTION "Collections of objects providing information for Classifys"
  ::= { alaQoSMIBGroups 34 }

alaQoSMIBRuleGroupsObjects OBJECT-GROUP
  OBJECTS {
    alaQoSRuleGroupsSource,
    alaQoSRuleGroupsType,
    alaQoSRuleGroupsEnabled,
    alaQoSRuleGroupsStatus
  }
  STATUS      current
  DESCRIPTION "Collections of objects providing information for RuleGroupss"
  ::= { alaQoSMIBGroups 35 }

alaQoSMIBAppliedRuleGroupsObjects OBJECT-GROUP
  OBJECTS {
    alaQoSAppliedRuleGroupsSource,
    alaQoSAppliedRuleGroupsType,
    alaQoSAppliedRuleGroupsEnabled,
    alaQoSAppliedRuleGroupsStatus
  }
  STATUS      current
  DESCRIPTION "Collections of objects providing information
               for applied RuleGroupss"
  ::= { alaQoSMIBGroups 36 }

alaQoSMIBRuleGroupObjects OBJECT-GROUP
  OBJECTS {
    alaQoSRuleGroupMatches,
    alaQoSRuleGroupCountType,
    alaQoSRuleGroupPacketCount,
    alaQoSRuleGroupByteCount,
    alaQoSRuleGroupStatus,
    alaQoSRuleGroupPacketRate,
    alaQoSRuleGroupBitRate,
    alaQoSRuleGroupAccPacketCount,
    alaQoSRuleGroupAccByteCount 
  }
  STATUS      current
  DESCRIPTION "Collections of objects providing information for RuleGroups"
  ::= { alaQoSMIBGroups 37 }

alaQoSMIBAppliedRuleGroupObjects OBJECT-GROUP
  OBJECTS {
    alaQoSAppliedRuleGroupMatches,
    alaQoSAppliedRuleGroupCountType,
    alaQoSAppliedRuleGroupPacketCount,
    alaQoSAppliedRuleGroupByteCount,
    alaQoSAppliedRuleGroupStatus,
    alaQosAppliedRuleGroupPacketRate,
    alaQosAppliedRuleGroupBitRate,
    alaQoSAppliedRuleGroupAccPacketCount,
    alaQoSAppliedRuleGroupAccByteCount
  }
  STATUS      current
  DESCRIPTION "Collections of objects providing information
               for applied RuleGroups"
  ::= { alaQoSMIBGroups 38 }

alaQoSVlanGroupsObjects OBJECT-GROUP
  OBJECTS {
    alaQoSVlanGroupsSource,
    alaQoSVlanGroupsStatus
  }
  STATUS      current
  DESCRIPTION "Collections of objects providing QoS Vlan Groups definitions."
  ::= { alaQoSMIBGroups 39 }

alaQoSAppliedVlanGroupsObjects OBJECT-GROUP    
  OBJECTS {     
    alaQoSAppliedVlanGroupsSource,
    alaQoSAppliedVlanGroupsStatus 
  }
  STATUS      current   
  DESCRIPTION "Collections of objects providing applied QoS Vlan Groups
	      definitions."
  ::= { alaQoSMIBGroups 40 }

alaQoSVlanGroupObjects OBJECT-GROUP    
  OBJECTS {     
    alaQoSVlanGroupStatus
  }
  STATUS      current   
  DESCRIPTION "Collections of objects providing QoS Vlan Groups definitions."
  ::= { alaQoSMIBGroups 41 }

alaQoSAppliedVlanGroupObjects OBJECT-GROUP
  OBJECTS {
    alaQoSAppliedVlanGroupStatus
  }
  STATUS      current
  DESCRIPTION "Collections of objects providing applied QoS Vlan Groups 
	      definitions."
  ::= { alaQoSMIBGroups 42 }

alaQoSMIBHwLoopBackProfileObjects OBJECT-GROUP   
 OBJECTS {   
   alaQoSHwLoopbackSourceMac,   
   alaQoSHwLoopbackDestinationMac,   
   alaQoSHwLoopbackVlan,   
   alaQoSHwLoopbackPort,   
   alaQoSHwLoopbackType,   
   alaQoSHwLoopbackProfileStatus,   
   alaQoSHwLoopbackProfileRowStatus,
   alaQosHwLoopbackSapId    
 }   
 STATUS      current   
 DESCRIPTION "Collections of objects providing information   
              for Hardware Loopback"   
 ::= { alaQoSMIBGroups 43 } 

alQosQueueStatsGroupObjects OBJECT-GROUP
  OBJECTS {
    alaQoSQueueStatsSlot,
    alaQoSQueueStatsPort,
    alaQoSQueueStatsTransmitQueue,
    alaQoSQueueStatsPriority,
    alaQoSQueueStatsPacketsSent,
    alaQoSQueueStatsPacketsDropped,
    alaQoSQueueStatsBytesSent,
    alaQoSQueueStatsBytesDropped,
    alaQoSQueueStatsRateSent, 
    alaQoSQueueStatsRateDropped
   }
  STATUS      current
  DESCRIPTION "Collection of objects providing statistics information 
	     for egress queues."
  ::= { alaQoSMIBGroups 44 }

alaQoSAppliedImportGroup OBJECT-GROUP
  OBJECTS {
    alaQoSAppliedImportPrecedence,
    alaQoSAppliedImportPrefix,
    alaQoSAppliedImportSlot,
    alaQoSAppliedImportPort,
    alaQoSAppliedImportPortend,
    alaQoSAppliedImportPortgroup,
    alaQoSAppliedImportRowStatus
  }
  STATUS      current
  DESCRIPTION "Definition of QoS Applied Import."
  ::= { alaQoSMIBGroups 45 }
alaQoSAppliedValidityPeriodGroup OBJECT-GROUP
  OBJECTS {
    alaQoSAppliedValidityPeriodSource,
    alaQoSAppliedValidityPeriodDays,
    alaQoSAppliedValidityPeriodDaysStatus,
    alaQoSAppliedValidityPeriodMonths,
    alaQoSAppliedValidityPeriodMonthsStatus,
    alaQoSAppliedValidityPeriodHour,
    alaQoSAppliedValidityPeriodHourStatus,
    alaQoSAppliedValidityPeriodEndHour,
    alaQoSAppliedValidityPeriodInterval,
    alaQoSAppliedValidityPeriodIntervalStatus,
    alaQoSAppliedValidityPeriodEndInterval,
    alaQoSAppliedValidityPeriodRowStatus
  }
  STATUS      current
  DESCRIPTION "Definition of QoS Applied Import."
  ::= { alaQoSMIBGroups 46 }
alaQoSImportGroup OBJECT-GROUP
  OBJECTS 
  {
  		alaQoSImportPort,
  		alaQoSImportPortend ,
  		alaQoSImportPortgroup ,
  		alaQoSImportPrecedence,
  		alaQoSImportPrefix,
  		alaQoSImportRowStatus,
  		alaQoSImportSlot     
  }
  STATUS      current
  DESCRIPTION "Definition of QoS Import."
  ::= { alaQoSMIBGroups 47 }
 
  alaQoSPortPdiGroup  OBJECT-GROUP
  OBJECTS 
  {
  	alaQoSPortPdiPriorityP0,
  	alaQoSPortPdiPriorityP1,
  	alaQoSPortPdiPriorityP2,
  	alaQoSPortPdiPriorityP3,
  	alaQoSPortPdiPriorityP4,
  	alaQoSPortPdiPriorityP5,
  	alaQoSPortPdiPriorityP6 ,
  	alaQoSPortPdiPriorityP7,
  	alaQoSPortPdiPriorityType,
  	alaQoSPortProtocolClassification
  }
  STATUS      current
  DESCRIPTION "Definition of QoS PortPdi."
  ::= { alaQoSMIBGroups 48 }
  
  alaQoSPortPriorityGroup  OBJECT-GROUP
  OBJECTS 
  {
  	alaQoSPortProtocolPriorityP0,
  	alaQoSPortProtocolPriorityP1,
  	alaQoSPortProtocolPriorityP2,
  	alaQoSPortProtocolPriorityP3,
  	alaQoSPortProtocolPriorityP4,
  	alaQoSPortProtocolPriorityP5,
  	alaQoSPortProtocolPriorityP6,
  	alaQoSPortProtocolPriorityP7,
  	alaQoSPortProtocolRowStatus  
  }
  STATUS      current
  DESCRIPTION "Definition of QoS Port Priority."
  ::= { alaQoSMIBGroups 49 }
  
 alaQoSSlotDscpGroup   OBJECT-GROUP
  OBJECTS 
  {
  	alaQoSSlotDscpPriority 
  }
  STATUS      current
  DESCRIPTION "Definition of QoS SlotDscp."
  ::= { alaQoSMIBGroups 50 }
  
  alaQoSSlotPcamGroup   OBJECT-GROUP
  OBJECTS 
  {
  	alaQoSSlotPcam8023Enabled,
  	alaQoSSlotPcamDsap,
  	alaQoSSlotPcamEnable8023,
  	alaQoSSlotPcamEnableDsap,
  	alaQoSSlotPcamEnableEntry,
  	alaQoSSlotPcamEnableEthertype ,
  	alaQoSSlotPcamEnableSsap,
  	alaQoSSlotPcamEthertype,
  	alaQoSSlotPcamProtocolNumber,
  	alaQoSSlotPcamSsap
  	 
  	 
  }
  STATUS      current
  DESCRIPTION "Definition of QoS SlotDscp."
  ::= { alaQoSMIBGroups 51 }
  
	alaQoSSlotProtocolGroup  OBJECT-GROUP
  OBJECTS 
  {
  	alaQoSSlotProtocol8023Enabled ,
  	alaQoSSlotProtocolDsap ,
  	alaQoSSlotProtocolEthertype,
  	 alaQoSSlotProtocolRowStatus,
  	 alaQoSSlotProtocolSsap,
  	 alaQoSSlotProtocolType
  	  
  }
   STATUS      current
  DESCRIPTION "Definition of QoS SlotDscp."
  ::= { alaQoSMIBGroups 52 }
  
  alaQoSValidityPeriodGroup OBJECT-GROUP
  OBJECTS 
  {
	  	alaQoSValidityPeriodDays,
	  	alaQoSValidityPeriodDaysStatus ,
	  	alaQoSValidityPeriodEndHour,
	  	alaQoSValidityPeriodEndInterval,
	  	alaQoSValidityPeriodHour,
	  	alaQoSValidityPeriodHourStatus,
	  	alaQoSValidityPeriodInterval,
	  	alaQoSValidityPeriodIntervalStatus,
	  	alaQoSValidityPeriodMonths,
	  	alaQoSValidityPeriodMonthsStatus,
	  	alaQoSValidityPeriodRowStatus,
	  	alaQoSValidityPeriodSource       
  }
   STATUS      current
  DESCRIPTION "Definition of QoS SlotDscp."
  ::= { alaQoSMIBGroups 53 }
  
--
-- Definition of DSCP table
--
alaQoSDSCPTable OBJECT-TYPE
  SYNTAX      SEQUENCE OF QoSDSCPEntry 
  MAX-ACCESS  not-accessible
  STATUS      current
  DESCRIPTION "Table of QoS Condition definitions"
  ::= { alaQoSMIBObjects 55 }
alaQoSDSCPEntry OBJECT-TYPE
  SYNTAX      QoSDSCPEntry
  MAX-ACCESS  not-accessible
  STATUS      current
  DESCRIPTION "Definition of QoS DSCP"
  INDEX {
          alaQoSDSCPEntryNumber
        }
  ::= { alaQoSDSCPTable 1 }
QoSDSCPEntry ::=
  SEQUENCE
  {
	alaQoSDSCPEntryNumber		Integer32,
	alaQoSDSCPPriority			Integer32,
	alaQoSDSCPDropPrecedence	INTEGER,
        alaQoSDSCPRowStatus             RowStatus 
   }
alaQoSDSCPEntryNumber OBJECT-TYPE
  SYNTAX      		Integer32
  MAX-ACCESS  		not-accessible
  STATUS      		current
  DESCRIPTION 		"DSCP Entry number for the traffic."
  ::= { alaQoSDSCPEntry 1}
alaQoSDSCPPriority OBJECT-TYPE
  SYNTAX      		Integer32
  MAX-ACCESS 		read-create
  STATUS      		current
  DESCRIPTION 		"DSCP priority for the traffic."
  ::= { alaQoSDSCPEntry 2}
alaQoSDSCPDropPrecedence OBJECT-TYPE
  SYNTAX	INTEGER {
				low (1),
				medium (2),
				high (3)
			}		
  MAX-ACCESS 		read-create
  STATUS      		current
  DESCRIPTION 		"DSCP drop precedence for the traffic."
  DEFVAL      	{low}
  ::= { alaQoSDSCPEntry 3}
alaQoSDSCPRowStatus OBJECT-TYPE
  SYNTAX      		RowStatus 
  MAX-ACCESS 		read-create
  STATUS      		current
  DESCRIPTION 		"RowStatus entry for QoS DSCP."
  ::= { alaQoSDSCPEntry 4}
 
alaQoSMIBCompliance MODULE-COMPLIANCE
  STATUS      current
  DESCRIPTION "Compliance statement for QoS."
  MODULE
  MANDATORY-GROUPS {
    alaQoSMIBRuleObjects,
    alaQoSMIBAppliedRuleObjects,
    alaQoSMIBConditionObjects,
    alaQoSMIBAppliedConditionObjects,
    alaQoSMIBServiceObjects,
    alaQoSMIBAppliedServiceObjects,
    alaQoSMIBServiceGroupsObjects,
    alaQoSMIBAppliedServiceGroupsObjects,
    alaQoSMIBServiceGroupObjects,
    alaQoSMIBAppliedServiceGroupObjects,
    alaQoSMIBNetworkGroupsObjects,
    alaQoSMIBAppliedNetworkGroupsObjects,
    alaQoSMIBNetworkGroupObjects,
    alaQoSMIBAppliedNetworkGroupObjects,
    alaQoSMIBMACGroupsObjects,
    alaQoSMIBAppliedMACGroupsObjects,
    alaQoSMIBMACGroupObjects,
    alaQoSMIBAppliedMACGroupObjects,
    alaQoSMIBPortGroupsObjects,
    alaQoSMIBAppliedPortGroupsObjects,
    alaQoSMIBPortGroupObjects,
    alaQoSMIBAppliedPortGroupObjects,
    alaQoSMIBMapGroupsObjects,
    alaQoSMIBAppliedMapGroupsObjects,
    alaQoSMIBMapGroupObjects,
    alaQoSMIBAppliedMapGroupObjects,
    alaQoSMIBActionObjects,
    alaQoSMIBAppliedActionObjects,
    alaQoSMIBPortObjects,
    alaQoSMIBConfigObjects,
    alaQoSMIBStatsObjects,
    alaQoSMIBQueueObjects,
    alaQoSMIBSlotObjects,
    alaQoSMIBClassifyObjects,
    alaQoSMIBRuleGroupsObjects,
    alaQoSMIBAppliedRuleGroupsObjects,
    alaQoSMIBRuleGroupObjects,
    alaQoSMIBAppliedRuleGroupObjects,
    alaQoSVlanGroupsObjects,
    alaQoSAppliedVlanGroupsObjects,
    alaQoSVlanGroupObjects,
    alaQoSAppliedVlanGroupObjects,
    alaQoSMIBHwLoopBackProfileObjects,
    alQosQueueStatsGroupObjects,
    alaQoSAppliedImportGroup,
    alaQoSAppliedValidityPeriodGroup,
    alaQoSImportGroup,
    alaQoSPortPdiGroup,
    alaQoSPortPriorityGroup,
    alaQoSSlotDscpGroup,
    alaQoSSlotPcamGroup,
    alaQoSSlotProtocolGroup,
    alaQoSValidityPeriodGroup 
  }
  ::= { alaQoSMIBCompliances 1 }

END
