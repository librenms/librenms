ALCATEL-IND1-SNMP-AGENT-MIB DEFINITIONS ::= BEGIN

IMPORTS
	OBJECT-TYPE,
	OBJECT-IDENTITY,
	MODULE-IDENTITY,

	IpAddress		FROM SNMPv2-SMI
	TEXTUAL-CONVENTION,DisplayString 	FROM SNMPv2-TC
        OBJECT-GROUP,
	MODULE-COMPLIANCE       FROM SNMPv2-CONF
	softentIND1SnmpAgt	FROM ALCATEL-IND1-BASE;


alcatelIND1SNMPAgentMIB  MODULE-IDENTITY
	LAST-UPDATED  "201910070000Z"
	ORGANIZATION  "ALE USA Inc"
	CONTACT-INFO
	    "Please consult with Customer Service to ensure the most appropriate
	     version of this document is used with the products in question:
 
			    Alcatel-Lucent Enterprise,		      
			       26801 West Agoura Road
			    Agoura Hills, CA  91301-5122
			      United States Of America
	
	    Telephone:               +1 800 995 2696 
 				                	
	    Electronic Mail:         ebg_global_supportcenter@al-enterprise.com
	    World Wide Web:          https://www.al-enterprise.com"

	DESCRIPTION
	    "This module describes an authoritative enterprise-specific Simple
             Network Management Protocol (SNMP) Management Information Base (MIB):
         
                 For the OmniSwitch Product Line
                 SNMP Agent Subsystem.
         
             The right to make changes in specification and other information
             contained in this document without prior notice is reserved.
         
             No liability shall be assumed for any incidental, indirect, special, or
             consequential damages whatsoever arising from or related to this
             document or the information contained herein.
         
             Vendors, end-users, and other interested parties are granted
             non-exclusive license to use this specification in connection with
             management of the products for which it is intended to be used.
         
                         Copyright (C) ALE USA Inc. 2014-2019
			 Copyright (C) 1995-2013 Alcatel-Lucent
                         ALL RIGHTS RESERVED WORLDWIDE"

	REVISION      "201910070000Z"
        DESCRIPTION
            "Updated the latest contact and Copyright information for ALE USA Inc."
	::= { softentIND1SnmpAgt 1 }

    alcatelIND1SNMPAgentMIBObjects OBJECT-IDENTITY
        STATUS current
        DESCRIPTION
            "Branch For SNMP Agent Subsystem Managed Objects."
        ::= { alcatelIND1SNMPAgentMIB 1 }


    alcatelIND1SNMPAgentMIBConformance OBJECT-IDENTITY
        STATUS current
        DESCRIPTION
            "Branch For SNMP Agent Subsystem Conformance Information."
        ::= { alcatelIND1SNMPAgentMIB 2 }


    alcatelIND1SNMPAgentMIBGroups OBJECT-IDENTITY
        STATUS current
        DESCRIPTION
            "Branch For SNMP Agent Subsystem Units Of Conformance."
        ::= { alcatelIND1SNMPAgentMIBConformance 1 }


    alcatelIND1SNMPAgentMIBCompliances OBJECT-IDENTITY
        STATUS current
        DESCRIPTION
            "Branch For SNMP Agent Subsystem Compliance Statements."
        ::= { alcatelIND1SNMPAgentMIBConformance 2 }


--
-- SNMP Agent configuration
--

snmpAgtConfig  OBJECT IDENTIFIER ::= { alcatelIND1SNMPAgentMIBObjects 1 }

SnmpAgtSecurityLevel ::= TEXTUAL-CONVENTION
	STATUS current
	DESCRIPTION
	"The switch security level"
	SYNTAX INTEGER {
		noSec(1),
		authSet(2),
		authAll(3),
		privSet(4),
		privAll(5),
		trapOnly(6)
	}  
	
snmpAgtSecurityLevel OBJECT-TYPE
	SYNTAX     SnmpAgtSecurityLevel
	MAX-ACCESS read-write
	STATUS     current
	DESCRIPTION
	"Level of security required for SNMP get or SET.
	 noSec: no security; all the PDU with a known user id
		are accepted
	 authSet: authentication required for set; all GET
		are accepted, but not authenticated SET are
		rejected.
	 authAll: authentication required for SET and GET; not
		authenticated SET and GET are rejected.
	 privSet: authentication required for GET and encryption
 		required for SET.
	 privAll: encryption required for SET and GET.
	 trapOnly: no SNMP GET or SET are accepted."
  	DEFVAL     { noSec }
	::= { snmpAgtConfig 1}

snmpAgtCommunityMode OBJECT-TYPE
	SYNTAX  INTEGER {
		enabled(1),
		disabled(2) }
	MAX-ACCESS  read-write
	STATUS  current
	DESCRIPTION
		"If the community mode is enabled,
		 the SNMPv1/v2 packets must use 
		 the community names."
	DEFVAL { enabled }
	::= { snmpAgtConfig 2 }


-- 
-- SNMP Agent Epilogue Control Files anchoring
--

      snmpAgtCtlFiles OBJECT-IDENTITY
	STATUS current
	DESCRIPTION 
	"MIB entity on which to attach the MODULE-IDENTITY for the
	Epilogue(R) control files."
	::= { alcatelIND1SNMPAgentMIBObjects 3}

--
-- SNMP Source Ip Preferred Configuration
--
 
      snmpAgtSourceIpConfig  OBJECT-TYPE
        SYNTAX INTEGER {
             default (1),
             noLoopback0 (2),
             ipInterface (3)
       }
       MAX-ACCESS read-write
       STATUS        current
       DESCRIPTION
              "The SNMP Agent Configuration
              1 -- Default(Loopback0 or closest IP)
              2 -- No Loopback0
              3 -- Interface IP Specified by User"
       DEFVAL        { default }
       ::= {  alcatelIND1SNMPAgentMIBObjects 4 }
 
      snmpAgtSourceIp  OBJECT-TYPE
	SYNTAX     IpAddress
        MAX-ACCESS read-write
        STATUS        current
        DESCRIPTION
               "The Source IP of SNMP Packets"
        ::= {  alcatelIND1SNMPAgentMIBObjects 5 }

--
-- Compliance Statements
--

    alcatelIND1SNMPAgentMIBCompliance MODULE-COMPLIANCE
        STATUS  current
        DESCRIPTION
            "Compliance statement for SNMP Agent Subsystem."
        MODULE  -- this module

            MANDATORY-GROUPS
            {
                snmpAgtConfigGroup,
                snmpAgtCtlFilesGroup
            }

        ::= { alcatelIND1SNMPAgentMIBCompliances 1 }


--
-- Units Of Conformance
--

     snmpAgtConfigGroup OBJECT-GROUP
        OBJECTS
        {
	    snmpAgtSecurityLevel,
	    snmpAgtCommunityMode
        }
        STATUS  current
        DESCRIPTION
            "Collection of objects for SNMP Agent configuration."
        ::= { alcatelIND1SNMPAgentMIBGroups 1 }

snmpAgtCtlFilesGroup OBJECT-GROUP
        OBJECTS
        {
            snmpAgtSourceIpConfig,
            snmpAgtSourceIp
        }
        STATUS  current
        DESCRIPTION
            "Collection of objects for SNMP Agent Contorl Files configuration."
        ::= { alcatelIND1SNMPAgentMIBGroups 2 }

--	 
--    SNMP View local database configuration table	 
--	 
    snmpAgtViewMIB    OBJECT IDENTIFIER ::= { alcatelIND1SNMPAgentMIBObjects 6 }	 
	 
    snmpAgtViewTable OBJECT-TYPE	 
        SYNTAX        SEQUENCE OF SnmpAgtViewEntry	 
        MAX-ACCESS    not-accessible	 
        STATUS        current	 
        DESCRIPTION	 
            "This table shows current configuration for the local SNMP View database."	 
        ::= { snmpAgtViewMIB 1 }	 
	 
    snmpAgtViewEntry OBJECT-TYPE	 
        SYNTAX        SnmpAgtViewEntry	 
        MAX-ACCESS    not-accessible	 
        STATUS        current	 
        DESCRIPTION	 
            "An View configuration identified by its View name."	 
	INDEX { snmpAgtViewName,snmpAgtViewTableID }
        ::= { snmpAgtViewTable 1 }	 
	 
    SnmpAgtViewEntry ::= SEQUENCE	 
        {	 
            snmpAgtViewName                   DisplayString,	 
            snmpAgtViewTableID                DisplayString,	 
            snmpAgtViewType                   INTEGER	 
       }	 
           	 
    snmpAgtViewName OBJECT-TYPE	 
        SYNTAX        DisplayString ( SIZE( 0 .. 63 ) )	 
        MAX-ACCESS    not-accessible
        STATUS        current	 
        DESCRIPTION	 
            "Name of the View."	 
        ::= { snmpAgtViewEntry 1}	 
                	 
    snmpAgtViewTableID OBJECT-TYPE	 
        SYNTAX        DisplayString ( SIZE( 0 .. 63 ) )
        MAX-ACCESS    not-accessible
        STATUS        current	 
        DESCRIPTION	 
            "OID need to added in view table"	 
        ::= { snmpAgtViewEntry 2}	 
                	 
    snmpAgtViewType OBJECT-TYPE	 
        SYNTAX        INTEGER	 
                      {	 
                           include(1),	 
                           exclude(2)  	 
                      }	 
        MAX-ACCESS    not-accessible
        STATUS        current	 
        DESCRIPTION	 
            "Specifies type of the Table OID to be added in the view table.	 
                 include(1) - If OID is need to be allowed for the user.	 
                 exclude(2) - If OID is not to be allowed for the user."	 
        ::= { snmpAgtViewEntry 3}	 
END
