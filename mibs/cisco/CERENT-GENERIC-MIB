-- **************************************************************
-- File name: cerentGeneric.mib
-- Module name: Cerent-GENERIC-MIB module
--
-- This module contains the generic objects and generic events 
-- for the Cisco ONS Network Element ONS 15327, 15310 .

-- Copyright (c) 1998-1999 by Cerent Corporation, Inc.
-- Copyright (c) 1999-2004 by Cisco Systems, Inc.
-- All rights reserved.
--
-- **************************************************************

CERENT-GENERIC-MIB DEFINITIONS ::= BEGIN

IMPORTS
    MODULE-IDENTITY,
    OBJECT-TYPE,
    OBJECT-IDENTITY,
    NOTIFICATION-TYPE,
    Integer32,
    Unsigned32,
    Counter32
                      FROM SNMPv2-SMI
    TEXTUAL-CONVENTION,
    DisplayString, 
    TruthValue,
    TimeStamp
                      FROM SNMPv2-TC
    MODULE-COMPLIANCE, 
    OBJECT-GROUP, 
    NOTIFICATION-GROUP 
                      FROM SNMPv2-CONF
    cerentGeneric,
    cerentRequirements,
    cerentModules
                      FROM CERENT-GLOBAL-REGISTRY
    CerentNotificationClass,
    CerentAlarmSeverity,
    CerentAlarmStatus,
    CerentAlarmServiceAffecting,
    CerentMonitorType,
    CerentLocation,
    CerentPeriod,
    CerentPortNumber
                      FROM CERENT-TC;

cerentGenericMibModule MODULE-IDENTITY
    LAST-UPDATED "0410010000Z" -- 2004/Oct/01
    ORGANIZATION "Cisco Systems, Inc."
    CONTACT-INFO
        "         support@Cisco.com

         Postal:  Cisco Systems
                  1450 N. McDowell Blvd.
                  Petaluma, CA  94954
                  USA

            Tel:  +1-877-323-7368"
    DESCRIPTION
        "This module provides the definitions for 
         generic objects and notifications of 
         Cisco ONS network device, ONS 15327, 15310."

    REVISION "0410010000Z" -- 2004/Oct/01
    DESCRIPTION
         "This file can be used with R5.0 release."

    ::= { cerentModules 40 }

cerentConformance OBJECT-IDENTITY
      STATUS      current
      DESCRIPTION
            "This node is created for compliance. Has 
             objects as required by the RFCs"
      ::= { cerentRequirements 10 }

--  ********************************************************

cerentGenericGroups OBJECT-IDENTITY
      STATUS      current
      DESCRIPTION
            "All the objects and events are
             grouped under this for conformance"
      ::= { cerentConformance 10 }

cerentCompliance OBJECT-IDENTITY
      STATUS      current
      DESCRIPTION
            "The compliance statements
             for Cisco ONS 15327, 15310."
      ::= { cerentConformance 20 }

-- **************************************************************
-- Cisco ONS generic textual conventions
-- **************************************************************

CerentGenericAlarmType ::= TEXTUAL-CONVENTION
--   DISPLAY-HINT "d"
   STATUS current
   DESCRIPTION
       "This TC is used by the NMS to map the alarm type
        received by the trap and and display the string
        shown in LHS."
   SYNTAX INTEGER {
       galarmUnknown                                       (  1 ), 
       galarmCutoffIsInManualMode                         ( 10 ), 
       gfailureDetectedExternalToTheNE                    ( 20 ),
       gexternalError                                     ( 30 ), 
       gexcessiveSwitching                                ( 40 ), 
       gsdccTerminationFailure                            ( 50 ), 
       gincomingFailureCondition                          ( 60 ), 
       galarmIndicationSignal                             ( 70 ), 
       galarmIndicationSignalLine                         ( 80 ), 
       galarmIndicationSignalPath                         ( 90 ), 
       galarmIndicationSignalVT                           ( 100 ),
       gapsChannelFailure                                 ( 110 ), 
       gchannelByteFailureAPS                             ( 120 ), 
       gchannelProtectionSwitchingChannelMatchFailureAPS  ( 130 ), 
       gchannelAutomaticProtectionSwitchModeMismatchAPS   ( 140 ), 
       gfarEndProtectionLineFailure                       ( 150 ), 
       ginconsistentAPSCode                               ( 160 ), 
       gimproperAPSCode                                   ( 170 ), 
       gnodeIdMismatch                                    ( 180 ), 
       gchannelDefaultKAPS                                ( 190 ), 
       gconnectionLoss                                    ( 200 ), 

       gbipolarViolation                                  ( 210 ), 
       gcarrierLossOnTheLAN                               ( 220 ), 
       gconcatenationErrorSTS                             ( 230 ), 
       gexcessCollisionsOnTheLAN                          ( 240 ), 
       gfacilityFailure                                   ( 250 ), 
       gfarEndAIS                                         ( 260 ), 
       gfarEndMultipleDS1LOSDetectedOnDS3                 ( 270 ), 
       gfarEndDS1EqptFailNonServiceAffecting              ( 280 ), 
       gfarEndDS1EqptFailServiceAffecting                 ( 290 ), 
       gfarEndSingleDS1LOS                                ( 300 ), 
       gfarEndDS3EqptFailNonServiceAffecting              ( 310 ), 
       gfarEndDS3EqptFailServiceAffecting                 ( 320 ), 
       gfarEndCommonEquipmentFailureNonServiceAffecting   ( 330 ), 
       gfarEndIDLE                                        ( 340 ), 
       gfarEndLOS                                         ( 350 ), 
       gfarEndLOF                                         ( 360 ), 
       gfarEndBlockError                                  ( 370 ), 
       gds3IdleCondition                                  ( 380 ), 
       glossOfFrame                                       ( 390 ), 
       glossOfPointer                                     ( 400 ), 

       glossOfPointerPath                                 ( 410 ), 
       glossOfPointerVT                                   ( 420 ), 
       glossOfSignal                                      ( 430 ), 
       goutOfFrame                                        ( 440 ), 
       gpathSelectorFailure                               ( 450 ), 
       gremoteAlarmIndication                             ( 460 ), 
       gremoteFailureIndication                           ( 470 ), 
       gremoteFailureIndicationLine                       ( 480 ), 
       gremoteFailureIndicationPath                       ( 490 ), 
       gremoteFailureIndicationVT                         ( 500 ), 

       gsignalDegrade					 ( 510 ), 
       gseverelyErroredFrame                              ( 520 ), 
       gsignalFailure					 ( 530 ), 
       gsignalLabelMismatchFailure                  ( 540 ), 
       gpayloadDefectIndication                           ( 550 ), 

       gpayloadDefectIndicationPath                            ( 560 ), 
       gpayloadLabelMismatchPath                               ( 570 ), 
       gsignalLabelMismatchFailurePayloadLabelMismatchVT       ( 580 ), 
       gunequippedPath                                         ( 590 ), 
       gsignalLabelMismatchFailureUnequippedVT                 ( 600 ), 
       glossOfSynchronization                                  ( 610 ), 
       goutOfSynchronization                                   ( 620 ), 
       gprimarySynchronizationReferenceFailure                 ( 630 ), 
       gsecondarySynchronizationReferenceFailure               ( 640 ), 
       gthirdSynchronizationReferenceFailure                   ( 650 ), 
       gfourthSynchronizationReferenceFailure                  ( 660 ), 
       gfifthSynchronizationReferenceFailure                   ( 670 ), 
       gsixthSynchronizationReferenceFailure                   ( 680 ), 

       gfailedToReceiveSynchronizationStatusMessage             ( 690 ),
       gsynchronizationStatusMessagesAreDisabledOnThisInterface ( 700 ),
       gstratum1PrimaryReferenceSourceTraceable                 ( 710 ),
       gsynchronizedTraceabilityUnknown                         ( 720 ),
       gstratum2Traceable                                       ( 730 ),
       gtransitNodeClockTraceable                               ( 740 ),

       gstratum3ETraceable                    ( 750 ),
       gstratum3Traceable                     ( 760 ),
       gsonetMinimumClockTraceable            ( 770 ),
       gstratum4Traceable                     ( 780 ),
       gdoNotUseForSynchronization            ( 790 ),
       greservedForNetworkSynchronizationUse  ( 800 ),

       goutgoingFailureCondition          ( 810 ), 
       gremoteDefectIndicationLine        ( 820 ), 
       gremoteDefectIndicationPath        ( 830 ), 
       gfreeRunningSynchronizationMode    ( 840 ), 
       gholdoverSynchronizationMode       ( 850 ), 
       gfastStartSynchronizationMode      ( 860 ), 
       ginternalFault                     ( 870 ), 
       ginternalError                     ( 880 ), 
       ginternalMessageError              ( 890 ), 
       gmismatchOfEquipmentAndAttributes  ( 900 ), 
       gwatchdogTimerTimeout              ( 910 ), 
       gsoftwareFaultOrFailure            ( 920 ), 
       gsoftwareFaultDataIntegrityFault   ( 930 ), 
       gprogramFailure                    ( 940 ), 

       gcontrolEquipmentFailure                                 ( 950 ), 
       gprimaryNonVolatileBackupMemoryFailure                   ( 960 ), 
       gsecondaryNonVolatileBackupMemoryFailure                 ( 970 ), 
       gcontrolBusFailure                                       ( 980 ), 
       gcontrolBus1Failure                                      ( 990 ), 
       gcontrolBus2Failure                                     ( 1000 ),

       gtccAToShelfSlot1DROP1CommunicationFailure        ( 1010 ),
       gtccAToShelfSlot2DROP2CommunicationFailure        ( 1020 ),
       gtccAToShelfSlot3DROP3CommunicationFailure        ( 1030 ),
       gtccAToShelfSlot4DROP4CommunicationFailure        ( 1040 ),
       gtccAToShelfSlot5TRUNK1CommunicationFailure       ( 1050 ),
       gtccAToShelfSlot6TRUNK2CommunicationFailure       ( 1060 ),
       gtccAToShelfSlot7TCCACommunicationFailure         ( 1070 ),
       gtccAToShelfSlot8XCONACommunicationFailure        ( 1080 ),
       gtccAToShelfSlot9AICCommunicationFailure          ( 1090 ),
       gtccAToShelfSlot10XCONBCommunicationFailure       ( 1100 ),
       gtccAToShelfSlot11TCCBCommunicationFailure        ( 1110 ),
       gtccAToShelfSlot12TRUNK3CommunicationFailure      ( 1120 ),
       gtccAToShelfSlot13TRUNK4CommunicationFailure      ( 1130 ),
       gtccAToShelfSlot14DROP5CommunicationFailure       ( 1140 ),
       gtccAToShelfSlot15DROP6CommunicationFailure       ( 1150 ),
       gtccAToShelfSlot16DROP7CommunicationFailure       ( 1160 ),
       gtccAToShelfSlot17DROP8CommunicationFailure       ( 1170 ),
       gtccAToDCCAProcessorCommunicationFailure          ( 1180 ),
       gtccBToShelfSlot1DROP1CommunicationFailure        ( 1190 ),
       gtccBToShelfSlot2DROP2CommunicationFailure        ( 1200 ),
       gtccBToShelfSlot3DROP3CommunicationFailure        ( 1210 ),
       gtccBToShelfSlot4DROP4CommunicationFailure        ( 1220 ),
       gtccBToShelfSlot5TRUNK1CommunicationFailure       ( 1230 ),
       gtccBToShelfSlot6TRUNK2CommunicationFailure       ( 1240 ),
       gtccBToShelfSlot7TCCACommunicationFailure         ( 1250 ),
       gtccBToShelfSlot8XCONACommunicationFailure        ( 1260 ),
       gtccBToShelfSlot9AICCommunicationFailure          ( 1270 ),
       gtccBToShelfSlot10XCONBCommunicationFailure       ( 1280 ),
       gtccBToShelfSlot11TCCBCommunicationFailure        ( 1290 ),
       gtccBToShelfSlot12TRUNK3CommunicationFailure      ( 1300 ),
       gtccBToShelfSlot13TRUNK4CommunicationFailure      ( 1310 ),
       gtccBToShelfSlot14DROP5CommunicationFailure       ( 1320 ),
       gtccBToShelfSlot15DROP6CommunicationFailure       ( 1330 ),
       gtccBToShelfSlot16DROP7CommunicationFailure       ( 1340 ),
       gtccBToShelfSlot17DROP8CommunicationFailure       ( 1350 ),
       gtccBToDCCBProcessorCommunicationFailure          ( 1360 ),

       gcontrolEquipmentControlCommunicationsEquipmentFailure ( 1370 ),
       gcontrolProcessorFailure                               ( 1380 ),
       gworkingMemoryFailure                                  ( 1390 ),

       ginterconnectionEquipmentFailure                     ( 1400 ),
       gpayloadBusFailureToIOSlot1XCONSlot8                  ( 1410 ),
       gpayloadBusFailureToIOSlot2XCONSlot8                  ( 1420 ),
       gpayloadBusFailureToIOSlot3XCONSlot8                  ( 1430 ),
       gpayloadBusFailureToIOSlot4XCONSlot8                  ( 1440 ),
       gpayloadBusFailureToIOSlot5XCONSlot8                  ( 1450 ),
       gpayloadBusFailureToIOSlot6XCONSlot8                  ( 1460 ),
       gpayloadBusFailureToIOSlot12XCONSlot8                 ( 1470 ),
       gpayloadBusFailureToIOSlot13XCONSlot8                 ( 1480 ),
       gpayloadBusFailureToIOSlot14XCONSlot8                 ( 1490 ),
       gpayloadBusFailureToIOSlot15XCONSlot8                ( 1500 ),
       gpayloadBusFailureToIOSlot16XCONSlot8                ( 1510 ),
       gpayloadBusFailureToIOSlot17XCONSlot8                ( 1520 ),
       gpayloadBusFailureToIOSlot1XCONSlot10                ( 1530 ),
       gpayloadBusFailureToIOSlot2XCONSlot10                ( 1540 ),
       gpayloadBusFailureToIOSlot3XCONSlot10                ( 1550 ),
       gpayloadBusFailureToIOSlot4XCONSlot10                ( 1560 ),
       gpayloadBusFailureToIOSlot5XCONSlot10                ( 1570 ),
       gpayloadBusFailureToIOSlot6XCONSlot10                ( 1580 ),
       gpayloadBusFailureToIOSlot12XCONSlot10               ( 1590 ),
       gpayloadBusFailureToIOSlot13XCONSlot10               ( 1600 ),
       gpayloadBusFailureToIOSlot14XCONSlot10               ( 1610 ),
       gpayloadBusFailureToIOSlot15XCONSlot10               ( 1620 ),
       gpayloadBusFailureToIOSlot16XCONSlot10               ( 1630 ),
       gpayloadBusFailureToIOSlot17XCONSlot10               ( 1640 ),
       gtimeSlotInterchangeEquipmentFailure                 ( 1650 ),

       gequipmentFailure                                    ( 1660 ),
       ghighTemperature                                     ( 1670 ),
       ginvalidMACAddress                                   ( 1680 ),
       gboardFailure                                        ( 1690 ),
       gdiagnosticFailure                                   ( 1700 ),
       gmediumAccessControlFailure                          ( 1710 ),
       gfacilityTerminationEquipmentFailure                 ( 1720 ),
       gautomaticLaserShutoffDueToHighTemperature           ( 1730 ),
       gfailureToReleaseFromProtection                      ( 1740 ),
       greceiverFailure                                     ( 1750 ),
       gtransmitFailure                                     ( 1760 ),
       gfacilityTerminationEquipmentReceiverMissing         ( 1770 ),
       gfacilityTerminationEquipmentTransmitterMissing      ( 1780 ),
       gfailureToSwitchToProtection                         ( 1790 ),
       gfailureToSwitchToProtectionRing                     ( 1800 ),

       gfailureToSwitchToProtectionSpan                     ( 1810 ),
       gfailureToSwitchToProtectionPath                     ( 1820 ),
       gfanFailure                                          ( 1830 ),
       gequipmentUnitPlugIn                                 ( 1840 ),
       gnePowerFailureAtConnector                           ( 1850 ),
       gfuseAlarm                                           ( 1860 ),
       gsynchronizationUnitFailure                          ( 1870 ),
       gsynchronizationSwitchingEquipmentFailure            ( 1880 ),
       gequipmentUnitUnplugged                              ( 1890 ),
       gloopback                                            ( 1900 ),

       gds1LoopbackDueToFEACCommand                         ( 1910 ),
       gloopbackCommandSentToFarEndDS1                      ( 1920 ),
       gds3LoopbackDueToFEACCommand                         ( 1930 ),
       gds3LoopbackCommandSentToFarEnd                      ( 1940 ),
       gds2LoopbackDueToFarEndCommand                       ( 1950 ),
       gds2LoopbackCommandSentToFarEnd                      ( 1960 ),
       gfacilityLoopback                                    ( 1970 ),
       gnetworkLoopback                                     ( 1980 ),
       gterminalLoopback                                    ( 1990 ),
       gmanuallyCausedAbnormalCondition                     ( 2000 ),
       gethernetBridgeIsNewRootOfSpanningTree               ( 2010 ),
       gethernetBridgeTopologyChange                        ( 2020 ),
       gnormalCondition                                     ( 2030 ),
       gembeddedOperationsChannelFailureLinkDown            ( 2040 ),
       gpeerStateMismatch                                   ( 2050 ),
       gproceduralError                                     ( 2060 ),
       gimproperRemoval                                     ( 2070 ),
       gduplicateNodeID                                     ( 2080 ),
       gblsrOutOfSync                                       ( 2090 ),
       gblsrMultiNodeTableUpdateCompleted                   ( 2100 ),
       gprotectionUnitNotAvailable                          ( 2110 ),
       gperformanceMonitorThresholdCrossingAlert            ( 2120 ),
       gprotectionSwitch                                    ( 2130 ),
       grecoveryOrServiceProtectionActionHasBeenInitiated   ( 2140 ),
       gautomaticSystemReset                                ( 2150 ),
       gautomaticUPSRSwitchCausedByAIS          ( 2160 ),
       gautomaticUPSRSwitchCausedByLOP          ( 2170 ),
       gautomaticUPSRSwitchCausedByUNEQ         ( 2180 ),
       gautomaticUPSRSwitchCausedByPDI          ( 2190 ),
       gautomaticUPSRSwitchCausedBySFBER        ( 2200 ),
       gautomaticUPSRSwitchCausedBySDBER        ( 2210 ),
       gcoldRestart                              ( 2220 ),
       gforcedSwitchBackToWorking( 2230 ),
       gforcedSwitchBackToWorkingRing                     ( 2240 ),
       gforcedSwitchBackToWorkingSpan                     ( 2250 ),
       gforcedSwitchToProtection                          ( 2260 ),

       gforcedSwitchToProtectionRing                          ( 2270 ),
       gforcedSwitchToProtectionSpan                          ( 2280 ),
       gworkingFacilityOrEquipmentForcedToSwitchToProtectionPath( 2290 ),

       ginitializationInitiated   ( 2300 ),
       glockoutOfProtection       ( 2310 ),
       glockoutOfProtectionRing   ( 2320 ),
       glockoutOfProtectionSpan   ( 2330 ),
       glockoutOfProtectionPath   ( 2340 ),
       glockoutOfWorking          ( 2350 ),
       glockoutOfWorkingRing      ( 2360 ),
       glockoutOfWorkingSpan      ( 2370 ),

       gmanualSystemReset         ( 2380 ),

       gmanualSwitchToInternalClock                   ( 2390 ),
       gmanualSwitchToPrimaryReference                ( 2400 ),
       gmanualSwitchToSecondReference                 ( 2410 ),
       gmanualSwitchToThirdReference                  ( 2420 ),
       gmanualSwitchToFourthReference                 ( 2430 ),
       gmanualSwitchToFifthReference                  ( 2440 ),
       gmanualSwitchToSixthReference                  ( 2450 ),

       gmanualSwitchBackToWorking                             ( 2460 ),
       gmanualSwitchBackToWorkingRing                         ( 2470 ),
       gmanualSwitchBackToWorkingSpan                         ( 2480 ),
       gmanualSwitchToProtection                              ( 2490 ),
       gmanualSwitchToProtectionRing                          ( 2500 ),
       gmanualSwitchToProtectionSpan                          ( 2510 ),
       gmanualSwitchOfWorkingFacilityOrEquipmentToProtectionPath ( 2520 ),

       gpowerfailRestart           ( 2530 ),
       gringIsSquelchingTraffic    ( 2540 ),
       gsoftwareDownloadInProgress ( 2550 ),

       gswitchToInternalClock   ( 2560 ),
       gswitchToPrimaryReference               ( 2570 ),
       gswitchToSecondReference                ( 2580 ),
       gswitchToThirdReference                 ( 2590 ),
       gswitchToFourthReference                ( 2600 ),
       gswitchToFifthReference                 ( 2610 ),
       gswitchToSixthReference                 ( 2620 ),

       gsystemReboot                                        ( 2630 ),
       gswitchedBackToWorking                               ( 2640 ),
       gswitchedToProtection                                ( 2650 ),
       gwarmRestart                                         ( 2660 ),
       gringIsInWaitToRestoreState                          ( 2670 ),
       gmanualSwitchRequest            ( 2680 ),
       gforcedSwitchRequest             ( 2690 ),
       glockoutSwitchRequest           ( 2700 ),
       grmonHistoriesAndAlarmsResetReboot                ( 2710 ),
       grmonThresholdCrossingAlarm                 ( 2720 ),
       galarmsSuppressedByUserCommand             ( 2730 ),
       galarmsSuppressedForMaintenance             ( 2740 ),
       gswitchingMatrixModuleFailure             ( 2750 ),
       glanConnectionPolarityReversed             ( 2760 ),
       gautonomousPMReportMessageInhibited           ( 2780 ),
       gioSlotToXCONCommunicationFailure             ( 2790 ),

         -- Intentional gap

       gstsPathTraceIdentifierMismatch             ( 2800 ),
       gnePowerFailureAtConnectorA                 ( 2810 ),
       gnePowerFailureAtConnectorB                 ( 2820 ),

       gfreeMemoryOnCardVeryLow                    ( 2830 ),
       gfreeMemoryOnCardNearZero                   ( 2840 ),

       gexerciseRequestOnRing                      ( 2850 ),
       gexerciseRequestOnSpan                      ( 2860 ),
       gsquelchingPath                             ( 2870 ),
       gextraTrafficPreempted                      ( 2880 ),

       gfarEndLockoutOfWorkingRing                 ( 2890 ),
       gfarEndLockoutOfWorkingSpan                 ( 2900 ),
       gfarEndLockoutOfProtectionRing              ( 2910 ),
       gfarEndLockoutOfProtectionAllSpans          ( 2920 ),

       gfarEndWorkingFacilityForcedToSwitchToProtectionRing     ( 2930 ),
       gfarEndWorkingFacilityForcedToSwitchToProtectionSpan     ( 2940 ),

       gfarEndManualSwitchOfWorkingFacilityToProtectionRing     ( 2950 ),
       gfarEndManualSwitchOfWorkingFacilityToProtectionSpan     ( 2960 ),
       gfarEndExercisingRing                                    ( 2970 ),
       gfarEndExercisingSpan                                    ( 2980 ),
       gfarEndBERThresholdPassedForSignalFailureRing ( 2990 ),
       gfarEndBERThresholdPassedForSignalFailureSpan ( 3000 ),
       gfarEndBERThresholdPassedForSignalDegradeRing ( 3010 ),
       gfarEndBERThresholdPassedForSignalDegradeSpan ( 3020 ),
       gapsChannelFarEndProtectionLineSignalDegrade  ( 3030 ),

       gringSwitchIsActiveOnTheEastSide      ( 3040 ),
       gringSwitchIsActiveOnTheWestSide      ( 3050 ),
       gspanSwitchIsActiveOnTheEastSide      ( 3060 ),
       gspanSwitchIsActiveOnTheWestSide      ( 3070 ),

       guniDirectionalFullPassThroughIsActive  ( 3080 ),
       gbiDirectionalFullPassThroughIsActive   ( 3090 ),

       gkBytesPassThroughIsActive       ( 3100 ),
       gringIsSegmented                 ( 3110 ),
       gringTopologyIsUnderConstruction ( 3120 ),

       glockoutOfProtectionAllSpans                   ( 3130 ),
       gfarEndOfFiberIsProvisionedWithDifferentRingID ( 3140 ),
       gbothEndsOfFiberProvisionedAsEastOrBothAsWest  ( 3150 ),
       gsecurityInvalidLoginUsernameSeeAuditTrail     ( 3160 ),

       gautonomousMessagesInhibited        ( 3170 ),
       gtrafficStormOnLANLANTemporarilyDisabled( 3180 ),

       greptdbchgMessagesInhibited    ( 3190 ),
       gsecurityUserIDHasExpired      ( 3200 ),
       gpartialFanFailure             ( 3210 ),
       gforcedSwitchRequestOnRing     ( 3220 ),
       gforcedSwitchRequestOnSpan     ( 3230 ),
       glockoutSwitchRequestOnRing    ( 3240 ),
       glockoutSwitchRequestOnSpan    ( 3250 ),
       gmanualSwitchRequestOnRing     ( 3260 ),
       gmanualSwitchRequestOnSpan     ( 3270 ),

       gcommunicationFailurePeerToPeerSlotControlBusA ( 3280 ),
       gcommunicationFailurePeerToPeerSlotControlBusB ( 3290 ),
       gcontrollerAToShelfSlotCommunicationFailure ( 3300 ),
       gcontrollerBToShelfSlotCommunicationFailure ( 3310 ),

       ginterconnectionEquipmentFailureWorkingPayloadBus ( 3320 ),
       ginterconnectionEquipmentFailureProtectPayloadBus ( 3330 ),
       ginhibitSwitchToProtectRequestOnEquipment ( 3340 ),
       ginhibitSwitchToWorkingRequestOnEquipment ( 3350 ),

       gberThresholdExceededForSignalDegradeLine ( 3360 ),
       gberThresholdExceededForSignalDegradePath ( 3370 ),
       gberThresholdExceededForSignalFailureLine ( 3380 ),
       gberThresholdExceededForSignalFailurePath ( 3390 ),
       gexercisingRingSuccessfully               ( 3400 ),
       gexercisingSpanSuccessfully               ( 3410 ),
       gspanIsInWaitToRestoreState        ( 3420 ),
       gexerciseRequestOnRingFailed            ( 3430 ),
       gexerciseRequestOnSpanFailed            ( 3440 ),
       gfarEndLockoutOfProtectionSpan          ( 3450 ),

       gmanufacturingDataMemoryEEPROMFailure   ( 3460 ),
       greplaceableEquipmentOrUnitIsMissing    ( 3470 ),
       gsoftwareDownloadFailed                 ( 3480 ),
       gextraTrafficPCADropped                 ( 3490 ),

       getherTxOversubscribed          ( 3500 ),
       getherRxOverSubscribed          ( 3510 ),
       getherTxExcessFlowCtrl          ( 3520 ),
       getherRxExcessFlowCtrl          ( 3530 ),
       gtransportLayerFailure          ( 3540 ),
       getherTxUnderrun                ( 3550 ),

       gsynchronizationReferenceFrequencyOutOfBounds  ( 3560 ),
       gntpOrSntpHostFailure                          ( 3570 ),
       gpeerCardNotResponding                         ( 3580 ),
       galarmsAndEventsSuppressedForThisObject        ( 3590 ),
       gds3FrameFormatMismatch                        ( 3600 ),

       gwaitToRestore             ( 3610 ),
       gextremeHighVoltBatteryA   ( 3620 ),
       gextremeLowVoltBatteryA    ( 3630 ),
       gextremeHighVoltBatteryB   ( 3640 ),
       gextremeLowVoltBatteryB    ( 3650 ),
       giosConfigCopyFailed             ( 3660 ),
       giosConfigCopyInProgress             ( 3670 ),
       giosConfigCopySuccess             ( 3680 ),

       gsignalingUnableToSetupCircuit        ( 3710 ),
       gerrorInStartupConfig             ( 3712 ),
       gnoStartupConfig             ( 3714 ),
       gneedToSaveRunningConfig             ( 3716 ),
       ginvalidAlarm             ( 3718 ),
       grsvpHelloFSMToNeighborDown ( 3720 ),
       gsecurityInvalidLoginUsername     ( 3722 ),
       gdatabaseBackupFailed             ( 3724 ),
       gdatabaseRestoreFailed             ( 3726 ),
       glmpHelloFSMToControlChannelDown   ( 3730 ),
       glmpNeighborDiscoveryHasFailed        ( 3740 ),
       gunauthorizedIncomingSignalingRequest ( 3750 ),
       gauditLog80PercentFull             ( 3760 ),
       gmoduleCommunicationFailure             ( 3762 ),
       gauditLog100PercentFullOldestRecordsWillBeLost             ( 3764 ),
       gstandbyDatabaseOutOfSync             ( 3766 ),
       gredundantPowerCapabilityLost             ( 3768 ),
       gforcedSwitchToPrimaryReference       ( 3770 ),
       gforcedSwitchToSecondReference             ( 3780 ),
       gforcedSwitchToThirdReference             ( 3790 ),
       gforcedSwitchToInternalClock             ( 3800 ),
       gindustrialHighTemperature             ( 3805 ),
       gimproperMatrixEquipmentInserted               ( 3810 ),
       geqptProblemOnCarrierOrPIM                     ( 3820 ),
       geqptProblemOnPIMOrPPM                         ( 3830 ),
       gtimSectionTraceIdentifierMismatchFailure    ( 4000 ),
       gaisMultiplexSectionAlarmIndicationSignal      ( 4010 ),
       grdiMultiplexSectionRemoteDefectOrAlarmIndication( 4020 ),
       gtimHighOrderTraceIdentifierMismatchFailure    ( 4030 ),
       gaisAdministrationUnitAlarmIndicationSignal    ( 4040 ),
       glopAdministrationUnitLossOfPointer            ( 4050 ),
       gslmfUnequippedHighOrderPathUnequipped         ( 4060 ),
       gslmfPLMHighOrderPathLabelMismatch             ( 4070 ),
       grdiHighOrderRemoteDefectOrAlarmIndication    ( 4080 ),
       glopTributaryUnitLossOfPointer                 ( 4090 ),
       gaisTributaryUnitAlarmIndicationSignal         ( 4100 ),
       gslmfUnequippedLowOrderPathUnequipped          ( 4110 ),
       gslmfPLMLowOrderPathLabelMismatch              ( 4120 ),
       gtimLowOrderTraceIdentifierMismatchFailure     ( 4130 ),
       grfiLowOrderRemoteFailureOrAlarmIndication     ( 4140 ),
       gg811PrimaryReferenceClockTraceable            ( 4150 ),
       gg812TransitNodeClockTraceable                 ( 4160 ),
       gg812LocalNodeClockTraceable                   ( 4170 ),
       gg813SynchronousEquipmentTimingSourceTraceable ( 4180 ),
       ge1LoopbackDueToFEACCommand                    ( 4190 ),
       ge1LoopbackCommandSentToFarEnd                 ( 4200 ),
       ge3LoopbackDueToFEACCommand                    ( 4210 ),
       gfarEndMultipleE1LOSDetectedOnE3               ( 4220 ),
       gfarEndE1EqptFailNonServiceAffecting           ( 4230 ),
       gfarEndE1EqptFailServiceAffecting              ( 4240 ),
       gfarEndSingleE1LOS                             ( 4250 ),
       gfarEndE3EqptFailServiceAffecting              ( 4260 ),
       ge3LoopbackCommandSentToFarEnd                 ( 4270 ),
       gfarEndE3EqptFailNonServiceAffecting           ( 4280 ),
       glowVoltBatteryA                               ( 4290 ),
       ghighVoltBatteryA                              ( 4300 ),
       glowVoltBatteryB                               ( 4310 ),
       ghighVoltBatteryB                              ( 4320 ),
       gmsspRingOutOfSync                             ( 4330 ),
       gmsspMultiNodeTableUpdateCompleted             ( 4340 ),
       gautomaticSNCPSwitchCausedByAIS                ( 4350 ),
       gautomaticSNCPSwitchCausedByLOP                ( 4360 ),
       gautomaticSNCPSwitchCausedByUNEQ               ( 4370 ),
       gautomaticSNCPSwitchCausedByPDI                ( 4380 ),
       gautomaticSNCPSwitchCausedBySFBER              ( 4390 ),
       gautomaticSNCPSwitchCausedBySDBER              ( 4400 ),
       gstmConcatenationError                         ( 4410 ),
       ge3IdleCondition                               ( 4420 ),
       gchannelMSSPInconsistentAPSCode                ( 4430 ),
       gchannelMSSPImproperAPSCodeAPS                 ( 4440 ),
       gchannelMSSPNodeIdMismatchAPS                  ( 4450 ),
       gchannelMSSPDefaultKAPS                        ( 4460 ),
       gchannelMSSPConnectionLossAPS                  ( 4470 ),
       gminimumClockTraceableSDH                      ( 4480 ),
       glineIsInWaitToRestoreStateSDH                 ( 4490 ),
       gberThresholdExceededForSignalDegradeHighOrder ( 4500 ),
       gberThresholdExceededForSignalFailureHighOrder ( 4510 ),
       gberThresholdExceededForSignalDegradeLowOrder  ( 4520 ),
       gberThresholdExceededForSignalFailureLowOrder  ( 4530 ),
       gfailureToSwitchToProtectionHighOrderPath      ( 4540 ),
       gfailureToSwitchToProtectionLowOrderPath       ( 4550 ),
       glofAdministrationUnitLossOfMultiFrame         ( 4560 ),
       gsdhSpanIsInWaitToRestoreState                 ( 4570 ),
       ga8b10bOutOfSync                               ( 4755 ),
       godukPMAlarmIndicationSignal                   ( 4760 ),
       gotukAlarmIndicationSignal                     ( 4765 ),
       gotukSMBackwardDefectIndication                ( 4770 ),
       gfecUncorrectedWord                            ( 4780 ),
       ggccTerminationFailure                         ( 4785 ),
       gotukIncomingAlignmentError                    ( 4790 ),
       godukLockedDefectPM                            ( 4795 ),
       glossOfMultiFrame                              ( 4800 ),
       godukOpenConnectionIndication                  ( 4805 ),
       gpayloadTypeIdentifierMismatch                 ( 4810 ),
       godukTrailTraceIdentifierMismatch              ( 4815 ),
       gotukTrailTraceIdentifierMismatch              ( 4820 ),
       gequipmentHighLaserBias                        ( 4825 ),
       gequipmentHighLaserTemp                        ( 4830 ),
       gequipmentHighLaserPeltier                     ( 4835 ),
       gfacilityHighRxPower                          ( 4840 ),
       gequipmentHighTxPower                          ( 4845 ),
       gequipmentHighTransceiverVoltage               ( 4850 ),
       gequipmentLowLaserBias                         ( 4855 ),
       gequipmentLowLaserTemp                         ( 4860 ),
       gequipmentLowLaserPeltier                      ( 4865 ),
       gfacilityLowRxPower                           ( 4870 ),
       gequipmentLowTxPower                           ( 4875 ),
       gequipmentLowTransceiverVoltage                ( 4880 ),
       gequipmentRxLocked                             ( 4885 ),
       gequipmentSquelched                            ( 4890 ),
       gequipmentTxLocked                             ( 4895 ),
       gotukSignalFailure                              ( 4900 ),
       godukSignalFailure                              ( 4905 ),
       gotukSignalDegrade                              ( 4910 ),
       godukSignalDegrade                              ( 4915 ),
       gpluggablePortMissing                          ( 4920 ),
       gpluggablePortRateMismatch                     ( 4925 ),
       gpluggablePortSecurityCodeMismatch             ( 4930 ),
       gtciNotSelected                                ( 4935 ),
       gtci1ClockFailure                              ( 4940 ),
       godukPMBackwardDefectIndication                 ( 4945 ),
       godukTCM1BackwardDefectIndication               ( 4950 ),
       godukTCM2BackwardDefectIndication               ( 4955 ),
       gequipmentHighRxTemperature                    ( 4960 ),
       gequipmentLowRxTemperature                     ( 4965 ),
       gtci2ClockFailure                              ( 4970 ),
       gequipmentWavelengthMismatch                   ( 4975 ),
       gdspCommunicationFailure                       ( 4980 ),
       gdspFailure                                    ( 4985 ),
       glaserApproachingEndOfLife                     ( 5000 ),
       gcrossconnectLoopback                          ( 5010 ),
       gadminLogoutOfUser                             ( 5020 ),
       guserLockedOut                                 ( 5030 ),
       gadminLockoutOfUser                            ( 5040 ),
       gadminLockoutClear                             ( 5050 ),
       ginvalidLoginUsername                          ( 5060 ),
       gsecurityInvalidLoginPassword                  ( 5070 ),
       gsecurityInvalidLoginLockedOut                 ( 5080 ),
       gsecurityInvalidLoginAlreadyLoggedOn           ( 5090 ),
       gloginOfUser                                   ( 5100 ),
       gautomaticLogoutOfIdleUser                     ( 5110 ),
       glogoutOfUser                                  ( 5120 ),
       genhancedRemoteFailureIndicationPathServer     ( 5200 ),
       genhancedRemoteFailureIndicationPathConnectivity( 5210 ),
       genhancedRemoteFailureIndicationPathPayload    ( 5220 ),
       gfirewallHasBeenDisabled                       ( 5230 ),
       gsecurityIntrusionDetPwd                       ( 5240 ),
       gsecurityIntrusionDetUser                      ( 5250 ),
       gconnectionEquipmentMismatch                   ( 5260 ),
       gdisableInactiveUser                           ( 5270 ),
       gdisableInactiveClear                          ( 5280 ),
       gbatteryFailure                                ( 5290 ),

       gextremeHighVolt                               ( 5300 ),
       gextremeLowVolt                                ( 5310 ),
       ghighVolt                                      ( 5320 ),
       glowVolt                                       ( 5330 ),
       gsuspendUser                                   ( 5340 ), 
       gsuspendUserClear                              ( 5350 ),
       glineDccTerminationFailure                     ( 5360 ),
       gmultiplexSectionDccTerminationFailure         ( 5370 ),
       ggigaBitEthernetOutOfSync                      ( 5380 ),
       gsequenceMismatch                              ( 5390 ),
       glossOfAlignment                               ( 5400 ),
       goutOfUseByAdministrativeCommand               ( 5410 ),
       goutOfUseTransportFailure                      ( 5420 ),
       gvcatGroupDown                                 ( 5430 ),
       gvcatGroupDegraded                             ( 5440 ),
       gvcatGroupIncomplete                           ( 5450 ),
       galarmIndicationSignalInTX                     ( 5460 ),
       gremoteAlarmIndicationInTX                     ( 5470 ),
       gkByteAPSChannelFailure                        ( 5480 ),
       gapsInvalidMode                                ( 5490 ),
       gipAddressAlreadyInUseWithinTheSameDccArea     ( 5500 ),
       gnodeNameInUseWithinTheSameDccArea             ( 5510 ),
       grearPanelEthernetLinkRemoved                  ( 5520 ),
       gmanualSwitchToProtectResultedInNoTrafficSwitch      ( 5530 ),
       gmanualSwitchBackToWorkingResultedInNoTrafficSwitch  ( 5540 ),
       gforcedSwitchToProtectResultedInNoTrafficSwitch      ( 5550 ),
       gforcedSwitchBackToWorkingResultedInNoTrafficSwitch  ( 5560 ),
       gduplicateSerialNumberDetectedOnAPluggableEntity     ( 5570 ),
       glossOfSignalForOpticalChannel                       ( 5600 ),
       gencapsulationMismatchPath                           ( 5610 ),
       gencapsulationMismatchVT             ( 5620 ),
       gencapsulationMismatchHighOrderPath             ( 5630 ),
       gencapsulationMismatchLowOrderPath             ( 5640 ),
       ggfpUserPayloadMismatch                              ( 5650 ),
       ggfpFibreChannelDistanceExtensionMismatch            ( 5660 ),
       ggfpFibreChannelDistanceExtensionBufferStarvation    ( 5670 ),
       ggfpFibreChannelDistanceExtensionCreditStarvation    ( 5680 ),
       gautomaticWdmAnsFinished                             ( 5690 ),
       ggfpClientSignalFailDetected                         ( 5700 ),
       ggfpLossOfFrameDelineation                           ( 5710 ),
       ggfpExtensionHeaderMismatch                          ( 5730 ),
       gincomingOverheadSignalAbsent                  ( 5740 ),
       gopticalSafetyRemoteInterlockOn                ( 5750 ),
       gautomaticPowerControlCorrectionSkipped        ( 5770 ),
       gapcCannotSetValueDueToRangeLimits             ( 5780 ),
       glcasVcgMemberTxSideInAddState                 ( 5790 ),
       gfarEndManualSwitchBackToWorkingSpan             ( 5800 ),
       gfarEndForcedSwitchBackToWorkingSpan             ( 5810 ),
       guniversalTransponderModuleHardwareFailure             ( 5820 ),
       guniversalTransponderModuleCommunicationFailure             ( 5830 ),
       gpluginModuleRangeSettingsMismatch             ( 5840 ),
       glcasVcgMemberTxSideInDnuState                 ( 5850 ),
       glcasControlWordCrcCheckFailure            ( 5860 ),
       glcasVcgMemberRxSideInFailState            ( 5870 ),
       gsignalLossOnDataInterface             ( 5880 ),
       gsynchronizationLossOnDataInterface             ( 5890 ),
       gportFAIL               ( 5900 ),
       gunreachablePortTargetPower               ( 5910 ),
       gportAddPowerDegradeLow               ( 5920 ),
       gportAddPowerDegradeHigh             ( 5930 ),
       gportAddPowerFailLow             ( 5940 ),
       gportAddPowerFailHigh             ( 5950 ),
       gautomaticPowerControlTerminatedOnManualRequest             ( 6000 ),
       goduk1AlarmIndicationSignal             ( 6010 ),
       goduk2AlarmIndicationSignal             ( 6020 ),
       goduk3AlarmIndicationSignal             ( 6030 ),
       goduk4AlarmIndicationSignal             ( 6040 ),
       gtemperatureReadingMismatchBetweenSCCards             ( 6050 ),
       gvoltageReadingMismatchBetweenSCCards             ( 6060 ),
       galarmsSuppressedonOutOfGroupVcatMember           ( 6070 ),
       gblsrSoftwareVersionMismatch             ( 6080 ),
       goptimized1Plus1ApsPrimaryFacility       ( 6090 ),
       goptimized1Plus1ApsPrimarySectionMismatch( 6100 ),
       goptimized1Plus1ApsInvalidPrimarySection ( 6110 ),
       gcompositeClockHighLineVoltage             ( 6120 ),
       gberThresholdExceededForSignalDegradeVt             ( 6130 ),
       gberThresholdExceededForSignalFailureVt             ( 6140 ),
       gspanLengthOutOfRange             ( 6150 ),
       gidleSignalCondition             ( 6170 ),
       gidleSignalConditionInTx             ( 6180 ),
       gvtPathTraceIdentifierMismatch             ( 6190 ),
       glossOfFrameInTX             ( 6200 ),
       gprovisioningMismatch             ( 6210 ),
       gsectionTraceIdentifierMismatch             ( 6220 ),
       gregeneratorSectionTraceIdentifierMismatch             ( 6230 ),
       gswitchingMatrixModuleFailureWorking             ( 6240 ),
       gswitchingMatrixModuleFailureProtect             ( 6250 ),
       gslotCommunicationDisabled             ( 6260 ),
       gsessionTimeLimitExpired             ( 6270 ),
       guserPasswordChangeRequired             ( 6280 ),
       gisisAdjacencyFailure             ( 6290 ),
       gmsspSoftwareVersionMismatch             ( 6300 ),
       gremoteAuthenticationFailSeeAuditLog             ( 6310 ),
       gillegalRouteAdditionToNetwork             ( 6320 ),
       gringIsSquelchingStsTraffic            ( 6330 ),
       gringIsSquelchingVtTraffic             ( 6340 ),
       garchiveOfAuditLogFailed               ( 6350 ),
       grprWrapped             ( 6360 ),
       gshelfCommunicationFailure             ( 6370 ),
       gduplicatedShelfIdentifier             ( 6380 ),
       gsoftwareMismatch             ( 6390 ),
       glmpFailure             ( 6400 ),
       gopticalTerminationIncomplete             ( 6410 ),
       gforwardDefectIndication             ( 6420 ),
       gpayloadMissingIndication             ( 6430 ),
       gspanMeasurementCannotBePerformed     ( 6440 ),
       gringIsSquelchingHighOrderTraffic             ( 6450 ),
       gringIsSquelchingLowOrderTraffic             ( 6460 ),
       gbadPacketCountExceedsThreshold             ( 6470 ),
       glinkLayerKeepAliveFailure             ( 6480 ),
       gautonegotiationRemoteFailureIndication             ( 6490 ),
       gtrailSignalFail             ( 6500 ),
       gds1LoopbackCommandSentToFarEnd             ( 6510 ),
       gmultiplexSectionSignalDegraded             ( 6520 ),
       gmultiplexSectionExcessiveErrors             ( 6530 ),
       ghighOrderPathSignalDegraded             ( 6540 ),
       ghighOrderPathExcessiveErrors             ( 6550 ),
       glowOrderPathSignalDegraded             ( 6560 ),
       glowOrderPathExcessiveErrors             ( 6570 ),
       gregeneratorSectionDccTerminationFailure ( 6580 ),
       gnetworkMemoryPoolLow             ( 6590 ),
       gospfRoutingTableOverflow             ( 6600 ),
       gautoLaserShutdownDisabled             ( 6610 ),
       gwavelengthOutOfLock                           ( 6620 ),
       grprProtectionIsActive             ( 6630 ),
       gmaxRPRStationNumberExceeded             ( 6640 ),
       grprProtectionConfigurationMismatched             ( 6650 ),
       greservedBandwidthLinkRateExceededOnRinglet0             ( 6660 ),
       greservedBandwidthLinkRateExceededOnRinglet1             ( 6670 ),
       grprInterfaceInPassThroughMode             ( 6680 ),
       grprPeerNodeIsMissing             ( 6690 ),
       grprRiFailure                 ( 6700 ),
       grprSignalFailure             ( 6710 ),
       grprSignalDegrade             ( 6720 ),
       ginterlinkFailure             ( 6730 ),
       gapcWrongGain             ( 6740 ),
       grprSpanMismatch             ( 6750 ),
       gefmRemoteFaultInidicationCriticalEvent             ( 6760 ),
       gefmRemoteFaultInidicationDyingGasp             ( 6770 ),
       gefmRemoteFaultInidicationLinkFault             ( 6780 ),
       gefmLinkMonitoringErroredSymbolPeriodEvent             ( 6790 ),
       gefmLinkMonitoringErroredFrameEvent             ( 6800 ),
       gefmLinkMonitoringErroredFramePeriodEvent             ( 6810 ),
       gefmLinkMonitoringErroredFrameSecondsSummary             ( 6820 ),
       gefmRemoteLoopbackRequestFailed             ( 6830 ),
       gfastAutomaticProtectionSwitching             ( 6840 ),
       gfastAutomaticProtectionSwitchingConfigMismatch             ( 6850 ),
       glcasSinkGroupError             ( 6860 ),
       glcasVcgMemberRxSideInDnuState             ( 6870 ),
       gfcDistanceExtFuncNotEstablished             ( 6880 ),
       gnonCiscoPPMInserted             ( 6890 ),
       gunqualifiedPPMInserted             ( 6900 ),
       gftaMismatch             ( 6910 ),
       gcardPortsUnableToProvideProtection             ( 6920 ),
       glmpSignalDegrade             ( 6930 ),
       glmpSignalFailure             ( 6940 ),
       glmpUnallocatedDataLink             ( 6950 ),
       gfrontPortLinkLoss             ( 6960 ),
       gbertEnbl             ( 6970 ),
       gbertSyncFail             ( 6975 ),
       gworkQueueFull             ( 6980 ),
       gequipmentPowerFailureAtConnectorA             ( 7000 ),
       gequipmentPowerFailureAtConnectorB             ( 7005 ),
       gequipmentPowerFailureAtReturnConnectorA       ( 7010 ),
       gequipmentPowerFailureAtReturnConnectorB       ( 7015 ),
       gloginFailThresholdExceeded                    ( 7020 ),
       gconnectionIdMismatchOnMatrixA                 ( 7025 ),
       gconnectionIdMismatchOnMatrixB                 ( 7030 ),
       gmanufacturingEepromFailure		     ( 7035 ),
       gequipmentFailureHighTemperature               ( 7040 ),
       glaserBiasCurrentHigh                          ( 7045 ),
       ghighLaserTemperature                          ( 7050 ),
       gbridgeAndRollHasOccurred                      ( 7055 ),
       gbridgeAndRollIsPendingAValidSignal            ( 7060 ),
       gairFlow                                       ( 7065 ),
       gpartialFanFailurePartsFailure                 ( 7070 ),
       gunprotectedSyncronizationEquipment            ( 7075 ),
       gunprotectedMatrixEquipment                    ( 7080 ),
       gmatrixEquipmentUnavailable                    ( 7085 ),
       gcontrolBusFailureTscA                         ( 7090 ),
       gcontrolBusFailureTscB                         ( 7095 ),
       gpayloadBusFailureMatrixA                      ( 7100 ),
       gpayloadBusFailureMatrixB                      ( 7105 ),
       gmatrixOperationSuspended                      ( 7110 ),
       gclockFailureTsc                               ( 7115 ),
       gpayloadLoopback				     ( 7120 ),
       gdccChannelLoss                                ( 7125 ),
       greptPmMsgInhibited                            ( 7130 ),
       gloopbackCrs                                   ( 7135 ),
       gsyncRefFreqOutOfBound                         ( 7140 ),
       gsystemUpgradeInProgress                       ( 7145 ),
       geqptFailToBoot                                ( 7150 ),
       geqptPowerFailure                              ( 7155 ),
       gclockBusFailureTscA                           ( 7160 ),
       gclockBusFailureTscB                           ( 7165 ),
       gpowerFuseFailure                              ( 7170 ),
       gcontrolCommunicationsEquipmentFailure         ( 7175 ),
       gdifferentSoftwareVersion                      ( 7180 ),
       gospfHelloFail                                 ( 7185 ),
       gclockModuleFrequencyMismatch                  ( 7190 ),
       getherPortSwitch                               ( 7195 ),
       gopenIOSlots                                   ( 7200 ),
       gequipmentBootInProgress                       ( 7205 ),
       glossOfClockFromMateShelfController	     ( 7210 ),
       gvirtualLanAlarmIndicationSignal             ( 7225 ),
       gdcuLossFailure             ( 7230 ),
       gochncMaintenance             ( 7235 ),
       gramanLaserShutdown             ( 7240 ),
       glosOfRamanSignal             ( 7245 ),
       gmcastMacTableFull             ( 7250 ),
       gmulticastMacAddressAliasing             ( 7255 ),
       gramanPwrProtOn             ( 7260 ),
       gcppPeerNotResponding             ( 7265 ),
       gvoaControlLoopDisableDueToExcessiveCounterPropagationLight             ( 7275 ),
       gwizardIsRunning             ( 7280 ),
       gramanGainNotReached             ( 7285 ),
       glocalFault             ( 7315 ),
       gremoteFault             ( 7320 ),
       gefmRemoteLoopbackConfigured            ( 7325 ),
       gefmPeerMissing             ( 7330 ),
       geqptDegrade             ( 7335 ),
       gexcessiveBackPropagation             ( 7340 ),
       gremoteMaintenanceEndPointIsDown             ( 7345 ),
       gcrossConnectedCFMService             ( 7350 ),
       gcfmLoop             ( 7355 ),
       gcfmConfigurationError             ( 7360 ),
       goutOfChannelGroupBundle             ( 7365 ),
       grepNeighborAdjacencyFailure             ( 7370 ),
       grepLinkFlapping             ( 7375 ),
       gfaultInREPSegment             ( 7380 ),
       gprimaryREPEdgePortElected             ( 7385 ),
       gsecondaryREPEdgePortElected             ( 7390 ),
       gstcnREPGenerated             ( 7395 ),
       gvlbREPActivated             ( 7400 ),
       gvlbREPTriggerSoakingDelayActive             ( 7405 ),
       gpprForwardDefectIndication             ( 7295 ),
       gpprBackwardDefectIndication             ( 7300 ),
       gpprCoordinatedMaintenance             ( 7305 ),
       gpprTriggerThresholdBERExceeded             ( 7310 ),
       gwanSyncloss             ( 7410 ),
       glaserShutdownDueToWavelengthDrift             ( 7415 ),
       gmanualLaserRestart             ( 7420 ),
       glaserShutdownDueToNonCiscoPPMInserted             ( 7425 ),
       gethernetOSCTerminationFailure             ( 7430 ),
       gsoftwareSignatureVerificationFailed             ( 7445 ),
       gprotectVolumeSoftwareSignatureVerification             ( 7450 ),
       gactiveSoftwareSignatureVerificationFailed             ( 7455 ),
       gpeerPortClientSignalFailDetected (7460),
       gchannelShutdownDuetoWavelengthDrift              ( 7465 ),
       gusbWriteFailure             ( 7475 ),
       gusbSyncInProgress             ( 7480 ),
       gautoSensingUnableToDetectValidPayload (7485),
	   gpayloadAutoSensingInProgress (7490),
	   ggfpClientSignalFailDetectedDueToSigloss (7495),
	   ggfpClientSignalFailDetectedDueToSyncloss (7500),
       gpmdDegrade (7510),
       gstandbyTccNEClockIsInternalClock             ( 7515 ),
       gchromaticDispersionValue             ( 7520 ),
       gpackettransportservicefailed             ( 7525 ),
       gsatellitePanelDiscoveryFailure             ( 7530 ),
       gsatellitePanelActiveLinkFailure             ( 7535 ),
       gsatellitePanelCommunicationFailure             ( 7540 ),
       gsatellitePanelImproperConfiguration             ( 7545 ),
       gsatellitePanelFanMismatchOfEquipmentAndAttributes             ( 7550 ),
       gsatellitePanelFanFailure             ( 7555 ),
       gsatellitePanelPartialFanFailure             ( 7560 ),
       gsatellitePanelFANManufacturingDataMemoryEEPROMFailure             ( 7565 ),
       gsatellitePanelFANUnitIsMissing             ( 7570 ),
       gsatellitePanelIndustrialHighTemperature             ( 7575 ),
       gsatellitePanelHighTemperature             ( 7580 ),
       gsatellitePanelBatteryFailureA             ( 7585 ),
       gplannedSwitchOver             ( 7590 ),
       gprotectionCardConfigurationMismatch             ( 7595 ),
       grouterProcessorSwitchOver             ( 7600 ),
       grunningLowOnResources             ( 7605 ),
       gnoMoreResourcesAreAvailable             ( 7610 ),
       gesmcFailure	( 7615 ),
       glicenseWillExpireWithin24Hours             ( 7620 ),
       glicenseWillExpireAnytimeAfter1DayButBefore14Days             ( 7625 ),
       glicenseIsExpired             ( 7630 ),
       glicenseCountViolation             ( 7635 ),
       gtemporaryLicenseIsInUse             ( 7640 ),
       gevaluationLicenseIsInUse             ( 7645 ),
       glicenseIsMissing             ( 7650 ),
       gpseudowireDown             ( 7655 ),
       gworkingPseudowireControlPlaneDown             ( 7660 ),
       gprotectPseudowireControlPlaneDown             ( 7665 ),
       gworkingPseudowireConnectivityCheckDown             ( 7670 ),
       gprotectPseudowireConnectivityCheckDown             ( 7675 ),
       gpseudowireTrafficSwitchedToPretection             ( 7680 ),
       gworkingPseudowireLocalAcTxPortFault             ( 7685 ),
       gprotectPseudowireLocalAcTxPortFault             ( 7690 ),
       gworkingPseudowireLocalAcRxPortFault             ( 7695 ),
       gprotectPseudowireLocalAcRxPortFault             ( 7700 ),
       gworkingPseudowireRemoteAcTxPortFault             ( 7705 ),
       gprotectPseudowireRemoteAcTxPortFault             ( 7710 ),
       gworkingPseudowireRemoteAcRxPortFault             ( 7715 ),
       gprotectPseudowireRemoteAcRxPortFault             ( 7720 ),
       gslaThresholdCrossAlert		                 ( 7725 ),
       gprotectLocalPseudowireNotForwarding             ( 7730 ),
       gworkingRemotePseudowireNotForwarding             ( 7735 ),
       gprotectRemotePseudowireNotForwarding             ( 7740 ),
       gtpTunnelDown             ( 7745 ),
       gworkingLabelSwitchedPathDown             ( 7750 ),
       gprotectLabelSwitchedPathDown             ( 7755 ),
       gworkingLabelSwitchedPathAlarmIndicationSignal             ( 7760 ),
       gprotectLabelSwitchedPathAlarmIndicationSignal             ( 7765 ),
       gworkingLabelSwitchedPathRemoteDefectIndication             ( 7770 ),
       gprotectLabelSwitchedPathRemoteDefectIndication             ( 7775 ),
       gbidirectionalForwardDetectionDown             ( 7780 ),
       gtpTrafficSwitchedFromWorkingToProtection             ( 7785 ),
       gworkingTpLockout             ( 7790 ),
       gprotectTpLockout             ( 7795 ),
       gethernetFlowPointFailed             ( 7800 ),
       gteTunnelDown             ( 7805 ),
       gmacSystemLimitReached             ( 7810 ),
       gmacBridgeDomainLimitReached             ( 7815 ),
       gautoSensingDisabled                          ( 7820 ),
       gsmBackwardIncomingAlignmentError             (7825),
       gresourceAllocationFailed             (7830),
       glossOfDFBSignal               ( 7835 ),
       gworkingLabelSwitchedPathLinkDownIndication             ( 7840 ),
       gprotectLabelSwitchedPathLinkDownIndication             ( 7845 ),
       gworkingLabelSwitchedPathLockReport             ( 7850 ),
       gprotectLabelSwitchedPathLockReport             ( 7855 ),
       gsatellitePanelBatteryFailureB             ( 7860 ),
       ghighBitErrorRate		(7865),
       gbackPanelFacilityLoopback        (7870),
       gbackPanelTerminalLoopback        (7875),
       gtrunkPayloadTypeMismatch	 (7880),
       ginvalidMuxponderConfiguration	 (7885),
       gcoolingProfileMismatch		 (7890),
       gtrunkOduAlarmIndicationSignal	 (7895),
       gcompanionCardMissing		 (7900),
       gcontrolPlaneUnverifiedClearedAlarmsPresent (7905),
       gpowerConsumptionLimitHasCrossed  (7910),
       gmasterKeyExchangeFailed		(7915),
       gunitHighTemperature              (7930),
       goverTemperatureUnitProtected     (7935),
       gseqMismatchCount                 (7945),
       gkeyProgramOnAlteraFpgaFailed     (7960),
       gduplicateNodeControllerDetected   (7970),
       grestorationInProg                (7975),
       gramanPumpsCalibrationProcedureIsRunning (7980),
       gramanPumpsCalibrationIsScheduledToRunInTheNextMinutes (7985),
       godukTCM1AlarmIndicationSignal                 ( 13100 ),
       godukTCM2AlarmIndicationSignal                 ( 13105 ),
       godukLockedDefectTCM1                          ( 13110 ),
       godukLockedDefectTCM2                          ( 13115 ),
       gotukLossOfFrame                               ( 13120 ),
       godukOpenConnectionIndicationTCM1		     ( 13125 ),
       godukOpenConnectionIndicationTCM2		     ( 13130 ),
       godukTrailTraceIdentifierMismatchTCM1          ( 13135 ),
       godukTrailTraceIdentifierMismatchTCM2          ( 13140 ),
       godukSignalFailureTCM1                         ( 13145 ),
       godukSignalFailureTCM2                         ( 13150 ),
       godukSignalDegradeTCM1                         ( 13155 ),
       godukSignalDegradeTCM2                         ( 13160 ),
       glossOfChannel                                 ( 13165 ),
       gfecMismatch                                   ( 13170 ),
       gtimSectionMonitorTraceIdentifierMismatchFailure ( 13175 ),
       gautomaticLaserShutdown                        ( 13180 ),
       gshutterInsertionLossVariationDegradeLow       ( 13200 ),
       gopticalChannelDeactivationFailure             ( 13205 ),
       gshutterInsertionLossVariationDegradeHigh      ( 13210 ),
       gnetworkTopologyIncomplete                     ( 13215 ),
       gpluginModuleCommunicationFailure              ( 13220 ),
       gopticalNetworkTypeMismatch                    ( 13225 ),
       gopticalPowerDegradeLow                        ( 13230 ),
       gautomaticPowerControlFailure                  ( 13235 ),
       gopticalPowerDegradeHigh                       ( 13240 ),
       gautomaticPowerControlDisabled                 ( 13245 ),
       gopticalPowerFailureLow                        ( 13250 ),
       gringIdMismatch                                ( 13255 ),
       gopticalPowerFailureHigh                       ( 13260 ),
       glossOfContinuity                              ( 13270 ),
       gvariableOpticalAttenuatorDegradeLow           ( 13280 ),
       gvariableOpticalAttenuatorDegradeHigh          ( 13290 ),
       gvariableOpticalAttenuatorFailureLow           ( 13300 ),
       gvariableOpticalAttenuatorFailureHigh          ( 13310 ),
       glaserBiasDegrade                              ( 13320 ),
       glaserBiasFailure                              ( 13330 ),
       glaserTemperatureDegrade                       ( 13340 ),
       gopticalAmplifierGainDegradeLow                ( 13350 ),
       gopticalAmplifierGainDegradeHigh               ( 13360 ),
       gopticalAmplifierGainFailureLow                ( 13370 ),
       gopticalAmplifierGainFailureHigh               ( 13380 ),
       gopticalChannelConnectionFailure               ( 13390 ),
       gopticalChannelIncomplete                      ( 13395 ),
       gopticalChannelActivationFailure               ( 13400 ),
       glaserAutoPowerReduction                       ( 13410 ),
       gcaseTemperatureDegrade                        ( 13420 ),
       gfiberTemperatureDegrade                       ( 13430 ),
       gshutterOpen                                   ( 13440 ),
       gawgTemperatureDegrade                         ( 13450 ),
       gawgTemperatureFailure                         ( 13460 ),
       gawgOverTemperature                            ( 13470 ),
       gopticalAmplifierInitialization                ( 13480 ),
       gawgWarmUp                                     ( 13490 ),
       gincSigloss                                    ( 13510 ),
       gincSyncloss                                   ( 13515 ),
       gincGfpOutOfFrame                              ( 13520 ),
       gincGfpSigLoss                                 ( 13525 ),
       gincGfpSyncLoss                                ( 13530 )
} 

CerentGenericEntityClass ::= TEXTUAL-CONVENTION
--   DISPLAY-HINT "d"
   STATUS current
   DESCRIPTION
       "This is the TC used to find out to which cerentGenericEntityClass
        an alarm belongs to."
   SYNTAX INTEGER {
  unknownEntity   (  1 ),
  ne              ( 10 ),
  backplane       ( 30 ),
  eqpt            ( 50 ),
  port            ( 60 ),
  ocn             ( 70 ),
  stmn            ( 71 ),
  aip             ( 80 ),
  fanTray         ( 90 ),
  crs             ( 100 ),
  ds3             ( 110 ),
  almExpPanel     ( 120 ),
  almIfExtnsn     ( 130 ),
  stsMon          ( 140 ),
  vcMonHp         ( 141 ),
  dwdmClient      ( 150 ),
  stsTerm         ( 160 ),
  vcTermHp        ( 161 ),
  dwdmTrunk       ( 170 ),
  dwdmOptics      ( 180 ),
  psSts           ( 190 ),
  rsms            ( 200 ),
  xcSts           ( 210 ),
  bits            ( 220 ),
  dwdmFec         ( 230 ),
  neSynchRef      ( 240 ),
  dwdm8b10b       ( 250 ),
  extSynchRef     ( 260 ),
  dwdmOtn         ( 270 ),
  envAlrm         ( 280 ),
  envCtrl         ( 290 ),
  neRing          ( 360 ),
  ds1             ( 390 ),
  vtMon           ( 410 ),
  vcMonLp         ( 411 ),
  vtTerm          ( 420 ),
  vcTermLP        ( 421 ),
  fUdc            ( 430 ),
  msUdc           ( 440 ),
  spareSdcc       ( 450 ),
  ucpCircuit      ( 480 ),
  ucpIpcc         ( 490 ),
  ucpNeighbor     ( 500 ),
  ec1             ( 510 ),
  ps              ( 520 ),
  psVt            ( 530 ),
  e100t           ( 540 ),
  e1000t          ( 550 ),
  etherBridge     ( 560 ),
  e1              ( 600 ),
  e3              ( 630 ),
  e4              ( 640 ),
  stm1E           ( 650 ),
  ds3i            ( 660 ),
  g1000           ( 670 ),
  ml100t          ( 680 ),
  ml1000          ( 690 ),
  dwdmSfp         ( 700 ),
  dwdmScl         ( 710 ),
  dwdmTcm1        ( 720 ),
  dwdmTcm2        ( 730 ),
  dwdmOcn         ( 740 ),
  dwdmSm          ( 750 ),
  dwdmPm          ( 760 ),
  dwdmTcm         ( 770 ),
  pwr             ( 780 ),
  stsTermVcat     ( 790 ),
  vtTermVcat      ( 800 ),
  vcatGroup       ( 810 ),
  fcmr            ( 820 ),
  entOptics       ( 830 ),
  ce100t          ( 840 ),
  ppm             ( 850 ),
  twor            ( 860 ),
  isc             ( 870 ),
  escon           ( 880 ),
  bic             ( 890 ),
  gfp             ( 900 ),
  gige            ( 910 ),
  pos             ( 920 ),
  cap             ( 930 ),
  dwdmData        ( 940 ),
  logFac          ( 950 ),
  ge              ( 960 ),
  fc              ( 970 ),
  ec1p1           ( 980 ),
  mlFx            ( 990 ),
  ochTerm          ( 1000 ),
  shelf          ( 1010 ),
  ce1000          ( 1020 ),
  cemr           ( 1030 ),
  lmp          ( 1040 ),
  lmpControlChannel          ( 1050 ),
  lmpTeLink          ( 1060 ),
  lmpDataLink          ( 1070 ),
  rpr          ( 1080 ),
  ether          ( 1090 ),
  mlmr          ( 1100 ),
  otu          ( 1110 ),
  aots           ( 3200 ),
  ots            ( 3210 ),
  oms            ( 3220 ),
  och            ( 3230 ),
  osc            ( 3240 ),
  ochc           ( 3250 ),
  ib			 ( 3260 ),
  chgrp			 (3270),
  hdlc           ( 3280 ),
  msISC          ( 3290 ),
  ecu            ( 3300 ),
  lcdFlash       ( 3310 ),
  usb            ( 3320 ),
  fe	         ( 3330 ),
  odu0		 ( 3350 ),
  odu1		 ( 3360 )
}

-- **************************************************************
cerentGenericObjects OBJECT-IDENTITY
      STATUS      current
      DESCRIPTION
            "All the generic objects definitions are grouped
             under this" 
      ::= { cerentGeneric 10 }

-- **************************************************************

cerentGenericCommonObjectsGroup OBJECT-IDENTITY
      STATUS      current
      DESCRIPTION
            "The group to combine all the Cisco OTBU common 
             objects" 
      ::= { cerentGenericObjects 10 }

cerentGenericEnableNotification   OBJECT-TYPE
       SYNTAX      TruthValue
       MAX-ACCESS  read-write
       STATUS      current
       DESCRIPTION
               "This variable indicates whether the system produces
                notifications.  A value=FALSE will prevent notifications
                from being sent by this system."
       DEFVAL { true }
       ::= { cerentGenericCommonObjectsGroup 10 }

cerentGenericNodeTime OBJECT-TYPE
       SYNTAX       DisplayString 
       MAX-ACCESS   read-only
       STATUS current
       DESCRIPTION
       "Indicates current local time as reflected by
        the Cisco OTBU equipment. The format this scalar is
        YYYYMMDDhhmmss{S/D}. E.g., 
        20011103133453D means 1:34:53 PM PDT on 03/Nov/2001
        19990614095436S means 9:54:36 AM PST on 14/Jun/1999.
        If the last octet is S then the time is standard time.
        Otherwise it is D to indicate it is daylight saving
        time, if applicable"
       ::= { cerentGenericCommonObjectsGroup 20 }

cerentGenericSentNotifications OBJECT-TYPE  
       SYNTAX      Counter32 
       MAX-ACCESS read-only
       STATUS current
       DESCRIPTION
              "A count of v1+v2 notifications sent out
               by the agent. Resets to zero after
               cold/warm start."
       ::= { cerentGenericCommonObjectsGroup 30 }

cerentGenericLastChangeTime OBJECT-TYPE
    SYNTAX      TimeStamp
    MAX-ACCESS  read-only
    STATUS      current
    DESCRIPTION
            "The value of sysUpTime at the time 
             a conceptual row is created or deleted 
             in cerentGenericAlarmTable "
    ::= { cerentGenericCommonObjectsGroup 40 }

cerentGenericMultishelfEnabled   OBJECT-TYPE
    SYNTAX      TruthValue
    MAX-ACCESS  read-only
    STATUS      current
    DESCRIPTION
    "This variable indicates whether the system is configured
     in multi-shelf mode or single-shelf mode."
    DEFVAL { false }
    ::= { cerentGenericCommonObjectsGroup 50 }

-- **************************************************************
-- 
cerentGenericGeneralGroup OBJECT-IDENTITY
       STATUS       current
       DESCRIPTION
              "Another class of objects found in
               Cisco ONS 15327, 15310 "
       ::= { cerentGenericObjects 20 }

cerentGenericSoftwareVersion OBJECT-TYPE
       SYNTAX       DisplayString
       MAX-ACCESS   read-only
       STATUS current
       DESCRIPTION
       "Indicates the version of software that is
        used in Cisco ONS Network element, 
        ONS 15327, 15310. E.g., 2.2.03"
       ::= { cerentGenericGeneralGroup 10 }

cerentGenericAlarmGroup OBJECT-IDENTITY
       STATUS       current
       DESCRIPTION
              "The group that will represent all the
               alarm info in the Cisco ONS network element, 
               ONS 15327, 15310"
       ::= { cerentGenericObjects 30 }

cerentGenericAlarmCount       OBJECT-TYPE
       SYNTAX       Unsigned32
       MAX-ACCESS   read-only
       STATUS current
       DESCRIPTION
           "Total number of active alarms in the 
            Cisco ONS network element, ONS 15327, 15310.
            This equals the total number of rows in
            cerentGenericAlarmTable at any time."
       ::= { cerentGenericAlarmGroup 10 }

cerentGenericAlarmTable       OBJECT-TYPE
       SYNTAX SEQUENCE OF CerentGenericAlarmEntry
       MAX-ACCESS not-accessible 
       STATUS current
       DESCRIPTION
               "This table has all currently raised conditions
                for the network node. A Condition is a fault or
                status detected by hardware or software."
       ::= { cerentGenericAlarmGroup 20 }

cerentGenericAlarmEntry       OBJECT-TYPE
       SYNTAX CerentGenericAlarmEntry
       MAX-ACCESS not-accessible
       STATUS current
       DESCRIPTION
              "Row definition for cerentGenericAlarmTable"
       INDEX { cerentGenericAlarmIndex, cerentGenericAlarmType }
       ::= { cerentGenericAlarmTable 1 }

CerentGenericAlarmEntry ::= SEQUENCE {
       cerentGenericAlarmIndex           	Integer32,
       cerentGenericAlarmObjectType      	CerentGenericEntityClass,
       cerentGenericAlarmSlotNumber      	Integer32,
       cerentGenericAlarmPortNumber      	CerentPortNumber,
       cerentGenericAlarmLineNumber      	Integer32,
       cerentGenericAlarmObjectIndex     	Integer32,
       cerentGenericAlarmType            	CerentGenericAlarmType, 
       cerentGenericAlarmState           	CerentNotificationClass,
       cerentGenericAlarmTimeStamp       	TimeStamp,
       cerentGenericAlarmObjectName      	DisplayString,
       cerentGenericAlarmAdditionalInfo  	DisplayString,
       cerentGenericAlarmSeverity	 	CerentAlarmSeverity,
       cerentGenericAlarmStatus		 	CerentAlarmStatus,
       cerentGenericAlarmServiceAffecting	CerentAlarmServiceAffecting
       }

cerentGenericAlarmIndex       OBJECT-TYPE
       SYNTAX Integer32 ( 1..2147483647 ) -- all +ve values
       MAX-ACCESS not-accessible
       STATUS current
       DESCRIPTION
              "Uniquely identifies each entry in alarm table.
               May not start with one and there may be some
               missing numbers."
       ::= { cerentGenericAlarmEntry 10 }

cerentGenericAlarmObjectType       OBJECT-TYPE
       SYNTAX CerentGenericEntityClass
       MAX-ACCESS read-only
       STATUS current
       DESCRIPTION
              "This will indicate what is the type
               of the entity which raised this alarm.
               ( E.g., DS3, etherBridge, VT-TERM, etc ) 
               The NMS is expected to use this value
               to decide which table to poll for 
               further info about the alarm"
       ::= { cerentGenericAlarmEntry 20 }

cerentGenericAlarmSlotNumber           OBJECT-TYPE
       SYNTAX Integer32
       MAX-ACCESS read-only
       STATUS current
       DESCRIPTION
              "This will indicate what is the slot 
               of the object which raised this alarm.
               If not relevant to the alarm, will be
               zero."
       ::= { cerentGenericAlarmEntry 30 }

cerentGenericAlarmPortNumber          OBJECT-TYPE
       SYNTAX CerentPortNumber 
       MAX-ACCESS read-only
       STATUS current
       DESCRIPTION
              "This will indicate what is the port
               of the object which raised this alarm."
       ::= { cerentGenericAlarmEntry 40 }
 
cerentGenericAlarmLineNumber           OBJECT-TYPE
       SYNTAX Integer32
       MAX-ACCESS read-only
       STATUS     current
       DESCRIPTION
              "This will indicate what is the port
               of the object which raised this alarm.
               If not relevant to the alarm, will be
               zero."
       ::= { cerentGenericAlarmEntry 50 }

cerentGenericAlarmObjectIndex       OBJECT-TYPE
       SYNTAX Integer32
       MAX-ACCESS read-only
       STATUS current
       DESCRIPTION
              "Every alarm is raised by an object and 
               this object is an entry in a specific 
               table. This is the index of the object
               in that table E.g., if the alarm is interface
               related, this index is the index of the
               interface in the interface table."
       ::= { cerentGenericAlarmEntry 60 }

cerentGenericAlarmType       OBJECT-TYPE
       SYNTAX CerentGenericAlarmType
       MAX-ACCESS read-only
       STATUS current
       DESCRIPTION
              "Indicates what the exact nature of the
               alarm. See the CerentGenericAlarmType TC
               for mapping details "
       ::= {cerentGenericAlarmEntry  70 }

cerentGenericAlarmState OBJECT-TYPE  
       SYNTAX        CerentNotificationClass
       MAX-ACCESS read-only
       STATUS current
       DESCRIPTION
              "Specifies alarm severity and service 
               affecting status ( SA/NSA ). Only 
               {minor|major|critical}+{NA|NSA} alarms and
               standing conditions will be represented here.

               However, this mib object is included in each
               trap dispatched and in the trap this object
               can contain all the possible values of
               CerentNotificationClass type."
       ::= { cerentGenericAlarmEntry 80 }

cerentGenericAlarmTimeStamp OBJECT-TYPE  
       SYNTAX   TimeStamp
       MAX-ACCESS read-only
       STATUS current
       DESCRIPTION
              "The value of sysUpTime when this entry was
               created. This is accurate only upto a second."
       ::= { cerentGenericAlarmEntry 90 }

cerentGenericAlarmObjectName OBJECT-TYPE
       SYNTAX  DisplayString
       MAX-ACCESS read-only
       STATUS current
       DESCRIPTION
              "TL1-style user-visible name which uniquely
               identifies an object in the system"
       ::= { cerentGenericAlarmEntry 100 }

cerentGenericAlarmAdditionalInfo OBJECT-TYPE
       SYNTAX  DisplayString 
       MAX-ACCESS read-only
       STATUS current
       DESCRIPTION
              "Additional information for the alarm object.
              In the current version of the MIB, this object 
              contains the following information :-
              
              a) Provisioned description for alarms of type
              'failureDetectedExternalToTheNE'.

              This object would be a null string if no 
              additional information is specified."
       ::= { cerentGenericAlarmEntry 110 }
       
cerentGenericAlarmSeverity OBJECT-TYPE
       SYNTAX       CerentAlarmSeverity
       MAX-ACCESS read-only
       STATUS current
       DESCRIPTION
              "Specifies severity of the alarm
               being sent out." 

       ::= { cerentGenericAlarmEntry 120 }

cerentGenericAlarmStatus OBJECT-TYPE
       SYNTAX       CerentAlarmStatus
       MAX-ACCESS read-only
       STATUS current
       DESCRIPTION
              "Represents if an alarm is currently raised or cleared."

       ::= { cerentGenericAlarmEntry 130 }

cerentGenericAlarmServiceAffecting OBJECT-TYPE
       SYNTAX       CerentAlarmServiceAffecting
       MAX-ACCESS read-only
       STATUS current
       DESCRIPTION
              "Specifies whether the alarm that is being
               sent out is Service Affecting (SA) or Non-
               Service Affecting (NSA)."

       ::= { cerentGenericAlarmEntry 140 }


cerentGenericReportedAlarmCount       OBJECT-TYPE
       SYNTAX       Unsigned32
       MAX-ACCESS   read-only
       STATUS current
       DESCRIPTION
           "Number of alarms currently reported against Cisco
            ONS platform. This equals the number of rows in
            cerentGenericReportedAlarmTable."
       ::= { cerentGenericAlarmGroup 30 }


cerentGenericReportedAlarmTable       OBJECT-TYPE
       SYNTAX SEQUENCE OF CerentGenericReportedAlarmEntry
       MAX-ACCESS not-accessible
       STATUS current
       DESCRIPTION
              "This table has the list of alarms currently
               reported for the Cisco ONS node. It does not
               include any cleared alarms. The alarms in this
               table are in compliance with Telcordia GR-253.
               This means that if a network problem causes two
               alarms, such a as loss of frame(LOF) and loss of
               signal(LOS), only LOS alarm will be in this table
                because it supersedes and replaces the LOF."
       ::= { cerentGenericAlarmGroup 40 }

cerentGenericReportedAlarmEntry       OBJECT-TYPE
       SYNTAX CerentGenericReportedAlarmEntry
       MAX-ACCESS not-accessible
       STATUS current
       DESCRIPTION
              "Row definition for cerentGenericReportedAlarmTable"
       INDEX { cerentGenericReportedAlarmIndex, cerentGenericReportedAlarmType }
       ::= { cerentGenericReportedAlarmTable 1 }

CerentGenericReportedAlarmEntry ::= SEQUENCE {
       cerentGenericReportedAlarmIndex               Integer32,
       cerentGenericReportedAlarmObjectType          CerentGenericEntityClass,
       cerentGenericReportedAlarmSlotNumber          Integer32,
       cerentGenericReportedAlarmPortNumber          CerentPortNumber,
       cerentGenericReportedAlarmObjectIndex         Integer32,
       cerentGenericReportedAlarmType                CerentGenericAlarmType,
       cerentGenericReportedAlarmTimeStamp           TimeStamp,
       cerentGenericReportedAlarmObjectName          DisplayString,
       cerentGenericReportedAlarmAdditionalInfo      DisplayString,
       cerentGenericReportedAlarmSeverity            CerentAlarmSeverity,
       cerentGenericReportedAlarmStatus              CerentAlarmStatus,
       cerentGenericReportedAlarmServiceAffecting    CerentAlarmServiceAffecting
       }

cerentGenericReportedAlarmIndex       OBJECT-TYPE
       SYNTAX Integer32 ( 1..2147483647 ) -- all +ve values
       MAX-ACCESS not-accessible
       STATUS current
       DESCRIPTION
              "Identifies each entry in ReportedAlarm table.
               May not start with one and there may be some
               missing numbers."
       ::= { cerentGenericReportedAlarmEntry 10 }

cerentGenericReportedAlarmObjectType       OBJECT-TYPE
       SYNTAX CerentGenericEntityClass
       MAX-ACCESS read-only
       STATUS current
       DESCRIPTION
              "This will indicate the type
               of the entity which raised this alarm.
               ( E.g., DS3, etherBridge, VT-TERM, etc )
               The NMS is expected to use this value
               to decide which table to poll for
               further info about the alarm"
       ::= { cerentGenericReportedAlarmEntry 20 }

cerentGenericReportedAlarmSlotNumber           OBJECT-TYPE
       SYNTAX Integer32
       MAX-ACCESS read-only
       STATUS current
       DESCRIPTION
              "This will indicate what is the slot
               of the object which raised this alarm.
               If not relevant to the alarm, will be
               zero."
       ::= { cerentGenericReportedAlarmEntry 30 }

cerentGenericReportedAlarmPortNumber          OBJECT-TYPE
       SYNTAX CerentPortNumber
       MAX-ACCESS read-only
       STATUS current
       DESCRIPTION
              "This will indicate what is the port
               of the object which raised this alarm."
       ::= { cerentGenericReportedAlarmEntry 40 }

cerentGenericReportedAlarmObjectIndex       OBJECT-TYPE
       SYNTAX Integer32
       MAX-ACCESS read-only
       STATUS current
       DESCRIPTION
              "Every alarm is raised by an object and
               this object is an entry in a specific
               table. This is the index of the object
               in that table E.g., if the alarm is interface
               related, this is the index of the
               interface in the interface table."
       ::= { cerentGenericReportedAlarmEntry 50 }

cerentGenericReportedAlarmType       OBJECT-TYPE
       SYNTAX CerentGenericAlarmType
       MAX-ACCESS read-only
       STATUS current
       DESCRIPTION
              "Indicates the exact nature of the
               alarm." 
       ::= {cerentGenericReportedAlarmEntry  60 }

cerentGenericReportedAlarmTimeStamp OBJECT-TYPE
       SYNTAX   TimeStamp
       MAX-ACCESS read-only
       STATUS current
       DESCRIPTION
              "The value of sysUpTime when this entry was
               created. This is accurate only upto a second."
       ::= { cerentGenericReportedAlarmEntry 70 }

cerentGenericReportedAlarmObjectName OBJECT-TYPE
       SYNTAX  DisplayString
       MAX-ACCESS read-only
       STATUS current
       DESCRIPTION
              "TL1-style user-visible name which uniquely
               identifies an object in the system"
       ::= { cerentGenericReportedAlarmEntry 80 }

cerentGenericReportedAlarmAdditionalInfo OBJECT-TYPE
       SYNTAX  DisplayString
       MAX-ACCESS read-only
       STATUS current
       DESCRIPTION
              "Additional information for the alarm object.
              In the current version of the MIB, this object
              contains the following information :-

              a) Provisioned description for alarms of type
              'failureDetectedExternalToTheNE'.

              This object would be a null string if no
              additional information is specified."
       ::= { cerentGenericReportedAlarmEntry 90 }

cerentGenericReportedAlarmSeverity OBJECT-TYPE
       SYNTAX       CerentAlarmSeverity
       MAX-ACCESS read-only
       STATUS current
       DESCRIPTION
              "Specifies severity of the alarm."

       ::= { cerentGenericReportedAlarmEntry 100 }

cerentGenericReportedAlarmStatus OBJECT-TYPE
       SYNTAX       CerentAlarmStatus
       MAX-ACCESS read-only
       STATUS current
       DESCRIPTION
              "Represents if the alarm is currently raised
               or cleared."

       ::= { cerentGenericReportedAlarmEntry 110 }

cerentGenericReportedAlarmServiceAffecting OBJECT-TYPE
       SYNTAX       CerentAlarmServiceAffecting
       MAX-ACCESS read-only
       STATUS current
       DESCRIPTION
              "Specifies whether the alarm that is being
               sent out is Service Affecting (SA) or Non-
               Service Affecting (NSA)."

       ::= { cerentGenericReportedAlarmEntry 120 }


--  All Cisco ONS Generic Threshold Group.

cerentGenericThresholdGroup OBJECT-IDENTITY
       STATUS       current
       DESCRIPTION
              "The group that will represent all the
               threshold info in the Cisco ONS network element,
               ONS 15327, 15310"
       ::= { cerentGenericObjects 40 }

cerentGenericThresholdTable       OBJECT-TYPE
       SYNTAX SEQUENCE OF CerentGenericThresholdEntry
       MAX-ACCESS not-accessible
       STATUS current
       DESCRIPTION
              "This table holds all the provisioned 
               Thresholds.  
   
               This table is currently unimplemented."
       ::= { cerentGenericThresholdGroup 10 }

cerentGenericThresholdEntry       OBJECT-TYPE
       SYNTAX CerentGenericThresholdEntry
       MAX-ACCESS not-accessible
       STATUS current
       DESCRIPTION
              "Row definition for cerentGenericThresholdTable"
       INDEX { cerentGenericThresholdIndex }
       ::= { cerentGenericThresholdTable 1 }

CerentGenericThresholdEntry ::= SEQUENCE {
      cerentGenericThresholdIndex           Integer32,
      cerentGenericThresholdMonitorType     CerentMonitorType,
      cerentGenericThresholdLocation        CerentLocation,
      cerentGenericThresholdPeriod          CerentPeriod,
      cerentGenericThresholdSetValue        Integer32,
      cerentGenericThresholdCurrentValue    Integer32,
      cerentGenericThresholdDetectType      INTEGER
    }

cerentGenericThresholdIndex  OBJECT-TYPE
       SYNTAX  Integer32 (1..2147483647) -- Same as IfIndex from IF-MIB
       MAX-ACCESS not-accessible
       STATUS current
       DESCRIPTION
              "Uniquely identifies each entry in Threshold table.
               May not start with one and there will be some
               missing numbers."
       ::= { cerentGenericThresholdEntry 10 }

cerentGenericThresholdMonitorType  OBJECT-TYPE
       SYNTAX                  CerentMonitorType
       MAX-ACCESS read-only
       STATUS current
       DESCRIPTION
       "This object indicates the type of metric monitored."
       ::= { cerentGenericThresholdEntry 20 }

cerentGenericThresholdLocation     OBJECT-TYPE
       SYNTAX                  CerentLocation
       MAX-ACCESS read-only
       STATUS current
       DESCRIPTION
       "This indicates if it near or far end"
       ::= { cerentGenericThresholdEntry 30 }

cerentGenericThresholdPeriod       OBJECT-TYPE
       SYNTAX                  CerentPeriod
       MAX-ACCESS read-only
       STATUS current
       DESCRIPTION
       "The sampling interval period is indicated here"
       ::= { cerentGenericThresholdEntry 40 }

cerentGenericThresholdSetValue     OBJECT-TYPE
       SYNTAX                  Integer32
       MAX-ACCESS read-only
       STATUS current
       DESCRIPTION
       "The value of this object will be threshold that was 
        provisioned by the NMS"
       ::= { cerentGenericThresholdEntry 50 }

cerentGenericThresholdCurrentValue OBJECT-TYPE
       SYNTAX                  Integer32
       MAX-ACCESS read-only
       STATUS current
       DESCRIPTION
       "The current value of the counter which 
        measures the metric.

        This column will never be implemented as
        these values are already accessible through
        IETF MIB objects."

       ::= { cerentGenericThresholdEntry 60 }

cerentGenericThresholdDetectType  OBJECT-TYPE
       SYNTAX  INTEGER {
                  unknown(1),
                  none(10),
                  mon(20),
                  term(30) 
                  }
       MAX-ACCESS read-only
       STATUS current
       DESCRIPTION
       "The value of this object will be the detect type for the
        threshold."
       ::= { cerentGenericThresholdEntry 70 }      

--  All Cisco ONS Generic Notifications definitions.

cerentGenericEvents OBJECT-IDENTITY
      STATUS      current
      DESCRIPTION
            "Place holder for all notifications
             of Cisco ONS network device, ONS 15327, 15310 "
      ::= { cerentGeneric 20 }

cerentGenericV2Events OBJECT-IDENTITY
      STATUS      current
      DESCRIPTION
                 "The sub-identifier has to be zero, as part
                  of the interoperability agreement between
                  SNMPv1 and SNMPv2 worlds."
      ::= { cerentGenericEvents 0  } 

-- ---------------------------------------------
-- All the Cisco ONS generic notifications definitions
-- ---------------------------------------------

-- object and event groups

galarmUnknown
  NOTIFICATION-TYPE 
    OBJECTS { 
        cerentGenericNodeTime, 
        cerentGenericAlarmState,
        cerentGenericAlarmObjectType, 
        cerentGenericAlarmObjectIndex,
        cerentGenericAlarmSlotNumber, 
        cerentGenericAlarmPortNumber, 
        cerentGenericAlarmLineNumber,
        cerentGenericAlarmObjectName,
        cerentGenericAlarmSeverity,
        cerentGenericAlarmStatus,
        cerentGenericAlarmServiceAffecting
    }
    STATUS current 
    DESCRIPTION "alarm unknown" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events  1 } 

galarmCutoffIsInManualMode
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm cutoff is in manual mode" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 10 }
 
gfailureDetectedExternalToTheNE
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmAdditionalInfo,
      cerentGenericAlarmSeverity,
      cerentGenericAlarmStatus,
      cerentGenericAlarmServiceAffecting
    }
    STATUS current 
    DESCRIPTION "failure detected External to the NE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 20 }

gexternalError
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "external error" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 30 }
 
gexcessiveSwitching
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "excessive switching" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 40 }
 
gsdccTerminationFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "SDCC Termination failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 50 }
 
gincomingFailureCondition
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "incoming failure condition" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 60 }
 
galarmIndicationSignal       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm indication signal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 70 }
 
galarmIndicationSignalLine
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm indication signal LINE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 80 }
 
galarmIndicationSignalPath  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm indication signal Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 90 }
 
galarmIndicationSignalVT    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "alarm indication signal VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 100 }

gapsChannelFailure           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel failure APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 110 }
 
gchannelByteFailureAPS      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel Byte failure APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 120 }
 
gchannelProtectionSwitchingChannelMatchFailureAPS   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel Protection Switching Channel Match failure APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 130 }
 
gchannelAutomaticProtectionSwitchModeMismatchAPS    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel Automatic Protection Switch Mode Mismatch APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 140 }
 
gfarEndProtectionLineFailure              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "channel far end protection line failure APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 150 }
 
ginconsistentAPSCode       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Inconsistent APS code" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 160 }
 
gimproperAPSCode       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Improper APS code APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 170 }
 
gnodeIdMismatch        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Node Id Mismatch APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 180 }
 
gchannelDefaultKAPS    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Default K APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 190 }
 
gconnectionLoss         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Connection loss APS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 200 }
 
gbipolarViolation             
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "bipolar Violation" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 210 }
 
gcarrierLossOnTheLAN       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "carrier Loss on the LAN" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 220 }
 
gconcatenationErrorSTS
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "concatenation error STS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 230 }
 
gexcessCollisionsOnTheLAN  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "excess collisions on the LAN" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 240 }
 
gfacilityFailure   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility critical alarm caused by DS3 facility failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 250 }
 
gfarEndAIS   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end AIS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 260 }
 
gfarEndMultipleDS1LOSDetectedOnDS3 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end Multiple DS1 LOS detected on DS3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 270 }
 
gfarEndDS1EqptFailNonServiceAffecting              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end DS1 eqpt fail non service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 280 }
 
gfarEndDS1EqptFailServiceAffecting  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end DS1 Eqpt fail service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 290 }
 
gfarEndSingleDS1LOS        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end Single DS1 LOS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 300 }
 
gfarEndDS3EqptFailNonServiceAffecting              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end DS3 Eqpt failure non service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 310 }
 
gfarEndDS3EqptFailServiceAffecting  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end DS3 Eqpt failure service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 320 }
 
gfarEndCommonEquipmentFailureNonServiceAffecting              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end common Eqpt failure non service affecting" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 330 }
 
gfarEndIDLE  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end IDLE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 340 }
 
gfarEndLOS   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end LOS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 350 }
 
gfarEndLOF   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far end LOF" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 360 }
 
gfarEndBlockError           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "far End Block Error" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 370 }
 
gds3IdleCondition            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "idle Condition DS3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 380 }
 
glossOfFrame 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Frame" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 390 }
 
glossOfPointer               
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Pointer" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 400 }
 
glossOfPointerPath
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Pointer Path " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 410 }
 
glossOfPointerVT            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Pointer VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 420 }
 
glossOfSignal                
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loss of Signal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 430 }
 
goutOfFrame  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "out of Frame" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 440 }
 
gpathSelectorFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "path Selector inability to swtich to a valid signal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 450 }
 
gremoteAlarmIndication       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Alarm Indication" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 460 }
 
gremoteFailureIndication     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Failure Indication" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 470 }
 
gremoteFailureIndicationLine           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Failure Indication LINE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 480 }
 
gremoteFailureIndicationPath           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Failure Indication Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 490 }
 
gremoteFailureIndicationVT  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Failure Indication VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 500 }
 
gsignalDegrade
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Signal Degrade" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 510 }
 
gseverelyErroredFrame        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "severely Errored Frame" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 520 }
 
gsignalFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Signal Failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 530 }
 
gsignalLabelMismatchFailure     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "signal Label Mismatch Failures" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 540 }
 
gpayloadDefectIndication  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Payload Defect Indication" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 550 }

gpayloadDefectIndicationPath 
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Payload Defect Indication - Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 560 }
 
gpayloadLabelMismatchPath      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Payload Label Mismatch - Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 570 }
 
gsignalLabelMismatchFailurePayloadLabelMismatchVT        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "signal Label Mismatch Failure Payload Label Mismatch VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 580 }
 
gunequippedPath  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Unequipped - Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 590 }
 
gsignalLabelMismatchFailureUnequippedVT    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "signal Label Mismatch Failure Unequipped VT" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 600 }
 
glossOfSynchronization         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Loss of Synchronization"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 610 }
 
goutOfSynchronization
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Out of Synchronization"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 620 }
 
gprimarySynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Primary Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 630 }
 
gsecondarySynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Secondary Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 640 }
 
gthirdSynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Third Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 650 }
 
gfourthSynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Fourth Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 660 }
 
gfifthSynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Fifth Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 670 }
 
gsixthSynchronizationReferenceFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Sixth Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 680 }
 
gfailedToReceiveSynchronizationStatusMessage 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failed to receive Synchronization Status Message" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 690 }

gsynchronizationStatusMessagesAreDisabledOnThisInterface
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "synchronization Status Messages are disabled on this interface" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 700 }

gstratum1PrimaryReferenceSourceTraceable     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Stratum1 Primary Reference Source Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 710 }

gsynchronizedTraceabilityUnknown     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "synchronized Traceability Unknown" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 720 }

gstratum2Traceable   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "stratum 2 Traceable " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 730 }

gtransitNodeClockTraceable          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "transit Node clock Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 740 }

gstratum3ETraceable  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "stratum 3E Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 750 }

gstratum3Traceable   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "stratum 3 Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 760 }

gsonetMinimumClockTraceable
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Minimum clock Traceable - SONET " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 770 }

gstratum4Traceable   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "stratum 4 Traceable" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 780 }

gdoNotUseForSynchronization        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "do not Use for Synchronization" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 790 }

greservedForNetworkSynchronizationUse         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "reserved for Network Synchronization Use" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 800 }

goutgoingFailureCondition            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "outgoing failure condition" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 810 }
 
gremoteDefectIndicationLine         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Defect Indication LINE" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 820 }
 
gremoteDefectIndicationPath         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "remote Defect Indication Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 830 }
 
gfreeRunningSynchronizationMode     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "free Running Synchronization mode" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 840 }
 
gholdoverSynchronizationMode         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "holdover synchronization mode" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 850 }
 
gfastStartSynchronizationMode       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "fast Start synchronization mode" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 860 }
 
ginternalFault
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "internal hardware fault or failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 870 }
 
ginternalError
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "error Internal to the NE Detected" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 880 }
 
ginternalMessageError                
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "internal Message Error" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 890 }
 
gmismatchOfEquipmentAndAttributes  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "mismatch of Equipment and Attributes" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 900 }
 
gwatchdogTimerTimeout                
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "watchdog Timer Timeout" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 910 }
 
gsoftwareFaultOrFailure             
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "software Fault or failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 920 }
 
gsoftwareFaultDataIntegrityFault   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "software Fault -  Data integrity fault :
                 The newly added provisioning or hardware has 
                 caused the database to grow beyond its limit. 
                 That is, the newly added object(s) in the system 
                 has(have) enough memory to exist onboard but
                 too large to be saved in the database." 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 930 }
 
gprogramFailure       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "program failure " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 940 }
 
gcontrolEquipmentFailure            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 950 }
 
gprimaryNonVolatileBackupMemoryFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Primary non volatile Backup Memory failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 960 }
 
gsecondaryNonVolatileBackupMemoryFailure 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Secondary non volatile Backup Memory failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 970 }
 
gcontrolBusFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Control Bus failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 980 }
 
gcontrolBus1Failure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Control Bus 1 failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 990 }
 
gcontrolBus2Failure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Control Bus 2 failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1000 }

gtccAToShelfSlot1DROP1CommunicationFailure NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 1" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1010 }

gtccAToShelfSlot2DROP2CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 2" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1020 }

gtccAToShelfSlot3DROP3CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1030 }

gtccAToShelfSlot4DROP4CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 4" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1040 }

gtccAToShelfSlot5TRUNK1CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 5" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1050 }

gtccAToShelfSlot6TRUNK2CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 6" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1060 }

gtccAToShelfSlot7TCCACommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 7 " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1070 }

gtccAToShelfSlot8XCONACommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 8" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1080 }

gtccAToShelfSlot9AICCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 9" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1090 }

gtccAToShelfSlot10XCONBCommunicationFailure NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 10" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1100 }

gtccAToShelfSlot11TCCBCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 11" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1110 }

gtccAToShelfSlot12TRUNK3CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 12" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1120 }

gtccAToShelfSlot13TRUNK4CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 13" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1130 }

gtccAToShelfSlot14DROP5CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 14" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1140 }

gtccAToShelfSlot15DROP6CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 15" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1150 }

gtccAToShelfSlot16DROP7CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 16" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1160 }

gtccAToShelfSlot17DROP8CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller A to Shelf SLOT 17 " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1170 }

gtccAToDCCAProcessorCommunicationFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure ControllerP A to ControllerJ A processor" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1180 }

gtccBToShelfSlot1DROP1CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 1 " 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1190 }

gtccBToShelfSlot2DROP2CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 2" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1200 }

gtccBToShelfSlot3DROP3CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1210 }

gtccBToShelfSlot4DROP4CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 4" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1220 }

gtccBToShelfSlot5TRUNK1CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 5" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1230 }

gtccBToShelfSlot6TRUNK2CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 6" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1240 }

gtccBToShelfSlot7TCCACommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 7" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1250 }

gtccBToShelfSlot8XCONACommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 8" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1260 }

gtccBToShelfSlot9AICCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 9" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1270 }

gtccBToShelfSlot10XCONBCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 10" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1280 }

gtccBToShelfSlot11TCCBCommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 11" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1290 }

gtccBToShelfSlot12TRUNK3CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 12" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1300 }

gtccBToShelfSlot13TRUNK4CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 13" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1310 }

gtccBToShelfSlot14DROP5CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 14" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1320 }

gtccBToShelfSlot15DROP6CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 15" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1330 }

gtccBToShelfSlot16DROP7CommunicationFailure 
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 16" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1340 }

gtccBToShelfSlot17DROP8CommunicationFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure Controller B to Shelf SLOT 17" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1350 }

gtccBToDCCBProcessorCommunicationFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "communication failure ControllerP B to ControllerJ A processor" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1360 }

gcontrolEquipmentControlCommunicationsEquipmentFailure
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS deprecated 
    DESCRIPTION "control Equipment Control Communications equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1370 }

gcontrolProcessorFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Control processor failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1380 }

gworkingMemoryFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "control Equipment Working memory failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1390 }

ginterconnectionEquipmentFailure         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1400 }

gpayloadBusFailureToIOSlot1XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 1 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1410 }

gpayloadBusFailureToIOSlot2XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 2 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1420 }

gpayloadBusFailureToIOSlot3XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 3 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1430 }

gpayloadBusFailureToIOSlot4XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 4 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1440 }

gpayloadBusFailureToIOSlot5XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 5 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1450 }

gpayloadBusFailureToIOSlot6XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 6 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1460 }

gpayloadBusFailureToIOSlot12XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 7 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1470 }

gpayloadBusFailureToIOSlot13XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 8 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1480 }

gpayloadBusFailureToIOSlot14XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 9 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1490 }

gpayloadBusFailureToIOSlot15XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 10 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1500 }

gpayloadBusFailureToIOSlot16XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 11 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1510 }

gpayloadBusFailureToIOSlot17XCONSlot8
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 12 Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1520 }

gpayloadBusFailureToIOSlot1XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 1 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1530 }

gpayloadBusFailureToIOSlot2XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 2 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1540 }

gpayloadBusFailureToIOSlot3XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 3 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1550 }

gpayloadBusFailureToIOSlot4XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 4 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1560 }

gpayloadBusFailureToIOSlot5XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 5 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1570 }

gpayloadBusFailureToIOSlot6XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 6 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1580 }

gpayloadBusFailureToIOSlot12XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 7 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1590 }

gpayloadBusFailureToIOSlot13XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 8 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1600 }

gpayloadBusFailureToIOSlot14XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 9 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1610 }

gpayloadBusFailureToIOSlot15XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 10 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1620 }

gpayloadBusFailureToIOSlot16XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 11 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1630 }

gpayloadBusFailureToIOSlot17XCONSlot10
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Equipment failure Payload Bus 12 Protect" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1640 }

gtimeSlotInterchangeEquipmentFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "interconnection Eqpt Time slot interchange eqpt failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1650 }

gequipmentFailure           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1660 }

ghighTemperature        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "High Temperature" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1670 }

ginvalidMACAddress
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure Invalid MAC Address" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1680 }

gboardFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure Board Failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1690 }

gdiagnosticFailure     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure Diagnostics Failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1700 }

gmediumAccessControlFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment failure Medium Access Control" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1710 }

gfacilityTerminationEquipmentFailure    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1720 }

gautomaticLaserShutoffDueToHighTemperature              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Automatic Laser Shutoff Due To High Temperature" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1730 }

gfailureToReleaseFromProtection        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure To Release from protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1740 }

greceiverFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment Receiver failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1750 }

gtransmitFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment Transmit failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1760 }

gfacilityTerminationEquipmentReceiverMissing      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment Receiver missing" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1770 }

gfacilityTerminationEquipmentTransmitterMissing   
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "facility Termination equipment Transmitter missing" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1780 }

gfailureToSwitchToProtection           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure To Switch to protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1790 }

gfailureToSwitchToProtectionRing      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure To Switch to protection Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1800 }

gfailureToSwitchToProtectionSpan      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure To Switch to protection Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1810 }

gfailureToSwitchToProtectionPath      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure to Switch to protection Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1820 }

gfanFailure
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "failure of cooling fan tray" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1830 }

gequipmentUnitPlugIn    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment unit plug in" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1840 }

gnePowerFailureAtConnector
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "NE Power Failure At Connector" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1850 }

gfuseAlarm
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "power failure Fuse Alarm" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1860 }

gsynchronizationUnitFailure              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "synchronization unit failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1870 }

gsynchronizationSwitchingEquipmentFailure          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "synchronization switching Equipment failure" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1880 }

gequipmentUnitUnplugged
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "equipment unit un plug" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1890 }

gloopback                 
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loop back" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1900 }

gds1LoopbackDueToFEACCommand
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback due to FEAC command DS1" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1910 }

gloopbackCommandSentToFarEndDS1
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback Command sent to Far End DS1" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1920 }

gds3LoopbackDueToFEACCommand          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback due to FEAC command DS3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1930 }

gds3LoopbackCommandSentToFarEnd
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback Command sent to Far End DS3" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1940 }

gds2LoopbackDueToFarEndCommand
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback due to Far End Command DS2" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1950 }

gds2LoopbackCommandSentToFarEnd
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loopback Command sent to Far End DS2" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1960 }

gfacilityLoopback
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loop back facility" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1970 }

gnetworkLoopback 
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loop back Network" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1980 }

gterminalLoopback
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "loop back Terminal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 1990 }

gmanuallyCausedAbnormalCondition        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manually caused abnormal condition" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2000 }

gethernetBridgeIsNewRootOfSpanningTree  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "new Root discovered in bridged network" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2010 }

gethernetBridgeTopologyChange        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "topology change discovered in bridged network" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2020 }

gnormalCondition          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "normal condition" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2030 }

gembeddedOperationsChannelFailureLinkDown        
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "embedded Operations Channel failure link down" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2040 }

gpeerStateMismatch       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "peer state mismatch" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2050 }

gproceduralError          
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "procedural Error" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2060 }

gimproperRemoval         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Improper Removal" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2070 }

gduplicateNodeID
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Duplicate Node ID" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2080 }

gblsrOutOfSync         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "BLSR out of sync" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2090 }

gblsrMultiNodeTableUpdateCompleted
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "BLSR tables resynchronized" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2100 }

gprotectionUnitNotAvailable             
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "protection unit not available" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2110 }

gperformanceMonitorThresholdCrossingAlert         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericThresholdMonitorType,
      cerentGenericThresholdLocation,
      cerentGenericThresholdPeriod,
      cerentGenericThresholdSetValue,
      cerentGenericThresholdCurrentValue,
      cerentGenericThresholdDetectType,
      cerentGenericAlarmSeverity,
      cerentGenericAlarmStatus,
      cerentGenericAlarmServiceAffecting
    }
    STATUS current 
    DESCRIPTION "performance Monitor Threshold Crossing Alert" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2120 }

gprotectionSwitch
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "occurrence of a protection switching event" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2130 }

grecoveryOrServiceProtectionActionHasBeenInitiated             
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "recovery or service protection action has been initiated" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2140 }

gautomaticSystemReset    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic system Reset" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2150 }

gautomaticUPSRSwitchCausedByAIS      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by AIS" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2160 }

gautomaticUPSRSwitchCausedByLOP      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by Lop" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2170 }

gautomaticUPSRSwitchCausedByUNEQ
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by Uneq" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2180 }

gautomaticUPSRSwitchCausedByPDI      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by PDI" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2190 }

gautomaticUPSRSwitchCausedBySFBER
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by Sfber" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2200 }

gautomaticUPSRSwitchCausedBySDBER
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "automatic UPSR switch caused by Sdber"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2210 }

gcoldRestart              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "cold Restart" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2220 }

gforcedSwitchBackToWorking
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched to working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2230 }

gforcedSwitchBackToWorkingRing
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched to working Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2240 }

gforcedSwitchBackToWorkingSpan
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched to working Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2250 }

gforcedSwitchToProtection
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched protection unit" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2260 }

gforcedSwitchToProtectionRing
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched protection unit Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2270 }

gforcedSwitchToProtectionSpan
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched protection unit Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2280 }

gworkingFacilityOrEquipmentForcedToSwitchToProtectionPath
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt forced switched protection unit Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2290 }

ginitializationInitiated      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "initialization initiated" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2300 }

glockoutOfProtection         
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of Protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2310 }

glockoutOfProtectionRing    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of Protection Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2320 }

glockoutOfProtectionSpan    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of Protection Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2330 }

glockoutOfProtectionPath    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of Protection Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2340 }

glockoutOfWorking            
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2350 }

glockoutOfWorkingRing       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of working Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2360 }

glockoutOfWorkingSpan       
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "lockout of working Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2370 }

gmanualSystemReset           
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual system Reset" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2380 }

gmanualSwitchToInternalClock
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual switch to internal clock" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2390 }

gmanualSwitchToPrimaryReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Primary refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2400 }

gmanualSwitchToSecondReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Second reference" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2410 }

gmanualSwitchToThirdReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Third refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2420 }

gmanualSwitchToFourthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Fourth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2430 }

gmanualSwitchToFifthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Fifth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2440 }

gmanualSwitchToSixthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manual Switch To Sixth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2450 }

gmanualSwitchBackToWorking
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of working facility or eqpt to protection Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2460 }

gmanualSwitchBackToWorkingRing
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of working facility or eqpt to protection Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2470 }

gmanualSwitchBackToWorkingSpan
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of working facility or eqpt to protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2480 }

gmanualSwitchToProtection
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of Working facility or eqpt to Protection unit" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2490 }

gmanualSwitchToProtectionRing
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt manualSwitch to Protection unit Ring" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2500 }

gmanualSwitchToProtectionSpan
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "working facility or eqpt manualSwitch to Protection unit Span" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2510 }

gmanualSwitchOfWorkingFacilityOrEquipmentToProtectionPath
NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "manualSwitch of working facility or eqpt to Protection Path" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2520 }

gpowerfailRestart
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Powerfail Restart" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2530 }

gringIsSquelchingTraffic     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "ring is squelching traffic" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2540 }

gsoftwareDownloadInProgress  
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "software download in progress"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2550 }

gswitchToInternalClock
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Internal clock" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2560 }

gswitchToPrimaryReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Primary refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2570 }

gswitchToSecondReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Second refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2580 }

gswitchToThirdReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Third refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2590 }

gswitchToFourthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Fourth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2600 }

gswitchToFifthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Fifth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2610 }

gswitchToSixthReference
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switch To Sixth refernce" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2620 }

gsystemReboot    
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "system reboot" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2630 }

gswitchedBackToWorking      
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switched Back To Working" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2640 }

gswitchedToProtection
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Switched To Protection" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2650 }

gwarmRestart     
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "warm Restart" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2660 }

gringIsInWaitToRestoreState
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Ring is in Wait To Restore state" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2670 }

gmanualSwitchRequest              
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Manual Switch Request" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2680 }

gforcedSwitchRequest               
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Forced Switch Request" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2690 }

glockoutSwitchRequest
  NOTIFICATION-TYPE 
    OBJECTS { 
      cerentGenericNodeTime, 
      cerentGenericAlarmState,
      cerentGenericAlarmObjectType, 
      cerentGenericAlarmObjectIndex,
      cerentGenericAlarmSlotNumber, 
      cerentGenericAlarmPortNumber, 
      cerentGenericAlarmLineNumber,
      cerentGenericAlarmObjectName,
      cerentGenericAlarmSeverity,
      cerentGenericAlarmStatus,
      cerentGenericAlarmServiceAffecting
    }
    STATUS current 
    DESCRIPTION "Lockout Switch Request" 
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2700 } 

grmonHistoriesAndAlarmsResetReboot
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RMON histories and alarms have been reset due to chipset reboot"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2710 }

grmonThresholdCrossingAlarm
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
   }
   STATUS current
    DESCRIPTION "Crossing of Falling/Rising Threshold detected"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2720 }

galarmsSuppressedByUserCommand
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarms Suppressed By User Command"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2730 }

galarmsSuppressedForMaintenance
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarms Suppressed For Maintenance"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2740 }

gswitchingMatrixModuleFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Switching Matrix Module Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2750 }

glanConnectionPolarityReversed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Lan Connection Polarity Reversed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2760 }

gautonomousPMReportMessageInhibited
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Autonomous Performance Monitoring Report Message Inhibited"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2780 }

gioSlotToXCONCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "IO Slot To XCON Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2790 }

gstsPathTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "STS path trace identifier mismatch"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2800 }

gnePowerFailureAtConnectorA 
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "NE power failure at connector A"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2810 }

gnePowerFailureAtConnectorB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "NE power failure at connector B"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2820 }

gfreeMemoryOnCardVeryLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Free memory on the card is very low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2830 }

gfreeMemoryOnCardNearZero  
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Free memory on the card is near zero"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2840 }

gexerciseRequestOnRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercise Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2850 }

gexerciseRequestOnSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercise Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2860 }

gsquelchingPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Squelching Path: "

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2870 }

gextraTrafficPreempted
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extra Traffic Preempted."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2880 }

gfarEndLockoutOfWorkingRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Lockout of working - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2890 }

gfarEndLockoutOfWorkingSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Lockout of working - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2900 }

gfarEndLockoutOfProtectionRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Lockout of Protection - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2910 }

gfarEndLockoutOfProtectionAllSpans
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Lockout of Protection - All Spans."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2920 }

gfarEndWorkingFacilityForcedToSwitchToProtectionRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Working facility forced to switch to protection unit - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2930 }

gfarEndWorkingFacilityForcedToSwitchToProtectionSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Working facility forced to switch to protection unit - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2940 }

gfarEndManualSwitchOfWorkingFacilityToProtectionRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Manual Switch of Working facility to Protection unit - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2950 }

gfarEndManualSwitchOfWorkingFacilityToProtectionSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Manual Switch of Working facility to Protection unit - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2960 }

gfarEndExercisingRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Exercise Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2970 }

gfarEndExercisingSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Exercise Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2980 }

gfarEndBERThresholdPassedForSignalFailureRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End BER threshold passed for Signal Failure - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 2990 }

gfarEndBERThresholdPassedForSignalFailureSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End BER threshold passed for Signal Failure - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3000 }

gfarEndBERThresholdPassedForSignalDegradeRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End BER threshold passed for Signal Degrade - Ring."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3010 }

gfarEndBERThresholdPassedForSignalDegradeSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End BER threshold passed for Signal Degrade - Span."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3020 }

gapsChannelFarEndProtectionLineSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "APS Channel - Far End Protection Line Signal Degrade."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3030 }

gringSwitchIsActiveOnTheEastSide
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Switch is active on the East Side."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3040 }

gringSwitchIsActiveOnTheWestSide
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Switch is active on the West Side."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3050 }

gspanSwitchIsActiveOnTheEastSide
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span Switch is active on the East Side."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3060 }

gspanSwitchIsActiveOnTheWestSide
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span Switch is active on the West Side."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3070 }

guniDirectionalFullPassThroughIsActive
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Uni-directional Full Pass Through is active."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3080 }

gbiDirectionalFullPassThroughIsActive
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Bi-directional Full Pass Through is active."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3090 }

gkBytesPassThroughIsActive
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "K Bytes Pass Through is active."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3100 }

gringIsSegmented
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring is Segmented."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3110 }

gringTopologyIsUnderConstruction
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Topology is under construction."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3120 }

glockoutOfProtectionAllSpans
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Lockout of Protection - All Spans."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3130 }

gfarEndOfFiberIsProvisionedWithDifferentRingID
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far end of fiber is provisioned with different ring ID"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3140 }

gbothEndsOfFiberProvisionedAsEastOrBothAsWest    
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Both ends of fiber provisioned as East, or both as West"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3150 }

gsecurityInvalidLoginUsernameSeeAuditTrail
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS deprecated
    DESCRIPTION "Security: Invalid Login Username - See Audit Trail"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3160 }

gautonomousMessagesInhibited
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Autonomous messages inhibited"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3170 }

gtrafficStormOnLANLANTemporarilyDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Traffic storm on LAN. LAN temporarily disabled."

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3180 }

greptdbchgMessagesInhibited
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "REPT^DBCHG messages of TL1 inhibited"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3190 }

gsecurityUserIDHasExpired
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Security: user ID has expired"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3200 }

gpartialFanFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Partial Fan Failure"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3210 }
gforcedSwitchRequestOnRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Force switch request on Ring"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3220 }

gforcedSwitchRequestOnSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Force switch request on Span"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3230 }

glockoutSwitchRequestOnRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Lockout switch request on Ring"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3240 }

glockoutSwitchRequestOnSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Lockout switch request on Span"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3250 }

gmanualSwitchRequestOnRing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manual switch request on Ring"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3260 }

gmanualSwitchRequestOnSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manual switch request on Span"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3270 }

gcommunicationFailurePeerToPeerSlotControlBusA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Peer to Peer Slot communication failure - Control Bus A"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3280 }

gcommunicationFailurePeerToPeerSlotControlBusB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Peer to Peer Slot communication failure - Control Bus B"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3290 }

gcontrollerAToShelfSlotCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Controller A to shelf slot communication failure"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3300 }

gcontrollerBToShelfSlotCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Controller B to shelf slot communication failure"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3310 }

ginterconnectionEquipmentFailureWorkingPayloadBus
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Interconnection Equipment Failure - Working Payload Bus"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3320 }

ginterconnectionEquipmentFailureProtectPayloadBus
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Interconnection Equipment Failure - Protect Payload Bus"

    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3330 }

ginhibitSwitchToProtectRequestOnEquipment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Inhibit Switch to Protect Request on equipment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3340 }

ginhibitSwitchToWorkingRequestOnEquipment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Inhibit Switch to Working Request on equipment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3350 }

gberThresholdExceededForSignalDegradeLine
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Degrade - Line"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3360 }

gberThresholdExceededForSignalDegradePath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Degrade - Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3370 }

gberThresholdExceededForSignalFailureLine
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold Exceeded For Signal Failure - Line"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3380 }

gberThresholdExceededForSignalFailurePath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold Exceeded For Signal Failure - Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3390 }

gexercisingRingSuccessfully
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercising Ring Successfully"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3400}

gexercisingSpanSuccessfully
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercising Span Successfully"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3410}

gspanIsInWaitToRestoreState
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span is in Wait To Restore state"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3420 }

gexerciseRequestOnRingFailed
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercise Ring Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3430 }

gexerciseRequestOnSpanFailed
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Exercise Span Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3440 }

gfarEndLockoutOfProtectionSpan
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far end Lockout of Protection Channel - Span"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3450 }

gmanufacturingDataMemoryEEPROMFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manufacturing EEPROM Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3460 }

greplaceableEquipmentOrUnitIsMissing
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Replaceable Equipment/Unit Is Missing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3470 }

gsoftwareDownloadFailed                  
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Software Download Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3480 }

gextraTrafficPCADropped
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extra Traffic Dropped"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3490 }

getherTxOversubscribed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "pkt loss due to oversubscribed xmit"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3500 }

getherRxOverSubscribed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "pkt loss due to oversubscribed rcv"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3510 }

getherTxExcessFlowCtrl
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "excessive ethernet flow ctl xmited"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3520 }

getherRxExcessFlowCtrl
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "excessive ethernet flow ctl recvd"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3530 }

gtransportLayerFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "transport layer failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3540 }

getherTxUnderrun
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ether hdge internal fifo underrun"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3550 }

gsynchronizationReferenceFrequencyOutOfBounds
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Synchronization reference frequency out of bounds."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3560 }

gntpOrSntpHostFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "NTP/SNTP Host Failure."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3570 }

gpeerCardNotResponding
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Peer Card Not Responding"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3580 }

galarmsAndEventsSuppressedForThisObject
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarms and events suppressed for this object"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3590 }

gds3FrameFormatMismatch
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DS3 Frame Format Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3600 }

gwaitToRestore
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Wait To Restore"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3610 }

gextremeHighVoltBatteryA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme High Volt Battery A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3620 }

gextremeLowVoltBatteryA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme Low Volt Battery A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3630 }

gextremeHighVoltBatteryB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme High Volt Battery B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3640 }

gextremeLowVoltBatteryB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme Low Volt Battery B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3650 }

giosConfigCopyFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "IOS config copy failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3660 }

giosConfigCopyInProgress
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "IOS config copy in progress"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3670 }

giosConfigCopySuccess
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "IOS Config Copy Success"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3680 }

-- Begin: UCP traps

gsignalingUnableToSetupCircuit
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Signaling Unable to setup circuit"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3710 }

gerrorInStartupConfig
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Error in Startup Config"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3712 }

gnoStartupConfig
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "No Startup Config"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3714 }

gneedToSaveRunningConfig
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Need to Save Running Config"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3716 }

ginvalidAlarm
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Alarm"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3718 }

grsvpHelloFSMToNeighborDown
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RSVP Hello FSM to Neighbor down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3720 }

gsecurityInvalidLoginUsername
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Security: Invalid Login - Username - See Audit Log"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3722 }

gdatabaseBackupFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Database Backup Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3724 }

gdatabaseRestoreFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Database Restore Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3726 }

glmpHelloFSMToControlChannelDown
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Hello FSM to Control Channel down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3730 }

glmpNeighborDiscoveryHasFailed
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Neighbor Discovery has failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3740 }

gunauthorizedIncomingSignalingRequest
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unauthorized incoming signaling request"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3750 }

gauditLog80PercentFull
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Audit Log 80 Percent Full"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3760 }

gmoduleCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Module Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3762 }

gauditLog100PercentFullOldestRecordsWillBeLost
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Audit Log 100 Percent Full - Oldest records will be lost"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3764 }

gstandbyDatabaseOutOfSync
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Standby Database Out of Sync"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3766 }

gredundantPowerCapabilityLost
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Redundant Power Capability Lost"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3768 }

-- End: UCP traps

gforcedSwitchToPrimaryReference
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Primary Reference"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3770 }

gforcedSwitchToSecondReference
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Second Reference"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3780 }

gforcedSwitchToThirdReference
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Third Reference"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3790 }

gforcedSwitchToInternalClock
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Internal Clock"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3800 }

gindustrialHighTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Industrial High Temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3805 }

gimproperMatrixEquipmentInserted
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Improper matrix equipment inserted"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3810 }

geqptProblemOnCarrierOrPIM
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EQPT problem on Carrier or PIM"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3820 }

geqptProblemOnPIMOrPPM
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EQPT problem on PIM or PPM"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 3830 }


-- Begin: SDH traps

gtimSectionTraceIdentifierMismatchFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "TIM Section - Trace Identifier Mismatch Failure."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4000 }

gaisMultiplexSectionAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Multiplex Section - Alarm Indication Signal."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4010 }

grdiMultiplexSectionRemoteDefectOrAlarmIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Multiplex Section - Remote Defect Indication."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4020 }

gtimHighOrderTraceIdentifierMismatchFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH High Order - Trace Identifier Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4030 }

gaisAdministrationUnitAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Administration Unit - Alarm Indication Signal."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4040 }

glopAdministrationUnitLossOfPointer
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Administration Unit - Loss of Pointer."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4050 }

gslmfUnequippedHighOrderPathUnequipped
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH SLMF High Order - Unequipped Path."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4060 }

gslmfPLMHighOrderPathLabelMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH SLMF High Order - Path Label Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4070 }

grdiHighOrderRemoteDefectOrAlarmIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH High Order - Remote Defect Indication."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4080 }

glopTributaryUnitLossOfPointer
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Tributary Unit - Loss of Pointer."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4090 }

gaisTributaryUnitAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Tributary Unit - Alarm Indication Signal."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4100 }

gslmfUnequippedLowOrderPathUnequipped
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Low Order - SLMF Unequipped Path."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4110 }

gslmfPLMLowOrderPathLabelMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Low Order - SLMF Path Label Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4120 }

gtimLowOrderTraceIdentifierMismatchFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Low Order - Trace Identifier Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4130 }

grfiLowOrderRemoteFailureOrAlarmIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Low Order - Remote Failure Indication."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4140 }

gg811PrimaryReferenceClockTraceable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "G811 - Primary Reference Clock traceable."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4150 }


gg812TransitNodeClockTraceable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "G812 - Transit Node Clock traceable."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4160 }

gg812LocalNodeClockTraceable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "G812 - Local Node Clock traceable."    
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4170 }

gg813SynchronousEquipmentTimingSourceTraceable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "G813 - Synchronous Equipment Timing Source traceable."    
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4180 }

ge1LoopbackDueToFEACCommand
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "loopback due to FEAC Command E1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4190 }

ge1LoopbackCommandSentToFarEnd
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "loopback Command sent to Far End E1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4200 }
 
ge3LoopbackDueToFEACCommand
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "loopback due to FEAC Command E3"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4210 }

gfarEndMultipleE1LOSDetectedOnE3
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end Multiple E1 LOS detected on E3"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4220 }

gfarEndE1EqptFailNonServiceAffecting
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end E1 eqpt fail non service affecting"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4230 }

gfarEndE1EqptFailServiceAffecting
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end E1 eqpt fail service affecting"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4240 }


gfarEndSingleE1LOS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end Single E1 LOS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4250 }

gfarEndE3EqptFailServiceAffecting
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end E3 eqpt fail service affecting"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4260 }
 
ge3LoopbackCommandSentToFarEnd
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "loopback Command sent to Far End E3"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4270 }

gfarEndE3EqptFailNonServiceAffecting
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "far end E3 eqpt fail non service affecting"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4280 }

glowVoltBatteryA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Volt - Battery A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4290 }

ghighVoltBatteryA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Volt - Battery A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4300 }

glowVoltBatteryB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Volt - Battery B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4310 }

ghighVoltBatteryB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Volt - Battery B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4320 }

gmsspRingOutOfSync
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "MS-SP ring out of sync"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4330 }

gmsspMultiNodeTableUpdateCompleted
NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "MS-SP ring tables resynchronized"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4340 }

gautomaticSNCPSwitchCausedByAIS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by AIS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4350 }

gautomaticSNCPSwitchCausedByLOP
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by Lop"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4360 }

gautomaticSNCPSwitchCausedByUNEQ
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by Uneq"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4370 }
 
gautomaticSNCPSwitchCausedByPDI
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by PDI"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4380 }

gautomaticSNCPSwitchCausedBySFBER
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by Sfber"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4390 }

gautomaticSNCPSwitchCausedBySDBER
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "automatic SNCP switch caused by Sdber"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4400 }

gstmConcatenationError
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "concatenation error STM"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4410 }

ge3IdleCondition
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "idle Condition E3"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4420 }

gchannelMSSPInconsistentAPSCode
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP inconsistent APS code"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4430 }

gchannelMSSPImproperAPSCodeAPS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP Improper APS code APS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4440 }

gchannelMSSPNodeIdMismatchAPS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP Node Id Mismatch APS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4450 }

gchannelMSSPDefaultKAPS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP Default K APS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4460 }

gchannelMSSPConnectionLossAPS
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "channel MSSP Connection loss APS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4470 }

gminimumClockTraceableSDH
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Minimum clock Traceable"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4480 }

glineIsInWaitToRestoreStateSDH
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH line is in Wait To Restore state "
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4490 }

gberThresholdExceededForSignalDegradeHighOrder
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Degrade - High Order"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4500 }

gberThresholdExceededForSignalFailureHighOrder
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Failure - High Order"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4510 }

gberThresholdExceededForSignalDegradeLowOrder
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Degrade - Low Order"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4520 }

gberThresholdExceededForSignalFailureLowOrder
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold exceeded for Signal Failure - Low Order"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4530 }

gfailureToSwitchToProtectionHighOrderPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Failure To Switch To Protection - High Order Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4540 }

gfailureToSwitchToProtectionLowOrderPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Failure To Switch To Protection - Low Order Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4550 }
    
glofAdministrationUnitLossOfMultiFrame
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH Administration Unit Loss of Multiframe."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4560 }

gsdhSpanIsInWaitToRestoreState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SDH span is in Wait To Restore state"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4570 }

ga8b10bOutOfSync
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "8B10B Out of Sync"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4755 }

godukPMAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4760 }

gotukAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4765 }

gotukSMBackwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4770 }

gfecUncorrectedWord
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "FEC Uncorrected Word"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4780 }

ggccTerminationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4785 }

gotukIncomingAlignmentError
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Incoming Alignment Error"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4790 }

godukLockedDefectPM
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: Locked Defect PM"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4795 }

glossOfMultiFrame
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Multi-Frame"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4800 }

godukOpenConnectionIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: Open Connection Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4805 }

gpayloadTypeIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Type Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4810 }

godukTrailTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: Trail Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4815 }

gotukTrailTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Trail Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4820 }

gequipmentHighLaserBias
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Laser Bias"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4825 }

gequipmentHighLaserTemp
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Laser Temp"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4830 }

gequipmentHighLaserPeltier
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Laser Peltier"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4835 }

gfacilityHighRxPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Facility High Rx power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4840 }

gequipmentHighTxPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Tx power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4845 }

gequipmentHighTransceiverVoltage
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Transceiver voltage"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4850 }

gequipmentLowLaserBias
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Laser Bias"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4855 }

gequipmentLowLaserTemp
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Laser Temp"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4860 }

gequipmentLowLaserPeltier
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Laser Peltier "
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4865 }

gfacilityLowRxPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Facility Low Rx power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4870 }

gequipmentLowTxPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Tx power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4875 }

gequipmentLowTransceiverVoltage
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Transceiver voltage"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4880 }

gequipmentRxLocked
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Rx Locked"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4885 }

gequipmentSquelched
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Squelched"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4890 }

gequipmentTxLocked
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Tx Locked"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4895 }

gotukSignalFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUK Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4900 }

godukSignalFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUK Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4905 }

gotukSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUK Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4910 }

godukSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUK Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4915 }

gpluggablePortMissing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Pluggable Port missing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4920 }

gpluggablePortRateMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Pluggable Port rate mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4925 }

gpluggablePortSecurityCodeMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Pluggable Port security code mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4930 }

gtciNotSelected
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Tci not selected"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4935 }

gtci1ClockFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Tci 1 Clock Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4940 }

godukPMBackwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: PM Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4945 }

godukTCM1BackwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: TCM1 Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4950 }

godukTCM2BackwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk: TCM2 Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4955 }

gequipmentHighRxTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment High Rx temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4960 }

gequipmentLowRxTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Low Rx temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4965 }

gtci2ClockFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Tci 2 Clock Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4970 }

gequipmentWavelengthMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Wavelength Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4975 }

gdspCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DSP Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4980 }

gdspFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DSP Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 4985 }
glaserApproachingEndOfLife
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Approaching End of Life"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5000 }

gcrossconnectLoopback
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Cross-connect Loopback"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5010 }

gadminLogoutOfUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Admin Logout of User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5020 }

guserLockedOut
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "User Locked Out"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5030 }

gadminLockoutOfUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Admin Lockout of User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5040 }

gadminLockoutClear
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Admin Lockout Clear"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5050 }

ginvalidLoginUsername
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Login: Username"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5060 }

gsecurityInvalidLoginPassword
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Login: Password"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5070 }

gsecurityInvalidLoginLockedOut
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Login: Locked Out"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5080 }

gsecurityInvalidLoginAlreadyLoggedOn
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid Login: Already Logged On"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5090 }

gloginOfUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Login of User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5100 }

gautomaticLogoutOfIdleUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Logout of IdleUser"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5110 }

glogoutOfUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Logout of User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5120 }

genhancedRemoteFailureIndicationPathServer
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Enhanced Remote Failure Indication - Path - Server"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5200 }

genhancedRemoteFailureIndicationPathConnectivity
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Enhanced Remote Failure Indication - Path - Connectivity"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5210 }

genhancedRemoteFailureIndicationPathPayload
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Enhanced Remote Failure Indication - Path - Payload"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5220 }

gfirewallHasBeenDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Firewall Has Been Disabled"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5230 }

gsecurityIntrusionDetPwd
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Security Intrusion - Incorrect Password"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5240 }

gsecurityIntrusionDetUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Security Intrusion - Incorrect Username"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5250 }

    gconnectionEquipmentMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Connection Equipment Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5260 }

gdisableInactiveUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Disable Inactive User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5270 }

gdisableInactiveClear
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Disable Inactive Clear"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5280 }

gbatteryFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Battery Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5290 }

gextremeHighVolt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme High Volt"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5300 }

gextremeLowVolt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Extreme Low Volt"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5310 }

ghighVolt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Volt"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5320 }

glowVolt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Volt"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5330 }

gsuspendUser
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Suspend User"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5340 }

gsuspendUserClear
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Suspend User Clear"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5350 }

glineDccTerminationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Line DCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5360 }

gmultiplexSectionDccTerminationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Multiplex Section DCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5370 }

ggigaBitEthernetOutOfSync
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GigaBit Ethernet Out of Sync"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5380 }

gsequenceMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Sequence Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5390 }

glossOfAlignment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Alignment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5400 }

goutOfUseByAdministrativeCommand
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Out of Use - Administrative Command"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5410 }

goutOfUseTransportFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Out of Use - Transport Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5420 }

gvcatGroupDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VCAT Group Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5430 }

gvcatGroupDegraded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VCAT Group Degraded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5440 }

gvcatGroupIncomplete
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VCAT Group Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5450 }

galarmIndicationSignalInTX
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarm Indication Signal in TX"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5460 }

gremoteAlarmIndicationInTX
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Remote Alarm Indication in TX"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5470 }

gkByteAPSChannelFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Kbyte Channel Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5480 }

gapsInvalidMode
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "APS Invalid Mode"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5490 }

gipAddressAlreadyInUseWithinTheSameDccArea
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "IP address already in use within the same DCC Area"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5500 }

gnodeNameInUseWithinTheSameDccArea
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Node name already in use within the same DCC Area"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5510 }

grearPanelEthernetLinkRemoved
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Rear Panel Ethernet Link Removed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5520 }

gmanualSwitchToProtectResultedInNoTrafficSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manual Switch To Protect Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5530 }

gmanualSwitchBackToWorkingResultedInNoTrafficSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Manual Switch Back To Working Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5540 }

gforcedSwitchToProtectResultedInNoTrafficSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch To Protection Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5550 }

gforcedSwitchBackToWorkingResultedInNoTrafficSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forced Switch Back To Working Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5560 }

gduplicateSerialNumberDetectedOnAPluggableEntity
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Duplicate Serial number detected on a pluggable entity"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5570 }

glossOfSignalForOpticalChannel
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Incoming Payload Signal Absent"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5600 }

gencapsulationMismatchPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Encapsulation Type Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5610 }

gencapsulationMismatchVT
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Encapsulation Mismatch - VT"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5620 }

gencapsulationMismatchHighOrderPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Encapsulation Mismatch High Order - Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5630 }

gencapsulationMismatchLowOrderPath
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Encapsulation Mismatch Low Order - Path"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5640 }

ggfpUserPayloadMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP User Payload Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5650 }

ggfpFibreChannelDistanceExtensionMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Fibre Channel Distance Extension Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5660 }

ggfpFibreChannelDistanceExtensionBufferStarvation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Fibre Channel Distance Extension Buffer Starvation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5670 }



ggfpFibreChannelDistanceExtensionCreditStarvation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Fibre Channel Distance Extension Credit Starvation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5680 }

gautomaticWdmAnsFinished
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic WDM ANS Finished"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5690 }

ggfpClientSignalFailDetected
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Client Signal Fail Detected"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5700 }

ggfpLossOfFrameDelineation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Loss of Frame Delineation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5710 }

ggfpExtensionHeaderMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Extension Header Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5730 }

gincomingOverheadSignalAbsent
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Signal for Overhead"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5740 }

gopticalSafetyRemoteInterlockOn
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Safety Remote Interlock On"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5750 }

gautomaticPowerControlCorrectionSkipped
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Power Control Correction Skipped"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5770 }

gapcCannotSetValueDueToRangeLimits
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "APC cannot set value due to range limits"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5780 }

glcasVcgMemberTxSideInAddState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS VCG Member Tx Side In ADD State"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5790 }
    
gfarEndManualSwitchBackToWorkingSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Manual Switch Back to Working - Span"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5800 }

gfarEndForcedSwitchBackToWorkingSpan
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Far End Forced Switch Back to Working - Span"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5810 }

guniversalTransponderModuleHardwareFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Universal Transponder Module Hardware Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5820 }

guniversalTransponderModuleCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Universal Transponder Module Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5830 }

gpluginModuleRangeSettingsMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Plug-in Module Range Settings Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5840 }

glcasVcgMemberTxSideInDnuState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS VCG Member Tx Side In DNU State"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5850 }

glcasControlWordCrcCheckFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS Control Word CRC Check Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5860 }

glcasVcgMemberRxSideInFailState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS VCG Member Rx Side In FAIL State"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5870 }

gsignalLossOnDataInterface
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Signal Loss on Data Interface"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5880 }

gsynchronizationLossOnDataInterface
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Synchronization Loss on Data Interface"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5890 }

gportFAIL
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "PORT FAIL"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5900 }

gunreachablePortTargetPower
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unreachable port target power"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5910 }

gportAddPowerDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Port Add Power Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5920 }

gportAddPowerDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Port Add Power Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5930 }

gportAddPowerFailLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Port Add Power Fail Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5940 }

gportAddPowerFailHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Port Add Power Fail High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 5950 }


gautomaticPowerControlTerminatedOnManualRequest
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Power Control Terminated on Manual request"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6000 }

goduk1AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk-1: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6010 }

goduk2AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk-2: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6020 }

goduk3AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk-3: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6030 }

goduk4AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk-4: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6040 }

gtemperatureReadingMismatchBetweenSCCards
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Temperature Reading Mismatch Between SC Cards"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6050 }

gvoltageReadingMismatchBetweenSCCards
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Voltage Reading Mismatch Between SC Cards"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6060 }

galarmsSuppressedonOutOfGroupVcatMember
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Alarms Suppressed on Out-Of-Group VCAT Member"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6070 }

gblsrSoftwareVersionMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BLSR Software Version Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6080 }

goptimized1Plus1ApsPrimaryFacility
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optimized 1+1 APS Primary Facility"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6090 }

goptimized1Plus1ApsPrimarySectionMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optimized 1+1 APS Primary Section Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6100 }

goptimized1Plus1ApsInvalidPrimarySection
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optimized 1+1 APS Invalid Primary Section"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6110 }

gcompositeClockHighLineVoltage
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Composite Clock High Line Voltage"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6120 }

gberThresholdExceededForSignalDegradeVt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold Exceeded For Signal Degrade - VT"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6130 }

gberThresholdExceededForSignalFailureVt
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BER Threshold Exceeded For Signal Failure - VT"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6140 }

gspanLengthOutOfRange
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span Length Out of Range"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6150 }

gidleSignalCondition
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Idle Signal Condition"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6170 }

gidleSignalConditionInTx
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Idle Signal Condition in TX"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6180 }

gvtPathTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VT Path Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6190 }

glossOfFrameInTX
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Frame in TX"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6200 }

gprovisioningMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Provisioning Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6210 }

gsectionTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Section Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6220 }

gregeneratorSectionTraceIdentifierMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Regenerator Section Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6230 }

gswitchingMatrixModuleFailureWorking
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Switching Matrix Module Failure - Working"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6240 }

gswitchingMatrixModuleFailureProtect
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Switching Matrix Module Failure - Protect"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6250 }

gslotCommunicationDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Slot Communication Disabled"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6260 }

gsessionTimeLimitExpired
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Session Time Limit Expired"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6270 }

guserPasswordChangeRequired
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "User Password Change Required"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6280 }

gisisAdjacencyFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ISIS Adjacency Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6290 }

gmsspSoftwareVersionMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "MSSP Software Version Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6300 }

gremoteAuthenticationFailSeeAuditLog
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Remote Authentication Fail - See Audit Log"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6310 }

gillegalRouteAdditionToNetwork
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Illegal route addition to the Network"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6320 }

gringIsSquelchingStsTraffic
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Is Squelching STS Traffic"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6330 }

gringIsSquelchingVtTraffic
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Is Squelching VT Traffic"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6340 }

garchiveOfAuditLogFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Archival of Audit Log Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6350 }

grprWrapped
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Wrapped"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6360 }

gshelfCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Shelf Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6370 }

gduplicatedShelfIdentifier
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Duplicated Shelf Identifier"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6380 }

gsoftwareMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Software Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6390 }

glmpFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6400 }

gopticalTerminationIncomplete
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Termination Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6410 }

gforwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Forward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6420 }

gpayloadMissingIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Missing Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6430 }

gspanMeasurementCannotBePerformed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Span loss not checked"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6440 }

gringIsSquelchingHighOrderTraffic
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Is Squelching Higher Order Traffic"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6450 }

gringIsSquelchingLowOrderTraffic
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Is Squelching Lower Order Traffic"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6460 }

gbadPacketCountExceedsThreshold
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Bad Packet Count Exceeds Threshold"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6470 }

glinkLayerKeepAliveFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Link Layer Keep-Alive Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6480 }

gautonegotiationRemoteFailureIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Auto-Negotiation Remote Failure Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6490 }

gtrailSignalFail
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Trail Signal Fail"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6500 }

gds1LoopbackCommandSentToFarEnd
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DS1 Loopback Command Sent To Far End"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6510 }

gmultiplexSectionSignalDegraded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Multiplex Section - Signal Degraded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6520 }

gmultiplexSectionExcessiveErrors
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Multiplex Section - Excessive Errors"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6530 }

ghighOrderPathSignalDegraded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Order Path - Signal Degraded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6540 }

ghighOrderPathExcessiveErrors
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Order Path - Excessive Errors"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6550 }

glowOrderPathSignalDegraded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Order Path - Signal Degraded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6560 }

glowOrderPathExcessiveErrors
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Low Order Path - Excessive Errors"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6570 }

gregeneratorSectionDccTerminationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Regenerator Section - DCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6580 }

gnetworkMemoryPoolLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Network Memory Pool Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6590 }

gospfRoutingTableOverflow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OSPF Routing Table Overflow"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6600 }

gautoLaserShutdownDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Auto Laser Shutdown Disabled"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6610 }

gwavelengthOutOfLock
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Wavelength Out of Lock"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6620 }

grprProtectionIsActive
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Protection Is Active"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6630 }

gmaxRPRStationNumberExceeded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Max RPR Station Number Exceeded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6640 }

grprProtectionConfigurationMismatched
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Protection Configuration Mismatched"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6650 }

greservedBandwidthLinkRateExceededOnRinglet0
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Reserved Bandwidth Link Rate Exceeded On Ringlet0"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6660 }

greservedBandwidthLinkRateExceededOnRinglet1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Reserved Bandwidth Link Rate Exceeded On Ringlet1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6670 }

grprInterfaceInPassThroughMode
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Interface In Pass Through Mode"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6680 }

grprPeerNodeIsMissing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Peer Node is Missing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6690 }

grprRiFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR RI Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6700 }

grprSignalFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6710 }

grprSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6720 }

ginterlinkFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ADM Peer Cards Interlink Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6730 }

gapcWrongGain
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "APC Wrong Gain Set Point"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6740 }

grprSpanMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "RPR Span Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6750 }

gefmRemoteFaultIndicationCriticalEvent
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Remote Fault Indication- Critical Event"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6760 }

gefmRemoteFaultIndicationDyingGasp
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Remote Fault Indication- Dying Gasp"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6770 }

gefmRemoteFaultIndicationLinkFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Remote Fault Indication- Link Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6780 }

gefmLinkMonitoringErroredSymbolPeriodEvent
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Link Monitoring- Errored Symbol Period Event"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6790 }

gefmLinkMonitoringErroredFrameEvent
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Link Monitoring- Errored Frame Event"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6800 }

gefmLinkMonitoringErroredFramePeriodEvent
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Link Monitoring- Errored Frame Period Event"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6810 }

gefmLinkMonitoringErroredFrameSecondsSummary
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Link Monitoring- Errored Frame Seconds Summary"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6820 }

gefmRemoteLoopbackRequestFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Remote Loopback Request Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6830 }

gfastAutomaticProtectionSwitching
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Fast Automatic Protection Switching"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6840 }

gfastAutomaticProtectionSwitchingConfigMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Fast Automatic Protection Switching Config Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6850 }

glcasSinkGroupError
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS Sink Group Error"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6860 }

glcasVcgMemberRxSideInDnuState
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LCAS VCG Member Rx Side In DNU State"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6870 }

gfcDistanceExtFuncNotEstablished
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION " Fibre Channel Distance Extension Function Not Established"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6880 }

gnonCiscoPPMInserted
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Non Cisco PPM Inserted"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6890 }

gunqualifiedPPMInserted
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unqualified PPM Inserted"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6900 }

gftaMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "FanTray Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6910 }

gcardPortsUnableToProvideProtection
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Card/Ports Unable To Provide Protection"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6920 }

glmpSignalDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6930 }

glmpSignalFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6940 }

glmpUnallocatedDataLink
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "LMP Unallocated Data Link"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6950 }

gfrontPortLinkLoss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "TCC Front Port Link Loss"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6960 }

gbertEnbl
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BERT Enabled "
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6970 }

gbertSyncFail
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "BERT Synchronization Status Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6975 }

gworkQueueFull
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Work Queue Full"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 6980 }

gequipmentPowerFailureAtConnectorA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure At Connector A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7000 }

gequipmentPowerFailureAtConnectorB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure At Connector B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7005 }

gequipmentPowerFailureAtReturnConnectorA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure At Return Connector A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7010 }

gequipmentPowerFailureAtReturnConnectorB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure At Return Connector B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7015 }

gloginFailThresholdExceeded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Invalid login attempt threshold exceeded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7020 }

gconnectionIdMismatchOnMatrixA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Connection ID mismatch on Matrix A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7025 }

gconnectionIdMismatchOnMatrixB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Connection ID mismatch on Matrix B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7030 }

gmanufacturingEepromFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS deprecated 
    DESCRIPTION "Manufacturing data memory (EEPROM) failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7035 }

gequipmentFailureHighTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment failure high temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7040 }

glaserBiasCurrentHigh                         
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser bias current high"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7045 }

ghighLaserTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High laser temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7050 }

gbridgeAndRollHasOccurred
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Bridge and Roll Has Occurred"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7055 }

gbridgeAndRollIsPendingAValidSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Bridge and Roll is Pending a Valid Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7060 }

gairFlow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS deprecated
    DESCRIPTION "Air Flow"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7065 }

gpartialFanFailurePartsFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Partial Fan Failure - Parts Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7070 }

gunprotectedSyncronizationEquipment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unprotected Synchronization Equipment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7075 }

gunprotectedMatrixEquipment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Unprotected Matrix Equipment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7080 }

gmatrixEquipmentUnavailable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Matrix Equipment Unavailable"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7085 }

gcontrolBusFailureTscA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Control Bus Failure - TSC A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7090 }

gcontrolBusFailureTscB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Control Bus Failure - TSC B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7095 }

gpayloadBusFailureMatrixA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Bus Failure - Matrix A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7100 }

gpayloadBusFailureMatrixB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Bus Failure - Matrix B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7105 }

gmatrixOperationSuspended
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Matrix Operation Suspended"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7110 }

gclockFailureTsc
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Clock Module Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7115 }

gpayloadLoopback
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loopback - Payload"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7120 }

gdccChannelLoss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DCC Channel Loss"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7125 }

greptPmMsgInhibited


  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Autonomous PM Report Message Inhibited"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7130 }

gloopbackCrs
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loopback - Cross Connect"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7135 }

gsyncRefFreqOutOfBound
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Synchronization Reference Frequency Out Of Bounds"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7140 }

gsystemUpgradeInProgress
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "System Upgrade In Progress"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7145 }

geqptFailToBoot
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Fails To Boot"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7150 }

geqptPowerFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Power Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7155 }

gclockBusFailureTscA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Clock Bus Failure - Shelf Controller A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7160 }

gclockBusFailureTscB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Clock Bus Failure - Shelf Controller B"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7165 }

gpowerFuseFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Power Fuse Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7170 }

gcontrolCommunicationsEquipmentFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Control Communication Equipment Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7175 }

gdifferentSoftwareVersion
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Different Software Version"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7180 }

gospfHelloFail
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OSPF Hello Fail"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7185 }

gclockModuleFrequencyMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Clock Module Frequency Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7190 }

getherPortSwitch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "TSC switched to alternate ethernet port"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7195 }

gopenIOSlots
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Open IO Slot(s)"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7200 }

gequipmentBootInProgress
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment boot in-progress."
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7205 }

glossOfClockFromMateShelfController
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Clock from mate Shelf Controller"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7210 }

gvirtualLanAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Virtual Lan AIS"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7225 }

gdcuLossFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "DCU Loss Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7230 }

gochncMaintenance
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OCHNC Maintenance"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7235 }

gramanLaserShutdown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Raman Laser Shutdown"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7240 }

glosOfRamanSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss Of Raman Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7245 }

gmcastMacTableFull
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Multicast Mac Address Table Full"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7250 }

gmulticastMacAddressAliasing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Multicast Mac Address Aliasing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7255 }

gramanPwrProtOn
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Raman Power Protection On"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7260 }

gcppPeerNotResponding
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "CPP Peer Not Responding"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7265 }

gvoaControlLoopDisableDueToExcessiveCounterPropagationLight
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VOA Control Loop Disable Due To Excessive Counter-Propagation Light"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7275 }

gwizardIsRunning
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Wizard Is Running"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7280 }

gramanGainNotReached
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Raman Span Not Tuned"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7285 }


gpprForwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "pprForwardDefectIndication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7295 }

gpprBackwardDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "pprBackwardDefectIndication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7300 }

gpprCoordinatedMaintenance
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "pprCoordinatedMaintenance"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7305 }

gpprTriggerThresholdBERExceeded
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "pprTriggerThresholdBERExceeded"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7310 }
glocalFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Local Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7315 }

gremoteFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Remote Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7320 }

gefmRemoteLoopbackConfigured
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Port In Remote Loopback"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7325 }

gefmPeerMissing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "EFM Link To Peer Missing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7330 }

geqptDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Equipment Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7335 }

gexcessiveBackPropagation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Excessive Back Propagation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7340 }

gremoteMaintenanceEndPointIsDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "CFM Remote Maintenance End Point Is Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7345 }

gcrossConnectedCFMService
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Cross Connected CFM Service"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7350 }

gcfmLoop
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "CFM Loop"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7355 }

gcfmConfigurationError
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "CFM Configuration Error"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7360 }

goutOfChannelGroupBundle
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Out Of Channel Group Bundle"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7365 }

grepNeighborAdjacencyFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "REP Neighbor Adjacency Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7370 }

grepLinkFlapping
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "REP Link Flapping"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7375 }

gfaultInREPSegment
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Fault In REP Segment"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7380 }

gprimaryREPEdgePortElected
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Primary REP Edge Port Elected"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7385 }

gsecondaryREPEdgePortElected
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Secondary REP Edge Port Elected"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7390 }

gstcnREPGenerated
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "STCN REP Generated"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7395 }

gvlbREPActivated
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VLB REP Activated"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7400 }

gvlbREPTriggerSoakingDelayActive
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "VLB REP Trigger Soaking Delay Active"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7405 }


gwanSyncloss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ethernet Syncloss On WAN Port"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7410 }

glaserShutdownDueToWavelengthDrift
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "laser Shutdown Due To Wavelength Drift"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7415 }

gmanualLaserRestart
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "manual Laser Restart"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7420 }

glaserShutdownDueToNonCiscoPPMInserted
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "laserShutdownDueToNonCiscoPPMInserted"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7425 }

gethernetOSCTerminationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ethernet OSC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7430 }

gsoftwareSignatureVerificationFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "software Signature Verification Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7445 }

gprotectVolumeSoftwareSignatureVerificationFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Volume Software Signature Verification"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7450 }
	
gactiveVolumeSoftwareSignatureVerificationFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Active Software Signature Verification Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7455 }
	
gpeerPortClientSignalFailDetected
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Peer Port Client Signal Fail Detected"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7460 }
	
gchannelShutdownDuetoWavelengthDrift
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Channel Shutdown Due to Wavelength Drift "
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7465 }

gusbWriteFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "USB Write Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7475 }

gusbSyncInProgress
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "USB Sync in Progress"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7480 }
	
gautoSensingUnableToDetectValidPayload
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Auto-Sensing Unable To Detect Valid Payload"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7485 }

gpayloadAutoSensingInProgress
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Auto-Sensing In Progress"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7490 }
	
ggfpClientSignalFailDetectedDueToSigloss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Client Signal Fail Detected Due To Sigloss"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7495 }

ggfpClientSignalFailDetectedDueToSyncloss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "GFP Client Signal Fail Detected Due To Syncloss"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7500 }

gpmdDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "PMD Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7510 }

gstandbyTccNEClockIsInternalClock
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Standby Tcc NE Clock Is Internal Clock"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7515 }

gchromaticDispersionValue
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "chromatic Dispersion Value"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7520 }

gpacketTransportServiceFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "packetTransportServiceFailed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7525 }

gsatellitePanelDiscoveryFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel Discovery Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7530 }

gsatellitePanelActiveLinkFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel Active Link Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7535 }

gsatellitePanelCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7540 }

gsatellitePanelImproperConfiguration
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel Improper Configuration"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7545 }

gsatellitePanelFanMismatchOfEquipmentAndAttributes
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel Fan Mismatch Of Equipment And Attributes"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7550 }

gsatellitePanelFanFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel Fan Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7555 }

gsatellitePanelPartialFanFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel Partial Fan Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7560 }

gsatellitePanelFANManufacturingDataMemoryEEPROMFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel FAN Manufacturing Data Memory (EEPROM) Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7565 }

gsatellitePanelFANUnitIsMissing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel FAN Unit Is Missing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7570 }

gsatellitePanelIndustrialHighTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel Industrial High Temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7575 }

gsatellitePanelHighTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel High Temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7580 }

gsatellitePanelBatteryFailureA
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Satellite Panel Battery Failure A"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7585 }

gplannedSwitchOver
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Planned Switch Over"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7590 }

gprotectionCardConfigurationMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "protection Card Configuration Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7595 }

grouterProcessorSwitchOver
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Router Processor Switch Over"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7600 }

grunningLowOnResources
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Running Low On Resources"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7605 }

gnoMoreResourcesAreAvailable
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "No More Resources Are Available"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7610 }

gesmcFailure
  NOTIFICATION-TYPE
      OBJECTS {
        cerentGenericNodeTime,
        cerentGenericAlarmState,
        cerentGenericAlarmObjectType,
        cerentGenericAlarmObjectIndex,
        cerentGenericAlarmSlotNumber,
        cerentGenericAlarmPortNumber,
        cerentGenericAlarmLineNumber,
        cerentGenericAlarmObjectName,
        cerentGenericAlarmSeverity,
        cerentGenericAlarmStatus,
        cerentGenericAlarmServiceAffecting
      }
      STATUS current
      DESCRIPTION "ESMC Failure"
      --#SUMMARY "%d Object:%d Index:%d Slot:%d Port:%d AID:%s"
      --#ARGUMENTS {$2, $3, $4, $5, $6, $8}
      --#GENERIC 6
      --#SOURCE_ID "A"
      --#TIMEINDEX 0
      ::= { cerentGenericV2Events 7615 }


glicenseWillExpireWithin24Hours
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "license Will Expire Within 24 Hours"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7620 }

glicenseWillExpireAnytimeAfter1DayButBefore14Days
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "license Will Expire Anytime After 1Day But Before 14 Days"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7625 }

glicenseIsExpired
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "license Is Expired"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7630 }

glicenseCountViolation
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "license Count Violation"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7635 }

gtemporaryLicenseIsInUse
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Temporary License Is In Use"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7640 }

gevaluationLicenseIsInUse
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Evaluation License Is In Use"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7645 }

glicenseIsMissing
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "License Is Missing"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7650 }

gpseudowireDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Pseudowire Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7655 }

gworkingPseudowireControlPlaneDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Pseudowire Control Plane Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7660 }

gprotectPseudowireControlPlaneDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Pseudowire Control Plane Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7665 }

gworkingPseudowireConnectivityCheckDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Pseudowire Connectivity Check Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7670 }

gprotectPseudowireConnectivityCheckDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Pseudowire Connectivity Check Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7675 }

gpseudowireTrafficSwitchedToPretection
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Pseudowire Traffic Switched To Pretection"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7680 }

gworkingPseudowireLocalAcTxPortFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Pseudowire Local AcTx Port Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7685 }

gprotectPseudowireLocalAcTxPortFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Pseudowire Local AcTx Port Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7690 }

gworkingPseudowireLocalAcRxPortFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Pseudowire Local AcRx Port Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7695 }

gprotectPseudowireLocalAcRxPortFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Pseudowire Local AcRx Port Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7700 }

gworkingPseudowireRemoteAcTxPortFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Pseudowire Remote AcTx Port Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7705 }

gprotectPseudowireRemoteAcTxPortFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Pseudowire Remote AcTx Port Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7710 }

gworkingPseudowireRemoteAcRxPortFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "working Pseudowire Remote AcRx Port Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7715 }

gprotectPseudowireRemoteAcRxPortFault
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Pseudowire Remote AcRx Port Fault"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7720 }

gslaThresholdCrossAlert
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SLA Threshold Cross Alert"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7725 }

gprotectLocalPseudowireNotForwarding
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Local Pseudowire Not Forwarding"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7730 }

gworkingRemotePseudowireNotForwarding   
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Remote Pseudowire Not Forwarding"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7735 }

gprotectRemotePseudowireNotForwarding     
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Remote Pseudowire Not Forwarding"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7740 }

gtpTunnelDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Tp Tunnel Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7745 }

gworkingLabelSwitchedPathDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Label Switched Path Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7750 }

gprotectLabelSwitchedPathDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Label Switched Path Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7755 }

gworkingLabelSwitchedPathAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Label Switched Path Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7760 }

gprotectLabelSwitchedPathAlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Label Switched Path Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7765 }

gworkingLabelSwitchedPathRemoteDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Label Switched Path Remote Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7770 }

gprotectLabelSwitchedPathRemoteDefectIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Label Switched Path Remote Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7775 }

gbidirectionalForwardDetectionDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Bidirectional Forward Detection Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7780 }

gtpTrafficSwitchedFromWorkingToProtection
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Tp Traffic Switched From Working To Protection"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7785 }

gworkingTpLockout
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "working Tp Lockout"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7790 }

gprotectTpLockout
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "protect Tp Lockout"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7795 }

gethernetFlowPointFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ethernet Flow Point Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7800 }

gteTunnelDown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "TE Tunnel Down"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7805 }

gmacSystemLimitReached
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "MAC System Limit Reached"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7810 }

gmacBridgeDomainLimitReached
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "MAC Bridge Domain Limit Reached"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7815 }

gautoSensingDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
	}
    STATUS current
	DESCRIPTION "Auto Sense Disabled"
	--#SUMMARY "%d Object:%d Index:%d Slot:%d Port:%d AID:%s"
	--#ARGUMENTS {$2, $3, $4, $5, $6, $8}
	--#GENERIC 6
	--#SOURCE_ID "A"
	--#TIMEINDEX 0
	::= { cerentGenericV2Events 7820 }

gsmBackwardIncomingAlignmentError
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "SM Backward Incoming Alignment Error"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7825 }

gresourceAllocationFailed
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Resource Allocation Failed"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7830 }
    
glossOfDFBSignal
  NOTIFICATION-TYPE
      OBJECTS {
        cerentGenericNodeTime,
        cerentGenericAlarmState,
        cerentGenericAlarmObjectType,
        cerentGenericAlarmObjectIndex,
        cerentGenericAlarmSlotNumber,
        cerentGenericAlarmPortNumber,
        cerentGenericAlarmLineNumber,
        cerentGenericAlarmObjectName,
        cerentGenericAlarmSeverity,
        cerentGenericAlarmStatus,
        cerentGenericAlarmServiceAffecting
      }
      STATUS current
      DESCRIPTION "loss Of DFB Signal"
      --#SUMMARY "%d Object:%d Index:%d Slot:%d Port:%d AID:%s"
      --#ARGUMENTS {$2, $3, $4, $5, $6, $8}
      --#GENERIC 6
      --#SOURCE_ID "A"
      --#TIMEINDEX 0
    ::= { cerentGenericV2Events 7835 }

gworkingLabelSwitchedPathLinkDownIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Label Switched Path Link Down Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7840 }

gprotectLabelSwitchedPathLinkDownIndication
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Label Switched Path Link Down Indication"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7845 }
	
gworkingLabelSwitchedPathLockReport
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Working Label Switched Path Lock Report"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7850 }

gprotectLabelSwitchedPathLockReport
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Protect Label Switched Path Lock Report"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7855 }

gsatellitePanelBatteryFailureB
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "satellite Panel Battery FailureB"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7860 }
    
ghighBitErrorRate
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "High Bit Error Rate"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7865 }
    
gbackPanelFacilityLoopback
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Back Panel Facility Loopback"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7870 }

gbackPanelTerminalLoopback
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Back Panel Terminal Loopback"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7875 }
    
gtrunkPayloadTypeMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Payload Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 7880 }
    
ginvalidMuxponderConfiguration
    NOTIFICATION-TYPE
        OBJECTS {
          cerentGenericNodeTime,
          cerentGenericAlarmState,
          cerentGenericAlarmObjectType,
          cerentGenericAlarmObjectIndex,
          cerentGenericAlarmSlotNumber,
          cerentGenericAlarmPortNumber,
          cerentGenericAlarmLineNumber,
          cerentGenericAlarmObjectName,
          cerentGenericAlarmSeverity,
          cerentGenericAlarmStatus,
          cerentGenericAlarmServiceAffecting
        }
        STATUS current
        DESCRIPTION "Invalid Muxponder Configuration"
        --#SUMMARY "%d Object:%d Index:%d Slot:%d Port:%d AID:%s"
        --#ARGUMENTS {$2, $3, $4, $5, $6, $8}
        --#GENERIC 6
        --#SOURCE_ID "A"
        --#TIMEINDEX 0
    ::= { cerentGenericV2Events 7885 }
    
gcoolingProfileMismatch 
  NOTIFICATION-TYPE
      OBJECTS {
        cerentGenericNodeTime,
        cerentGenericAlarmState,
        cerentGenericAlarmObjectType,
        cerentGenericAlarmObjectIndex,
        cerentGenericAlarmSlotNumber,
        cerentGenericAlarmPortNumber,
        cerentGenericAlarmLineNumber,
        cerentGenericAlarmObjectName,
        cerentGenericAlarmSeverity,
        cerentGenericAlarmStatus,
        cerentGenericAlarmServiceAffecting
      }
      STATUS current
      DESCRIPTION "Cooling Profile Mismatch"
      --#SUMMARY "%d Object:%d Index:%d Slot:%d Port:%d AID:%s"
      --#ARGUMENTS {$2, $3, $4, $5, $6, $8}
      --#GENERIC 6
      --#SOURCE_ID "A"
      --#TIMEINDEX 0
    ::= { cerentGenericV2Events 7890 }
    
gtrunkOduAlarmIndicationSignal
  NOTIFICATION-TYPE
        OBJECTS {
          cerentGenericNodeTime,
          cerentGenericAlarmState,
          cerentGenericAlarmObjectType,
          cerentGenericAlarmObjectIndex,
          cerentGenericAlarmSlotNumber,
          cerentGenericAlarmPortNumber,
          cerentGenericAlarmLineNumber,
          cerentGenericAlarmObjectName,
          cerentGenericAlarmSeverity,
          cerentGenericAlarmStatus,
          cerentGenericAlarmServiceAffecting
        }
        STATUS current
        DESCRIPTION "Trunk ODU: Alarm Indication Signal"
        --#SUMMARY "%d Object:%d Index:%d Slot:%d Port:%d AID:%s"
        --#ARGUMENTS {$2, $3, $4, $5, $6, $8}
        --#GENERIC 6
        --#SOURCE_ID "A"
        --#TIMEINDEX 0
    ::= { cerentGenericV2Events 7895 }
    
gcompanionCardMissing
  NOTIFICATION-TYPE
          OBJECTS {
            cerentGenericNodeTime,
            cerentGenericAlarmState,
            cerentGenericAlarmObjectType,
            cerentGenericAlarmObjectIndex,
            cerentGenericAlarmSlotNumber,
            cerentGenericAlarmPortNumber,
            cerentGenericAlarmLineNumber,
            cerentGenericAlarmObjectName,
            cerentGenericAlarmSeverity,
            cerentGenericAlarmStatus,
            cerentGenericAlarmServiceAffecting
          }
          STATUS current
          DESCRIPTION "Companion Card Missing"
          --#SUMMARY "%d Object:%d Index:%d Slot:%d Port:%d AID:%s"
          --#ARGUMENTS {$2, $3, $4, $5, $6, $8}
          --#GENERIC 6
          --#SOURCE_ID "A"
          --#TIMEINDEX 0
    ::= { cerentGenericV2Events 7900 }

gcontrolPlaneUnverifiedClearedAlarmsPresent
  NOTIFICATION-TYPE
          OBJECTS {
            cerentGenericNodeTime,
            cerentGenericAlarmState,
            cerentGenericAlarmObjectType,
            cerentGenericAlarmObjectIndex,
            cerentGenericAlarmSlotNumber,
            cerentGenericAlarmPortNumber,
            cerentGenericAlarmLineNumber,
            cerentGenericAlarmObjectName,
            cerentGenericAlarmSeverity,
            cerentGenericAlarmStatus,
            cerentGenericAlarmServiceAffecting
          }
          STATUS current
          DESCRIPTION "Control Plane Unverified Cleared Alarms Present"
          --#SUMMARY "%d Object:%d Index:%d Slot:%d Port:%d AID:%s"
          --#ARGUMENTS {$2, $3, $4, $5, $6, $8}
          --#GENERIC 6
          --#SOURCE_ID "A"
          --#TIMEINDEX 0
    ::= { cerentGenericV2Events 7905 }

gpowerConsumptionLimitHasCrossed
  NOTIFICATION-TYPE
          OBJECTS {
            cerentGenericNodeTime,
            cerentGenericAlarmState,
            cerentGenericAlarmObjectType,
            cerentGenericAlarmObjectIndex,
            cerentGenericAlarmSlotNumber,
            cerentGenericAlarmPortNumber,
            cerentGenericAlarmLineNumber,
            cerentGenericAlarmObjectName,
            cerentGenericAlarmSeverity,
            cerentGenericAlarmStatus,
            cerentGenericAlarmServiceAffecting
          }
          STATUS current
          DESCRIPTION "Power Consumption Limit Has Crossed"
          --#SUMMARY "%d Object:%d Index:%d Slot:%d Port:%d AID:%s"
          --#ARGUMENTS {$2, $3, $4, $5, $6, $8}
          --#GENERIC 6
          --#SOURCE_ID "A"
          --#TIMEINDEX 0
    ::= { cerentGenericV2Events 7910 }

gmasterKeyExchangeFailed
  NOTIFICATION-TYPE
          OBJECTS {
            cerentGenericNodeTime,
            cerentGenericAlarmState,
            cerentGenericAlarmObjectType,
            cerentGenericAlarmObjectIndex,
            cerentGenericAlarmSlotNumber,
            cerentGenericAlarmPortNumber,
            cerentGenericAlarmLineNumber,
            cerentGenericAlarmObjectName,
            cerentGenericAlarmSeverity,
            cerentGenericAlarmStatus,
            cerentGenericAlarmServiceAffecting
          }
          STATUS current
          DESCRIPTION "Master Key Exchange Failed"
          --#SUMMARY "%d Object:%d Index:%d Slot:%d Port:%d AID:%s"
          --#ARGUMENTS {$2, $3, $4, $5, $6, $8}
          --#GENERIC 6
          --#SOURCE_ID "A"
          --#TIMEINDEX 0
    ::= { cerentGenericV2Events 7915 }
    
gunitHighTemperature
  NOTIFICATION-TYPE
            OBJECTS {
              cerentGenericNodeTime,
              cerentGenericAlarmState,
              cerentGenericAlarmObjectType,
              cerentGenericAlarmObjectIndex,
              cerentGenericAlarmSlotNumber,
              cerentGenericAlarmPortNumber,
              cerentGenericAlarmLineNumber,
              cerentGenericAlarmObjectName,
              cerentGenericAlarmSeverity,
              cerentGenericAlarmStatus,
              cerentGenericAlarmServiceAffecting
            }
            STATUS current
            DESCRIPTION "Unit High Temperature"
            --#SUMMARY "%d Object:%d Index:%d Slot:%d Port:%d AID:%s"
            --#ARGUMENTS {$2, $3, $4, $5, $6, $8}
            --#GENERIC 6
            --#SOURCE_ID "A"
            --#TIMEINDEX 0
    ::= { cerentGenericV2Events 7930 }

goverTemperatureUnitProtected
  NOTIFICATION-TYPE
            OBJECTS {
              cerentGenericNodeTime,
              cerentGenericAlarmState,
              cerentGenericAlarmObjectType,
              cerentGenericAlarmObjectIndex,
              cerentGenericAlarmSlotNumber,
              cerentGenericAlarmPortNumber,
              cerentGenericAlarmLineNumber,
              cerentGenericAlarmObjectName,
              cerentGenericAlarmSeverity,
              cerentGenericAlarmStatus,
              cerentGenericAlarmServiceAffecting
            }
            STATUS current
            DESCRIPTION "Over Temperature Unit Protected"
            --#SUMMARY "%d Object:%d Index:%d Slot:%d Port:%d AID:%s"
            --#ARGUMENTS {$2, $3, $4, $5, $6, $8}
            --#GENERIC 6
            --#SOURCE_ID "A"
            --#TIMEINDEX 0
    ::= { cerentGenericV2Events 7935 }

gseqMismatchCount
  NOTIFICATION-TYPE
            OBJECTS {
              cerentGenericNodeTime,
              cerentGenericAlarmState,
              cerentGenericAlarmObjectType,
              cerentGenericAlarmObjectIndex,
              cerentGenericAlarmSlotNumber,
              cerentGenericAlarmPortNumber,
              cerentGenericAlarmLineNumber,
              cerentGenericAlarmObjectName,
              cerentGenericAlarmSeverity,
              cerentGenericAlarmStatus,
              cerentGenericAlarmServiceAffecting
            }
            STATUS current
            DESCRIPTION "Sequence Mismatch Count"
            --#SUMMARY "%d Object:%d Index:%d Slot:%d Port:%d AID:%s"
            --#ARGUMENTS {$2, $3, $4, $5, $6, $8}
            --#GENERIC 6
            --#SOURCE_ID "A"
            --#TIMEINDEX 0
    ::= { cerentGenericV2Events 7945 }

gkeyProgramOnAlteraFpgaFailed
  NOTIFICATION-TYPE
            OBJECTS {
              cerentGenericNodeTime,
              cerentGenericAlarmState,
              cerentGenericAlarmObjectType,
              cerentGenericAlarmObjectIndex,
              cerentGenericAlarmSlotNumber,
              cerentGenericAlarmPortNumber,
              cerentGenericAlarmLineNumber,
              cerentGenericAlarmObjectName,
              cerentGenericAlarmSeverity,
              cerentGenericAlarmStatus,
              cerentGenericAlarmServiceAffecting
            }
            STATUS current
            DESCRIPTION "Key Program On Altera FPGA Failed"
            --#SUMMARY "%d Object:%d Index:%d Slot:%d Port:%d AID:%s"
            --#ARGUMENTS {$2, $3, $4, $5, $6, $8}
            --#GENERIC 6
            --#SOURCE_ID "A"
            --#TIMEINDEX 0
    ::= { cerentGenericV2Events 7960 }

gduplicateNodeControllerDetected
  NOTIFICATION-TYPE
            OBJECTS {
              cerentGenericNodeTime,
              cerentGenericAlarmState,
              cerentGenericAlarmObjectType,
              cerentGenericAlarmObjectIndex,
              cerentGenericAlarmSlotNumber,
              cerentGenericAlarmPortNumber,
              cerentGenericAlarmLineNumber,
              cerentGenericAlarmObjectName,
              cerentGenericAlarmSeverity,
              cerentGenericAlarmStatus,
              cerentGenericAlarmServiceAffecting
            }
            STATUS current
            DESCRIPTION "Duplicate Node Controller Detected"
            --#SUMMARY "%d Object:%d Index:%d Slot:%d Port:%d AID:%s"
            --#ARGUMENTS {$2, $3, $4, $5, $6, $8}
            --#GENERIC 6
            --#SOURCE_ID "A"
            --#TIMEINDEX 0
    ::= { cerentGenericV2Events 7970 }

grestorationInProg
  NOTIFICATION-TYPE
            OBJECTS {
              cerentGenericNodeTime,
              cerentGenericAlarmState,
              cerentGenericAlarmObjectType,
              cerentGenericAlarmObjectIndex,
              cerentGenericAlarmSlotNumber,
              cerentGenericAlarmPortNumber,
              cerentGenericAlarmLineNumber,
              cerentGenericAlarmObjectName,
              cerentGenericAlarmSeverity,
              cerentGenericAlarmStatus,
              cerentGenericAlarmServiceAffecting
            }
            STATUS current
            DESCRIPTION "Restoration in Progress"
            --#SUMMARY "%d Object:%d Index:%d Slot:%d Port:%d AID:%s"
            --#ARGUMENTS {$2, $3, $4, $5, $6, $8}
            --#GENERIC 6
            --#SOURCE_ID "A"
            --#TIMEINDEX 0
    ::= { cerentGenericV2Events 7975 }

gramanPumpsCalibrationProcedureIsRunning
  NOTIFICATION-TYPE
            OBJECTS {
              cerentGenericNodeTime,
              cerentGenericAlarmState,
              cerentGenericAlarmObjectType,
              cerentGenericAlarmObjectIndex,
              cerentGenericAlarmSlotNumber,
              cerentGenericAlarmPortNumber,
              cerentGenericAlarmLineNumber,
              cerentGenericAlarmObjectName,
              cerentGenericAlarmSeverity,
              cerentGenericAlarmStatus,
              cerentGenericAlarmServiceAffecting
            }
            STATUS current
            DESCRIPTION "Raman Calibration Running"
            --#SUMMARY "%d Object:%d Index:%d Slot:%d Port:%d AID:%s"
            --#ARGUMENTS {$2, $3, $4, $5, $6, $8}
            --#GENERIC 6
            --#SOURCE_ID "A"
            --#TIMEINDEX 0
    ::= { cerentGenericV2Events 7980 }

gramanPumpsCalibrationIsScheduledToRunInTheNextMinutes
  NOTIFICATION-TYPE
            OBJECTS {
              cerentGenericNodeTime,
              cerentGenericAlarmState,
              cerentGenericAlarmObjectType,
              cerentGenericAlarmObjectIndex,
              cerentGenericAlarmSlotNumber,
              cerentGenericAlarmPortNumber,
              cerentGenericAlarmLineNumber,
              cerentGenericAlarmObjectName,
              cerentGenericAlarmSeverity,
              cerentGenericAlarmStatus,
              cerentGenericAlarmServiceAffecting
            }
            STATUS current
            DESCRIPTION "Raman Calibration Pending"
            --#SUMMARY "%d Object:%d Index:%d Slot:%d Port:%d AID:%s"
            --#ARGUMENTS {$2, $3, $4, $5, $6, $8}
            --#GENERIC 6
            --#SOURCE_ID "A"
            --#TIMEINDEX 0
    ::= { cerentGenericV2Events 7985 }

godukTCM1AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Alarm Indication Signal TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13100 }

godukTCM2AlarmIndicationSignal
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Alarm Indication Signal TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13105 }

godukLockedDefectTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Locked Defect - TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13110 }

godukLockedDefectTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Locked Defect - TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13115 }

gotukLossOfFrame
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "OTUk: Loss Of Frame"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13120 }

godukOpenConnectionIndicationTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Open Connection Indication TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13125 }

godukOpenConnectionIndicationTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Open Connection Indication TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13130 }

godukTrailTraceIdentifierMismatchTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Trail Trace Identifier Mismatch TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13135 }

godukTrailTraceIdentifierMismatchTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Trail Trace Identifier Mismatch TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13140 }

godukSignalFailureTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Signal Failure - TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13145 }

godukSignalFailureTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Signal Failure - TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13150 }

godukSignalDegradeTCM1
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Signal Degrade - TCM1"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13155 }

godukSignalDegradeTCM2
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "ODUk Signal Degrade - TCM2"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13160 }

glossOfChannel
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss of Channel"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13165 }

gfecMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "FEC Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13170 }

    gtimSectionMonitorTraceIdentifierMismatchFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "TIM Section Monitor - Trace Identifier Mismatch Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13175 }

gautomaticLaserShutdown
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Laser Shutdown"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13180 }

gshutterInsertionLossVariationDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Shutter Insertion Loss Variation Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13200 }

    gopticalChannelDeactivationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Channel de-activation failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13205 }

gshutterInsertionLossVariationDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Shutter Insertion Loss Variation Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13210 }

gnetworkTopologyIncomplete
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Network Topology Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13215 }

gpluginModuleCommunicationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Plug-in Module Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13220 }

gopticalNetworkTypeMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Network Type Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13225 }

gopticalPowerDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Power Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13230 }

gautomaticPowerControlFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Power Control Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13235 }

gopticalPowerDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Power Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13240 }

gautomaticPowerControlDisabled
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Automatic Power Control Disabled"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13245 }

gopticalPowerFailureLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Power Failure Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13250 }

gringIdMismatch
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Ring Id Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13255 }

gopticalPowerFailureHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Power Failure High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13260 }

glossOfContinuity
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Loss Of Continuity"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13270 }

gvariableOpticalAttenuatorDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Variable Optical Attenuator Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13280 }

gvariableOpticalAttenuatorDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Variable Optical Attenuator Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13290 }

gvariableOpticalAttenuatorFailureLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Variable Optical Attenuator Failure Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13300 }

gvariableOpticalAttenuatorFailureHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Variable Optical Attenuator Failure High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13310 }

glaserBiasDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Bias Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13320 }

glaserBiasFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "aser Bias Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13330 }

glaserTemperatureDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13340 }

gopticalAmplifierGainDegradeLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Gain Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13350 }

gopticalAmplifierGainDegradeHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Gain Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13360 }

gopticalAmplifierGainFailureLow
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Gain Failure Low"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13370 }

gopticalAmplifierGainFailureHigh
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Gain Failure High"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13380 }

gopticalChannelConnectionFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Channel connection failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13390 }

gopticalChannelIncomplete
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Channel Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13395 }

gopticalChannelActivationFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Channel activation failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13400 }

glaserAutoPowerReduction
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Laser Auto Power Reduction"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13410 }

gcaseTemperatureDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Case Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13420 }

gfiberTemperatureDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Fiber Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13430 }

gshutterOpen
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Shutter Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13440 }

gawgTemperatureDegrade
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "AWG Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13450 }

gawgTemperatureFailure
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "AWG Temperature Failure"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13460 }

gawgOverTemperature
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "AWG Over-Temperature"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13470 }

gopticalAmplifierInitialization
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Optical Amplifier Initialization"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13480 }

gawgWarmUp
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "AWG Warm Up"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13490 }

gincSigloss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Incoming Signal Loss on Fibre Channel Interface"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13510 }

gincSyncloss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Incoming Synchronization Loss on Fibre Channel Interface"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13515 }

gincGfpOutOfFrame
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Out Of Frame Detected by GFP Receiver"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13520 }

gincGfpSigLoss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Client Signal Loss Frames Detected by GFP Receiver"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13525 }

gincGfpSyncLoss
  NOTIFICATION-TYPE
    OBJECTS {
      cerentGenericNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName,
      cerentGenericAlarmSeverity,
      cerentGenericAlarmStatus,
      cerentGenericAlarmServiceAffecting
    }
    STATUS current
    DESCRIPTION "Client Sychronization Loss Frames Detected by GFP Receiver"
    --#SUMMARY "%d Object:%d Index:%d Slot:%d Port:%d AID:%s"
    --#ARGUMENTS {$2, $3, $4, $5, $6, $8}
    --#GENERIC 6
    --#SOURCE_ID "A"
    --#TIMEINDEX 0
    ::= { cerentGenericV2Events 13530 }

nodeGenericGroup OBJECT-GROUP
        OBJECTS { 
          cerentGenericSoftwareVersion }
        STATUS current
        DESCRIPTION
          "The group for node related objects"
        ::= { cerentGenericGroups 10 }
        
alarmGenericGroup OBJECT-GROUP
        OBJECTS {
          cerentGenericAlarmCount,
          cerentGenericAlarmObjectIndex,
          cerentGenericAlarmObjectType,
          cerentGenericAlarmSlotNumber,
          cerentGenericAlarmPortNumber,
          cerentGenericAlarmLineNumber,
          cerentGenericAlarmType,
          cerentGenericAlarmState,
          cerentGenericAlarmTimeStamp,
          cerentGenericAlarmObjectName,
          cerentGenericAlarmAdditionalInfo,
          cerentGenericAlarmSeverity,
          cerentGenericAlarmStatus,
          cerentGenericAlarmServiceAffecting
        }
        STATUS current
        DESCRIPTION
          "The group for node related objects"
        ::= { cerentGenericGroups 20 }
        
eventGenericGroup NOTIFICATION-GROUP
     NOTIFICATIONS {
       galarmUnknown,
       galarmCutoffIsInManualMode,
       gfailureDetectedExternalToTheNE,
       gexternalError,
       gexcessiveSwitching,
       gsdccTerminationFailure,
       gincomingFailureCondition,
       galarmIndicationSignal,
       galarmIndicationSignalLine,
       galarmIndicationSignalPath,
       galarmIndicationSignalVT,
       gapsChannelFailure,
       gchannelByteFailureAPS,
       gchannelProtectionSwitchingChannelMatchFailureAPS,
       gchannelAutomaticProtectionSwitchModeMismatchAPS,
       gfarEndProtectionLineFailure,
       ginconsistentAPSCode,
       gimproperAPSCode,
       gnodeIdMismatch,
       gchannelDefaultKAPS,
       gconnectionLoss,
       gbipolarViolation,
       gcarrierLossOnTheLAN,
       gconcatenationErrorSTS,
       gexcessCollisionsOnTheLAN,
       gfacilityFailure,
       gfarEndAIS,
       gfarEndMultipleDS1LOSDetectedOnDS3,
       gfarEndDS1EqptFailNonServiceAffecting,
       gfarEndDS1EqptFailServiceAffecting,
       gfarEndSingleDS1LOS,
       gfarEndDS3EqptFailNonServiceAffecting,
       gfarEndDS3EqptFailServiceAffecting,
       gfarEndCommonEquipmentFailureNonServiceAffecting,
       gfarEndIDLE,
       gfarEndLOS,
       gfarEndLOF,
       gfarEndBlockError,
       gds3IdleCondition,
       glossOfFrame,
       glossOfPointer,
       glossOfPointerPath,
       glossOfPointerVT,
       glossOfSignal,
       goutOfFrame,
       gpathSelectorFailure,
       gremoteAlarmIndication,
       gremoteFailureIndication,
       gremoteFailureIndicationLine,
       gremoteFailureIndicationPath,
       gremoteFailureIndicationVT,
       gsignalDegrade,
       gseverelyErroredFrame,
       gsignalFailure,
       gsignalLabelMismatchFailure,
       gpayloadDefectIndication,
       gpayloadDefectIndicationPath,
       gpayloadLabelMismatchPath,
       gsignalLabelMismatchFailurePayloadLabelMismatchVT,
       gunequippedPath,
       gsignalLabelMismatchFailureUnequippedVT,
       glossOfSynchronization,
       goutOfSynchronization,
       gprimarySynchronizationReferenceFailure,
       gsecondarySynchronizationReferenceFailure,
       gthirdSynchronizationReferenceFailure,
       gfourthSynchronizationReferenceFailure,
       gfifthSynchronizationReferenceFailure,
       gsixthSynchronizationReferenceFailure,
       gfailedToReceiveSynchronizationStatusMessage,
       gsynchronizationStatusMessagesAreDisabledOnThisInterface,
       gstratum1PrimaryReferenceSourceTraceable,
       gsynchronizedTraceabilityUnknown,
       gstratum2Traceable,
       gtransitNodeClockTraceable,
       gstratum3ETraceable,
       gstratum3Traceable,
       gsonetMinimumClockTraceable,
       gstratum4Traceable,
       gdoNotUseForSynchronization,
       greservedForNetworkSynchronizationUse,
       goutgoingFailureCondition,
       gremoteDefectIndicationLine,
       gremoteDefectIndicationPath,
       gfreeRunningSynchronizationMode,
       gholdoverSynchronizationMode,
       gfastStartSynchronizationMode,
       ginternalFault,
       ginternalError,
       ginternalMessageError,
       gmismatchOfEquipmentAndAttributes,
       gwatchdogTimerTimeout,
       gsoftwareFaultOrFailure,
       gsoftwareFaultDataIntegrityFault,
       gprogramFailure,
       gcontrolEquipmentFailure,
       gprimaryNonVolatileBackupMemoryFailure,
       gsecondaryNonVolatileBackupMemoryFailure,
       gcontrolBusFailure,
       gcontrolBus1Failure,
       gcontrolBus2Failure,
       gtccAToShelfSlot1DROP1CommunicationFailure,
       gtccAToShelfSlot2DROP2CommunicationFailure,
       gtccAToShelfSlot3DROP3CommunicationFailure,
       gtccAToShelfSlot4DROP4CommunicationFailure,
       gtccAToShelfSlot5TRUNK1CommunicationFailure,
       gtccAToShelfSlot6TRUNK2CommunicationFailure,
       gtccAToShelfSlot7TCCACommunicationFailure,
       gtccAToShelfSlot8XCONACommunicationFailure,
       gtccAToShelfSlot9AICCommunicationFailure,
       gtccAToShelfSlot10XCONBCommunicationFailure,
       gtccAToShelfSlot11TCCBCommunicationFailure,
       gtccAToShelfSlot12TRUNK3CommunicationFailure,
       gtccAToShelfSlot13TRUNK4CommunicationFailure,
       gtccAToShelfSlot14DROP5CommunicationFailure,
       gtccAToShelfSlot15DROP6CommunicationFailure,
       gtccAToShelfSlot16DROP7CommunicationFailure,
       gtccAToShelfSlot17DROP8CommunicationFailure,
       gtccAToDCCAProcessorCommunicationFailure,
       gtccBToShelfSlot1DROP1CommunicationFailure,
       gtccBToShelfSlot2DROP2CommunicationFailure,
       gtccBToShelfSlot3DROP3CommunicationFailure,
       gtccBToShelfSlot4DROP4CommunicationFailure,
       gtccBToShelfSlot5TRUNK1CommunicationFailure,
       gtccBToShelfSlot6TRUNK2CommunicationFailure,
       gtccBToShelfSlot7TCCACommunicationFailure,
       gtccBToShelfSlot8XCONACommunicationFailure,
       gtccBToShelfSlot9AICCommunicationFailure,
       gtccBToShelfSlot10XCONBCommunicationFailure,
       gtccBToShelfSlot11TCCBCommunicationFailure,
       gtccBToShelfSlot12TRUNK3CommunicationFailure,
       gtccBToShelfSlot13TRUNK4CommunicationFailure,
       gtccBToShelfSlot14DROP5CommunicationFailure,
       gtccBToShelfSlot15DROP6CommunicationFailure,
       gtccBToShelfSlot16DROP7CommunicationFailure,
       gtccBToShelfSlot17DROP8CommunicationFailure,
       gtccBToDCCBProcessorCommunicationFailure,
       gcontrolProcessorFailure,
       gworkingMemoryFailure,
       ginterconnectionEquipmentFailure,
       gpayloadBusFailureToIOSlot1XCONSlot8,
       gpayloadBusFailureToIOSlot2XCONSlot8,
       gpayloadBusFailureToIOSlot3XCONSlot8,
       gpayloadBusFailureToIOSlot4XCONSlot8,
       gpayloadBusFailureToIOSlot5XCONSlot8,
       gpayloadBusFailureToIOSlot6XCONSlot8,
       gpayloadBusFailureToIOSlot12XCONSlot8,
       gpayloadBusFailureToIOSlot13XCONSlot8,
       gpayloadBusFailureToIOSlot14XCONSlot8,
       gpayloadBusFailureToIOSlot15XCONSlot8,
       gpayloadBusFailureToIOSlot16XCONSlot8,
       gpayloadBusFailureToIOSlot17XCONSlot8,
       gpayloadBusFailureToIOSlot1XCONSlot10,
       gpayloadBusFailureToIOSlot2XCONSlot10,
       gpayloadBusFailureToIOSlot3XCONSlot10,
       gpayloadBusFailureToIOSlot4XCONSlot10,
       gpayloadBusFailureToIOSlot5XCONSlot10,
       gpayloadBusFailureToIOSlot6XCONSlot10,
       gpayloadBusFailureToIOSlot12XCONSlot10,
       gpayloadBusFailureToIOSlot13XCONSlot10,
       gpayloadBusFailureToIOSlot14XCONSlot10,
       gpayloadBusFailureToIOSlot15XCONSlot10,
       gpayloadBusFailureToIOSlot16XCONSlot10,
       gpayloadBusFailureToIOSlot17XCONSlot10,
       gtimeSlotInterchangeEquipmentFailure,
       gequipmentFailure,
       ghighTemperature,
       ginvalidMACAddress,
       gboardFailure,
       gdiagnosticFailure,
       gmediumAccessControlFailure,
       gfacilityTerminationEquipmentFailure,
       gautomaticLaserShutoffDueToHighTemperature,
       gfailureToReleaseFromProtection,
       greceiverFailure,
       gtransmitFailure,
       gfacilityTerminationEquipmentReceiverMissing,
       gfacilityTerminationEquipmentTransmitterMissing,
       gfailureToSwitchToProtection,
       gfailureToSwitchToProtectionRing,
       gfailureToSwitchToProtectionSpan,
       gfailureToSwitchToProtectionPath,
       gfanFailure,
       gequipmentUnitPlugIn,
       gnePowerFailureAtConnector,
       gfuseAlarm,
       gsynchronizationUnitFailure,
       gsynchronizationSwitchingEquipmentFailure,
       gequipmentUnitUnplugged,
       gloopback,
       gds1LoopbackDueToFEACCommand,
       gloopbackCommandSentToFarEndDS1,
       gds3LoopbackDueToFEACCommand,
       gds3LoopbackCommandSentToFarEnd,
       gds2LoopbackDueToFarEndCommand,
       gds2LoopbackCommandSentToFarEnd,
       gfacilityLoopback,
       gnetworkLoopback,
       gterminalLoopback,
       gmanuallyCausedAbnormalCondition,
       gethernetBridgeIsNewRootOfSpanningTree,
       gethernetBridgeTopologyChange,
       gnormalCondition,
       gembeddedOperationsChannelFailureLinkDown,
       gpeerStateMismatch,
       gproceduralError,
       gimproperRemoval,
       gduplicateNodeID,
       gblsrOutOfSync,
       gblsrMultiNodeTableUpdateCompleted,
       gprotectionUnitNotAvailable,
       gperformanceMonitorThresholdCrossingAlert,
       gprotectionSwitch,
       grecoveryOrServiceProtectionActionHasBeenInitiated,
       gautomaticSystemReset,
       gautomaticUPSRSwitchCausedByAIS,
       gautomaticUPSRSwitchCausedByLOP,
       gautomaticUPSRSwitchCausedByUNEQ,
       gautomaticUPSRSwitchCausedByPDI,
       gautomaticUPSRSwitchCausedBySFBER,
       gautomaticUPSRSwitchCausedBySDBER,
       gcoldRestart,
       gforcedSwitchBackToWorking,
       gforcedSwitchBackToWorkingRing,
       gforcedSwitchBackToWorkingSpan,
       gforcedSwitchToProtection,
       gforcedSwitchToProtectionRing,
       gforcedSwitchToProtectionSpan,
       gworkingFacilityOrEquipmentForcedToSwitchToProtectionPath,
       ginitializationInitiated,
       glockoutOfProtection,
       glockoutOfProtectionRing,
       glockoutOfProtectionSpan,
       glockoutOfProtectionPath,
       glockoutOfWorking,
       glockoutOfWorkingRing,
       glockoutOfWorkingSpan,
       gmanualSystemReset,
       gmanualSwitchToInternalClock,
       gmanualSwitchToPrimaryReference,
       gmanualSwitchToSecondReference,
       gmanualSwitchToThirdReference,
       gmanualSwitchToFourthReference,
       gmanualSwitchToFifthReference,
       gmanualSwitchToSixthReference,
       gmanualSwitchBackToWorking,
       gmanualSwitchBackToWorkingRing,
       gmanualSwitchBackToWorkingSpan,
       gmanualSwitchToProtection,
       gmanualSwitchToProtectionRing,
       gmanualSwitchToProtectionSpan,
       gmanualSwitchOfWorkingFacilityOrEquipmentToProtectionPath,
       gpowerfailRestart,
       gringIsSquelchingTraffic,
       gsoftwareDownloadInProgress,
       gswitchToInternalClock,
       gswitchToPrimaryReference,
       gswitchToSecondReference,
       gswitchToThirdReference,
       gswitchToFourthReference,
       gswitchToFifthReference,
       gswitchToSixthReference,
       gsystemReboot,
       gswitchedBackToWorking,
       gswitchedToProtection,
       gwarmRestart,
       gringIsInWaitToRestoreState,
       gmanualSwitchRequest,
       gforcedSwitchRequest,
       glockoutSwitchRequest,

       grmonHistoriesAndAlarmsResetReboot,
       grmonThresholdCrossingAlarm,
       galarmsSuppressedByUserCommand,
       galarmsSuppressedForMaintenance,
       gswitchingMatrixModuleFailure,
       glanConnectionPolarityReversed,
       gautonomousPMReportMessageInhibited,
       gioSlotToXCONCommunicationFailure,
       gstsPathTraceIdentifierMismatch,
       gnePowerFailureAtConnectorA,
       gnePowerFailureAtConnectorB,
       gfreeMemoryOnCardVeryLow,
       gfreeMemoryOnCardNearZero,
       gexerciseRequestOnRing,
       gexerciseRequestOnSpan,
       gsquelchingPath,
       gextraTrafficPreempted,
       gfarEndLockoutOfWorkingRing,
       gfarEndLockoutOfWorkingSpan,
       gfarEndLockoutOfProtectionRing,
       gfarEndLockoutOfProtectionAllSpans,
       gfarEndWorkingFacilityForcedToSwitchToProtectionRing,
       gfarEndWorkingFacilityForcedToSwitchToProtectionSpan,
       gfarEndManualSwitchOfWorkingFacilityToProtectionRing,
       gfarEndManualSwitchOfWorkingFacilityToProtectionSpan,
       gfarEndExercisingRing,
       gfarEndExercisingSpan,
       gfarEndBERThresholdPassedForSignalFailureRing,
       gfarEndBERThresholdPassedForSignalFailureSpan,
       gfarEndBERThresholdPassedForSignalDegradeRing,
       gfarEndBERThresholdPassedForSignalDegradeSpan,
       gapsChannelFarEndProtectionLineSignalDegrade,
       gringSwitchIsActiveOnTheEastSide,
       gringSwitchIsActiveOnTheWestSide,
       gspanSwitchIsActiveOnTheEastSide,
       gspanSwitchIsActiveOnTheWestSide,
       guniDirectionalFullPassThroughIsActive,
       gbiDirectionalFullPassThroughIsActive,
       gkBytesPassThroughIsActive,
       gringIsSegmented,
       gringTopologyIsUnderConstruction,
       glockoutOfProtectionAllSpans,
       gfarEndOfFiberIsProvisionedWithDifferentRingID,
       gbothEndsOfFiberProvisionedAsEastOrBothAsWest,
       gautonomousMessagesInhibited,
       gtrafficStormOnLANLANTemporarilyDisabled,
       greptdbchgMessagesInhibited,
       gsecurityUserIDHasExpired,
       gpartialFanFailure,
       gforcedSwitchRequestOnRing,
       gforcedSwitchRequestOnSpan,
       glockoutSwitchRequestOnRing,
       glockoutSwitchRequestOnSpan,
       gmanualSwitchRequestOnRing,
       gmanualSwitchRequestOnSpan,
       gcommunicationFailurePeerToPeerSlotControlBusA,
       gcommunicationFailurePeerToPeerSlotControlBusB,
       gcontrollerAToShelfSlotCommunicationFailure,
       gcontrollerBToShelfSlotCommunicationFailure,
       ginterconnectionEquipmentFailureWorkingPayloadBus,
       ginterconnectionEquipmentFailureProtectPayloadBus,
       ginhibitSwitchToProtectRequestOnEquipment,
       ginhibitSwitchToWorkingRequestOnEquipment,

       gexercisingRingSuccessfully,
       gexercisingSpanSuccessfully,
       gspanIsInWaitToRestoreState,
       gexerciseRequestOnRingFailed,
       gexerciseRequestOnSpanFailed,
       gfarEndLockoutOfProtectionSpan,

       gmanufacturingDataMemoryEEPROMFailure,
       greplaceableEquipmentOrUnitIsMissing,
       gsoftwareDownloadFailed,
       gextraTrafficPCADropped,

       getherTxOversubscribed,
       getherRxOverSubscribed,
       getherTxExcessFlowCtrl,
       getherRxExcessFlowCtrl,
       gtransportLayerFailure,
       getherTxUnderrun,
       gsynchronizationReferenceFrequencyOutOfBounds,
       gntpOrSntpHostFailure,
       gpeerCardNotResponding,
       galarmsAndEventsSuppressedForThisObject,
       gds3FrameFormatMismatch,

       gtimSectionTraceIdentifierMismatchFailure,
       gaisMultiplexSectionAlarmIndicationSignal,
       grdiMultiplexSectionRemoteDefectOrAlarmIndication,
       gtimHighOrderTraceIdentifierMismatchFailure,
       gaisAdministrationUnitAlarmIndicationSignal,
       glopAdministrationUnitLossOfPointer,
       gslmfUnequippedHighOrderPathUnequipped,
       gslmfPLMHighOrderPathLabelMismatch,
       grdiHighOrderRemoteDefectOrAlarmIndication,
       glopTributaryUnitLossOfPointer,
       gaisTributaryUnitAlarmIndicationSignal,
       gslmfUnequippedLowOrderPathUnequipped,
       gslmfPLMLowOrderPathLabelMismatch,
       gtimLowOrderTraceIdentifierMismatchFailure,
       grfiLowOrderRemoteFailureOrAlarmIndication,
       gg811PrimaryReferenceClockTraceable,
       gg812TransitNodeClockTraceable,
       gg812LocalNodeClockTraceable,
       gg813SynchronousEquipmentTimingSourceTraceable,
       ge1LoopbackDueToFEACCommand,
       ge1LoopbackCommandSentToFarEnd,
       ge3LoopbackDueToFEACCommand,
       gfarEndMultipleE1LOSDetectedOnE3,
       gfarEndE1EqptFailNonServiceAffecting,
       gfarEndE1EqptFailServiceAffecting,
       gfarEndSingleE1LOS,
       gfarEndE3EqptFailServiceAffecting,
       ge3LoopbackCommandSentToFarEnd,
       gfarEndE3EqptFailNonServiceAffecting,
       glowVoltBatteryA,
       ghighVoltBatteryA,
       glowVoltBatteryB,
       ghighVoltBatteryB,
       gmsspRingOutOfSync,
       gmsspMultiNodeTableUpdateCompleted,
       gautomaticSNCPSwitchCausedByAIS,
       gautomaticSNCPSwitchCausedByLOP,
       gautomaticSNCPSwitchCausedByUNEQ,
       gautomaticSNCPSwitchCausedByPDI,
       gautomaticSNCPSwitchCausedBySFBER,
       gautomaticSNCPSwitchCausedBySDBER,
       gstmConcatenationError,
       ge3IdleCondition,
       gchannelMSSPInconsistentAPSCode,
       gchannelMSSPImproperAPSCodeAPS,
       gchannelMSSPNodeIdMismatchAPS,
       gchannelMSSPDefaultKAPS,
       gchannelMSSPConnectionLossAPS,
       gminimumClockTraceableSDH,
       glineIsInWaitToRestoreStateSDH,
       gberThresholdExceededForSignalDegradeHighOrder,
       gberThresholdExceededForSignalFailureHighOrder,
       gberThresholdExceededForSignalDegradeLowOrder,
       gberThresholdExceededForSignalFailureLowOrder,
       gfailureToSwitchToProtectionHighOrderPath,
       gfailureToSwitchToProtectionLowOrderPath,
       ga8b10bOutOfSync,
       godukPMAlarmIndicationSignal,
       gotukAlarmIndicationSignal,
       gotukSMBackwardDefectIndication,
       gfecUncorrectedWord,
       ggccTerminationFailure,
       gotukIncomingAlignmentError,
       godukLockedDefectPM,
       glossOfMultiFrame,
       godukOpenConnectionIndication,
       gpayloadTypeIdentifierMismatch,
       godukTrailTraceIdentifierMismatch,
       gotukTrailTraceIdentifierMismatch,
       gequipmentHighLaserBias,
       gequipmentHighLaserTemp,
       gequipmentHighLaserPeltier,
       gfacilityHighRxPower,
       gequipmentHighTxPower,
       gequipmentHighTransceiverVoltage,
       gequipmentLowLaserBias,
       gequipmentLowLaserTemp,
       gequipmentLowLaserPeltier,
       gfacilityLowRxPower,
       gequipmentLowTxPower,
       gequipmentLowTransceiverVoltage,
       gequipmentRxLocked,
       gequipmentSquelched,
       gequipmentTxLocked,
       gotukSignalFailure,
       godukSignalFailure,
       gotukSignalDegrade,
       godukSignalDegrade,
       gpluggablePortMissing,
       gpluggablePortRateMismatch,
       gpluggablePortSecurityCodeMismatch,
       gtciNotSelected,
       gtci1ClockFailure,
       godukPMBackwardDefectIndication,
       godukTCM1BackwardDefectIndication,
       godukTCM2BackwardDefectIndication,
       gequipmentHighRxTemperature,
       gequipmentLowRxTemperature,
       gopticalChannelDeactivationFailure,
       gopticalNetworkTypeMismatch,
       gnetworkTopologyIncomplete,
       glossOfChannel,
       gfecMismatch,
       gtimSectionMonitorTraceIdentifierMismatchFailure,
       gautomaticLaserShutdown,
       gtci2ClockFailure,
       gequipmentWavelengthMismatch,
       gdspCommunicationFailure,
       gdspFailure,
       glaserApproachingEndOfLife,
       gcrossconnectLoopback,
       gadminLogoutOfUser,
       guserLockedOut,
       gadminLockoutOfUser,
       gadminLockoutClear,
       ginvalidLoginUsername,
       gsecurityInvalidLoginPassword,
       gsecurityInvalidLoginLockedOut,
       gsecurityInvalidLoginAlreadyLoggedOn,
       gloginOfUser,
       gautomaticLogoutOfIdleUser,
       glogoutOfUser,
       gfirewallHasBeenDisabled,
       gconnectionEquipmentMismatch,
       gdisableInactiveUser,
       gdisableInactiveClear,
       gbatteryFailure,
       gextremeHighVolt,
       gextremeLowVolt,
       ghighVolt,
       glowVolt,
       gsuspendUser,
       gsuspendUserClear,
       glineDccTerminationFailure,
       gmultiplexSectionDccTerminationFailure,
       ggigaBitEthernetOutOfSync,
       gsequenceMismatch,
       glossOfAlignment,
       goutOfUseByAdministrativeCommand,
       goutOfUseTransportFailure,
       gvcatGroupDown,
       gvcatGroupDegraded,
       gvcatGroupIncomplete,
       galarmIndicationSignalInTX,
       gremoteAlarmIndicationInTX,
       gkByteAPSChannelFailure,
       gapsInvalidMode,
       gipAddressAlreadyInUseWithinTheSameDccArea,
       gnodeNameInUseWithinTheSameDccArea,
       grearPanelEthernetLinkRemoved,
       gmanualSwitchToProtectResultedInNoTrafficSwitch,
       gmanualSwitchBackToWorkingResultedInNoTrafficSwitch,
       gforcedSwitchToProtectResultedInNoTrafficSwitch,
       gforcedSwitchBackToWorkingResultedInNoTrafficSwitch,
       gduplicateSerialNumberDetectedOnAPluggableEntity,
       glossOfSignalForOpticalChannel,
       gencapsulationMismatchPath,
       gencapsulationMismatchVT,
       gencapsulationMismatchHighOrderPath,
       gencapsulationMismatchLowOrderPath,
       gimproperMatrixEquipmentInserted,
       geqptProblemOnCarrierOrPIM,
       geqptProblemOnPIMOrPPM,
       gportFAIL,
       gunreachablePortTargetPower,
       gportAddPowerDegradeLow,
       gportAddPowerDegradeHigh,
       gportAddPowerFailLow,
       gportAddPowerFailHigh,
       ggfpUserPayloadMismatch,
       ggfpFibreChannelDistanceExtensionMismatch,
       ggfpFibreChannelDistanceExtensionBufferStarvation,
       ggfpFibreChannelDistanceExtensionCreditStarvation,
       ggfpClientSignalFailDetected,
       ggfpLossOfFrameDelineation,
       ggfpExtensionHeaderMismatch,
       glcasVcgMemberTxSideInAddState,
       glcasVcgMemberTxSideInDnuState,
       glcasControlWordCrcCheckFailure,
       glcasVcgMemberRxSideInFailState,
       gsignalLossOnDataInterface,
       gsynchronizationLossOnDataInterface,
       gautomaticWdmAnsFinished,
       gincomingOverheadSignalAbsent,
       gopticalSafetyRemoteInterlockOn,
       gautomaticPowerControlCorrectionSkipped,
       gapcCannotSetValueDueToRangeLimits,
       gfarEndManualSwitchBackToWorkingSpan,
       gpluginModuleRangeSettingsMismatch,
       gautomaticPowerControlTerminatedOnManualRequest,
       goduk1AlarmIndicationSignal,
       goduk2AlarmIndicationSignal,
       goduk3AlarmIndicationSignal,
       goduk4AlarmIndicationSignal,
       gtemperatureReadingMismatchBetweenSCCards,
       gvoltageReadingMismatchBetweenSCCards,
       galarmsSuppressedonOutOfGroupVcatMember,
       gblsrSoftwareVersionMismatch,
       goptimized1Plus1ApsPrimaryFacility,
       goptimized1Plus1ApsPrimarySectionMismatch,
       goptimized1Plus1ApsInvalidPrimarySection,
       gcompositeClockHighLineVoltage,
       gberThresholdExceededForSignalDegradeVt,
       gberThresholdExceededForSignalFailureVt,
       gspanLengthOutOfRange,
       gidleSignalCondition,
       gidleSignalConditionInTx,
       gvtPathTraceIdentifierMismatch,
       glossOfFrameInTX,
       gprovisioningMismatch,
       gsectionTraceIdentifierMismatch,
       gregeneratorSectionTraceIdentifierMismatch,
       gswitchingMatrixModuleFailureWorking,
       gswitchingMatrixModuleFailureProtect,
       gslotCommunicationDisabled,
       gsessionTimeLimitExpired,
       guserPasswordChangeRequired,
       gisisAdjacencyFailure,
       gmsspSoftwareVersionMismatch,
       gremoteAuthenticationFailSeeAuditLog,
       gillegalRouteAdditionToNetwork,
       gringIsSquelchingStsTraffic,
       gringIsSquelchingVtTraffic,
       garchiveOfAuditLogFailed,
       grprWrapped,
       gshelfCommunicationFailure,
       gduplicatedShelfIdentifier,
       gsoftwareMismatch,
       glmpFailure,
       gopticalTerminationIncomplete,
       gforwardDefectIndication,
       gpayloadMissingIndication,
       gspanMeasurementCannotBePerformed,
       gringIsSquelchingHighOrderTraffic,
       gringIsSquelchingLowOrderTraffic,
       gbadPacketCountExceedsThreshold,
       glinkLayerKeepAliveFailure,
       gautonegotiationRemoteFailureIndication,
       gtrailSignalFail,
       gds1LoopbackCommandSentToFarEnd,
       gmultiplexSectionSignalDegraded,
       gmultiplexSectionExcessiveErrors,
       ghighOrderPathSignalDegraded,
       ghighOrderPathExcessiveErrors,
       glowOrderPathSignalDegraded,
       glowOrderPathExcessiveErrors,
       gregeneratorSectionDccTerminationFailure,
       gnetworkMemoryPoolLow,
       gospfRoutingTableOverflow,
       gautoLaserShutdownDisabled,
       gwavelengthOutOfLock,
       grprProtectionIsActive,
       gmaxRPRStationNumberExceeded,
       grprProtectionConfigurationMismatched,
       greservedBandwidthLinkRateExceededOnRinglet0,
       greservedBandwidthLinkRateExceededOnRinglet1,
       grprInterfaceInPassThroughMode,
       grprPeerNodeIsMissing,
       grprRiFailure,
       grprSignalFailure,
       grprSignalDegrade,
       ginterlinkFailure,
       gapcWrongGain,
       grprSpanMismatch,
       gefmRemoteFaultIndicationCriticalEvent,
       gefmRemoteFaultIndicationDyingGasp,
       gefmRemoteFaultIndicationLinkFault,
       gefmLinkMonitoringErroredSymbolPeriodEvent,
       gefmLinkMonitoringErroredFrameEvent,
       gefmLinkMonitoringErroredFramePeriodEvent,
       gefmLinkMonitoringErroredFrameSecondsSummary,
       gefmRemoteLoopbackRequestFailed,
       gfastAutomaticProtectionSwitching,
       gfastAutomaticProtectionSwitchingConfigMismatch,
       glcasSinkGroupError,
       glcasVcgMemberRxSideInDnuState,
       gfcDistanceExtFuncNotEstablished,
       gnonCiscoPPMInserted,
       gunqualifiedPPMInserted,
       gftaMismatch,
       gcardPortsUnableToProvideProtection,
       glmpSignalDegrade,
       glmpSignalFailure,
       glmpUnallocatedDataLink,
       gfrontPortLinkLoss,
       gbertEnbl,
       gbertSyncFail,
       gworkQueueFull,
       genhancedRemoteFailureIndicationPathServer,
       genhancedRemoteFailureIndicationPathConnectivity,
       genhancedRemoteFailureIndicationPathPayload,
       gsecurityIntrusionDetPwd,
       gsecurityIntrusionDetUser,
       gforcedSwitchToPrimaryReference,
       gforcedSwitchToSecondReference,
       gforcedSwitchToThirdReference,
       gforcedSwitchToInternalClock,
       gindustrialHighTemperature,
       gopticalPowerDegradeLow,
       gautomaticPowerControlFailure,
       gopticalPowerDegradeHigh,
       gautomaticPowerControlDisabled,
       gopticalPowerFailureLow,
       gringIdMismatch,
       gopticalPowerFailureHigh,
       glossOfContinuity,
       gvariableOpticalAttenuatorDegradeLow,
       gvariableOpticalAttenuatorDegradeHigh,
       gvariableOpticalAttenuatorFailureLow,
       gvariableOpticalAttenuatorFailureHigh,
       glaserBiasDegrade,
       glaserBiasFailure,
       glaserTemperatureDegrade,
       gopticalAmplifierGainDegradeLow,
       gopticalAmplifierGainDegradeHigh,
       gopticalAmplifierGainFailureLow,
       gopticalAmplifierGainFailureHigh,
       gopticalChannelConnectionFailure,
       gopticalChannelActivationFailure,
       glaserAutoPowerReduction,
       gcaseTemperatureDegrade,
       gfiberTemperatureDegrade,
       gshutterOpen,
       gawgTemperatureDegrade,
       gawgTemperatureFailure,
       gawgOverTemperature,
       gopticalAmplifierInitialization,
       gawgWarmUp,
       gincSigloss,
       gincSyncloss,
       gincGfpOutOfFrame,
       gincGfpSigLoss,
       gincGfpSyncLoss,
       gwaitToRestore,
       gextremeHighVoltBatteryA,
       gextremeLowVoltBatteryA,
       gextremeHighVoltBatteryB,
       gextremeLowVoltBatteryB,
       giosConfigCopyFailed,
       giosConfigCopyInProgress,
       giosConfigCopySuccess,
       gsignalingUnableToSetupCircuit,
       gerrorInStartupConfig,
       gnoStartupConfig,
       gneedToSaveRunningConfig,
       ginvalidAlarm,
       grsvpHelloFSMToNeighborDown,
       gsecurityInvalidLoginUsername,
       gdatabaseBackupFailed,
       gdatabaseRestoreFailed,
       glmpHelloFSMToControlChannelDown,
       glmpNeighborDiscoveryHasFailed,
       gunauthorizedIncomingSignalingRequest,
       gauditLog80PercentFull,
       gmoduleCommunicationFailure,
       gauditLog100PercentFullOldestRecordsWillBeLost,
       gstandbyDatabaseOutOfSync,
       gredundantPowerCapabilityLost,
       glofAdministrationUnitLossOfMultiFrame,
       gsdhSpanIsInWaitToRestoreState,
       gequipmentPowerFailureAtConnectorA,
       gequipmentPowerFailureAtConnectorB,
       gequipmentPowerFailureAtReturnConnectorA,
       gequipmentPowerFailureAtReturnConnectorB,
       gloginFailThresholdExceeded,
       gconnectionIdMismatchOnMatrixA,
       gconnectionIdMismatchOnMatrixB,
       gequipmentFailureHighTemperature,
       glaserBiasCurrentHigh,
       ghighLaserTemperature,
       gbridgeAndRollHasOccurred,
       gbridgeAndRollIsPendingAValidSignal,
       gfarEndForcedSwitchBackToWorkingSpan,
       gpartialFanFailurePartsFailure,
       gunprotectedSyncronizationEquipment,
       gunprotectedMatrixEquipment,
       gmatrixEquipmentUnavailable,
       gcontrolBusFailureTscA,
       gcontrolBusFailureTscB,
       gpayloadBusFailureMatrixA,
       gpayloadBusFailureMatrixB,
       gmatrixOperationSuspended,
       gclockFailureTsc,
       gpayloadLoopback,
       gdccChannelLoss,
       greptPmMsgInhibited,
       gloopbackCrs,
       gsyncRefFreqOutOfBound,
       gsystemUpgradeInProgress,
       geqptFailToBoot,
       geqptPowerFailure,
       gclockBusFailureTscA,
       gclockBusFailureTscB,
       gpowerFuseFailure,
       gcontrolCommunicationsEquipmentFailure,
       gdifferentSoftwareVersion,
       gospfHelloFail,
       gclockModuleFrequencyMismatch,
       getherPortSwitch,
       gopenIOSlots,
       glossOfDFBSignal,
       gbackPanelFacilityLoopback,
       gbackPanelTerminalLoopback,
       gtrunkPayloadTypeMismatch,
       ginvalidMuxponderConfiguration,
       gcoolingProfileMismatch,
       gtrunkOduAlarmIndicationSignal,
       gcompanionCardMissing,
       gmasterKeyExchangeFailed,
       gpowerConsumptionLimitHasCrossed,
       gcontrolPlaneUnverifiedClearedAlarmsPresent,
       gunitHighTemperature,
       goverTemperatureUnitProtected,
       gseqMismatchCount,
       gduplicateNodeControllerDetected,
       grestorationInProg,
       gramanPumpsCalibrationProcedureIsRunning,
       gramanPumpsCalibrationIsScheduledToRunInTheNextMinutes,
       gkeyProgramOnAlteraFpgaFailed,
       godukTCM1AlarmIndicationSignal,
       godukTCM2AlarmIndicationSignal,
       godukLockedDefectTCM1,
       godukLockedDefectTCM2,
       gotukLossOfFrame,
       godukOpenConnectionIndicationTCM1,
       godukOpenConnectionIndicationTCM2,
       godukTrailTraceIdentifierMismatchTCM1,
       godukTrailTraceIdentifierMismatchTCM2,
       godukSignalFailureTCM1,
       godukSignalFailureTCM2,
       godukSignalDegradeTCM1,
       godukSignalDegradeTCM2,
       gequipmentBootInProgress,
       glossOfClockFromMateShelfController,
       gvirtualLanAlarmIndicationSignal,
       gdcuLossFailure,
       gochncMaintenance,
       gramanLaserShutdown,
       glosOfRamanSignal,
       gmcastMacTableFull,
       gmulticastMacAddressAliasing,
       gramanPwrProtOn,
       gcppPeerNotResponding,
       gvoaControlLoopDisableDueToExcessiveCounterPropagationLight,
       gwizardIsRunning,
       gramanGainNotReached,
       glocalFault,
       gremoteFault,
       gefmRemoteLoopbackConfigured,
       gefmPeerMissing,
       geqptDegrade,
       gexcessiveBackPropagation,
       gremoteMaintenanceEndPointIsDown,
       gcrossConnectedCFMService,
       gcfmLoop,
       gcfmConfigurationError,
       goutOfChannelGroupBundle,
       grepNeighborAdjacencyFailure,
       grepLinkFlapping,
       gfaultInREPSegment,
       gprimaryREPEdgePortElected,
       gsecondaryREPEdgePortElected,
       gstcnREPGenerated,
       gvlbREPActivated,
       gvlbREPTriggerSoakingDelayActive,
       gpprForwardDefectIndication,
       gpprBackwardDefectIndication,
       gpprCoordinatedMaintenance,
       gpprTriggerThresholdBERExceeded,
       gwanSyncloss,
       gmanualLaserRestart,
       glaserShutdownDueToNonCiscoPPMInserted,
       gethernetOSCTerminationFailure,
       gshutterInsertionLossVariationDegradeLow,
       gshutterInsertionLossVariationDegradeHigh,
       gpluginModuleCommunicationFailure,
       guniversalTransponderModuleHardwareFailure,
       guniversalTransponderModuleCommunicationFailure,
       gberThresholdExceededForSignalDegradeLine,
       gberThresholdExceededForSignalDegradePath,
       gberThresholdExceededForSignalFailureLine,
       gberThresholdExceededForSignalFailurePath,
       gopticalChannelIncomplete
     }
        STATUS current
        DESCRIPTION
          "The generic notifications for Cisco ONS 
           network device, ONS 15327, 15310"
        ::= { cerentGenericGroups 30 }

-- This definition of group will move to a cerentCommon modules
-- eventually. 
        
cerentGenericCommonGroup OBJECT-GROUP
        OBJECTS {
          cerentGenericEnableNotification,
          cerentGenericNodeTime,
          cerentGenericSentNotifications,
          cerentGenericLastChangeTime,  
          cerentGenericMultishelfEnabled
          }
        STATUS current
        DESCRIPTION
          "The objects related to traps dispatch"
        ::= { cerentGenericGroups 40 }

-- This group covers for threshold display and TCA trap

cerentThresholdGroup OBJECT-GROUP
        OBJECTS {
          cerentGenericThresholdMonitorType,
          cerentGenericThresholdLocation,
          cerentGenericThresholdPeriod,
          cerentGenericThresholdSetValue,
          cerentGenericThresholdCurrentValue,
          cerentGenericThresholdDetectType
        }
        STATUS current
        DESCRIPTION
          "The objects for storing all the current alarms"
        ::= { cerentGenericGroups 50 }

eventGenericDeprecatedGroup NOTIFICATION-GROUP
     NOTIFICATIONS {
       gcontrolEquipmentControlCommunicationsEquipmentFailure,
       gsecurityInvalidLoginUsernameSeeAuditTrail,
       gmanufacturingEepromFailure,
       gairFlow
     }
        STATUS deprecated
        DESCRIPTION
          "The deprecated notifications for Cisco ONS 
           network devices"
        ::= { cerentGenericGroups 60 }

reportedAlarmGenericGroup OBJECT-GROUP
        OBJECTS {
          cerentGenericReportedAlarmCount,
          cerentGenericReportedAlarmObjectType,
          cerentGenericReportedAlarmSlotNumber,
          cerentGenericReportedAlarmPortNumber,
          cerentGenericReportedAlarmObjectIndex,
          cerentGenericReportedAlarmType,
          cerentGenericReportedAlarmTimeStamp,
          cerentGenericReportedAlarmObjectName,
          cerentGenericReportedAlarmAdditionalInfo,
          cerentGenericReportedAlarmSeverity,
          cerentGenericReportedAlarmStatus,
          cerentGenericReportedAlarmServiceAffecting
        }
        STATUS current
        DESCRIPTION
          "The group for reported alarm objects"
        ::= { cerentGenericGroups 70 }
        

-- the compliance specification for agent developers

cerentGenericBasicCompliance MODULE-COMPLIANCE
       STATUS current
       DESCRIPTION
         "The basic implementation requirements 
          for Cisco ONS network device, ONS 15327, 15310 "
       MODULE
         MANDATORY-GROUPS {
           nodeGenericGroup,
           eventGenericGroup
        }
       ::= { cerentCompliance 10 }
          
END
