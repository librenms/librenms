-- Copyright (C) 2018  Aricent Group . All Rights Reserved

   Aricent-MI-DHCP-SNOOPING-MIB DEFINITIONS ::= BEGIN
      IMPORTS
         MODULE-IDENTITY, OBJECT-TYPE,
         enterprises, Counter32, Integer32        FROM SNMPv2-SMI
         RowStatus                                FROM SNMPv2-TC;
                                    

fsMIDhcpSnp  MODULE-IDENTITY 
            LAST-UPDATED "202112210000Z"
            ORGANIZATION "ARICENT COMMUNICATIONS SOFTWARE" 
            CONTACT-INFO "support@aricent.com" 

            DESCRIPTION 
                " The proprietary MIB module is for configuration of DHCP
                snooping feature. DHCP snooping provides security between the 
                untrusted hosts and DHCP servers, by filtering the Untrusted DHCP 
                packets which is received from out of the network and also updates 
                the IP binding database present in the IPDB module. "
            REVISION "202112210000Z"
            DESCRIPTION
               " Add fsMIDhcpSnpInformationOptionStatus."
            REVISION "201209050000Z"
            DESCRIPTION
               " This mib module is for Proprietary Multiple Instance
                 DHCP Snooping mib."
            ::=  { enterprises aricent-communication-holding-ltd(29601)
            iss(2) 49} 

-- ***************************************************************************
--                         Groups in the MIB
-- ***************************************************************************

    fsMIDhcpSnpGlobalConfig          OBJECT IDENTIFIER ::= { fsMIDhcpSnp 1 }
    fsMIDhcpSnpInterface             OBJECT IDENTIFIER ::= { fsMIDhcpSnp 2 }

-- ***************************************************************************
--                      Global Configuration Table 
-- ***************************************************************************
    fsMIDhcpSnpGlobalConfigTable OBJECT-TYPE
        SYNTAX  SEQUENCE OF FsMIDhcpSnpGlobalConfigEntry
        MAX-ACCESS  not-accessible
        STATUS      current
        DESCRIPTION
            "This table contains the configuration & statistics collection
            parameters of DHCP snooping on a specific VLAN. "
    ::= { fsMIDhcpSnpGlobalConfig 1 } 

    fsMIDhcpSnpGlobalConfigEntry OBJECT-TYPE
        SYNTAX      FsMIDhcpSnpGlobalConfigEntry
        MAX-ACCESS  not-accessible
        STATUS      current
        DESCRIPTION
            "This object specifies each row instance that gives the DHCP snooping status on VLAN and the
             statistics collected in that VLAN for the DHCP snooping module."
        INDEX { fsMIDhcpSnpContextId }
    ::= { fsMIDhcpSnpGlobalConfigTable 1 }


   FsMIDhcpSnpGlobalConfigEntry ::=
     SEQUENCE {
           fsMIDhcpSnpContextId
              Integer32,
           fsMIDhcpSnpSnoopingAdminStatus
              INTEGER,
           fsMIDhcpSnpMacVerifyStatus
              INTEGER,
           fsMIDhcpSnpInformationOptionStatus
              INTEGER
             }
   fsMIDhcpSnpContextId OBJECT-TYPE
   SYNTAX        Integer32 (0..65535)
   MAX-ACCESS    not-accessible
   STATUS        current
   DESCRIPTION
      "Identifies the Virtual Context."
   ::= { fsMIDhcpSnpGlobalConfigEntry 1 }

    fsMIDhcpSnpSnoopingAdminStatus OBJECT-TYPE
        SYNTAX          INTEGER { enabled(1), disabled(2) }
        MAX-ACCESS      read-write
        STATUS          current
        DESCRIPTION
            "This object is used to enable or disable Layer 2 DHCP Snooping globally in the system.
             When set to 'enabled', the DHCP Snooping Module will start the 
             protocol operation. Layer 2 DHCP Snooping should be enabled on 
             per VLAN basis also. When set to 'disabled', the DHCP Snooping 
             Module will stop the protocol operation."
        DEFVAL  { disabled }
    ::= { fsMIDhcpSnpGlobalConfigEntry 2 }
    
     fsMIDhcpSnpMacVerifyStatus OBJECT-TYPE
        SYNTAX          INTEGER { enabled(1), disabled(2) }
        MAX-ACCESS      read-write
        STATUS          current
        DESCRIPTION
            "This object is used to enable or disable the MAC address verification. If this option 
             is enabled, the Layer 2 DHCP snooping module will verify the 
             source MAC Address against the client hardware address in the
             DHCP packets received."
         DEFVAL  { disabled }
     ::= { fsMIDhcpSnpGlobalConfigEntry 3 }

     fsMIDhcpSnpInformationOptionStatus OBJECT-TYPE
        SYNTAX          INTEGER { enabled(1), disabled(2) }
        MAX-ACCESS      read-write
        STATUS          current
        DESCRIPTION
            "This object is used to enable or disable the injection of agent information. If this option
             is enabled, the Layer 2 DHCP snooping module will inject DHCP option 82 (agent information) in the
             forwarded DHCP packets."
         DEFVAL  { enabled }
     ::= { fsMIDhcpSnpGlobalConfigEntry 4 }


-- ***************************************************************************
--                               GROUPS
-- ***************************************************************************

-- **************************** VLAN Entry ******************************

    fsMIDhcpSnpInterfaceTable OBJECT-TYPE
        SYNTAX  SEQUENCE OF FsMIDhcpSnpInterfaceEntry
        MAX-ACCESS  not-accessible
        STATUS      current
        DESCRIPTION
            "This table contains the configuration & statistics collection 
            parameters of DHCP snooping on a particular context for a specified
            VLAN. "
    ::= { fsMIDhcpSnpInterface 1 }
                               
    fsMIDhcpSnpInterfaceEntry OBJECT-TYPE
        SYNTAX FsMIDhcpSnpInterfaceEntry
        MAX-ACCESS  not-accessible
        STATUS      current
        DESCRIPTION
            "This object specifies each row instance that gives the DHCP snooping status on VLAN and the 
             statistics collected in that VLAN for the DHCP snooping module."
        INDEX { fsMIDhcpSnpContextId, fsMIDhcpSnpVlanId }
    ::= { fsMIDhcpSnpInterfaceTable 1 }

    FsMIDhcpSnpInterfaceEntry ::= SEQUENCE {
        fsMIDhcpSnpVlanId             Integer32,
        fsMIDhcpSnpVlanSnpStatus      INTEGER,
        fsMIDhcpSnpRxDiscovers        Counter32,
        fsMIDhcpSnpRxRequests         Counter32,
        fsMIDhcpSnpRxReleases         Counter32,
        fsMIDhcpSnpRxDeclines         Counter32,
        fsMIDhcpSnpRxInforms          Counter32,
        fsMIDhcpSnpTxOffers           Counter32,
        fsMIDhcpSnpTxAcks             Counter32,
        fsMIDhcpSnpTxNaks             Counter32,
        fsMIDhcpSnpNoOfDiscards       Counter32,
        fsMIDhcpSnpMacDiscards        Counter32,
        fsMIDhcpSnpServerDiscards     Counter32,
        fsMIDhcpSnpOptionDiscards     Counter32,
        fsMIDhcpSnpInterfaceStatus    RowStatus
    }

   fsMIDhcpSnpVlanId OBJECT-TYPE
        SYNTAX      Integer32 (1..4094)
        MAX-ACCESS  not-accessible
        STATUS      current
        DESCRIPTION
            "This object specifies the Vlan ID of the VLAN to which this table-entry is associated."
    ::= { fsMIDhcpSnpInterfaceEntry 2 }

   fsMIDhcpSnpVlanSnpStatus OBJECT-TYPE
        SYNTAX      INTEGER { enabled (1), disabled (2) }
        MAX-ACCESS  read-write
        STATUS      current
        DESCRIPTION
            "Setting this object Enables or disables Layer 2 DHCP Snooping 
             in the given VLAN."
        DEFVAL  { disabled }
    ::= { fsMIDhcpSnpInterfaceEntry 3 }

    fsMIDhcpSnpRxDiscovers OBJECT-TYPE
        SYNTAX      Counter32
        MAX-ACCESS  read-only
        STATUS      current
        DESCRIPTION
            "This object specifies the total number of DHCP Discovers received 
             from the hosts connected to this VLAN."
    ::= { fsMIDhcpSnpInterfaceEntry 4 }
    
    fsMIDhcpSnpRxRequests OBJECT-TYPE
        SYNTAX      Counter32
        MAX-ACCESS  read-only
        STATUS      current
        DESCRIPTION
            "This object specifies the total number of DHCP Requests received from 
             the hosts connected to this VLAN."
    ::= { fsMIDhcpSnpInterfaceEntry 5 }
   
    fsMIDhcpSnpRxReleases OBJECT-TYPE
        SYNTAX      Counter32
        MAX-ACCESS  read-only
        STATUS      current
        DESCRIPTION
            "This object specifies the total number of DHCP Releases received from 
             the hosts connected to this VLAN."
    ::= { fsMIDhcpSnpInterfaceEntry 6 }
    
    fsMIDhcpSnpRxDeclines OBJECT-TYPE
        SYNTAX      Counter32
        MAX-ACCESS  read-only
        STATUS      current
        DESCRIPTION
            "This object specifies the total number of DHCP Declines received from 
             the hosts connected to this VLAN."
    ::= { fsMIDhcpSnpInterfaceEntry 7 }
    
    fsMIDhcpSnpRxInforms OBJECT-TYPE
        SYNTAX      Counter32
        MAX-ACCESS  read-only
        STATUS      current
        DESCRIPTION
            "This object specifies the total number of DHCP Informs received from 
             the hosts connected to this VLAN."
    ::= { fsMIDhcpSnpInterfaceEntry 8 }

    fsMIDhcpSnpTxOffers OBJECT-TYPE
        SYNTAX      Counter32
        MAX-ACCESS  read-only
        STATUS      current
        DESCRIPTION
            "This object specifies the total number of DHCP Offers sent out on this
             VLAN to hosts."
    ::= { fsMIDhcpSnpInterfaceEntry 9 }

    fsMIDhcpSnpTxAcks OBJECT-TYPE
        SYNTAX      Counter32
        MAX-ACCESS  read-only
        STATUS      current
        DESCRIPTION
            "This object specifies the total number of DHCP Acks sent out on this
             VLAN to hosts."
    ::= { fsMIDhcpSnpInterfaceEntry 10 }

    fsMIDhcpSnpTxNaks OBJECT-TYPE
        SYNTAX      Counter32
        MAX-ACCESS  read-only
        STATUS      current
        DESCRIPTION
            "This object specifies the total number of DHCP Naks sent out on this
             VLAN to hosts."
    ::= { fsMIDhcpSnpInterfaceEntry 11 }

    fsMIDhcpSnpNoOfDiscards OBJECT-TYPE
        SYNTAX      Counter32
        MAX-ACCESS  read-only
        STATUS      current
        DESCRIPTION
            "This object specifies the total number of DHCP packets from hosts dropped 
             on this VLAN."
    ::= { fsMIDhcpSnpInterfaceEntry 12 }

    fsMIDhcpSnpMacDiscards OBJECT-TYPE
        SYNTAX      Counter32
        MAX-ACCESS  read-only
        STATUS      current
        DESCRIPTION
            "This object specifies the total number of DHCP packets from hosts dropped 
             due to failure in MAC Address verification."
    ::= { fsMIDhcpSnpInterfaceEntry 13 }

    fsMIDhcpSnpServerDiscards OBJECT-TYPE
        SYNTAX      Counter32
        MAX-ACCESS  read-only
        STATUS      current
        DESCRIPTION
            "This object specifies the total number of DHCP packets from hosts dropped 
             because they are supposed to be the messages from a server. 
             The DHCP packets so dropped will include DHCP ACK, DHCP NAK and 
             DHCP OFFERs received from untrusted host ports."
    ::= { fsMIDhcpSnpInterfaceEntry 14 }

    fsMIDhcpSnpOptionDiscards OBJECT-TYPE
        SYNTAX      Counter32
        MAX-ACCESS  read-only
        STATUS      current
        DESCRIPTION
            "This object specifies the total number of DHCP packets from hosts dropped 
             because either option-82 is present in them or giaddr field is 
             set."
    ::= { fsMIDhcpSnpInterfaceEntry 15 }
    
    fsMIDhcpSnpInterfaceStatus OBJECT-TYPE
        SYNTAX      RowStatus
        MAX-ACCESS  read-write
        STATUS      current
        DESCRIPTION
            "This object specifies Row-Status of the interface entry."
    ::= { fsMIDhcpSnpInterfaceEntry 16 }

END
