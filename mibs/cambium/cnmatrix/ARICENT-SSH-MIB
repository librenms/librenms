-- Copyright (C) 2006-2012 Aricent Group . All Rights Reserved

ARICENT-SSH-MIB DEFINITIONS ::= BEGIN

IMPORTS 
   MODULE-IDENTITY, OBJECT-TYPE, 
   enterprises, Integer32, Unsigned32   
   FROM SNMPv2-SMI 
   TruthValue 
   FROM SNMPv2-TC; 

   ssh MODULE-IDENTITY 
      LAST-UPDATED "202201170000Z"
      ORGANIZATION "CAMBIUM NETWORKS SOFTWARE" 
      CONTACT-INFO "support@cambiumnetworks.com" 
      DESCRIPTION
         "The proprietary MIB for SSH."
      REVISION "202201170000Z"
      DESCRIPTION
         "Was added object sshMaxSessions for setting SSH max sessions"
      REVISION "201906140000Z"
      DESCRIPTION 
         "The proprietary MIB for SSH." 
   ::= { enterprises futuresoftware (2076) 97 }


-- ----------------------------------------------------------------- --
-- groups in the MIB
-- ----------------------------------------------------------------- --
 
      sshGeneralGroup             OBJECT IDENTIFIER ::= { ssh 1 }
 
-- ---------------------------------------------------------------- --

-- General Group 

sshVersionCompatibility      OBJECT-TYPE
   SYNTAX      TruthValue 
   MAX-ACCESS  read-write 
   STATUS      current 
   DESCRIPTION 

   "This object is to configure the SSH version compatibility mode.
   When set to TRUE, both SSH version-1 and SSH Version-2 will be supported.
   When set to FALSE, SSH version-2 only will be supported.

   By default SSH version-2 is supported."

   DEFVAL  { false } 
   ::= { sshGeneralGroup 1 }

sshCipherList OBJECT-TYPE
      SYNTAX Integer32(1..511)
      MAX-ACCESS read-write
      STATUS current
      DESCRIPTION
      
      "This object is to configure the cipher-suites list.

      This object takes values as bit mask.  Setting a bit indicates that the 
      corresponding cipher-list will be used for Encryption. 

      The value of each bit position is as given below with bit 0 being the 
      least significant bit:
           BIT 8 - AES-GCM-256
           BIT 7 - AES-GCM-128
           BIT 6 - AES-CTR-256
           BIT 5 - AES-CTR-128
           BIT 4 - CHACHA20-POLY1305
           BIT 3 - AES-CBC-256
           BIT 2 - AES-CBC-128 
           BIT 1 - DES-CBC
           BIT 0 - 3DES-CBC
       All are enabled by default." 
          
   DEFVAL  { 511 }
   ::= { sshGeneralGroup 2}

sshMacList OBJECT-TYPE
      SYNTAX Integer32(1..1023)
      MAX-ACCESS read-write
      STATUS current
      DESCRIPTION

      "This object is to configure the MAC-list.

      This object takes values as bit mask. Setting a bit indicates that the 
      corresponding MAC-list will be used for authentication. 

      The value of each bit position is as given below with bit 0  being the 
      least significant bit: 
            BIT 1 - HMAC-MD5
            BIT 0 - HMAC-SHA1
            BIT 2 - HMAC-SHA256
            BIT 3 - HMAC-SHA512
            BIT 4 - UMAC128
            BIT 5 - HMAC-SHA1-ETM
            BIT 6 - HMAC-MD5-ETM
            BIT 7 - HMAC-SHA256-ETM
            BIT 8 - HMAC-SHA512-ETM
            BIT 9 - UMAC128-ETM"
            
   DEFVAL  { 256 }
   ::= { sshGeneralGroup 3}


sshTrace     OBJECT-TYPE
         SYNTAX        Integer32
         MAX-ACCESS    read-write
         STATUS        current
         DESCRIPTION
         "Set the trace level for SSH.
            BIT 0 - Initialisation and Shutdown Trace.
            BIT 1 - Management trace.
            BIT 2 - Data path trace.
            BIT 3 - Control Plane trace.
            BIT 4 - Packet Dump.
            BIT 5 - OS Resource trace.
            BIT 6 - All Failure trace (All failures including Packet Validation)
            BIT 7 - Buffer Trace.
            BIT 8 - SSH Server Trace.
            
            Note:BIT 0 - Least significant bit
                 BIT 7 - Most significant bit

            For example,setting the trace level to the value -0001 0101, 
            will enable Init-Shutdown, data path and packet dump trace levels.

            Setting all the bits will enable all the trace levels and 
            resetting them will disable all the trace levels."

         ::= { sshGeneralGroup 4 }

sshStatus  OBJECT-TYPE
   SYNTAX      TruthValue 
   MAX-ACCESS  read-write
   STATUS      current
   DESCRIPTION
      "This object is for enabling or disabling ssh in the system."

   DEFVAL  { true }
   ::= { sshGeneralGroup 5}
sshTransportMaxAllowedBytes        OBJECT-TYPE
        SYNTAX                 Integer32(1..32768)
        MAX-ACCESS        read-write
        STATUS                current
        DESCRIPTION
        "This object is used to configure the maximum number of bytes allowed in an SSH transport connection. The SSH connection will be allowed only if the packet size does not exceed the value configured in this object and dropped otherwise."
   DEFVAL    { 32768 }
   ::= { sshGeneralGroup 6 }

sshSrvBindAddr OBJECT-TYPE
    SYNTAX   OCTET STRING (SIZE (4|16))
    MAX-ACCESS  read-write
    STATUS  current
    DESCRIPTION "This object defines the Ip address on which Ssh Server listens"
    ::=  { sshGeneralGroup 7 }

sshServerBindPortNo OBJECT-TYPE
    SYNTAX   Unsigned32
    MAX-ACCESS  read-write
    STATUS  current
    DESCRIPTION "This object defines the primary port number on which Ssh Server listens"
    DEFVAL    { 22 }
    ::=  { sshGeneralGroup 8 }

sshMaxSessions OBJECT-TYPE
       SYNTAX            Integer32(1..8)
       MAX-ACCESS        read-write
       STATUS            current
       DESCRIPTION "This object defines SSH max sessions"
       DEFVAL    { 8 }
       ::= { sshGeneralGroup 9 }

END
