-- Copyright (C) 2006-2012 Aricent Group . All Rights Reserved

AricentMIMst-MIB DEFINITIONS ::= BEGIN

IMPORTS

    OBJECT-TYPE,MODULE-IDENTITY, Integer32, Unsigned32,
    enterprises,Counter32, TimeTicks,NOTIFICATION-TYPE FROM SNMPv2-SMI
    TEXTUAL-CONVENTION, MacAddress,
    TruthValue, DisplayString, RowStatus        FROM SNMPv2-TC;


futureMIMstMIB MODULE-IDENTITY
    LAST-UPDATED "201209050000Z"
    ORGANIZATION "ARICENT COMMUNICATIONS SOFTWARE"
    CONTACT-INFO "support@aricent.com"
    DESCRIPTION "This mib module is for Proprietary
       Multiple Instance MSTP mib" 
    REVISION "201209050000Z"
    DESCRIPTION "This mib module is for Proprietary
       Multiple Instance MSTP mib" 
::= { enterprises futuresoftware(2076) 118 }

VlanId ::= TEXTUAL-CONVENTION 
    DISPLAY-HINT  "d"
    STATUS      current 
    DESCRIPTION 
        "A 12-bit VLAN ID used in the VLAN Tag header."
    SYNTAX      Integer32 (1..4094)

BridgeId ::= TEXTUAL-CONVENTION
      STATUS  current
      DESCRIPTION
      " Identifier of Bridge in 8 byte format"
        SYNTAX          OCTET STRING (SIZE (8))

Timeout ::= TEXTUAL-CONVENTION
    DISPLAY-HINT "d4"
    STATUS       current
    DESCRIPTION
                " Time out value in 4 byte"
    SYNTAX       Integer32

EnabledStatus ::= TEXTUAL-CONVENTION
    STATUS      current
    DESCRIPTION 
        "A simple status value for the object." 
    SYNTAX      INTEGER { enabled(1), disabled(2) } 
      
      
fsMIDot1sFutureMst     OBJECT IDENTIFIER   ::= { futureMIMstMIB 1 }
fsMIDot1sFsMstTrapsControl OBJECT IDENTIFIER ::= { futureMIMstMIB 2 }
fsMIDot1sFutureMstTraps OBJECT IDENTIFIER ::= { futureMIMstMIB 3 }

-- fsMIDot1qFutureMst group

fsMIMstGlobalTrace OBJECT-TYPE
   SYNTAX        TruthValue
   MAX-ACCESS    read-write
   STATUS        current
   DESCRIPTION
      "This object is used to enable Global Trace 
      Statements in the MSTP Module."
    ::= { fsMIDot1sFutureMst 1 }

fsMIMstGlobalDebug OBJECT-TYPE
   SYNTAX        TruthValue
   MAX-ACCESS    read-write
   STATUS        current
   DESCRIPTION
      "This object is used to enable Global Debug 
      Statements in the MSTP Module."
    ::= { fsMIDot1sFutureMst 2 }

fsMIDot1sFutureMstTable OBJECT-TYPE
    SYNTAX SEQUENCE OF FsMIDot1sFutureMstEntry
    MAX-ACCESS    not-accessible
    STATUS        current
    DESCRIPTION
       "List of per Virtual Context Mst Module Parameters."
    ::= { fsMIDot1sFutureMst 3 }

fsMIDot1sFutureMstEntry OBJECT-TYPE
   SYNTAX       FsMIDot1sFutureMstEntry
   MAX-ACCESS   not-accessible
   STATUS       current
   DESCRIPTION
      "Virtual Context Mst Module Parameters."
   INDEX { fsMIDot1sFutureMstContextId }
   ::= { fsMIDot1sFutureMstTable 1 }

FsMIDot1sFutureMstEntry ::=
    SEQUENCE {
           fsMIDot1sFutureMstContextId
              Integer32,
           fsMIMstSystemControl
              INTEGER,
           fsMIMstModuleStatus
              EnabledStatus,
           fsMIMstMaxMstInstanceNumber
              Integer32,
           fsMIMstNoOfMstiSupported
              Integer32,
           fsMIMstMaxHopCount
              Integer32,
           fsMIMstBrgAddress
              MacAddress,
           fsMIMstCistRoot
              BridgeId,
           fsMIMstCistRegionalRoot
              BridgeId,
           fsMIMstCistRootCost
              Integer32,
           fsMIMstCistRegionalRootCost
              Integer32,
           fsMIMstCistRootPort
              Integer32,
           fsMIMstCistBridgePriority
              Integer32,
           fsMIMstCistBridgeMaxAge
              Timeout,
           fsMIMstCistBridgeForwardDelay
              Timeout,
           fsMIMstCistHoldTime
              Integer32,
           fsMIMstCistMaxAge
              Timeout,
           fsMIMstCistForwardDelay
              Timeout,
           fsMIMstMstpUpCount
              Counter32,
           fsMIMstMstpDownCount
              Counter32,
--         fsMIMstPathCostDefaultType
--            INTEGER,
           fsMIMstTrace
              Integer32,
           fsMIMstDebug
              Integer32,
           fsMIMstForceProtocolVersion
              INTEGER,
           fsMIMstTxHoldCount
              Integer32,
           fsMIMstMstiConfigIdSel
              Integer32,
           fsMIMstMstiRegionName
              OCTET STRING,
           fsMIMstMstiRegionVersion
              Integer32,
           fsMIMstMstiConfigDigest
              OCTET STRING,
           fsMIMstBufferOverFlowCount
              Counter32,
           fsMIMstMemAllocFailureCount
              Counter32,
           fsMIMstRegionConfigChangeCount
              Counter32,
           fsMIMstCistBridgeRoleSelectionSemState
              INTEGER,
           fsMIMstCistTimeSinceTopologyChange
              TimeTicks,
           fsMIMstCistTopChanges
              Counter32,
           fsMIMstCistNewRootBridgeCount
              Counter32,
           fsMIMstCistHelloTime
              Timeout,
           fsMIMstCistBridgeHelloTime
              Timeout,
	       fsMIMstCistDynamicPathcostCalculation
	          TruthValue,
           fsMIMstContextName
              DisplayString,
     	   fsMIMstCalcPortPathCostOnSpeedChg
	          TruthValue,
		   fsMIMstClearBridgeStats
			  TruthValue,
           fsMIMstRcvdEvent
              INTEGER,
           fsMIMstRcvdEventSubType
              Integer32,
           fsMIMstRcvdEventTimeStamp
              Unsigned32,
           fsMIMstPortStateChangeTimeStamp
              Unsigned32,
           fsMIMstFlushInterval
              Timeout,
           fsMIMstCistFlushIndicationThreshold
              Integer32,
           fsMIMstCistTotalFlushCount
		      Counter32,
           fsMIMstBpduGuard
              Integer32,
           fsMIMstStpPerfStatus
              INTEGER,
           fsMIMstInstPortsMap
	      TruthValue,
	   fsMIMstPathCostDefaultType
              INTEGER
	   
    }

fsMIDot1sFutureMstContextId OBJECT-TYPE
   SYNTAX        Integer32 (0..65535)
   MAX-ACCESS    not-accessible
   STATUS        current
   DESCRIPTION
      "Identifies the Virtual Context."
   ::= { fsMIDot1sFutureMstEntry 1 }

fsMIMstSystemControl OBJECT-TYPE
   SYNTAX      INTEGER { start(1), shutdown(2) } 
   MAX-ACCESS  read-write
   STATUS      current
   DESCRIPTION
      "The administrative shutdown status requested by management for the MST  
      feature. The value start (1) indicates that MST should be active in 
      the device on all ports. The value shutdown (2) indicates that MST 
      should be shutdown in the device on all ports. All memory should 
      be released on all ports."
   ::= { fsMIDot1sFutureMstEntry 2 }  

fsMIMstModuleStatus OBJECT-TYPE
   SYNTAX      EnabledStatus
   MAX-ACCESS  read-write
   STATUS      current
   DESCRIPTION
      "The administrative status requested by management for the MST  
      feature. The value enabled(1) indicates that Mst should be enabled  
      in the device on all ports. The value disabled(2) indicates that 
      Mst should be disabled in the device on all ports. The object can 
      be set to enabled(1) if and only if, fsMIMstSystemControl set to start."
   ::= { fsMIDot1sFutureMstEntry 3 }  

fsMIMstMaxMstInstanceNumber OBJECT-TYPE
   SYNTAX      Integer32 (1..64)
   MAX-ACCESS  read-write
   STATUS      current
   DESCRIPTION
      "The Maximun number of spanning trees to be allowed. An user may limit 
      the number of Spanning Tree instances to be allowed in the Bridge. 
      The value reflects the max number of active MSTIs that can be created.
      It does not include the special MSTID, the PTETID, used to identify
      VIDs used by Ethernet Switched Paths (ESPs)."
   ::= { fsMIDot1sFutureMstEntry 4 }  

fsMIMstNoOfMstiSupported OBJECT-TYPE
   SYNTAX      Integer32
   MAX-ACCESS  read-only
   STATUS      current
   DESCRIPTION
      "Indicates Maximum number of spanning tree Instances supported."
   ::= { fsMIDot1sFutureMstEntry 5 } 

fsMIMstMaxHopCount OBJECT-TYPE
   SYNTAX      Integer32 (600..4000)
   MAX-ACCESS  read-write
   STATUS      current
   DESCRIPTION
      "Indicates the Maximum Hop Count value. One-hundredth of the
      configured value will be set as Max Hop Count.
      An agent may return a badValue error if a set is attempted
      to a value which is not a multiples of hundred."
   DEFVAL { 2000 }
   ::= { fsMIDot1sFutureMstEntry 6 }  

fsMIMstBrgAddress OBJECT-TYPE
   SYNTAX      MacAddress
   MAX-ACCESS  read-only
   STATUS      current
   DESCRIPTION
         "The MAC address used by this bridge when it must
          be referred to in a unique fashion.   It is
          recommended that this be the numerically smallest
          MAC address of all ports that belong to this
          bridge.  However it is only required to be unique.
          When concatenated with fsMIMstCistBridgePriority or 
          fsMIMstMstiBridgePriority a unique BridgeIdentifier 
          is formed which is used in the Spanning Tree Protocol."
   ::= { fsMIDot1sFutureMstEntry 7 } 

fsMIMstCistRoot OBJECT-TYPE
   SYNTAX      BridgeId  
   MAX-ACCESS  read-only
   STATUS      current
   DESCRIPTION
        "The bridge identifier of the Root of the common spanning
         tree as determined by the Spanning Tree Protocol
         as executed by this node.  This value is used as
         the CIST Root Identifier parameter in all Configuration
         Bridge PDUs originated by this node."
   ::= { fsMIDot1sFutureMstEntry 8 } 

fsMIMstCistRegionalRoot OBJECT-TYPE
   SYNTAX      BridgeId  
   MAX-ACCESS  read-only
   STATUS      current
   DESCRIPTION
        "The bridge identifier of the Root of the Multiple
         spanning tree region as determined by the Spanning Tree
         Protocol as executed by this node.  This value is used as
         the CIST Regional Root Identifier parameter in all Configuration
         Bridge PDUs originated by this node."
   ::= { fsMIDot1sFutureMstEntry 9 } 

fsMIMstCistRootCost OBJECT-TYPE
   SYNTAX      Integer32 
   MAX-ACCESS  read-only
   STATUS      current
   DESCRIPTION
        "The Cost of the path to the CIST Root as seen 
        from this bridge."
   ::= { fsMIDot1sFutureMstEntry 10 } 

fsMIMstCistRegionalRootCost OBJECT-TYPE
   SYNTAX      Integer32 
   MAX-ACCESS  read-only
   STATUS      current
   DESCRIPTION
        "The Cost of the path to the CIST Regional Root 
        as seen from this bridge."
   ::= { fsMIDot1sFutureMstEntry 11 } 

fsMIMstCistRootPort OBJECT-TYPE
   SYNTAX      Integer32  
   MAX-ACCESS  read-only      
   STATUS      current 
   DESCRIPTION 
      "The Port Number of the Port which offers the lowest    
       path cost from this bridge to the CIST Root Bridge."
   ::= { fsMIDot1sFutureMstEntry 12 } 

fsMIMstCistBridgePriority OBJECT-TYPE
   SYNTAX      Integer32 (0..61440) 
   MAX-ACCESS  read-write
   STATUS      current
   DESCRIPTION
        "The Value of the writable portion of the Bridge
        Identifier comprising of the first two octets.
        The values that are set for Bridge Priority must be 
        in steps of 4096."
   DEFVAL {32768}
   ::= { fsMIDot1sFutureMstEntry 13 } 

fsMIMstCistBridgeMaxAge OBJECT-TYPE
   SYNTAX      Timeout (600..4000)  
   UNITS       "centi-seconds"
   MAX-ACCESS  read-write
   STATUS      current
   DESCRIPTION
        "The value that all bridges use for MaxAge when
         this bridge is acting as the root. The granularity 
         of this timer is specified to be 1 second.
         An agent may return a badValue error if a set is
         attempted to a value which is not a whole number
         of seconds."
   DEFVAL {2000}
   ::= { fsMIDot1sFutureMstEntry 14 } 

fsMIMstCistBridgeForwardDelay OBJECT-TYPE
   SYNTAX      Timeout (400..3000)  
   UNITS       "centi-seconds"
   MAX-ACCESS  read-write
   STATUS      current
   DESCRIPTION
        "The value that all bridges use for ForwardDelay
         when this bridge is acting as the root.  Note that
         802.1D specifies that the range for this
         parameter is related to the value of
         BridgeMaxAge.  The granularity of this
         timer is specified to be 1 second.
         An agent may return a badValue error if a set is
         attempted to a value which is not a whole number
         of seconds."
   DEFVAL {1500}
   ::= { fsMIDot1sFutureMstEntry 15 } 

fsMIMstCistHoldTime OBJECT-TYPE
   SYNTAX      Integer32 
   UNITS       "centi-seconds"
   MAX-ACCESS  read-only  
   STATUS      current
   DESCRIPTION
	 "This time value determines the interval length
	 during which no more than two Configuration bridge
	 PDUs shall be transmitted by this node, in units
	 of hundredths of a second."
   ::= { fsMIDot1sFutureMstEntry 16 } 

fsMIMstCistMaxAge OBJECT-TYPE
   SYNTAX      Timeout
   UNITS       "centi-seconds"
   MAX-ACCESS  read-only  
   STATUS      current
   DESCRIPTION
         "The maximum age of Spanning Tree Protocol
          information learned from the network on any port
          before it is discarded, in units of hundredths of
          a second.  This is the actual value that this
          bridge is currently using."
   ::= { fsMIDot1sFutureMstEntry 17 } 

fsMIMstCistForwardDelay OBJECT-TYPE
   SYNTAX      Timeout
   UNITS       "centi-seconds"
   MAX-ACCESS  read-only  
   STATUS      current
   DESCRIPTION
   	  "This time value, measured in units of hundredths
	   of a second, controls how fast a port changes its
	   spanning state when moving towards the Forwarding
	   state.  The value determines how long the port
	   stays in a particular state before moving to the
	   next state."
   ::= { fsMIDot1sFutureMstEntry 18 } 

fsMIMstMstpUpCount OBJECT-TYPE
   SYNTAX      Counter32 
   MAX-ACCESS  read-only  
   STATUS      current
   DESCRIPTION
        "The number of times MSTP Module has been enabled."
   ::= { fsMIDot1sFutureMstEntry 19 } 

fsMIMstMstpDownCount OBJECT-TYPE
   SYNTAX      Counter32 
   MAX-ACCESS  read-only  
   STATUS      current
   DESCRIPTION
        "The number of times MSTP Module has been disabled."
   ::= { fsMIDot1sFutureMstEntry 20 } 

-- fsMIMstPathCostDefaultType OBJECT-TYPE
-- SYNTAX      INTEGER {
--                stp8021d1998(1),
--                stp8021t2001(2)
--             }
--    MAX-ACCESS  read-write 
--    STATUS      obsolete
--    DESCRIPTION
--         "********* THIS OBJECT IS obsolete **********
--         The version of the Spanning Tree default Path Costs that
--          are to be used by this Bridge.  A value of 8021d1998(1)
--          uses the 16-bit default Path Costs from IEEE Std. 802.1D-1998.
--          A value of stp8021t2001(2) uses the 32-bit default Path
--          Costs from IEEE Std. 802.1t."
--    ::= { fsMIDot1sFutureMstEntry 21 } 

fsMIMstTrace OBJECT-TYPE
   SYNTAX      Integer32 (0..255) 
   MAX-ACCESS  read-write 
   STATUS      current
   DESCRIPTION
      "This object is used to enable Trace Statements in the MSTP
      Module.

      A FOUR BYTE integer is used for enabling the level of tracing. 
      Each BIT in the four byte integer, represents a particular 
      level of Trace. 

      The mapping between the bit positions & the level of trace is 
      as follows: 
      0 - Init and Shutdown Traces
      1 - Management Traces
      2 - Data Path Traces
      3 - Control Plane Traces
      4 - Packet Dump Traces
      5 - Traces related to All Resources except Buffers
      6 - All Failure Traces
      7 - Buffer Traces

      The remaining bits are unused. Combination of trace levels are 
      also allowed.

      For example if the bits 0 and 1 are set, then the Trace
      statements related to Init-Shutdown and management 
      will be printed.

      The user has to enter the corresponding INTEGER VALUE for the
      bits set. For example if bits 0 and 1 are to be set then user has
      to give the value for this object as 3.
      
      Setting the Trace Option to any value will cause the Debug Option
      to be set to 0 (i.e.) the Trace Option and Debug Option are mutually
      exclusive."
      
      DEFVAL  { 0 }
   ::= { fsMIDot1sFutureMstEntry 22 } 

fsMIMstDebug OBJECT-TYPE
   SYNTAX      Integer32 (0..524287)
   MAX-ACCESS  read-write
   STATUS      current
   DESCRIPTION
      "This object is used to enable Debug Statements in the MSTP
      Module.

      A FOUR BYTE integer is used for enabling the level of debugging. 
      Each BIT in the four byte integer, represents a particular 
      level of Debug. 

      The mapping between the bit positions & the level of debug is 
      as follows: 
      0 - Init and Shutdown Debug statements
      1 - Management Debug statements
      2 - Memory related Debug statements
      3 - BPDU related Debug statements
      4 - Event Handling Debug statements
      5 - Timer Module Debug statements
      6 - Port Information SEM Debug statements
      7 - Port Receive SEM Debug statements (valid in the case of MSTP alone)
      8 - Role Selection SEM Debug statements
      9 - Role Transition SEM Debug statements
     10 - State Transition SEM Debug statements
     11 - Protocol Migration SEM Debug statements
     12 - Topology Change SEM Debug statements
     13 - Port Transmit SEM Debug statements
     14 - Bridge Detection SEM Debug statements
     15 - All Failure Debug statements
     16 - Redundancy code flow Debug statements
     17 - State Machine variable changes Debug statements
     18 - Port Receive Pseudo Information SEM Debug statements

      The remaining bits are unused. Combination of debug levels are 
      also allowed.

      For example if the bits 0 and 1 are set, then the Debug
      statements related to Init-Shutdown and management 
      will be printed.

      The user has to enter the corresponding INTEGER VALUE for the
      bits set. For example if bits 0 and 1 are to be set then user has
      to give the value for this object as 3.
      
      Setting the Debug Option to any value will cause the Trace Option
      to be set to 0 (i.e.) the Trace Option and Debug Option are mutually
      exclusive."
      DEFVAL  { 0 }
   ::= { fsMIDot1sFutureMstEntry 23 } 

fsMIMstForceProtocolVersion OBJECT-TYPE
   SYNTAX      INTEGER {
                  stpCompatible(0),
                  rstp(2),
                  mstp(3)
               }
   MAX-ACCESS  read-write 
   STATUS      current
   DESCRIPTION
	"The version of Spanning Tree Protocol the bridge is
	currently running.  The value 'stpCompatible(0)'
	indicates the Spanning Tree Protocol specified in
	IEEE 802.1D and 'rstp(2)' indicates the Rapid Spanning
	Tree Protocol specified in IEEE 802.1w and 'mstp(3)'
	indicates the Multiple Spanning Tree Protocol Specified
	in IEEE 802.1s." 

   DEFVAL { mstp }
   ::= { fsMIDot1sFutureMstEntry 24 } 

fsMIMstTxHoldCount OBJECT-TYPE
    SYNTAX      Integer32 (1..10)
    MAX-ACCESS  read-write
    STATUS      current
    DESCRIPTION
        "The value used by the Port Transmit state machine to limit
         the maximum transmission rate."
    DEFVAL  { 6 }
   ::= { fsMIDot1sFutureMstEntry 25 } 

fsMIMstMstiConfigIdSel OBJECT-TYPE
   SYNTAX      Integer32 (0..255) 
   MAX-ACCESS  read-write 
   STATUS      current
   DESCRIPTION
      "The Configuration Identifier Format Selector used 
       by the Bridge. This has a fixed value of 0 to indicate
       RegionName, RegionVersion are specified as in Standard."
   ::= { fsMIDot1sFutureMstEntry 26 } 

fsMIMstMstiRegionName OBJECT-TYPE
   SYNTAX      OCTET STRING (SIZE (0..32))
   MAX-ACCESS  read-write 
   STATUS      current
   DESCRIPTION
      "The Name for the Region's configuration. By Default 
       Region Name will be equal to the Bridge Mac Address."
   ::= { fsMIDot1sFutureMstEntry 27 } 

fsMIMstMstiRegionVersion OBJECT-TYPE
   SYNTAX      Integer32 (0..65535)
   MAX-ACCESS  read-write 
   STATUS      current
   DESCRIPTION
      "Version of the MST Region."
   ::= { fsMIDot1sFutureMstEntry 28 } 

fsMIMstMstiConfigDigest OBJECT-TYPE
   SYNTAX      OCTET STRING (SIZE (0..32))
   MAX-ACCESS  read-only 
   STATUS      current
   DESCRIPTION
      "The Configuration Digest value for this Region."
   ::= { fsMIDot1sFutureMstEntry 29 } 

fsMIMstBufferOverFlowCount OBJECT-TYPE
   SYNTAX      Counter32 
   MAX-ACCESS  read-only  
   STATUS      current
   DESCRIPTION
        "The number of times Buffer overflows/failures have occured.
        A Trap is generated on the occurence of this event." 
   ::= { fsMIDot1sFutureMstEntry 30 } 

fsMIMstMemAllocFailureCount OBJECT-TYPE
   SYNTAX      Counter32 
   MAX-ACCESS  read-only  
   STATUS      current
   DESCRIPTION
        "The number of times memory allocation failures have occured.
        A Trap is generated on the occurence of this event." 
   ::= { fsMIDot1sFutureMstEntry 31 } 

fsMIMstRegionConfigChangeCount OBJECT-TYPE
   SYNTAX      Counter32 
   MAX-ACCESS  read-only  
   STATUS      current
   DESCRIPTION
        "The number of times a Region Configuration Identifier Change 
	      was detected. 
         A Trap is generated on the occurence of this event." 
   ::= { fsMIDot1sFutureMstEntry 32 } 

fsMIMstCistBridgeRoleSelectionSemState OBJECT-TYPE
      SYNTAX      INTEGER {
                  initbridge (0),
                  roleselection (1)
               }
      MAX-ACCESS  read-only
      STATUS      current
      DESCRIPTION
          "Current state of the Port Role Selection State Machine          
           of this bridge in Common Spanning Tree context"           
   ::= { fsMIDot1sFutureMstEntry 33 } 

fsMIMstCistTimeSinceTopologyChange OBJECT-TYPE
   SYNTAX      TimeTicks 
   UNITS       "centi-seconds"
   MAX-ACCESS  read-only
   STATUS      current
   DESCRIPTION
         "The time (in hundredths of a second) since the
         TcWhile Timer for any port in this Bridge was 
         non-zero for Common Spanning Tree context."
   ::= { fsMIDot1sFutureMstEntry 34 } 

fsMIMstCistTopChanges OBJECT-TYPE
   SYNTAX      Counter32
   MAX-ACCESS  read-only
   STATUS      current
   DESCRIPTION
         "The number of times that there have been atleast
         one non-zero TcWhile Timer on this Bridge for Common
         Spanning Tree context."
   ::= { fsMIDot1sFutureMstEntry 35 } 

fsMIMstCistNewRootBridgeCount OBJECT-TYPE
   SYNTAX      Counter32
   MAX-ACCESS  read-only
   STATUS      current
   DESCRIPTION
         "The number of times this Bridge has detected a Root
          Bridge change for Common Spanning Tree context.
          A Trap is generated on the occurence of this event."
   ::= { fsMIDot1sFutureMstEntry 36 } 

fsMIMstCistHelloTime OBJECT-TYPE
   SYNTAX      Timeout
   UNITS       "centi-seconds"
   MAX-ACCESS  read-only  
   STATUS      current
   DESCRIPTION
           "This time value, measured in units of hundredths
           of a second, specifies the amount of time between
           the transmission of configuration BPDUs by this node
           on any port when it is the root of the spanning tree 
           or trying to become so."
   ::= { fsMIDot1sFutureMstEntry 37 } 

fsMIMstCistBridgeHelloTime OBJECT-TYPE
   SYNTAX      Timeout (100|200)  
   UNITS       "centi-seconds"
   MAX-ACCESS  read-write  
   STATUS      current
   DESCRIPTION
           "The amount of time between the transmission of
           Configuration bridge PDUs by this node in units 
           of hundredths of a second."
      ::= { fsMIDot1sFutureMstEntry 38 }

fsMIMstCistDynamicPathcostCalculation OBJECT-TYPE
      SYNTAX      TruthValue               
      MAX-ACCESS  read-write           
      STATUS      current
      DESCRIPTION
         "This object is used to determine whether dynamic pathcost
          calculation is allowed or not.The value is determined by 
          management. If set to true, pathcost is calculated dynamically 
          from port speed(when the operational status of the port changes 
          from down to up), otherwise the link speed at the time of port 
          creation is used for calculating the path cost. In both cases
          if the user has configured a pathcost for the port that will be 
          used. By default dynamic pathcost calculation is set to false."
      DEFVAL { false }
      ::= { fsMIDot1sFutureMstEntry 39 }

fsMIMstContextName OBJECT-TYPE
      SYNTAX   DisplayString (SIZE (1..32))
      MAX-ACCESS   read-only
      STATUS   current
      DESCRIPTION
         "This object is used to identity the context-name."
      ::= { fsMIDot1sFutureMstEntry 40 }

fsMIMstCalcPortPathCostOnSpeedChg OBJECT-TYPE
      SYNTAX      TruthValue               
      MAX-ACCESS  read-write           
      STATUS      current
      DESCRIPTION
         "This object is used to determine whether dynamic pathcost
          calculation is done for a port for which Port Speed is changing
          dynamically. This is mainly intended for Link Aggregated ports where
          depening on Active ports speed of Link aggregated port changes.
          By default dynamic pathcost calculation on change in speed is set to
          false."
      DEFVAL { false }
      ::= { fsMIDot1sFutureMstEntry 41 }

fsMIMstClearBridgeStats OBJECT-TYPE
      SYNTAX      TruthValue
      MAX-ACCESS  read-write
      STATUS      current
      DESCRIPTION
         "This object is used to clear the statistical counters.When this 
		 object is set to TRUE,it resets the bridge specific counters   
		 and all the interface associated counters to zero.After resetting 
		 the counters the object is set to FALSE again.Configuration of this
		 MIB object to FALSE is not applicable."		 
      ::= { fsMIDot1sFutureMstEntry 42 }


fsMIMstRcvdEvent OBJECT-TYPE

    SYNTAX      INTEGER
    {
        configurationEvent (1),
        bpduEvent (2),
        timerExpiryEvent (3)
    }
    MAX-ACCESS  read-only
    STATUS      current
    DESCRIPTION
        "This object gives information about the recently received event in the system.
        Currently we support only ConfigurationEvent."
    ::= { fsMIDot1sFutureMstEntry 43 }

fsMIMstRcvdEventSubType OBJECT-TYPE
    SYNTAX      Integer32
    MAX-ACCESS  read-only
    STATUS      current
    DESCRIPTION
        "This object gives information about sub-type of the event received in the system
        recently. The value of this object depends on the value of the object fsMstRcvdEvent. 
        For ConfigurationEvent, the sub-types supported are PortUp and PortDown."
    ::= { fsMIDot1sFutureMstEntry 44 }

fsMIMstRcvdEventTimeStamp OBJECT-TYPE
   SYNTAX      Unsigned32
   MAX-ACCESS  read-only
   STATUS      current
   DESCRIPTION
      "The time stamp (in milli seconds) at which event specified by the object fsMstRcvdEvent
      was received in the system at MSTP module recently. This object is introduced to measure the 
      convergence time in MSTP module."
   ::= { fsMIDot1sFutureMstEntry 45 }


fsMIMstPortStateChangeTimeStamp OBJECT-TYPE
   SYNTAX      Unsigned32
   MAX-ACCESS  read-only
   STATUS      current
   DESCRIPTION
      "The time stamp (in milli seconds) at which port state has been changed in  
       the system. This object is introduced to measure the convergence time in MSTP module."
   ::= { fsMIDot1sFutureMstEntry 46 }


fsMIMstFlushInterval OBJECT-TYPE
   SYNTAX      Timeout (0..500) 
   UNITS       "centi-seconds"
   MAX-ACCESS  read-write  
   STATUS      current
   DESCRIPTION
           "This time value, measured in units of hundredths
		   of a second, controls the number of flush indications 
		   invoked from STP module per instance basis. 
		   
		   If set to zero, then normal port and instance based flushing 
		   will take place in MSTP (for backward compatibility, which will 
		   be retained as default value). 

		   If set to non-zero, then instance based flushing will be done.  
		   
		   This scale would help to adjust the timer value, 
		   based on the deployment scenario."
   DEFVAL {0}
   ::= { fsMIDot1sFutureMstEntry 47 }

fsMIMstCistFlushIndicationThreshold OBJECT-TYPE
   SYNTAX      Integer32 (0..65535) 
   MAX-ACCESS  read-write  
   STATUS      current
   DESCRIPTION
         "This indicates the number of flush indications to go before
         timer method triggers. (i.e) The number of flush indications
		 to trigger the FlushInterval Timer. 
		 
		 This value can be configurable only when fsMIMstFlushInterval
		 is other than default value. 
		 
		 When the value is retained as default value and flush interval 
		 is being configured other than default value(0), then 
		 instance based flushing will happen. 
		 
		 When this value is non-default and the flush interval is being 
		 configured other than default value(0), then the port-instance
		 based flushing will happen until the actual flush indication 
		 reaches the threshold. Once the threshold is reached, timer 
		 will be started and during timer expiry instance based 
		 flushing will happen. "
   DEFVAL {0}
   ::= { fsMIDot1sFutureMstEntry 48 }

fsMIMstCistTotalFlushCount OBJECT-TYPE
   SYNTAX      Counter32
   MAX-ACCESS  read-only
   STATUS      current
   DESCRIPTION
         "The number of times flush is being triggered from 
		 the STP stack in CIST level." 
   ::= { fsMIDot1sFutureMstEntry 49 } 
   
fsMIMstBpduGuard OBJECT-TYPE
    SYNTAX      INTEGER    {
                    enable (1),
                    disable (2)
                    }
      MAX-ACCESS  read-write
      STATUS      current
      DESCRIPTION
          "This object configures BPDU guard globally in MSTP 
           and this global BPDU is applicable if and only if no Port specific 
           BpduGuard is configured.
           Enable - enables  BPDU Guard feature on edge ports globally and
           moves the port to disabled discarding state when BPDU is received 
           on the edge ports.
           Disable - disables  BPDU Guard feature on edge ports globally"           
    DEFVAL { 2 }
   ::= { fsMIDot1sFutureMstEntry 50 } 

fsMIMstStpPerfStatus OBJECT-TYPE
   SYNTAX      INTEGER { enable(1), disable(2) }
   MAX-ACCESS  read-write
   STATUS      current
   DESCRIPTION
       "This object enables or disables the collection of performance data for the MSTP
        protocol. 'enable' (1) indicates that collection of mstp performance
        data is enabled in the device on all ports. 'disable'(2)
        indicates the collection of mstp performance data is disabled on all ports."
    DEFVAL { 2 }
   ::= { fsMIDot1sFutureMstEntry 51 }

fsMIMstInstPortsMap OBJECT-TYPE
      SYNTAX      TruthValue
      MAX-ACCESS  read-write
      STATUS      current
      DESCRIPTION
         "This object defines the spanning tree participating ports for an instance based on
          the GVRP enabled status. When the object is enabled and GVRP is enabled in the node,
          the member ports of the vlan which are mapped to the instance alone will be
          participating in the spanning tree topology of the instance. When the object is
          enabled and GVRP is disabled in the node, all the ports in the system will be
          participating in the spanning-tree of the instance. When this object is disabled,
          all the ports in the system will be participating in the spanning-tree of the instance.
          By default this is set to false."
     DEFVAL { false }
     ::= { fsMIDot1sFutureMstEntry 52 }
 
fsMIMstPathCostDefaultType OBJECT-TYPE
SYNTAX      INTEGER {
               stp8021d1998(1),
               stp8021t2001(2)
            }
   MAX-ACCESS  read-write 
   STATUS      current
   DESCRIPTION
        "The version of the Spanning Tree default Path Costs that
         are to be used by this Bridge.  A value of 8021d1998(1)
         uses the 16-bit default Path Costs from IEEE Std. 802.1D-1998.
         A value of stp8021t2001(2) uses the 32-bit default Path
         Costs from IEEE Std. 802.1t."
   DEFVAL { stp8021t2001 }
   ::= { fsMIDot1sFutureMstEntry 53 } 
-- -------------------------------------
-- fsMIDot1sFutureMstTable - End
-- -------------------------------------

-- -----------------------------------------------------------------
-- Future Mst Multiple Spanning Tree Instance Bridge Table
-- -----------------------------------------------------------------

fsMIMstMstiBridgeTable OBJECT-TYPE
   SYNTAX      SEQUENCE OF FsMIMstMstiBridgeEntry      
   MAX-ACCESS  not-accessible 
   STATUS      current 
   DESCRIPTION
      "Table containing Bridge Information specific to Spanning 
       Tree Instance. This table maintains context ID as one 
       more index to support Multiple Instances."
   ::= { fsMIDot1sFutureMst 4 } 
 
fsMIMstMstiBridgeEntry OBJECT-TYPE
   SYNTAX      FsMIMstMstiBridgeEntry       
   MAX-ACCESS  not-accessible
   STATUS      current
   DESCRIPTION
      "Entry indicating the Bridge Information."
   INDEX { fsMIDot1sFutureMstContextId, fsMIMstMstiInstanceIndex }
   ::= { fsMIMstMstiBridgeTable 1 }

FsMIMstMstiBridgeEntry ::=
   SEQUENCE {
      fsMIMstMstiInstanceIndex 
            Integer32,
      fsMIMstMstiBridgeRegionalRoot 
            BridgeId,
      fsMIMstMstiBridgePriority 
            Integer32,
      fsMIMstMstiRootCost 
            Integer32,
      fsMIMstMstiRootPort 
            Integer32,
      fsMIMstMstiTimeSinceTopologyChange 
            TimeTicks,
      fsMIMstMstiTopChanges 
            Counter32,
      fsMIMstMstiNewRootBridgeCount 
            Counter32,
      fsMIMstMstiBridgeRoleSelectionSemState 
            INTEGER,
      fsMIMstInstanceUpCount 
            Counter32,
      fsMIMstInstanceDownCount 
            Counter32,
      fsMIMstOldDesignatedRoot 
            BridgeId,
  	  fsMIMstMstiClearBridgeStats
			TruthValue,
      fsMIMstMstiFlushIndicationThreshold
            Integer32,
      fsMIMstMstiTotalFlushCount
            Counter32,
      fsMIMstiRootPriority
	    Integer32
   }

fsMIMstMstiInstanceIndex OBJECT-TYPE
   SYNTAX      Integer32 (1..64|4094)
   MAX-ACCESS  not-accessible 
   STATUS      current 
   DESCRIPTION 
      "Spanning Tree Instance to which the information belongs. The
       special MSTID of 4094, known as the PTETID, identifies VIDs 
       that are used by Ethernet Switched Paths (ESPs)."
   ::= { fsMIMstMstiBridgeEntry 1 }

fsMIMstMstiBridgeRegionalRoot OBJECT-TYPE
   SYNTAX      BridgeId  
   MAX-ACCESS  read-only      
   STATUS      current 
   DESCRIPTION 
      "MSTI Regional Root Identifier value for the Instance. This value 
       is used as the MSTI Regional Root Identifier parameter in all
       Configuration Bridge PDUs originated by this node"
   ::= { fsMIMstMstiBridgeEntry 2 }

fsMIMstMstiBridgePriority OBJECT-TYPE
   SYNTAX      Integer32 (0..61440) 
   MAX-ACCESS  read-write     
   STATUS      current 
   DESCRIPTION 
      "The writable portion of the MSTI Bridge Identifier.
       comprising of the first two octets.
       The values that are set for Bridge Priority must be 
       in steps of 4096."
   DEFVAL {32768}
   ::= { fsMIMstMstiBridgeEntry 3 }

fsMIMstMstiRootCost OBJECT-TYPE
   SYNTAX      Integer32  
   MAX-ACCESS  read-only      
   STATUS      current 
   DESCRIPTION 
      "The Cost of the path to the MSTI Regional Root as seen 
       by this bridge." 
   ::= { fsMIMstMstiBridgeEntry 4 }

fsMIMstMstiRootPort OBJECT-TYPE
   SYNTAX      Integer32  
   MAX-ACCESS  read-only      
   STATUS      current 
   DESCRIPTION 
      "The Port Number of the Port which offers the lowest    
       path cost from this bridge to the MSTI Region Root Bridge."
   ::= { fsMIMstMstiBridgeEntry 5 }

fsMIMstMstiTimeSinceTopologyChange OBJECT-TYPE
   SYNTAX      TimeTicks 
   UNITS       "centi-seconds"
   MAX-ACCESS  read-only
   STATUS      current
   DESCRIPTION
         "The time (in hundredths of a second) since the
         TcWhile Timer for any port in this Bridge was 
         non-zero for this spanning tree instance."
   ::= { fsMIMstMstiBridgeEntry 6 }

fsMIMstMstiTopChanges OBJECT-TYPE
   SYNTAX      Counter32
   MAX-ACCESS  read-only
   STATUS      current
   DESCRIPTION
         "The number of times that there have been atleast
         one non-zero TcWhile Timer on this Bridge for this
         spanning tree instance."
   ::= { fsMIMstMstiBridgeEntry 7 }

fsMIMstMstiNewRootBridgeCount OBJECT-TYPE
   SYNTAX      Counter32
   MAX-ACCESS  read-only
   STATUS      current
   DESCRIPTION
         "The number of times this Bridge has detected a Root
          Bridge change for this spanning tree instance.
          A Trap is generated on the occurence of this event."
   ::= { fsMIMstMstiBridgeEntry 8 }

fsMIMstMstiBridgeRoleSelectionSemState OBJECT-TYPE
      SYNTAX      INTEGER {
                  initbridge (0),
                  roleselection (1)
               }
      MAX-ACCESS  read-only
      STATUS      current
      DESCRIPTION
          "Current state of the Port Role Selection State Machine          
           for this spanning tree instance for this bridge."           
   ::= { fsMIMstMstiBridgeEntry 9 }

fsMIMstInstanceUpCount OBJECT-TYPE
   SYNTAX      Counter32 
   MAX-ACCESS  read-only  
   STATUS      current
   DESCRIPTION
        "The number of times a new spanning tree instance has
         been created. 
         A Trap is generated on the occurence of this event."
   ::= { fsMIMstMstiBridgeEntry 10 }

fsMIMstInstanceDownCount OBJECT-TYPE
   SYNTAX      Counter32 
   MAX-ACCESS  read-only  
   STATUS      current
   DESCRIPTION
        "The number of times a spanning tree instance has
         been deleted.
         A Trap is generated on the occurence of this event."
   ::= { fsMIMstMstiBridgeEntry 11 }

fsMIMstOldDesignatedRoot OBJECT-TYPE
       SYNTAX  BridgeId
       MAX-ACCESS  read-only
       STATUS  current
       DESCRIPTION
               "The bridge identifier of the old root of the spanning
               tree instance as determined by the Spanning Tree Protocol
               as executed by this node. "
       ::= { fsMIMstMstiBridgeEntry 12 }


fsMIMstMstiClearBridgeStats OBJECT-TYPE
		SYNTAX TruthValue
		MAX-ACCESS  read-write
		STATUS  current
		DESCRIPTION
			 "This object is used to clear the statistical counters.When this 
		 	  object is set to TRUE,it resets the bridge specific counters   
		      and all the interface associated counters,for the given instance,
              to zero.After resetting the counters the object is set to FALSE 
              again.Configuration of this MIB object to FALSE is not applicable."		 
		::= { fsMIMstMstiBridgeEntry 13 }

fsMIMstMstiFlushIndicationThreshold OBJECT-TYPE
   SYNTAX      Integer32 (0..65535) 
   MAX-ACCESS  read-write  
   STATUS      current
   DESCRIPTION
         "This indicates the number of flush indications to go before
         timer method triggers. (i.e) The number of flush indications
		 to trigger the FlushInterval Timer. 

		 This value can be configurable only when fsMIMstFlushInterval
		 is other than default value. 
		 
		 When the value is retained as default value and flush interval 
		 is being configured other than default value(0), then 
		 instance based flushing will happen. 
		 
		 When this value is non-default and the flush interval is being 
		 configured other than default value(0), then the port-instance
		 based flushing will happen until the actual flush indication 
		 reaches the threshold. Once the threshold is reached, timer 
		 will be started and during timer expiry instance based 
		 flushing will happen. "
   DEFVAL {0}
   ::= { fsMIMstMstiBridgeEntry 14 }

fsMIMstMstiTotalFlushCount OBJECT-TYPE
   SYNTAX      Counter32
   MAX-ACCESS  read-only
   STATUS      current
   DESCRIPTION
         "The number of times flush is being triggered from 
		 the STP stack for this specific instance level." 
     ::= { fsMIMstMstiBridgeEntry 15 } 

fsMIMstiRootPriority OBJECT-TYPE
   SYNTAX      INTEGER    {
                    primary (1),
                    secondary (2),
                    none (3)
                    }
   MAX-ACCESS  read-write
   STATUS      current
   DESCRIPTION
       "This object configures a switch to become either the root or the backup root (secondary)for the specified
       spanning-tree instance.

       Primary - Sets the bridge as root, by setting the priority of the bridge to 4096 less than
       the root bridge priority.
       If the bridge is already a root bridge, no operation happens.

       Secondary - Sets the bridge priority 28672. The switch is then likely to become the root switch for
       the specified instance if the primary root switch fails.

       None - Sets the bridge priority to default value i.e. 32768. "

   DEFVAL {3}
   ::= { fsMIMstMstiBridgeEntry 16 }

-- -----------------------------------------------------------------
-- Future Mst VlanId to Instance Mapping Table              
-- -----------------------------------------------------------------

fsMIMstVlanInstanceMappingTable OBJECT-TYPE
    SYNTAX      SEQUENCE OF FsMIMstVlanInstanceMappingEntry
    MAX-ACCESS  not-accessible
    STATUS      current
    DESCRIPTION
          "This table contains one entry for each instance of MSTP. 
	  This table maintains context ID as one more index to 
	  support Multiple Instances." 
     ::= { fsMIDot1sFutureMst 5 }

fsMIMstVlanInstanceMappingEntry OBJECT-TYPE
      SYNTAX      FsMIMstVlanInstanceMappingEntry
      MAX-ACCESS  not-accessible
      STATUS      current
      DESCRIPTION
          "A conceptual row containing the status of the MSTP instance."
      INDEX  { fsMIDot1sFutureMstContextId, fsMIMstInstanceIndex }
      ::= { fsMIMstVlanInstanceMappingTable 1 }

FsMIMstVlanInstanceMappingEntry ::= 
   SEQUENCE {
       fsMIMstInstanceIndex  
            Integer32,
       fsMIMstMapVlanIndex 
            VlanId,
       fsMIMstUnMapVlanIndex 
            VlanId,
       fsMIMstSetVlanList 
            OCTET STRING,
       fsMIMstResetVlanList 
            OCTET STRING,
       fsMIMstInstanceVlanMapped 
            OCTET STRING,
       fsMIMstInstanceVlanMapped2k 
            OCTET STRING,
       fsMIMstInstanceVlanMapped3k 
            OCTET STRING,
       fsMIMstInstanceVlanMapped4k 
            OCTET STRING
   }

fsMIMstInstanceIndex OBJECT-TYPE
      SYNTAX      Integer32 (1..64|4094)
      MAX-ACCESS  not-accessible
      STATUS      current
      DESCRIPTION
          "An arbitrary integer within the range from 1 to the value of
           Max Instance Number that uniquely identifies an instance. In
           a Bridge that supports PBB-TE, the special MSTID of 4094, the
           PTETID, identifies VIDs that can be used by Ethernet Switched
           Paths (ESPs). ESPs are provisioned seperately by any external agent
           and do not use spanning tree."
      ::= { fsMIMstVlanInstanceMappingEntry 1 }

fsMIMstMapVlanIndex OBJECT-TYPE
      SYNTAX        VlanId
      MAX-ACCESS    read-write
      STATUS        current
      DESCRIPTION 
          "The VlanId will get mapped to the spanning tree instance 
           specified. All the Instance Specific information for the 
           Member ports of the Vlan will be created.This object is 
           used only for SET operation.GET Operation returns null values.
           If the VlanId to Instance Mapping has to be known then any 
           one of the VlanMapped object should be used."
      ::= { fsMIMstVlanInstanceMappingEntry 2 }

fsMIMstUnMapVlanIndex OBJECT-TYPE
      SYNTAX        VlanId
      MAX-ACCESS    read-write
      STATUS        current
      DESCRIPTION 
          "The VlanId will get unmapped from spanning tree instance
          to which it it mapped. All the Instance Specific information
          for the Member ports of the Vlan will get released.This object 
          is used only for SET operation.GET Operation returns null values."
      ::= { fsMIMstVlanInstanceMappingEntry 3 }

fsMIMstSetVlanList OBJECT-TYPE
    SYNTAX     OCTET STRING (SIZE (0..512))
    MAX-ACCESS read-write
    STATUS     current
    DESCRIPTION
   	 "A string of octets containing one bit per VLAN. The
	  first octet corresponds to VLANs with VlanIndex values
	  1 through 8; the second octet to VLANs 9 through
	  16 etc.  The most significant bit of each octet
	  corresponds to the lowest VlanIndex value in that octet.
	  The set of vlans configured by management to map for this 
	  Instance.  If the VlanId to Instance Mapping has to be known
      then any one of the VlanMapped object should be used.If a 
      vlan is already mapped to this Instance, it may not be mapped 
      again. This object is used only for SET operation.
      GET Operation returns null values."
    ::= { fsMIMstVlanInstanceMappingEntry 4 }

fsMIMstResetVlanList OBJECT-TYPE
    SYNTAX     OCTET STRING (SIZE (0..512))
    MAX-ACCESS read-write
    STATUS     current
    DESCRIPTION
   	 "A string of octets containing one bit per VLAN. The
	  first octet corresponds to VLANs with VlanIndex values
	  1 through 8; the second octet to VLANs 9 through
	  16 etc.  The most significant bit of each octet
	  corresponds to the lowest VlanIndex value in that octet.
	  The set of vlans configured by management to unmap from this 
	  Instance. A vlan may not be unmapped from this instance if 
	  it is not already mapped to this Instance. This object is
      used only for SET operation.GET Operation returns null values."
    ::= { fsMIMstVlanInstanceMappingEntry 5 }

fsMIMstInstanceVlanMapped OBJECT-TYPE
    SYNTAX     OCTET STRING (SIZE (0..128))
    MAX-ACCESS read-only
    STATUS     current
    DESCRIPTION
            "A string of octets containing one bit per VLAN. The
            first octet corresponds to VLANs with VlanIndex values
            1 through 8; the second octet to VLANs 9 through
            16 etc.  The most significant bit of each octet
            corresponds to the lowest VlanIndex value in that octet.

            For each VLAN that is mapped to this MSTP instance,
            the bit corresponding to that VLAN is set to '1'."
    ::= { fsMIMstVlanInstanceMappingEntry 6 }

fsMIMstInstanceVlanMapped2k OBJECT-TYPE
    SYNTAX     OCTET STRING (SIZE (0..128))
    MAX-ACCESS read-only
    STATUS     current
    DESCRIPTION
            "A string of octets containing one bit per VLAN for
            VLANS with VlanIndex values 1025 through 2048. The
            first octet corresponds to VLANs with VlanIndex values
            1025 through 1032; the second octet to VLANs 1033
            through 1040 etc.  The most significant bit of each
            octet corresponds to the lowest VlanIndex value in that
            octet.

            For each VLAN that is mapped to this MSTP instance,
            the bit corresponding to that VLAN is set to '1'.
            
            This object is only instantiated on devices with 
            support for VlanIndex values up to 4095."
    ::= { fsMIMstVlanInstanceMappingEntry 7 }

fsMIMstInstanceVlanMapped3k OBJECT-TYPE
    SYNTAX     OCTET STRING (SIZE (0..128))
    MAX-ACCESS read-only
    STATUS     current
    DESCRIPTION
            "A string of octets containing one bit per VLAN for
            VLANS with VlanIndex values 2049 through 3072. The
            first octet corresponds to VLANs with VlanIndex values
            of 2049 through 2056; the second octet to VLANs 2057
            through 2064 etc.  The most significant bit of each
            octet corresponds to the lowest VlanIndex value in that
            octet.

            For each VLAN that is mapped to this MSTP instance,
            the bit corresponding to that VLAN is set to '1'.

            This object is only instantiated on devices with 
            support for VlanIndex values up to 4095."
    ::= { fsMIMstVlanInstanceMappingEntry 8 }

fsMIMstInstanceVlanMapped4k OBJECT-TYPE
    SYNTAX     OCTET STRING (SIZE (0..128))
    MAX-ACCESS read-only
    STATUS     current
    DESCRIPTION
            "A string of octets containing one bit per VLAN for
            VLANS with VlanIndex values 3073 through 4095. The
            first octet corresponds to VLANs with VlanIndex values
            3073 through 3080; the second octet to VLANs 3081
            through 3088 etc.  The most significant bit of each
            octet corresponds to the lowest VlanIndex value in that
            octet.

            For each VLAN that is mapped to this MSTP instance,
            the bit corresponding to that VLAN is set to '1'.

            This object is only instantiated on devices with 
            support for VlanIndex values up to 4095."
    ::= { fsMIMstVlanInstanceMappingEntry 9 }

-- -----------------------------------------------------------------
-- Future Mst Common Spanning Tree Port Table     
-- -----------------------------------------------------------------

fsMIMstCistPortTable OBJECT-TYPE
    SYNTAX      SEQUENCE OF FsMIMstCistPortEntry              
    MAX-ACCESS  not-accessible
    STATUS      current
    DESCRIPTION
          "This table contains Common Spanning Tree Port
           Information."
     ::= { fsMIDot1sFutureMst 6 }

fsMIMstCistPortEntry OBJECT-TYPE
      SYNTAX      FsMIMstCistPortEntry               
      MAX-ACCESS  not-accessible
      STATUS      current
      DESCRIPTION
          "A list of information maintained by every port for 
          Common Spanning tree."
      INDEX  { fsMIMstCistPort }
      ::= { fsMIMstCistPortTable 1 }

FsMIMstCistPortEntry ::= 
   SEQUENCE {
       fsMIMstCistPort  
            Integer32,
       fsMIMstCistPortPathCost 
            Integer32,
       fsMIMstCistPortPriority 
            Integer32,
       fsMIMstCistPortDesignatedRoot 
            BridgeId,
       fsMIMstCistPortDesignatedBridge 
            BridgeId,
       fsMIMstCistPortDesignatedPort 
            OCTET STRING,
       fsMIMstCistPortAdminP2P 
            INTEGER,
       fsMIMstCistPortOperP2P 
            TruthValue,
       fsMIMstCistPortAdminEdgeStatus 
            TruthValue,
       fsMIMstCistPortOperEdgeStatus 
            TruthValue,
       fsMIMstCistPortProtocolMigration 
            TruthValue,
       fsMIMstCistPortState 
            INTEGER,
       fsMIMstCistForcePortState 
            INTEGER,
       fsMIMstCistPortForwardTransitions 
            Counter32,
       fsMIMstCistPortRxMstBpduCount
            Counter32,
       fsMIMstCistPortRxRstBpduCount
            Counter32,
       fsMIMstCistPortRxConfigBpduCount
            Counter32,
       fsMIMstCistPortRxTcnBpduCount
            Counter32,
       fsMIMstCistPortTxMstBpduCount
            Counter32,
       fsMIMstCistPortTxRstBpduCount
            Counter32,
       fsMIMstCistPortTxConfigBpduCount
            Counter32,
       fsMIMstCistPortTxTcnBpduCount
            Counter32,
       fsMIMstCistPortInvalidMstBpduRxCount
            Counter32,
       fsMIMstCistPortInvalidRstBpduRxCount
            Counter32,
       fsMIMstCistPortInvalidConfigBpduRxCount
            Counter32,
       fsMIMstCistPortInvalidTcnBpduRxCount
            Counter32,
       fsMIMstCistPortTransmitSemState 
            INTEGER,        
       fsMIMstCistPortReceiveSemState 
            INTEGER,        
       fsMIMstCistPortProtMigrationSemState 
            INTEGER,        
       fsMIMstCistProtocolMigrationCount 
            Counter32,
       fsMIMstCistPortDesignatedCost 
            Integer32,
       fsMIMstCistPortRegionalRoot 
            BridgeId,
       fsMIMstCistPortRegionalPathCost 
            Integer32,
       fsMIMstCistSelectedPortRole 
            INTEGER,
       fsMIMstCistCurrentPortRole  
            INTEGER,
       fsMIMstCistPortInfoSemState 
            INTEGER,        
       fsMIMstCistPortRoleTransitionSemState 
            INTEGER,        
       fsMIMstCistPortStateTransitionSemState 
            INTEGER,         
       fsMIMstCistPortTopologyChangeSemState 
            INTEGER,
       fsMIMstCistPortHelloTime 
            Timeout,
       fsMIMstCistPortOperVersion
            INTEGER,
       fsMIMstCistPortEffectivePortState
            TruthValue,
       fsMIMstCistPortAutoEdgeStatus 
            TruthValue,
       fsMIMstCistPortRestrictedRole 
           TruthValue, 
       fsMIMstCistPortRestrictedTCN 
           TruthValue,
       fsMIMstCistPortAdminPathCost
           Integer32,
       fsMIMstCistPortEnableBPDURx
           TruthValue,
       fsMIMstCistPortEnableBPDUTx
           TruthValue,
       fsMIMstCistPortPseudoRootId
            BridgeId,
       fsMIMstCistPortIsL2Gp
           TruthValue,
       fsMIMstCistPortLoopGuard
           TruthValue,
       fsMIMstCistPortClearStats
  	   TruthValue,
       fsMIMstCistPortRcvdEvent
           INTEGER,
       fsMIMstCistPortRcvdEventSubType
           Integer32,
       fsMIMstCistPortRcvdEventTimeStamp
           Unsigned32,
       fsMIMstCistLoopInconsistentState 
           TruthValue,
       fsMIMstCistPortBpduGuard
           Integer32,
       fsMIMstCistPortRootGuard
	   TruthValue,
       fsMIMstCistPortRootInconsistentState
	   TruthValue,
       fsMIMstCistPortErrorRecovery
	   Timeout,
       fsMIMstPortBpduInconsistentState
       TruthValue,
       fsMIMstPortBpduGuardAction
       Integer32,
        fsMIMstCistPortTCDetectedCount
         Counter32,
        fsMIMstCistPortTCReceivedCount
         Counter32,
        fsMIMstCistPortTCDetectedTimeStamp
         TimeTicks,
        fsMIMstCistPortTCReceivedTimeStamp
         TimeTicks,
        fsMIMstCistPortRcvInfoWhileExpCount
         Counter32,
        fsMIMstCistPortRcvInfoWhileExpTimeStamp
         TimeTicks,
        fsMIMstCistPortProposalPktsSent
         Counter32,
        fsMIMstCistPortProposalPktsRcvd
         Counter32,
        fsMIMstCistPortProposalPktSentTimeStamp
         TimeTicks,
        fsMIMstCistPortProposalPktRcvdTimeStamp
         TimeTicks,
        fsMIMstCistPortAgreementPktSent
         Counter32,
        fsMIMstCistPortAgreementPktRcvd
         Counter32,
        fsMIMstCistPortAgreementPktSentTimeStamp
         TimeTicks,
        fsMIMstCistPortAgreementPktRcvdTimeStamp
         TimeTicks,
        fsMIMstCistPortImpStateOccurCount
         Counter32,
        fsMIMstCistPortImpStateOccurTimeStamp
         TimeTicks,
        fsMIMstCistPortOldPortState
          INTEGER
}

fsMIMstCistPort OBJECT-TYPE
      SYNTAX      Integer32 (1..65535)
      MAX-ACCESS  not-accessible
      STATUS      current
      DESCRIPTION
          "The Port number of the port for which this entry contains   
           spanning tree information."                                      
      ::= { fsMIMstCistPortEntry 1 }

fsMIMstCistPortPathCost OBJECT-TYPE
      SYNTAX      Integer32 (1..200000000)
      MAX-ACCESS  read-write           
      STATUS      current
      DESCRIPTION
            "The contribution of this port to the path cost of
             paths towards the CIST Root which include this port."
      ::= { fsMIMstCistPortEntry 2 }

fsMIMstCistPortPriority OBJECT-TYPE
      SYNTAX      Integer32 (0..240)
      MAX-ACCESS  read-write           
      STATUS      current
      DESCRIPTION
          "The four most significant bits of the Port Identifier 
          of the Spanning Tree instance can be modified by setting 
          the CistPortPriority value. The values that are set for Port 
          Priority must be in steps of 16."
     DEFVAL {128}
      ::= { fsMIMstCistPortEntry 3 }

fsMIMstCistPortDesignatedRoot OBJECT-TYPE
      SYNTAX      BridgeId                 
      MAX-ACCESS  read-only            
      STATUS      current
      DESCRIPTION
          "The unique Bridge Identifier of the bridge recorded as the  
           CIST Root in the configuration BPDUs transmitted."      
      ::= { fsMIMstCistPortEntry 4 }

fsMIMstCistPortDesignatedBridge OBJECT-TYPE
      SYNTAX      BridgeId                 
      MAX-ACCESS  read-only            
      STATUS      current
      DESCRIPTION
          "The unique Bridge Identifier of the bridge which this port  
           considers to be the Designated Bridge for the port's segment."   
      ::= { fsMIMstCistPortEntry 5 }

fsMIMstCistPortDesignatedPort OBJECT-TYPE
      SYNTAX  OCTET STRING (SIZE (2))
      MAX-ACCESS  read-only            
      STATUS      current
      DESCRIPTION
          "The Port identifier of the port on the Designated Bridge    
           for this port's segment."                                           
      ::= { fsMIMstCistPortEntry 6 }

fsMIMstCistPortAdminP2P OBJECT-TYPE
      SYNTAX      INTEGER {               
                    forceTrue(0),
                    forceFalse(1),
                    auto(2)
                  }
      MAX-ACCESS  read-write           
      STATUS      current
      DESCRIPTION
          "The administrative point-to-point status of the LAN segment
          attached to this port.  A value of forceTrue(0) indicates that
          this port should always be treated as if it is connected to
          a point-to-point link.  A value of forceFalse(1) indicates
          that this port should be treated as having a shared media
          connection.  A value of auto(2) indicates that this port is
          considered to have a point-to-point link if it is an Aggregator
          and all of its members are aggregatable, or if the MAC entity
          is configured for full duplex operation, either through
          auto-negotiation or by management means."
      ::= { fsMIMstCistPortEntry 7 }

fsMIMstCistPortOperP2P OBJECT-TYPE
      SYNTAX      TruthValue               
      MAX-ACCESS  read-only            
      STATUS      current
      DESCRIPTION
          "The operational point-to-point status of the LAN segment
          attached to this port.  It indicates whether a port is
          considered to have a point-to-point connection or not.
          The value is determined by management or by auto-detection,
          as described in the fsMIMstCistPortAdminP2P object."
      ::= { fsMIMstCistPortEntry 8 }

fsMIMstCistPortAdminEdgeStatus OBJECT-TYPE
      SYNTAX      TruthValue               
      MAX-ACCESS  read-write           
      STATUS      current
      DESCRIPTION
          "The administrative value of the Edge Port parameter.  A
          value of TRUE(1) indicates that this port should be
          assumed as an edge-port and a value of FALSE(2) indicates
          that this port should be assumed as a non-edge-port."
      ::= { fsMIMstCistPortEntry 9 }

fsMIMstCistPortOperEdgeStatus OBJECT-TYPE
      SYNTAX      TruthValue               
      MAX-ACCESS  read-only            
      STATUS      current
      DESCRIPTION
          "The operational value of the Edge Port parameter.  The
          object is initialized to the value of
          fsMIMstCistPortAdminEdgeStatus and is set FALSE on reception 
          of a BPDU."
      ::= { fsMIMstCistPortEntry 10 }

fsMIMstCistPortProtocolMigration OBJECT-TYPE
      SYNTAX      TruthValue                
      MAX-ACCESS  read-write           
      STATUS      current
      DESCRIPTION
          "This object represents the protocol migration state event
          machine variable 'mcheck' for this port.
          When operating in RSTP/MSTP (version >= 2) mode, writing
          TRUE(1) to this object forces this port to transmit MSTP
          BPDUs.

          Any other operation on this object has no effect and
          it always returns FALSE(2) when read."
      ::= { fsMIMstCistPortEntry 11 }

fsMIMstCistPortState OBJECT-TYPE
      SYNTAX      INTEGER {              
                  disabled (1),
                  discarding (2),
                  learning (4),
                  forwarding (5)
                  }
      MAX-ACCESS  read-only            
      STATUS      current
      DESCRIPTION
          "Current state of the Port as defined by the Common    
           spanning tree protocol." 
      ::= { fsMIMstCistPortEntry 12 }

fsMIMstCistForcePortState OBJECT-TYPE
      SYNTAX      INTEGER {
                   disabled(0),
                   enabled(1)
                  }
      MAX-ACCESS  read-write           
      STATUS      current
      DESCRIPTION
          "Current state of the Port which can be changed to either 
           Disabled or Enabled for ALL spanning tree   
           instances. Setting this object will override the port's
           status in any of the MSTI contexts"                                        
      ::= { fsMIMstCistPortEntry 13 }

fsMIMstCistPortForwardTransitions OBJECT-TYPE 
      SYNTAX      Counter32                
      MAX-ACCESS  read-only            
      STATUS      current
      DESCRIPTION
          "Number of times this port has transitioned to the     
           Forwarding State."                                     
      ::= { fsMIMstCistPortEntry 14 }

fsMIMstCistPortRxMstBpduCount OBJECT-TYPE 
      SYNTAX      Counter32                
      MAX-ACCESS  read-only            
      STATUS      current
      DESCRIPTION
          "Number of MST BPDUs received on this port."     
      ::= { fsMIMstCistPortEntry 15 }

fsMIMstCistPortRxRstBpduCount OBJECT-TYPE 
      SYNTAX      Counter32                
      MAX-ACCESS  read-only            
      STATUS      current
      DESCRIPTION
          "Number of RST BPDUs received on this port."     
      ::= { fsMIMstCistPortEntry 16 }

fsMIMstCistPortRxConfigBpduCount OBJECT-TYPE 
      SYNTAX      Counter32                
      MAX-ACCESS  read-only            
      STATUS      current
      DESCRIPTION
          "Number of Configuration BPDUs received on this port."     
      ::= { fsMIMstCistPortEntry 17 }

fsMIMstCistPortRxTcnBpduCount OBJECT-TYPE 
      SYNTAX      Counter32                
      MAX-ACCESS  read-only            
      STATUS      current
      DESCRIPTION
          "Number of TCN BPDUs received on this port."     
      ::= { fsMIMstCistPortEntry 18 }

fsMIMstCistPortTxMstBpduCount OBJECT-TYPE 
      SYNTAX      Counter32                
      MAX-ACCESS  read-only            
      STATUS      current
      DESCRIPTION
          "Number of MST BPDUs Transmitted from this port."     
      ::= { fsMIMstCistPortEntry 19 }

fsMIMstCistPortTxRstBpduCount OBJECT-TYPE 
      SYNTAX      Counter32                
      MAX-ACCESS  read-only            
      STATUS      current
      DESCRIPTION
          "Number of RST BPDUs Transmitted from this port."     
      ::= { fsMIMstCistPortEntry 20 }

fsMIMstCistPortTxConfigBpduCount OBJECT-TYPE 
      SYNTAX      Counter32                
      MAX-ACCESS  read-only            
      STATUS      current
      DESCRIPTION
          "Number of Configuration BPDUs Transmitted from this port."     
      ::= { fsMIMstCistPortEntry 21 }

fsMIMstCistPortTxTcnBpduCount OBJECT-TYPE 
      SYNTAX      Counter32                
      MAX-ACCESS  read-only            
      STATUS      current
      DESCRIPTION
          "Number of TCN BPDUs Transmitted from this port."     
      ::= { fsMIMstCistPortEntry 22 }

fsMIMstCistPortInvalidMstBpduRxCount OBJECT-TYPE 
      SYNTAX      Counter32                
      MAX-ACCESS  read-only            
      STATUS      current
      DESCRIPTION
          "Number of Invalid MST BPDUs Received on this port."     
      ::= { fsMIMstCistPortEntry 23 }

fsMIMstCistPortInvalidRstBpduRxCount OBJECT-TYPE 
      SYNTAX      Counter32                
      MAX-ACCESS  read-only            
      STATUS      current
      DESCRIPTION
          "Number of Invalid RST BPDUs Received on this port."     
      ::= { fsMIMstCistPortEntry 24 }

fsMIMstCistPortInvalidConfigBpduRxCount OBJECT-TYPE 
      SYNTAX      Counter32                
      MAX-ACCESS  read-only            
      STATUS      current
      DESCRIPTION
          "Number of Invalid Configuration BPDUs Received on this port."     
      ::= { fsMIMstCistPortEntry 25 }

fsMIMstCistPortInvalidTcnBpduRxCount OBJECT-TYPE 
      SYNTAX      Counter32                
      MAX-ACCESS  read-only            
      STATUS      current
      DESCRIPTION
          "Number of Invalid TCN BPDUs Received on this port."     
      ::= { fsMIMstCistPortEntry 26 }

fsMIMstCistPortTransmitSemState OBJECT-TYPE 
      SYNTAX      INTEGER {                 
                  transmitinit (0),
                  transmitperiodic (1),
                  transmitconfig (2),
                  transmittcn (3),
                  transmitrstp (4),
                  idle (5)
               }
      MAX-ACCESS  read-only            
      STATUS      current
      DESCRIPTION
          "Indicates current State of the Port Transmit state machine."
      ::= { fsMIMstCistPortEntry 27 }

fsMIMstCistPortReceiveSemState OBJECT-TYPE 
      SYNTAX      INTEGER {                 
                  discard (0),
                  receive (1)
               }
      MAX-ACCESS  read-only            
      STATUS      current
      DESCRIPTION
          "Indicates current State of the Port Receive state machine."
      ::= { fsMIMstCistPortEntry 28 }

fsMIMstCistPortProtMigrationSemState OBJECT-TYPE 
      SYNTAX      INTEGER {                 
                  init (0),
                  sendrstp (1),
                  sendingrstp (2),
                  sendstp (3),
                  sendingstp (4)
               }
      MAX-ACCESS  read-only            
      STATUS      current
      DESCRIPTION
          "Indicates current State of the Port Protocol Migration
           State machine."
      ::= { fsMIMstCistPortEntry 29 }

fsMIMstCistProtocolMigrationCount OBJECT-TYPE
   SYNTAX      Counter32 
   MAX-ACCESS  read-only  
   STATUS      current
   DESCRIPTION
        "The number of times this Port has migrated from one STP protocol 
        version to another. The relevant protocols are STP-COMPATIBLE and 
        RSTP/MSTP.
        A Trap is generated on the occurence of this event."
      ::= { fsMIMstCistPortEntry 30 }

fsMIMstCistPortDesignatedCost OBJECT-TYPE
      SYNTAX      Integer32
      MAX-ACCESS  read-only           
      STATUS      current
      DESCRIPTION
           "The path cost of the Designated Port of the
            segment connected to this port."
      ::= { fsMIMstCistPortEntry 31 }

fsMIMstCistPortRegionalRoot OBJECT-TYPE
      SYNTAX      BridgeId                 
      MAX-ACCESS  read-only            
      STATUS      current
      DESCRIPTION
          "The unique Bridge Identifier of the bridge recorded as the  
           CIST Regional Root Identifier in the configuration BPDUs 
           transmitted."      
      ::= { fsMIMstCistPortEntry 32 }

fsMIMstCistPortRegionalPathCost OBJECT-TYPE
      SYNTAX      Integer32
      MAX-ACCESS  read-only           
      STATUS      current
      DESCRIPTION
          "The contribution of this port to the path cost of paths     
           towards the CIST Regional Root which include this port."         
      ::= { fsMIMstCistPortEntry 33 }

fsMIMstCistSelectedPortRole OBJECT-TYPE
      SYNTAX      INTEGER {
                   disabled(0),
                   alternate(1),
                   backup(2),
                   root(3),
                   designated(4)
                  }
      MAX-ACCESS  read-only        
      STATUS      current
      DESCRIPTION
          "Selected Port Role of the port for this spanning 
          tree instance."                                      
      ::= { fsMIMstCistPortEntry 34 }

fsMIMstCistCurrentPortRole OBJECT-TYPE
      SYNTAX      INTEGER {              
                   disabled(0),
                   alternate(1),
                   backup(2),
                   root(3),
                   designated(4)
                  }
      MAX-ACCESS  read-only        
      STATUS      current
      DESCRIPTION
          "Current Port Role of the port for this spanning 
          tree instance."                                      
      ::= { fsMIMstCistPortEntry 35 }

fsMIMstCistPortInfoSemState OBJECT-TYPE
	SYNTAX      INTEGER {
               disabled (0),
               aged (1),
               update (2),
               superiordesg (3),
               repeatdesg (4),
               inferiordesg (5),
               notdesg (6),
               present (7),
               receive (8),
               other (9)
            }                
      MAX-ACCESS  read-only        
      STATUS      current
      DESCRIPTION
          "Current state of the Port Information State Machine          
           for this port in this spanning tree context."                                      
      ::= { fsMIMstCistPortEntry 36 }

fsMIMstCistPortRoleTransitionSemState OBJECT-TYPE
      SYNTAX      INTEGER {                
                  init (0),
                  disableport (1),
                  disabledport (2),
                  rootport (3),
                  designatedport (4),
                  alternateport (5),
                  masterport (6)
               }
      MAX-ACCESS  read-only        
      STATUS      current
      DESCRIPTION
          "Current state of the Port Role Transition State Machine          
           for this port in this spanning tree context."                                      
      ::= { fsMIMstCistPortEntry 37 }

fsMIMstCistPortStateTransitionSemState OBJECT-TYPE
      SYNTAX      INTEGER {                
                  discarding (0),
                  learning (1),
                  forwarding (2)
               }
      MAX-ACCESS  read-only        
      STATUS      current
      DESCRIPTION
          "Current state of the Port State Transition State Machine          
           for this port in this spanning tree context."                                      
      ::= { fsMIMstCistPortEntry 38 }

fsMIMstCistPortTopologyChangeSemState OBJECT-TYPE
      SYNTAX      INTEGER {                
                  inactive (0),
                  learning (1),
                  detected (2),
                  active (3),
                  notifiedtcn (4),
                  notifiedtc (5),
                  propagating (6),
                  acknowledged (7)
               }
      MAX-ACCESS  read-only        
      STATUS      current
      DESCRIPTION
          "Current state of the Topology Change State Machine          
           for this port in this spanning tree context."                                      
      ::= { fsMIMstCistPortEntry 39 }

fsMIMstCistPortHelloTime OBJECT-TYPE
   SYNTAX      Timeout (100|200)  
   UNITS       "centi-seconds"
   MAX-ACCESS  read-write  
   STATUS      current
   DESCRIPTION
   	  "The amount of time between the transmission of
	   Configuration bridge PDUs by this node on this port
	   in units of hundredths of a second."
      ::= { fsMIMstCistPortEntry 40 }

fsMIMstCistPortOperVersion OBJECT-TYPE
   SYNTAX      INTEGER {
               stpCompatible(0),
               rstp(2),
               mstp(3)
            }
   MAX-ACCESS  read-only  
   STATUS      current
   DESCRIPTION
   	  "This indicates whether the Port is operationally in the Mstp
       mode, Rstp mode or the Stp-compatible mode i.e., whether the
       Port is transmitting MST BPDUs, RST BPDUs or Config/TCN BPDUs."
      ::= { fsMIMstCistPortEntry 41 }
      
fsMIMstCistPortEffectivePortState OBJECT-TYPE
      SYNTAX      TruthValue
      MAX-ACCESS  read-only            
      STATUS      current
      DESCRIPTION
          "The effective operational state of the port for CIST. This will
          TRUE only when the port is operationally up in the Interface level
          and Protocol level for CIST. This is will be set to False for all 
          other times."

      ::= { fsMIMstCistPortEntry 42 }

fsMIMstCistPortAutoEdgeStatus OBJECT-TYPE
      SYNTAX      TruthValue               
      MAX-ACCESS  read-write           
      STATUS      current
      DESCRIPTION
          "This parameter when TRUE(1) indicates that detection 
          of a port as Edge Port happens automatically
          and FALSE(2) indicates that this feature is disabled."
      ::= { fsMIMstCistPortEntry 43 }

fsMIMstCistPortRestrictedRole OBJECT-TYPE 
    SYNTAX      TruthValue 
    MAX-ACCESS  read-write 
    STATUS      current 
    DESCRIPTION 
        "A Boolean value set by management. If TRUE causes the Port not 
        to be selected as Root Port for the CIST or any MSTI, even it has 
        the best spanning tree priority vector. Such a Port will be selected 
        as an Alternate Port after the Root Port has been selected. This 
        parameter should be FALSE by default. If set it can cause lack of 
        spanning tree connectivity. It is set by a network administrator to 
        prevent bridges external to a core region of the network influencing 
        the spanning tree active topology, possibly because those bridges are 
        not under the full control of the administrator. 
       
        This administrator configuration is also known as 'Root Guard'." 

        ::= {fsMIMstCistPortEntry 44} 

fsMIMstCistPortRestrictedTCN OBJECT-TYPE 
    SYNTAX      TruthValue 
    MAX-ACCESS  read-write 
    STATUS      current 
    DESCRIPTION 
        "A Boolean value set by management. If TRUE causes the Port not 
        to propagate received topology change notifications and topology 
        changes to other Ports. This parameter should be FALSE by default. 
        If set it can cause temporary loss of connectivity after changes in 
        a spanning trees active topology as a result of persistent 
        incorrectly learnt station location information. It is set by a 
        network administrator to prevent bridges external to a core region of 
        the network causing address flushing in that region, possibly because 
        those bridges are not under the full control of the administrator or 
        MAC_Operational for the attached LANs transitions frequently." 

        ::= {fsMIMstCistPortEntry 45} 

fsMIMstCistPortAdminPathCost OBJECT-TYPE
    SYNTAX      Integer32 (0..200000000)
    MAX-ACCESS  read-write
    STATUS      current
    DESCRIPTION
        "The administratively assigned value for the contribution
         of this port to the path cost of paths toward the spanning
         tree root.
         Writing a value of '0' assigns the automatically calculated
         default Path Cost value to the port.  If the default Path
         Cost is being used, this object returns '0' when read.
         This complements the object dot1dStpPortPathCost or
         dot1dStpPortPathCost32, which returns the operational value
         of the path cost."
    ::= {fsMIMstCistPortEntry 46}     

fsMIMstCistPortEnableBPDURx OBJECT-TYPE
    SYNTAX      TruthValue
    MAX-ACCESS  read-write
    STATUS      current
    DESCRIPTION
        "A Boolean value set by management. If FALSE, the BPDUs received on
        the port are ignored."
    REFERENCE   "IEEE802.1ah - 13.25.18"
    DEFVAL { true }
        ::= { fsMIMstCistPortEntry 47 }

fsMIMstCistPortEnableBPDUTx OBJECT-TYPE
    SYNTAX      TruthValue
    MAX-ACCESS  read-write
    STATUS      current
    DESCRIPTION
        "A Boolean value set by management. If FALSE, no BPDUs are transmitted
        by this port. This variable should be FALSE before configuring port
        as a Layer Two Gateway Port."
    REFERENCE   "IEEE802.1ah - 13.25.19"
    DEFVAL { true }
        ::= { fsMIMstCistPortEntry 48 }

fsMIMstCistPortPseudoRootId OBJECT-TYPE
    SYNTAX      BridgeId
    MAX-ACCESS  read-write
    STATUS      current
    DESCRIPTION
        "In MSTP Bridge, the pseudoRootId parameter value. By default, it
        is set to the BridgeIdentifier. The pseudoRootId is used by
        Layer Two Gateway Port as the RootId in generated BPDUs."
    REFERENCE   "IEEE802.1ah - 13.25.20"
        ::= { fsMIMstCistPortEntry 49 }

fsMIMstCistPortIsL2Gp OBJECT-TYPE
    SYNTAX      TruthValue
    MAX-ACCESS  read-write
    STATUS      current
    DESCRIPTION
        "A Boolean value set by management. If TRUE, then port is functioning
        as a Layer Two Gateway Port. The fsMIMstCistPortEnableBPDUTx should be
        FALSE to set fsMIMstCistPortIsL2Gp to TRUE."
    REFERENCE   "IEEE802.1ah - 13.25.21"
    DEFVAL { false }
        ::= { fsMIMstCistPortEntry 50 }
                                                                                                
fsMIMstCistPortLoopGuard OBJECT-TYPE
    SYNTAX     TruthValue
    MAX-ACCESS read-write
    STATUS     current
    DESCRIPTION
        "A Boolean value set by management. If TRUE, then it will not age out
        the information even if the peer does not send information. If the port
        continues to receive information through BPDUs the operation
        on this port will be normal. This will be useful when the neighbor
        bridge is faulty, i.e. it cannot send BPDUs but continues to send data
        traffic."

    DEFVAL { false }
        ::= { fsMIMstCistPortEntry 51 }

fsMIMstCistPortClearStats OBJECT-TYPE
    SYNTAX      TruthValue
    MAX-ACCESS  read-write
    STATUS      current
    DESCRIPTION
         "This object is used to clear the statistical counters.When this 
		 object is set to TRUE,it resets the given interface counters
         to zero.After resetting the counters the object is set to
         FALSE again.Configuration of this MIB object to FALSE 
		 is not applicable."		 
	::= { fsMIMstCistPortEntry 52 }

fsMIMstCistPortRcvdEvent OBJECT-TYPE
    SYNTAX      INTEGER{
        configurationEvent (1),
        bpduEvent (2),
        timerExpiryEvent (3)
    }
    MAX-ACCESS  read-only
    STATUS      current
    DESCRIPTION
        "This object gives information about the recently received event in the system.
        Currently we support only ConfigurationEvent."
    ::= { fsMIMstCistPortEntry 53 }


fsMIMstCistPortRcvdEventSubType OBJECT-TYPE
    SYNTAX      Integer32
    MAX-ACCESS  read-only
    STATUS      current
    DESCRIPTION
        "This object gives information about sub-type of the event received in the system
        recently. The value of this object depends on the value of the object fsRstPortRcvdEvent. 
        For ConfigurationEvent, the sub-types supported are PortUp and PortDown."
    ::= { fsMIMstCistPortEntry 54 }

fsMIMstCistPortRcvdEventTimeStamp OBJECT-TYPE
    SYNTAX      Unsigned32
    MAX-ACCESS  read-only
    STATUS      current
    DESCRIPTION
        "This object gives the time stamp (in milli seconds) at which the event specified by the object
        fsMIMstCistPortRcvdEvent was received in the system. This object was introduced to measure the
        convergence time in MSTP module."
    ::= { fsMIMstCistPortEntry 55 }

fsMIMstCistLoopInconsistentState   OBJECT-TYPE 
	SYNTAX      TruthValue 
	MAX-ACCESS  read-only 
	STATUS      current 
	DESCRIPTION 
		" A Boolean value set when the non-designated port on expiry of received information while timer 
		transitions to Designated/Discarding state when the superior BPDU's are not received  with the 
		loop guard feature being enabled on that port. 
		A value of TRUE, indicates that the state of this port is moved into an loop-inconsistent 
		state.A value of  FALSE, indicates that this port is not moved into an loop-inconsistent 
		state " 
	DEFVAL { false } 
	::= { fsMIMstCistPortEntry 56 } 

fsMIMstCistPortBpduGuard OBJECT-TYPE
    SYNTAX      INTEGER    {
                    none (0),
                    enable (1),
                    disable (2)
                    }
      MAX-ACCESS  read-write
      STATUS      current
      DESCRIPTION
          "This configures the BPDU guard feature on this port and has higher priority over Global BPDU Guard.
       Enable - prevents temporary loops and applicable to ports and 
       moves the port to disabled discarding state when BPDU is received on this port.
       Disable - Disables the Bpdu Guard feature and the port state will be maintained till it is manually made up.
       None - removes the BPDU Guard functionality on this port so that when Global BPDU guard
              configuration will take effect if this port is edge port"           
    DEFVAL { 0 }
   ::= { fsMIMstCistPortEntry 57 }

fsMIMstCistPortRootGuard OBJECT-TYPE
    SYNTAX      TruthValue
    MAX-ACCESS  read-write
    STATUS      current
    DESCRIPTION
        "A Boolean value set by management. If TRUE causes the Port not
        to be selected as Root Port for the CIST or any MSTI, even it has
        the best spanning tree priority vector. Such a Port will be selected
        as an Alternate Port after the Root Port has been selected. This
        parameter should be FALSE by default. If set it can cause lack of
        spanning tree connectivity. It is set by a network administrator to
        prevent bridges external to a core region of the network influencing
        the spanning tree active topology, possibly because those bridges are
        not under the full control of the administrator.

        This administrator configuration is also known as 'Root Guard'."
    DEFVAL { false }
        ::= {fsMIMstCistPortEntry 58}


fsMIMstCistPortRootInconsistentState OBJECT-TYPE
    SYNTAX      TruthValue
    MAX-ACCESS  read-only
    STATUS      current
    DESCRIPTION
          " A Boolean value set when the designated port receives a superior BPDU trying to transition itself
            to the Root Port.
            A value of TRUE, indicates that the state of this port is moved into an root-inconsistent
            state.A value of  FALSE, indicates that this port is not moved into an root-inconsistent
            state "
         DEFVAL { false }
    ::= { fsMIMstCistPortEntry 59 }

fsMIMstCistPortErrorRecovery OBJECT-TYPE
   SYNTAX      Timeout (3000..6553500)
   UNITS       "centi-seconds"
   MAX-ACCESS  read-write
   STATUS      current
   DESCRIPTION
          "The amount of time to bring the interface out of the
           error-disabled (err-disabled) state.
           The range is from 30 to 65535 seconds."
   DEFVAL {30000}
      ::= { fsMIMstCistPortEntry 60 }

fsMIMstPortBpduInconsistentState OBJECT-TYPE
   SYNTAX      TruthValue
   MAX-ACCESS  read-only
   STATUS      current
   DESCRIPTION
   "A Boolean value set indicates the port state goes to disabled / discarding
   due to the BPDU guard feature enabled on the port and the port receives BPDU on this.
   A value of TRUE, indicates that the state of this port is moved into an
   bpduguard-inconsistent state due to BPDU reception.
   A value of FALSE, indicates that this port is not received the BPDU when BPDU
   guard is enabled on this port or BPDU guard feature is disabled on that port."
   DEFVAL { false }
   ::= { fsMIMstCistPortEntry 61 }

fsMIMstPortBpduGuardAction OBJECT-TYPE
   SYNTAX     INTEGER    {
            disableDiscarding (1),
            adminDown (2)
    }
    MAX-ACCESS  read-write
    STATUS      current
    DESCRIPTION
         "This object specifies the action to be taken when BPDU is received
         on a BPDU guard enabled port.

         When action is set as admin down error recovery time will be set as
         zero. When action is set as disable-discarding, error recovery time
         will be set as 3000 centi-seconds.

         When action is set as admin down and BPDU is received on this
         port, then the port will be made down. When port is made admin up again,
         port moves to admin down if BPDU is received on this port.

         When BPDU is received in case of disable-discarding state, spanning-tree
         will be disabled on this port and port will move to discarding state.
         On expiry of error recovery timer, spanning tree will be enabled on
         the port. When BPDU is received again, spanning-tree will be disabled
         on the port and port moves to discarding state

         To recover from the admin down or disable discarding state, BPDU guard
         should be disabled on this port."

    DEFVAL { 1 }
   ::= { fsMIMstCistPortEntry 62 }

fsMIMstCistPortTCDetectedCount OBJECT-TYPE
   SYNTAX      Counter32
   MAX-ACCESS  read-only
   STATUS      current
   DESCRIPTION
       "Indicates the number of topology changes detected on this port for CIST instance ."
   ::= { fsMIMstCistPortEntry 63 }

fsMIMstCistPortTCReceivedCount OBJECT-TYPE
   SYNTAX      Counter32
   MAX-ACCESS  read-only
   STATUS      current
   DESCRIPTION
        "Indicates the number of topology change messages received on this port for CIST instance."
   ::= { fsMIMstCistPortEntry 64 }

fsMIMstCistPortTCDetectedTimeStamp OBJECT-TYPE
   SYNTAX      TimeTicks
   UNITS       "centi-seconds"
   MAX-ACCESS  read-only
   STATUS      current
   DESCRIPTION
        "Time stamp(in hundredths of a second) at which the topology change is detected on this port last time for CIST instance."
   ::= { fsMIMstCistPortEntry 65 }

fsMIMstCistPortTCReceivedTimeStamp OBJECT-TYPE
   SYNTAX      TimeTicks
   UNITS       "centi-seconds"
   MAX-ACCESS  read-only
   STATUS      current
   DESCRIPTION
        "Time stamp(in hundredths of a second) at which the topology change message received on this port last time for CIST instance."
   ::= { fsMIMstCistPortEntry 66 }

fsMIMstCistPortRcvInfoWhileExpCount OBJECT-TYPE
   SYNTAX      Counter32
   MAX-ACCESS  read-only
   STATUS      current
   DESCRIPTION
       "Indicates the number of times the received info while timer is expired on this port for CIST instance."
   ::= { fsMIMstCistPortEntry 67 }

fsMIMstCistPortRcvInfoWhileExpTimeStamp OBJECT-TYPE
   SYNTAX      TimeTicks
   UNITS       "centi-seconds"
   MAX-ACCESS  read-only
   STATUS      current
   DESCRIPTION
        "Time stamp(in hundredths of a second) at which the received info while timer is expired on this port last time for CIST instance."
   ::= { fsMIMstCistPortEntry 68 }

fsMIMstCistPortProposalPktsSent OBJECT-TYPE
   SYNTAX      Counter32
   MAX-ACCESS  read-only
   STATUS      current
   DESCRIPTION
        "The number of proposal packets sent by this port for CIST instance."
   ::= { fsMIMstCistPortEntry 69 }

fsMIMstCistPortProposalPktsRcvd OBJECT-TYPE
   SYNTAX      Counter32
   MAX-ACCESS  read-only
   STATUS      current
   DESCRIPTION
        "The number of proposal packets received on this port for CIST instance."
   ::= { fsMIMstCistPortEntry 70 }

fsMIMstCistPortProposalPktSentTimeStamp OBJECT-TYPE
   SYNTAX      TimeTicks
   UNITS       "centi-seconds"
   MAX-ACCESS  read-only
   STATUS      current
   DESCRIPTION
        "Time stamp(in hundredths of a second) at which proposal packet sent by this port last time for CIST instance."
   ::= { fsMIMstCistPortEntry 71 }

fsMIMstCistPortProposalPktRcvdTimeStamp OBJECT-TYPE
   SYNTAX      TimeTicks
   UNITS       "centi-seconds"
   MAX-ACCESS  read-only
   STATUS      current
   DESCRIPTION
        "Time stamp(in hundredths of a second) at which  proposal packet received on this port last time for CIST instance."
   ::= { fsMIMstCistPortEntry 72 }

fsMIMstCistPortAgreementPktSent OBJECT-TYPE
   SYNTAX      Counter32
   MAX-ACCESS  read-only
   STATUS      current
   DESCRIPTION
        "The number of agreement packets sent by this port for CIST instance."
   ::= { fsMIMstCistPortEntry 73 }

fsMIMstCistPortAgreementPktRcvd OBJECT-TYPE
   SYNTAX      Counter32
   MAX-ACCESS  read-only
   STATUS      current
   DESCRIPTION
        "The number of agreement packets received on this port for CIST instance."
   ::= { fsMIMstCistPortEntry 74 }

fsMIMstCistPortAgreementPktSentTimeStamp OBJECT-TYPE
   SYNTAX      TimeTicks
   UNITS       "centi-seconds"
   MAX-ACCESS  read-only
   STATUS      current
   DESCRIPTION
        " Time stamp(in hundredths of a second) at which agreement packet sent by this port last time for CIST instance."
   ::= { fsMIMstCistPortEntry 75 }

fsMIMstCistPortAgreementPktRcvdTimeStamp OBJECT-TYPE
   SYNTAX      TimeTicks
   UNITS       "centi-seconds"
   MAX-ACCESS  read-only
   STATUS      current
   DESCRIPTION
        "Time stamp(in hundredths of a second) at which agreement packet received on this port last time for CIST instance."
   ::= { fsMIMstCistPortEntry 76 }

fsMIMstCistPortImpStateOccurCount OBJECT-TYPE
   SYNTAX      Counter32
   MAX-ACCESS  read-only
   STATUS      current
   DESCRIPTION
        "Indicates the number of times impossible state that has occurred on this port for CIST instance."
   ::= { fsMIMstCistPortEntry 77 }

fsMIMstCistPortImpStateOccurTimeStamp OBJECT-TYPE
   SYNTAX      TimeTicks
   UNITS       "centi-seconds"
   MAX-ACCESS  read-only
   STATUS      current
   DESCRIPTION
        "Time stamp(in hundredths of a second) at which impossible state has occurred on this port last time for CIST instance."
   ::= { fsMIMstCistPortEntry 78 }

fsMIMstCistPortOldPortState OBJECT-TYPE
   SYNTAX      INTEGER {
               disabled (1),
               discarding (2),
               learning (4),
               forwarding (5)
               }
   MAX-ACCESS  read-only
   STATUS      current
   DESCRIPTION
        "This MIB object indicates the previous state of the port for CIST instance."
   ::= { fsMIMstCistPortEntry 79 }

-- -----------------------------------------------------------------
-- Future Mst Multiple Spanning Tree Instance Port Table     
-- -----------------------------------------------------------------
fsMIMstMstiPortTable OBJECT-TYPE
    SYNTAX      SEQUENCE OF FsMIMstMstiPortEntry              
    MAX-ACCESS  not-accessible
    STATUS      current
    DESCRIPTION
          "This table contains Spanning Tree Instance Specific Port
           Information."
     ::= { fsMIDot1sFutureMst 7 }

fsMIMstMstiPortEntry OBJECT-TYPE
      SYNTAX      FsMIMstMstiPortEntry               
      MAX-ACCESS  not-accessible
      STATUS      current
      DESCRIPTION
          "A list of information maintained by every port for each 
           and every spanning tree instance."
      INDEX  { fsMIMstMstiPort, fsMIMstInstanceIndex }
      ::= { fsMIMstMstiPortTable 1 }

FsMIMstMstiPortEntry ::= 
   SEQUENCE {
       fsMIMstMstiPort  
            Integer32,
       fsMIMstMstiPortPathCost 
            Integer32,
       fsMIMstMstiPortPriority 
            Integer32,
       fsMIMstMstiPortDesignatedRoot 
            BridgeId,
       fsMIMstMstiPortDesignatedBridge 
            BridgeId,
       fsMIMstMstiPortDesignatedPort 
            OCTET STRING,
       fsMIMstMstiPortState 
            INTEGER,
       fsMIMstMstiForcePortState 
            INTEGER,
       fsMIMstMstiPortForwardTransitions 
            Counter32,
       fsMIMstMstiPortReceivedBPDUs 
            Counter32,
       fsMIMstMstiPortTransmittedBPDUs 
            Counter32,
       fsMIMstMstiPortInvalidBPDUsRcvd 
            Counter32,
       fsMIMstMstiPortDesignatedCost 
            Integer32,
       fsMIMstMstiSelectedPortRole 
            INTEGER,
       fsMIMstMstiCurrentPortRole  
            INTEGER,
       fsMIMstMstiPortInfoSemState 
            INTEGER,        
       fsMIMstMstiPortRoleTransitionSemState 
            INTEGER,        
       fsMIMstMstiPortStateTransitionSemState 
            INTEGER,         
       fsMIMstMstiPortTopologyChangeSemState 
            INTEGER,        
       fsMIMstMstiPortEffectivePortState
            TruthValue,
       fsMIMstMstiPortAdminPathCost
            Integer32,
       fsMIMstMstiPortPseudoRootId
            BridgeId,
       fsMIMstMstiPortClearStats
            TruthValue,
       fsMIMstMstiPortStateChangeTimeStamp
            Unsigned32,
       fsMIMstMstiPortRootInconsistentState
	    TruthValue,
       fsMIMstMstiPortLoopInconsistentState
           TruthValue,
        fsMIMstMstiPortTCDetectedCount
         Counter32,
        fsMIMstMstiPortTCReceivedCount
         Counter32,
        fsMIMstMstiPortTCDetectedTimeStamp
         TimeTicks,
        fsMIMstMstiPortTCReceivedTimeStamp
         TimeTicks,
        fsMIMstMstiPortProposalPktsSent
         Counter32,
        fsMIMstMstiPortProposalPktsRcvd
         Counter32,
        fsMIMstMstiPortProposalPktSentTimeStamp
         TimeTicks,
        fsMIMstMstiPortProposalPktRcvdTimeStamp
         TimeTicks,
        fsMIMstMstiPortAgreementPktSent
         Counter32,
        fsMIMstMstiPortAgreementPktRcvd
         Counter32,
        fsMIMstMstiPortAgreementPktSentTimeStamp
         TimeTicks,
        fsMIMstMstiPortAgreementPktRcvdTimeStamp
         TimeTicks,
        fsMIMstMstiPortOldPortState
          INTEGER

}

fsMIMstMstiPort OBJECT-TYPE
      SYNTAX      Integer32 (1..65535)
      MAX-ACCESS  not-accessible
      STATUS      current
      DESCRIPTION
          "The Port number of the port for which this entry contains   
           spanning tree information."                                      
      ::= { fsMIMstMstiPortEntry 1 }

fsMIMstMstiPortPathCost OBJECT-TYPE
      SYNTAX      Integer32 (1..200000000)
      MAX-ACCESS  read-write           
      STATUS      current
      DESCRIPTION
          "The contribution of this port to the path cost of
           paths towards the MSTI Root which include this port."
      ::= { fsMIMstMstiPortEntry 2 }

fsMIMstMstiPortPriority OBJECT-TYPE
      SYNTAX      Integer32 (0..240)
      MAX-ACCESS  read-write           
      STATUS      current
      DESCRIPTION
          "The four most significant bits of the Port Identifier 
          for a given Spanning Tree instance can be modified 
          independently for each Spanning Tree instance 
          supported by the Bridge. The values that are set for Port 
          Priority must be in steps of 16."
    DEFVAL {128}
      ::= { fsMIMstMstiPortEntry 3 }

fsMIMstMstiPortDesignatedRoot OBJECT-TYPE
      SYNTAX      BridgeId                 
      MAX-ACCESS  read-only            
      STATUS      current
      DESCRIPTION
          "The unique Bridge Identifier of the bridge recorded as the  
           MSTI Regional Root in the configuration BPDUs transmitted."      
      ::= { fsMIMstMstiPortEntry 4 }

fsMIMstMstiPortDesignatedBridge OBJECT-TYPE
      SYNTAX      BridgeId                 
      MAX-ACCESS  read-only            
      STATUS      current
      DESCRIPTION
          "The unique Bridge Identifier of the bridge which this port  
           considers to be the Designated Bridge for the port's segment."   
      ::= { fsMIMstMstiPortEntry 5 }

fsMIMstMstiPortDesignatedPort OBJECT-TYPE
      SYNTAX  OCTET STRING (SIZE (2))
      MAX-ACCESS  read-only            
      STATUS      current
      DESCRIPTION
          "The Port identifier of the port on the Designated Bridge    
           for this port's segment."                                           
      ::= { fsMIMstMstiPortEntry 6 }

fsMIMstMstiPortState OBJECT-TYPE
      SYNTAX      INTEGER {
                  disabled (1),
                  discarding (2),
                  learning (4),
                  forwarding (5)
                  }
      MAX-ACCESS  read-only            
      STATUS      current
      DESCRIPTION
          "Current state of the Port as defined by the Multiple  
           spanning tree protocol. Port which is Forwarding state
           in one instance can be in Discarding (Blocking) state 
           in another instance."
      ::= { fsMIMstMstiPortEntry 7 }

fsMIMstMstiForcePortState OBJECT-TYPE
      SYNTAX      INTEGER {
                   disabled(0),
                   enabled(1)
                  }
      MAX-ACCESS  read-write           
      STATUS      current
      DESCRIPTION
          "Current state of the Port which can be changed to either 
           Disabled or Enabled for the specific spanning tree   
           instance. This object can be set to enabled only if the 
           'fsMIMstCistForcePortState' is set to 'enabled' for this port"                                            
      ::= { fsMIMstMstiPortEntry 8 }

fsMIMstMstiPortForwardTransitions OBJECT-TYPE 
      SYNTAX      Counter32                
      MAX-ACCESS  read-only            
      STATUS      current
      DESCRIPTION
          "Number of times this port has transitioned to the     
           Forwarding State for specific instance."                                     
      ::= { fsMIMstMstiPortEntry 9 }

fsMIMstMstiPortReceivedBPDUs OBJECT-TYPE 
      SYNTAX      Counter32                
      MAX-ACCESS  read-only            
      STATUS      current
      DESCRIPTION
          "Number of BPDUs received by this port for this 
          spanning tree instance."                            
      ::= { fsMIMstMstiPortEntry 10 }

fsMIMstMstiPortTransmittedBPDUs OBJECT-TYPE 
      SYNTAX      Counter32                
      MAX-ACCESS  read-only            
      STATUS      current
      DESCRIPTION
          "Number of BPDUs transmitted on this port for 
          this spanning tree instance."                            
      ::= { fsMIMstMstiPortEntry 11 }

fsMIMstMstiPortInvalidBPDUsRcvd OBJECT-TYPE 
      SYNTAX      Counter32                
      MAX-ACCESS  read-only            
      STATUS      current
      DESCRIPTION
          "Number of Invalid BPDUs received on this Port
           for this spanning tree instance."                            
      ::= { fsMIMstMstiPortEntry 12 }

fsMIMstMstiPortDesignatedCost OBJECT-TYPE
      SYNTAX      Integer32
      MAX-ACCESS  read-only           
      STATUS      current
      DESCRIPTION
            "The path cost of the Designated Port of the
             segment connected to this port."
      ::= { fsMIMstMstiPortEntry 13 }

fsMIMstMstiSelectedPortRole OBJECT-TYPE
      SYNTAX      INTEGER {
                   disabled(0),
                   alternate(1),
                   backup(2),
                   root(3),
                   designated(4),
                   master(5)
                  }
      MAX-ACCESS  read-only        
      STATUS      current
      DESCRIPTION
          "Selected Port Role of the port for this spanning 
          tree instance."                                      
      ::= { fsMIMstMstiPortEntry 14 }

fsMIMstMstiCurrentPortRole OBJECT-TYPE
      SYNTAX      INTEGER {              
                   disabled(0),
                   alternate(1),
                   backup(2),
                   root(3),
                   designated(4),
                   master(5)
                  }
      MAX-ACCESS  read-only        
      STATUS      current
      DESCRIPTION
          "Current Port Role of the port for this spanning 
          tree instance."                                      
      ::= { fsMIMstMstiPortEntry 15 }

fsMIMstMstiPortInfoSemState OBJECT-TYPE
	SYNTAX      INTEGER {
               disabled (0),
               aged (1),
               update (2),
               superiordesg (3),
               repeatdesg (4),
               inferiordesg (5),
               notdesg (6),
               present (7),
               receive (8),
               other (9)
            }                
      MAX-ACCESS  read-only        
      STATUS      current
      DESCRIPTION
          "Current state of the Port Information State Machine          
           for this port in this spanning tree context."                                      
      ::= { fsMIMstMstiPortEntry 16 }

fsMIMstMstiPortRoleTransitionSemState OBJECT-TYPE
      SYNTAX      INTEGER {                
                  init (0),
                  disableport (1),
                  disabledport (2),
                  rootport (3),
                  designatedport (4),
                  alternateport (5),
                  masterport (6)
               }
      MAX-ACCESS  read-only        
      STATUS      current
      DESCRIPTION
          "Current state of the Port Role Transition State Machine          
           for this port in this spanning tree context."                                      
      ::= { fsMIMstMstiPortEntry 17 }

fsMIMstMstiPortStateTransitionSemState OBJECT-TYPE
      SYNTAX      INTEGER {                
                  discarding (0),
                  learning (1),
                  forwarding (2)
               }
      MAX-ACCESS  read-only        
      STATUS      current
      DESCRIPTION
          "Current state of the Port State Transition State Machine          
           for this port in this spanning tree context."                                      
      ::= { fsMIMstMstiPortEntry 18 }

fsMIMstMstiPortTopologyChangeSemState OBJECT-TYPE
      SYNTAX      INTEGER {                
                  inactive (0),
                  learning (1),
                  detected (2),
                  active (3),
                  notifiedtcn (4),
                  notifiedtc (5),
                  propagating (6),
                  acknowledged (7)
               }
      MAX-ACCESS  read-only        
      STATUS      current
      DESCRIPTION
          "Current state of the Topology Change State Machine          
           for this port in this spanning tree context."                                      
      ::= { fsMIMstMstiPortEntry 19 }

fsMIMstMstiPortEffectivePortState OBJECT-TYPE
      SYNTAX      TruthValue
      MAX-ACCESS  read-only            
      STATUS      current
      DESCRIPTION
          "The effective operational stae of the port for specific instance.
          This is will be TRUE only when the port is operationally up in the
          interface level and Protocol level for the specific instance.
          This is will be set to false at all other times."

      ::= { fsMIMstMstiPortEntry 20 }

fsMIMstMstiPortAdminPathCost OBJECT-TYPE
      SYNTAX      Integer32 (0..200000000)
      MAX-ACCESS  read-write
      STATUS      current
      DESCRIPTION
          "The administratively assigned value for the contribution
           of this port to the path cost of paths toward the spanning
           tree root.
           Writing a value of '0' assigns the automatically calculated
           default Path Cost value to the port.  If the default Path
           Cost is being used, this object returns '0' when read.
           This complements the object dot1dStpPortPathCost or
           dot1dStpPortPathCost32, which returns the operational value
           of the path cost."
      ::= { fsMIMstMstiPortEntry 21 }

fsMIMstMstiPortPseudoRootId OBJECT-TYPE
    SYNTAX      BridgeId
    MAX-ACCESS  read-write
    STATUS      current
    DESCRIPTION
        "In MSTP Bridge, the pseudoRootId parameter value. By default, it
        is set to the BridgeIdentifier. The pseudoRootId is used by
        Layer Two Gateway Port as the RootId in generated BPDUs."
    REFERENCE   "IEEE802.1ah - 13.25.20"
      ::= { fsMIMstMstiPortEntry 22 }

fsMIMstMstiPortClearStats OBJECT-TYPE
	SYNTAX  TruthValue
	MAX-ACCESS  read-write
	STATUS  current
	DESCRIPTION
         "This object is used to clear the statistical counters.When this 
		 object is set to TRUE,it resets the interface associated 
		 counters for the given instance to zero.After resetting
     	         the counters the object is set to FALSE again.Configuration 
         	 of this MIB object to FALSE is not applicable."		 
	::= { fsMIMstMstiPortEntry 23 }


fsMIMstMstiPortStateChangeTimeStamp OBJECT-TYPE
    SYNTAX      Unsigned32
    MAX-ACCESS  read-only
    STATUS      current
    DESCRIPTION
        "Time Stamp (in milli seconds) at which port state has changed for a particular
         instance on this port.This object was introduced to measure the convergence time in MSTP module."
    ::= { fsMIMstMstiPortEntry 24 }

fsMIMstMstiPortRootInconsistentState OBJECT-TYPE
    SYNTAX      TruthValue
    MAX-ACCESS  read-only
    STATUS      current
    DESCRIPTION
          " A Boolean value set when the designated port receives a superior BPDU trying to transition itself
            to the Root Port.
            A value of TRUE, indicates that the state of this port is moved into an root-inconsistent
            state.A value of  FALSE, indicates that this port is not moved into an root-inconsistent
            state "
         DEFVAL { false }
    ::= { fsMIMstMstiPortEntry 25 }

fsMIMstMstiPortLoopInconsistentState   OBJECT-TYPE
        SYNTAX      TruthValue
        MAX-ACCESS  read-only
        STATUS      current
        DESCRIPTION
             " A Boolean value set when the non-designated port on which loop-guard is enabled, tries to transition
		to Designated/Forwarding due to the expiry of Receive info while timer when bpdus are not received. 
                A value of TRUE, indicates that the state of this port is moved into an loop-inconsistent
                state.A value of  FALSE, indicates that this port is not moved into an loop-inconsistent
                state "
        DEFVAL { false }
        ::= { fsMIMstMstiPortEntry 26 }


fsMIMstMstiPortTCDetectedCount OBJECT-TYPE
   SYNTAX      Counter32
   MAX-ACCESS  read-only
   STATUS      current
   DESCRIPTION
       "Indicates the number of topology changes detected on this port for MST instance ."
   ::= { fsMIMstMstiPortEntry 27 }

fsMIMstMstiPortTCReceivedCount OBJECT-TYPE
   SYNTAX      Counter32
   MAX-ACCESS  read-only
   STATUS      current
   DESCRIPTION
        "Indicates the number of topology change messages received on this port  for MST instance."
   ::= { fsMIMstMstiPortEntry 28 }

fsMIMstMstiPortTCDetectedTimeStamp OBJECT-TYPE
   SYNTAX      TimeTicks
   UNITS       "centi-seconds"
   MAX-ACCESS  read-only
   STATUS      current
   DESCRIPTION
        "Time stamp(in hundredths of a second) at which the topology change is detected on this port last time  for MST instance."
   ::= { fsMIMstMstiPortEntry 29 }

fsMIMstMstiPortTCReceivedTimeStamp OBJECT-TYPE
   SYNTAX      TimeTicks
   UNITS       "centi-seconds"
   MAX-ACCESS  read-only
   STATUS      current
   DESCRIPTION
        "Time stamp(in hundredths of a second) at which the topology change message received on this port last time for MST instance."
   ::= { fsMIMstMstiPortEntry 30 }

fsMIMstMstiPortProposalPktsSent OBJECT-TYPE
   SYNTAX      Counter32
   MAX-ACCESS  read-only
   STATUS      current
   DESCRIPTION
        "The number of proposal packets sent by this port for MST instance."
   ::= { fsMIMstMstiPortEntry 31 }

fsMIMstMstiPortProposalPktsRcvd OBJECT-TYPE
   SYNTAX      Counter32
   MAX-ACCESS  read-only
   STATUS      current
   DESCRIPTION
        "The number of proposal packets received on this port for MST instance."
   ::= { fsMIMstMstiPortEntry 32 }

fsMIMstMstiPortProposalPktSentTimeStamp OBJECT-TYPE
   SYNTAX      TimeTicks
   UNITS       "centi-seconds"
   MAX-ACCESS  read-only
   STATUS      current
   DESCRIPTION
        "Time stamp(in hundredths of a second) at which proposal packet sent by this port last time for MST instance."
   ::= { fsMIMstMstiPortEntry 33 }

fsMIMstMstiPortProposalPktRcvdTimeStamp OBJECT-TYPE
   SYNTAX      TimeTicks
   UNITS       "centi-seconds"
   MAX-ACCESS  read-only
   STATUS      current
   DESCRIPTION
        "Time stamp(in hundredths of a second) at which  proposal packet received on this port last time for MST instance."
   ::= { fsMIMstMstiPortEntry 34 }

fsMIMstMstiPortAgreementPktSent OBJECT-TYPE
   SYNTAX      Counter32
   MAX-ACCESS  read-only
   STATUS      current
   DESCRIPTION
        "The number of agreement packets sent by this port for MST instance."
   ::= { fsMIMstMstiPortEntry 35 }

fsMIMstMstiPortAgreementPktRcvd OBJECT-TYPE
   SYNTAX      Counter32
   MAX-ACCESS  read-only
   STATUS      current
   DESCRIPTION
        "The number of agreement packets received on this port for MST instance."
   ::= { fsMIMstMstiPortEntry 36 }

fsMIMstMstiPortAgreementPktSentTimeStamp OBJECT-TYPE
   SYNTAX      TimeTicks
   UNITS       "centi-seconds"
   MAX-ACCESS  read-only
   STATUS      current
   DESCRIPTION
        " Time stamp(in hundredths of a second) at which agreement packet sent by this port last time for MST instance."
   ::= { fsMIMstMstiPortEntry 37 }

fsMIMstMstiPortAgreementPktRcvdTimeStamp OBJECT-TYPE
   SYNTAX      TimeTicks
   UNITS       "centi-seconds"
   MAX-ACCESS  read-only
   STATUS      current
   DESCRIPTION
        "Time stamp(in hundredths of a second) at which agreement packet received on this port last time for MST instance."
   ::= { fsMIMstMstiPortEntry 38 }

fsMIMstMstiPortOldPortState OBJECT-TYPE
   SYNTAX      INTEGER {
               disabled (1),
               discarding (2),
               learning (4),
               forwarding (5)
               }
   MAX-ACCESS  read-only
   STATUS      current
   DESCRIPTION
        "This MIB object indicates the previous state of the port for MST instance."
   ::= { fsMIMstMstiPortEntry 39 }


fsMIMstPortExtTable OBJECT-TYPE
   SYNTAX        SEQUENCE OF FsMIMstPortExtEntry
   MAX-ACCESS not-accessible
   STATUS     current
   DESCRIPTION
      "This is a table that is an extension to the dot1dStpExtPortTable.
      This contains object(s) that are Port-based."
   ::= { fsMIDot1sFutureMst 8 }

fsMIMstPortExtEntry OBJECT-TYPE
   SYNTAX      FsMIMstPortExtEntry
   MAX-ACCESS  not-accessible
   STATUS      current
   DESCRIPTION
      "The entry in this table is for creating/deleting port at Mstp Module 
       Level. This table is indexed by the fsMstPort."
   INDEX { fsMIMstPort }
   ::= { fsMIMstPortExtTable 1 }

FsMIMstPortExtEntry ::=
   SEQUENCE {
      fsMIMstPort
         Integer32,
      fsMIMstPortRowStatus
         RowStatus
   }

fsMIMstPort OBJECT-TYPE
   SYNTAX      Integer32 (1..4096)
   MAX-ACCESS  not-accessible
   STATUS      current
   DESCRIPTION
      "A unique value, greater than zero, indicating the Port number."
   ::= { fsMIMstPortExtEntry 1 }

fsMIMstPortRowStatus OBJECT-TYPE
   SYNTAX      RowStatus
   MAX-ACCESS  read-create
   STATUS      current
   DESCRIPTION
      "This object is used to create or delete interfaces at MSTP module
       level.Ports can be created at MSTP module level only for ports that
       have been created in Interface manager.This is applicable only when
       Automatic Port Create Feature is Disabled."
   ::= { fsMIMstPortExtEntry 2 }


-- TRAP MIB BEGIN

fsMIDot1sFsMstSetGlobalTrapOption OBJECT-TYPE
        SYNTAX   Integer32 (0..1)
        MAX-ACCESS   read-write
        STATUS   current
        DESCRIPTION
           "This object is used to enable and disable MSTP traps for memory
	    failure or buffer failure irrespective of the context in which
	    the failure occurs.
           0 - Traps are not enabled.
           1 - Memory and buffer failure traps enabled" 
   ::= { fsMIDot1sFsMstTrapsControl 1 }

fsMIMstGlobalErrTrapType OBJECT-TYPE
       SYNTAX   INTEGER   {
                    none (0),
                    memfail (1),
                    bufffail (2)
                    }
       MAX-ACCESS  read-only
       STATUS  current
       DESCRIPTION
           "Used within the Trap Notification PDU. 
	    It returns the following values
            none - none of the below values
            memfail - memory allocation failure
            bufffail - buffer allocation failure"
   ::= { fsMIDot1sFsMstTrapsControl 2 }

fsMIDot1sFsMstTrapsControlTable OBJECT-TYPE
    SYNTAX        SEQUENCE OF FsMIDot1sFsMstTrapsControlEntry
    MAX-ACCESS    not-accessible
    STATUS        current
    DESCRIPTION
       "List of per virtual bridge Trap Control Info."
    ::= { fsMIDot1sFsMstTrapsControl 3 }

fsMIDot1sFsMstTrapsControlEntry OBJECT-TYPE
    SYNTAX        FsMIDot1sFsMstTrapsControlEntry
    MAX-ACCESS    not-accessible
    STATUS        current
    DESCRIPTION
       "Virtual bridge TrapsControl information."
    INDEX { fsMIDot1sFutureMstContextId }
    ::= { fsMIDot1sFsMstTrapsControlTable 1 }

FsMIDot1sFsMstTrapsControlEntry ::=
    SEQUENCE {
        fsMIMstSetTraps
           Integer32,
       fsMIMstGenTrapType
          INTEGER
           }

fsMIMstSetTraps OBJECT-TYPE
        SYNTAX   Integer32 (0..3)
        MAX-ACCESS   read-write
        STATUS   current
        DESCRIPTION
           "This object is used to enable and  disable context-specific
           MSTP traps. Currently the following are defined
           0 - Traps are not enabled.
           1 - General Traps like protocol up or down 
           2 - Exception Traps like port protocol migration or 
	       invalid packet rcvd in port
           3 - All the above Traps "
    ::= { fsMIDot1sFsMstTrapsControlEntry 1 }


 fsMIMstGenTrapType OBJECT-TYPE
       SYNTAX   INTEGER   {
                    none (0),
                    up (1),
                    down (2)
                    }
       MAX-ACCESS  read-only
       STATUS  current
       DESCRIPTION
          "Used within the Trap Notification PDU. 
	   It denotes general events like 
           none - none of the below values
           up - protocol UP,
           down - protocol DOWN" 
    ::= { fsMIDot1sFsMstTrapsControlEntry 2 }

fsMIMstPortTrapNotificationTable OBJECT-TYPE
   SYNTAX SEQUENCE OF FsMIMstPortTrapNotificationEntry 
   MAX-ACCESS not-accessible
   STATUS     current
   DESCRIPTION
       "This table is used to store the notification information
       occured in each of the port for protocol migration and 
       invalid packet received. This table is maintained per virtual
       context in the system."
   ::= { fsMIDot1sFsMstTrapsControl 4 }

fsMIMstPortTrapNotificationEntry OBJECT-TYPE
   SYNTAX      FsMIMstPortTrapNotificationEntry 
   MAX-ACCESS  not-accessible
   STATUS      current
   DESCRIPTION
       " This entry is used to store the notification information"
   INDEX { fsMIMstPortTrapIndex}
   ::= { fsMIMstPortTrapNotificationTable 1 }

FsMIMstPortTrapNotificationEntry ::=
        SEQUENCE {
               fsMIMstPortTrapIndex
               Integer32,
               fsMIMstPortMigrationType 
               INTEGER,
               fsMIMstPktErrType
               INTEGER,
               fsMIMstPktErrVal
               Integer32
        }

 fsMIMstPortTrapIndex OBJECT-TYPE
   SYNTAX      Integer32 (1..4096)
   MAX-ACCESS  not-accessible
   STATUS      current
   DESCRIPTION
      "A unique value, greater than zero, indicating the Port number."
   ::= { fsMIMstPortTrapNotificationEntry 1 }

 fsMIMstPortMigrationType OBJECT-TYPE
      SYNTAX      INTEGER {
                  sendstp (0),
                  sendrstp (1)
                  }
       MAX-ACCESS  read-only
       STATUS  current
       DESCRIPTION
           "Port Protocol migration type occured in the port"
   ::= { fsMIMstPortTrapNotificationEntry 2 }

 fsMIMstPktErrType OBJECT-TYPE
      SYNTAX      INTEGER {
                  protocolIdErr(0),
                  invalidBpdu(1),
                  configLengthErr(2),
                  tcnLengthErr(3),
                  rstpLengthErr(4),
                  maxAgeErr(5),
                  fwdDelayErr(6),
                  helloTimeErr(7),
                  mstpLengthErr(8)
                  }
       MAX-ACCESS  read-only
       STATUS  current
       DESCRIPTION
           "Type of invalid packet received in each of the port "
   ::= { fsMIMstPortTrapNotificationEntry 3 }

 fsMIMstPktErrVal OBJECT-TYPE
       SYNTAX   Integer32   
       MAX-ACCESS  read-only
       STATUS  current
       DESCRIPTION
           "Packet error value corresponding to the above type "
   ::= { fsMIMstPortTrapNotificationEntry 4 }

fsMIMstPortRoleTrapNotificationTable OBJECT-TYPE
   SYNTAX SEQUENCE OF FsMIMstPortRoleTrapNotificationEntry
   MAX-ACCESS not-accessible
   STATUS     current
   DESCRIPTION
       "This table is used to store the notification information
       occured in each of the port for its role change. This table 
       is maintained per virtual context in the system."
   ::= { fsMIDot1sFsMstTrapsControl 5 }

fsMIMstPortRoleTrapNotificationEntry OBJECT-TYPE
   SYNTAX      FsMIMstPortRoleTrapNotificationEntry 
   MAX-ACCESS  not-accessible
   STATUS      current
   DESCRIPTION
       " This entry is used to store the notification information"
   INDEX { fsMIMstPortTrapIndex, fsMIMstMstiInstanceIndex }
   ::= { fsMIMstPortRoleTrapNotificationTable 1 }

FsMIMstPortRoleTrapNotificationEntry ::=
        SEQUENCE {
	       fsMIMstPortRoleType
               INTEGER,
	       fsMIMstOldRoleType
               INTEGER
	}

 fsMIMstPortRoleType OBJECT-TYPE
      SYNTAX      INTEGER {
                  disabledPort(0),
                  alternatePort(1),
                  backupPort(2),
                  rootPort(3),
                  designatedPort(4),
		  masterport(5)
                  }
       MAX-ACCESS  read-only
       STATUS  current
       DESCRIPTION
           "Particular Role Selected for the Port"
   ::= { fsMIMstPortRoleTrapNotificationEntry 1 }

 fsMIMstOldRoleType OBJECT-TYPE
      SYNTAX      INTEGER {
                  disabledPort(0),
                  alternatePort(1),
                  backupPort(2),
                  rootPort(3),
                  designatedPort(4),
		            masterport(5)
                  }
       MAX-ACCESS  read-only
       STATUS  current
       DESCRIPTION
           "Particular Role which is existing for the Port"
   ::= { fsMIMstPortRoleTrapNotificationEntry 2 }


 fsMIMstTraps OBJECT IDENTIFIER ::= { fsMIDot1sFutureMstTraps 0 }

 fsMIMstGlobalErrTrap NOTIFICATION-TYPE
        OBJECTS {
            fsMIMstBrgAddress,
            fsMIMstGlobalErrTrapType
                }
        STATUS             current
        DESCRIPTION
         "Generated when any of the error events like memory failure or buffer failure
          or protocol migration or new root or topology change occurs "
   ::= { fsMIMstTraps 1 }

 fsMIMstGenTrap NOTIFICATION-TYPE
        OBJECTS {
            fsMIMstBrgAddress,
            fsMIMstContextName,
	         fsMIMstGenTrapType 
               }
        STATUS             current
        DESCRIPTION
         "Generated when any of the general events like protocol up or 
          protocol down occurs"
   ::= { fsMIMstTraps 2 }

 fsMIMstNewRootTrap NOTIFICATION-TYPE
        OBJECTS {
            fsMIMstBrgAddress,
            fsMIMstContextName,
            fsMIMstOldDesignatedRoot,
            fsMIMstMstiBridgeRegionalRoot
                }
        STATUS             current
        DESCRIPTION
         "Generated whenever a new root bridge is selected in the topology "
   ::= { fsMIMstTraps 3 }

 fsMIMstTopologyChgTrap NOTIFICATION-TYPE
        OBJECTS {
            fsMIMstBrgAddress,
            fsMIMstContextName,
            fsMIMstMstiTopChanges
                }
        STATUS             current
        DESCRIPTION
         "Generated when topology change is detected "
   ::= { fsMIMstTraps 4 }

 fsMIMstProtocolMigrationTrap NOTIFICATION-TYPE
        OBJECTS {
            fsMIMstBrgAddress,
            fsMIMstContextName,
            fsMIMstForceProtocolVersion,
            fsMIMstPortMigrationType 
                }
        STATUS             current
        DESCRIPTION
         "Generated when port protocol migration happens in the port "
   ::= { fsMIMstTraps 5 }

fsMIMstInvalidBpduRxdTrap NOTIFICATION-TYPE
        OBJECTS {
            fsMIMstBrgAddress,
            fsMIMstContextName,
            fsMIMstPktErrType,
            fsMIMstPktErrVal
                }
        STATUS             current
        DESCRIPTION
         "Generated when the invalid packet is received for 
          bpdu/stp/rstp/maximum age/forward delay/hello time"
   ::= { fsMIMstTraps 6 }

fsMIMstRegionConfigChangeTrap NOTIFICATION-TYPE
        OBJECTS {
            fsMIMstBrgAddress, 
            fsMIMstContextName,
            fsMIMstMstiConfigIdSel, 
            fsMIMstMstiRegionName, 
            fsMIMstMstiRegionVersion,
            fsMIMstMstiConfigDigest
                }
        STATUS             current
        DESCRIPTION
         "Generated when the MST region's configuration     
          identifier changes."
   ::= { fsMIMstTraps 7 }

fsMIMstNewPortRoleTrap NOTIFICATION-TYPE
        OBJECTS {
		  fsMIMstBrgAddress,
		  fsMIMstPortRoleType,
		  fsMIMstOldRoleType
                }
        STATUS             current
        DESCRIPTION
         "Generated whenever a new role is selected for the port "
   ::= { fsMIMstTraps 8 }

fsMIMstCistHwFailureTrap NOTIFICATION-TYPE
        OBJECTS {
          fsMIMstBrgAddress,
          fsMIMstContextName,
          fsMIMstCistPortState
                }
        STATUS             current
        DESCRIPTION
         "Generated whenever an NPAPI call that is invoked from the protocol
          to program the CIST port state in hardware fails."
   ::= { fsMIMstTraps 9 }

fsMIMstMstiHwFailureTrap NOTIFICATION-TYPE
       OBJECTS {
         fsMIMstBrgAddress,
         fsMIMstContextName,
         fsMIMstMstiPortState
               }
       STATUS             current
       DESCRIPTION
        "Generated whenever an NPAPI call that is invoked from the protocol
         to program the MSTI port state in hardware fails."
   ::= { fsMIMstTraps 10 }

fsMIMstCistLoopIncStateChange NOTIFICATION-TYPE
         OBJECTS {
                    fsMIMstBrgAddress,
                    fsMIMstCistLoopInconsistentState
                 }
         STATUS             current
         DESCRIPTION
         "Generated when the port has been moved to the loop inconsistent state for the CIST instance."
    ::= { fsMIMstTraps 11 }

fsMIMstMstiLoopIncStateChange NOTIFICATION-TYPE
         OBJECTS {
                    fsMIMstBrgAddress,
                    fsMIMstMstiPortLoopInconsistentState
                 }
         STATUS             current
         DESCRIPTION
         "Generated when the port has been moved to the loop inconsistent state for the MST instance."
    ::= { fsMIMstTraps 12 }

fsMIMstCistBpduIncStateChange  NOTIFICATION-TYPE
         OBJECTS {
                    fsMIMstBrgAddress,
                    fsMIMstPortBpduInconsistentState
                 }
         STATUS             current
         DESCRIPTION
         " Generated when the port state goes to BPDU inconsistent state for the CIST instance."
     ::= { fsMIMstTraps 13 }


fsMIMstCistRootIncStateChange  NOTIFICATION-TYPE
         OBJECTS {
                    fsMIMstBrgAddress,
                    fsMIMstCistPortRootInconsistentState
                 }
         STATUS             current
         DESCRIPTION
         "Generated when the port state goes to root inconsistent state for the CIST instance. "
     ::= { fsMIMstTraps 14 }

fsMIMstMstiRootIncStateChange  NOTIFICATION-TYPE
         OBJECTS {
                    fsMIMstBrgAddress,
                    fsMIMstMstiPortRootInconsistentState
                 }
         STATUS             current
         DESCRIPTION
         "Generated when the port state goes to root inconsistent state for the MST instance. "
     ::= { fsMIMstTraps 15 }

fsMIMstCistPortStateChange  NOTIFICATION-TYPE
         OBJECTS {
                    fsMIMstBrgAddress,
                    fsMIMstCistPortOldPortState,
                    fsMIMstCistPortState
                 }
         STATUS             current
         DESCRIPTION
         "Generated when the current state of the port has been changed for the CIST instance."
      ::= { fsMIMstTraps 16 }

fsMIMstMstiPortStateChange  NOTIFICATION-TYPE
         OBJECTS {
                    fsMIMstBrgAddress,
                    fsMIMstMstiPortOldPortState,
                    fsMIMstMstiPortState
                 }
         STATUS             current
         DESCRIPTION
         "Generated when the current state of the port has been changed for the MST instance."
      ::= { fsMIMstTraps 17 }


-- TRAP MIB END

END
