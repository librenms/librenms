-- Copyright (C) 2015 Aricent. All Rights Reserved.

ARICENT-VLAN-MIB DEFINITIONS ::= BEGIN 
 
IMPORTS 
 
    OBJECT-TYPE,MODULE-IDENTITY, Integer32, Unsigned32,
    enterprises, NOTIFICATION-TYPE, Counter32, IpAddress
         FROM SNMPv2-SMI 
    RowStatus, TEXTUAL-CONVENTION, MacAddress, TruthValue,
    DisplayString
         FROM SNMPv2-TC
    SnmpAdminString
         FROM SNMP-FRAMEWORK-MIB
    dot1qTpFdbPort
         FROM Q-BRIDGE-MIB
    dot1qStaticUnicastEntry
         FROM Q-BRIDGE-MIB
    dot1qVlanStaticEntry
         FROM Q-BRIDGE-MIB
    VlanIdOrNone
         FROM Q-BRIDGE-MIB
    dot1qTpFdbEntry, PortList
         FROM Q-BRIDGE-MIB;                                    -- [RFC4363]
 
futureVlanMIB MODULE-IDENTITY 
    LAST-UPDATED "202111150000Z" 
    ORGANIZATION "ARICENT COMMUNICATIONS SOFTWARE" 
    CONTACT-INFO "support@aricent.com" 
    DESCRIPTION "||||||"

    REVISION    "202111150000Z" -- Novenber 15, 2021
    DESCRIPTION "Ver 3: Added automated voice uplink."

    REVISION    "202108120000Z" -- August 12, 2021
    DESCRIPTION "Ver 2: Objects supporting automated voice
                VLAN capabilities defined."

    REVISION "202006010000Z"
    DESCRIPTION "||||||" 

::= { enterprises futuresoftware(2076) 65} 
 
VlanId ::= TEXTUAL-CONVENTION 
    STATUS      current 
    DESCRIPTION 
        "A 12-bit VLAN ID used in the VLAN Tag header." 
    SYNTAX      Integer32 (1..4094) 
 
EnabledStatus ::= TEXTUAL-CONVENTION 
    STATUS      current 
    DESCRIPTION 
        "A simple status value for the object." 
    SYNTAX      INTEGER { enabled(1), disabled(2) } 
 
MacLearningStatus ::= TEXTUAL-CONVENTION 
    STATUS      current 
    DESCRIPTION 
        "This object specifies a simple MAC learning status value specific to VLAN."
    SYNTAX      INTEGER { enabled(1), disabled(2), default(3) } 
 
dot1qFutureVlan     OBJECT IDENTIFIER   ::= { futureVlanMIB 1 } 
 
--dot1qFutureVlanTunnelConfig - This sub group contains MIB objects for 
-- configuring VLAN stacking (also known 802.1q in 802.1q) feature in VLAN.
dot1qFutureVlanTunnelConfig OBJECT IDENTIFIER  ::= { futureVlanMIB 2 }
dot1qFutureVlanTraps  OBJECT IDENTIFIER  ::= { futureVlanMIB 3 }
 
-- dot1qFutureVlan group 
 
-- SCALAR BEGIN 
 
dot1qFutureVlanStatus OBJECT-TYPE 
   SYNTAX      EnabledStatus 
   MAX-ACCESS  read-write 
   STATUS      current 
   DESCRIPTION 
      "This object specifies the administrative status requested by management for the VLAN 
      feature. The value enabled(1) indicates that VLAN should be enabled  
      in the device on all ports. The value disabled(2) indicates that 
      VLAN should be disabled in the device on all ports. The object can 
      be set to disabled if and only if, dot1qGvrpStatus and dot1dGmrpStatus  
      are disabled. The object should not be enabled before setting  
      'dot1qFutureVlanType'.
      Setting this object will affect the operational status of the
      VLAN module (dot1qFutureVlanOperStatus)." 
   ::= { dot1qFutureVlan 1 } 
 
dot1qFutureVlanMacBasedOnAllPorts OBJECT-TYPE 
   SYNTAX      EnabledStatus
   MAX-ACCESS  read-write
   STATUS      current
   DESCRIPTION 
      "This object is used to enable/disable the MAC based type on all ports
       of dot1qFutureVlanPortMacBasedClassification."
   ::= { dot1qFutureVlan 2 } 

dot1qFutureVlanPortProtoBasedOnAllPorts OBJECT-TYPE 
   SYNTAX      EnabledStatus
   MAX-ACCESS  read-write
   STATUS      current
   DESCRIPTION 
      "This object is only used to enable/disable the port protocol based type on all ports
       of dot1qFutureVlanPortPortProtoBasedClassification."
   ::= { dot1qFutureVlan 3 } 
 
-- OBSOLETED
-- dot1qFutureVlanOperLearningMode OBJECT-TYPE 
--   SYNTAX      INTEGER { 
--                  ivl (1), 
--                 svl (2), 
--                hybrid (3) 
--               } 
--   MAX-ACCESS  read-only
--   STATUS      current 
--   DESCRIPTION 
--      "This object specifies the type of the VLAN learning mode operational on this switch." 
--   ::= { dot1qFutureVlan 4 } 
 
dot1qFutureVlanShutdownStatus OBJECT-TYPE 
   SYNTAX      TruthValue 
   MAX-ACCESS  read-write 
   STATUS      deprecated 
   DESCRIPTION 
      "This object specifies the administrative shutdown status requested by management for VLAN  
      The value true(1) indicates that VLAN should be shutdown  
      in the device on all ports. All memory will be released. 
      The value false(2) indicates that VLAN should be active in the device  
      on all ports."
   DEFVAL   { false }       
   ::= { dot1qFutureVlan 5 } 
 
dot1qFutureGarpShutdownStatus OBJECT-TYPE 
   SYNTAX      TruthValue 
   MAX-ACCESS  read-write 
   STATUS      current 
   DESCRIPTION 
      "This object specifies the administrative status requested by management for GARP.  
      The value true(1) indicates that GARP should be shutdown  
      in the device on all ports. All memory will be released. 
      The value false(2) indicates that GARP should be active in  
      the device on all ports. This object can be set to true only  
      when none of the GARP applications (GVRP, GMRP) are enabled. 
      Whenever GARP is enabled after shutdown, GVRP and GMRP must 
      be enabled explicitly." 
   DEFVAL   { false }       
   ::= { dot1qFutureVlan 6 } 
 
dot1qFutureVlanDebug OBJECT-TYPE 
   SYNTAX      Integer32 (0..524287)
   MAX-ACCESS  read-write 
   STATUS      current 
   DESCRIPTION 
      "Enables the tracing in the selected submodule in VLAN. A 32 bit integer
      is used to store the tracing level in the specified module.
       Different Tracing Levels -
         BIT 0 - Initialization and Shutdown Trace.
         BIT 1 - Management trace.
         BIT 2 - Data path trace.
         BIT 3 - Control Plane trace.
         BIT 4 - Packet Dump.
         BIT 5 - OS Resource trace.
         BIT 6 - All Failure trace (All failures including Packet Validation)
         BIT 7 - Buffer Trace.

       Different submodule Tracing -
         BIT 16 - Tracing in VLAN module.
         BIT 17 - Tracing in VLAN Priority module.
         BIT 18 - Tracing in VLAN redundancy module.   

       The remaining bits are reserved. The combinations of levels and submodules 
       are allowed i.e. tracing can be allowed at all failure and data path 
       level in all submodules by setting the BIT appropriately.
       For example, setting the debug value to the following bit stream, 
          00000000000000010000000000000100 will enable data path trace 
       prints in VLAN module. Multiple submodules and multiple levels can
       be combined by setting the corresponding bits.
       For example, setting the debug value to the following bit stream,
          00000000000000110000000000001100 will enable data path and 
       control plane trace prints in VLAN and VLAN priority modules.
       
       Note: BIT0 is the least significant bit and BIT31 is the most
       significant bit."
   ::= { dot1qFutureVlan 7 } 
 
dot1qFutureVlanLearningMode OBJECT-TYPE
   SYNTAX      INTEGER {
               ivl(1),
               svl(2),
               hybrid(3)
               }
   MAX-ACCESS  read-write
   STATUS      current
   DESCRIPTION
         "This object specifies the type of VLAN learning mode.
          When the object value is modified, the static
          fid-vlan mappings and static unicast entries
          need to be reconfigured. Static unicast configurations 
          associated with old fid will get deleted." 
   DEFVAL  { ivl }
   ::= { dot1qFutureVlan 8 }

dot1qFutureVlanHybridTypeDefault OBJECT-TYPE
   SYNTAX      INTEGER {
               ivl(1),
               svl(2)
               }
   MAX-ACCESS  read-write
   STATUS      current
   DESCRIPTION
         "The default learning mode of the switch if 
          dot1qFutureVlanLearningMode is hvl (3).
          When the object value is modified, the static
          fid-vlan mappings and static unicast entries
          need to be reconfigured. Static unicast configurations 
          associated with old fid will get deleted."
   DEFVAL  { ivl }
   ::= { dot1qFutureVlan 9 }

-- SCALAR END 
 
-- ---------------------------------------------------------------------------- 
-- Future Vlan Port Table 
-- ---------------------------------------------------------------------------- 
 
dot1qFutureVlanPortTable OBJECT-TYPE 
   SYNTAX      SEQUENCE OF Dot1qFutureVlanPortEntry 
   MAX-ACCESS  not-accessible 
   STATUS      current 
   DESCRIPTION 
      "Table containing the port type information." 
   ::= { dot1qFutureVlan 10 } 
 
dot1qFutureVlanPortEntry OBJECT-TYPE 
   SYNTAX      Dot1qFutureVlanPortEntry 
   MAX-ACCESS  not-accessible 
   STATUS      current 
   DESCRIPTION 
      "Entry indicating the type of the port." 
   INDEX { dot1qFutureVlanPort } 
   ::= { dot1qFutureVlanPortTable 1 } 
    
Dot1qFutureVlanPortEntry ::= 
   SEQUENCE { 
      dot1qFutureVlanPort Integer32, 
      dot1qFutureVlanPortType INTEGER, 
      dot1qFutureVlanPortMacBasedClassification EnabledStatus,
      dot1qFutureVlanPortPortProtoBasedClassification EnabledStatus,
      dot1qFutureVlanFilteringUtilityCriteria INTEGER,
      dot1qFutureVlanPortProtected TruthValue,
      dot1qFutureVlanPortSubnetBasedClassification EnabledStatus,
      dot1qFutureVlanPortUnicastMacLearning EnabledStatus,
      dot1qFutureVlanPortIngressEtherType Integer32,
      dot1qFutureVlanPortEgressEtherType Integer32,
      dot1qFutureVlanPortEgressTPIDType INTEGER,
      dot1qFutureVlanPortAllowableTPID1 Integer32,
      dot1qFutureVlanPortAllowableTPID2 Integer32,
      dot1qFutureVlanPortAllowableTPID3 Integer32,
      dot1qFutureVlanPortUnicastMacSecType INTEGER,
      dot1qFuturePortPacketReflectionStatus TruthValue,
      dot1qFutureVlanPortProtectedStatic TruthValue
   } 
 
dot1qFutureVlanPort OBJECT-TYPE 
   SYNTAX      Integer32 (1..65535) 
   MAX-ACCESS  not-accessible 
   STATUS      current 
   DESCRIPTION 
      "The port number of the port for which this entry applies." 
   ::= { dot1qFutureVlanPortEntry 1 } 
 
dot1qFutureVlanPortType OBJECT-TYPE 
   SYNTAX      INTEGER { 
                  accessPort (1), 
                  trunkPort (2), 
                  hybridPort (3)
               } 
   MAX-ACCESS  read-write 
   STATUS      current 
   DESCRIPTION 
      "The type of the port is by default hybrid port. 
       When configured as access port, the port can accept and send 
       only untagged frames.
       When configured as a trunk port, port is added as 
       member of all the existing VLANs and also for any new VLAN
       created. 
       When configured as hybrid port, the port can send or accept both 
       tagged and untagged frames." 

   DEFVAL   { hybridPort } 
   ::= { dot1qFutureVlanPortEntry 2 } 

dot1qFutureVlanPortMacBasedClassification OBJECT-TYPE 
   SYNTAX      EnabledStatus
   MAX-ACCESS  read-write 
   STATUS      current 
   DESCRIPTION 
      "This Object is used to explicitly enable/disable the MAC based classification 
      on port. This can be independently set without 
      any dependency in available configuration of
       dot1qFutureVlanMacBasedOnAllPorts." 
   ::= { dot1qFutureVlanPortEntry 3 } 

dot1qFutureVlanPortPortProtoBasedClassification OBJECT-TYPE 
   SYNTAX      EnabledStatus
   MAX-ACCESS  read-write 
   STATUS      current 
   DESCRIPTION 
      "This Object is used to explicitly enable/disable the port and protocol
      classification on port. This can be independently set without 
      any dependency in available configuration of
       dot1qFutureVlanPortProtoBasedOnAllPorts." 
   ::= { dot1qFutureVlanPortEntry 4 } 
 
 dot1qFutureVlanFilteringUtilityCriteria OBJECT-TYPE 
   SYNTAX      INTEGER { 
                  default  (1), 
                  enhanced (2)
               } 
   MAX-ACCESS  read-write 
   STATUS      current 
   DESCRIPTION 
      "Based on this object, learning on a port is decided.
      
      If default filtering utility criteria is selected on a port, then
      learning of source MAC from a received packet on that port will be
      done only if there is at least one member port in that VLAN.

      If enhanced filtering utility criteria is selected on a port, then
      learning of source MAC from a received packet on that port will be
      done if the following are satisfied: 
      
      -    if at least one VLAN that uses the FID includes the reception
      port and at least one other Port with a Port State of Learning or
      Forwarding in its member set, and:
       
       o The operPointToPointMAC parameter is false for the reception port; or
       o Ingress to the VLAN is permitted through a third port.
       
       The third port can, but is not required to, be in the member set."
   DEFVAL   { default } 
   ::= { dot1qFutureVlanPortEntry 5 } 
 
dot1qFutureVlanPortProtected  OBJECT-TYPE
   SYNTAX      TruthValue
   MAX-ACCESS  read-write
   STATUS      current
   DESCRIPTION
      "The Split Horizon property of the port. If set to true, frames that 
       are received on any other port that has the same property set to true,
       will not be forwarded on this port."
   DEFVAL   { false }
   ::= { dot1qFutureVlanPortEntry 6 }
 
dot1qFutureVlanPortSubnetBasedClassification OBJECT-TYPE 
   SYNTAX      EnabledStatus
   MAX-ACCESS  read-write 
   STATUS      current 
   DESCRIPTION 
      "This Object is used to explicitly enable/disable the subnet based VLAN Classification 
      on port. This can be independently set without any dependency in 
      available configuration of dot1qFutureVlanSubnetBasedOnAllPorts. This
      object is not used in case of BCM chipsets." 
   ::= { dot1qFutureVlanPortEntry 7 }

dot1qFutureVlanPortUnicastMacLearning OBJECT-TYPE
   SYNTAX      EnabledStatus
   MAX-ACCESS  read-write
   STATUS      current
   DESCRIPTION
      "A truth value indicating the unicast MAC learning enabled/disabled
       status for this port. 
       When Unicast Mac Learning is disabled, no unicast MAC entry will be 
       learnt on this port.
       When MAC learning is enabled, unicast MAC entries will be learnt on this
       port. Configuration of this object will not get affected by the value
       configured for dot1qFutureVlanGlobalMacLearningStatus."
   DEFVAL   { enabled }
   ::= { dot1qFutureVlanPortEntry 8 }

dot1qFutureVlanPortIngressEtherType OBJECT-TYPE
    SYNTAX      Integer32 (1..65535)
    MAX-ACCESS  read-write
    STATUS      current
    DESCRIPTION
        "In Customer Bridge mode, this object indicates the primary C-VLAN tag ether 
          type used for the packets received on this port. Packets received on a port 
          are considered tagged, when the packet ether type matches with the port ether 
          type configured. Otherwise, they will be considered untagged.
          By default, on all the ports, 0x8100 will be configured as the ether type.

          In Provider-Egde Bridge Mode, this object indicates the primary S-VLAN 
          tag ether type used for the packets received on this port. Packets 
          received on a port are considered tagged, when the packet ethertype 
          matches with the port ether type configured. Otherwise, they will be 
          considered untagged. By default, on all the ports, 0x88a8 will be configured 
          as the ether type. On Proprietary Provider Network Ports, 0x8100 will be 
          configured as the ingress ether type."

    ::= { dot1qFutureVlanPortEntry 9 }

dot1qFutureVlanPortEgressEtherType OBJECT-TYPE
    SYNTAX      Integer32 (1..65535)
    MAX-ACCESS  read-write
    STATUS      current
    DESCRIPTION
        "In Customer Bridge Mode, this object indicates the ether type of
         the C-VLAN tag that has to be applied for all the outgoing packets on
         this port. If a valid value is in this object, all the packets which
         are outgoing on this port will contain the ether type as configured in
         this object. By Default, 0x8100 will be used for packets transmitted
         with C-VLAN on the ports.

         In Provider-Egde Bridge Mode, this object indicates the ether type of 
         the S-VLAN tag that has to be applied for all the outgoing packets on 
         this port. If a valid value is in this object, all the packets which 
         are outgoing on this port will contain the ether type as configured in 
         this object. By Default, 0x88a8 will be used for packets transmitted  
         with S-VLAN on the ports.
         On Proprietary Provider Network Ports and Customer Edge Ports, 0x8100
         will be used as the ether type for the outgoing packets."

    ::= { dot1qFutureVlanPortEntry 10}

dot1qFutureVlanPortEgressTPIDType OBJECT-TYPE
    SYNTAX      INTEGER {
                    portbased(1),
                    vlanbased(2)
                }
    MAX-ACCESS  read-write
    STATUS      current
    DESCRIPTION
        "This object defines the Egress TPID type for a Port.
         If the value is portbased(1) the egress TPID of the packet
         is selected from Egress Port Table.

         When the value is vlanbased(2), the Egress TPID is selected from
         Egress VLAN Table.
         Setting this MIB object is applicable only for hardware."
    DEFVAL      { portbased }
    ::= { dot1qFutureVlanPortEntry 11 }

dot1qFutureVlanPortAllowableTPID1 OBJECT-TYPE
    SYNTAX      Integer32 (0..65535)
    MAX-ACCESS  read-write
    STATUS      current
    DESCRIPTION
    " This object indicates the secondary ether type that is allowable for a port.
      The configurable values for this object are either 0x8100 or 0x88a8.

      Setting this MIB object is applicable only for hardware.

      When this object is set to zero, secondary ether type configurations will be
      deleted from the hardware."
    DEFVAL   { 0 }
    ::= { dot1qFutureVlanPortEntry 12 }

dot1qFutureVlanPortAllowableTPID2 OBJECT-TYPE
    SYNTAX      Integer32 (0..65535)
    MAX-ACCESS  read-write
    STATUS      current
    DESCRIPTION
    " This object indicates the standard ether type that is allowable for a port.
      The configurable value for this object is Q-in-Q EtherType [0x9100].
      Setting this MIB object is applicable only for hardware.

      When this object is set to zero, the additional standard ether type configurations
      will be deleted from the hardware."

    DEFVAL   { 0 }
    ::= { dot1qFutureVlanPortEntry 13 }

dot1qFutureVlanPortAllowableTPID3 OBJECT-TYPE
    SYNTAX      Integer32 (0..65535)
    MAX-ACCESS  read-write
    STATUS      current
    DESCRIPTION
    " This object indicates the additional user defined ether type that is allowable for a port.
      The value for this object is set by the dot1qFutureVlanUserDefinedTPID MIB.

      Setting this MIB object is applicable only for hardware.

      When this object is set to zero, the additional user defined ether type configurations will
      be deleted from the hardware."

    DEFVAL   { 0 }
    ::= { dot1qFutureVlanPortEntry 14 }

dot1qFutureVlanPortUnicastMacSecType OBJECT-TYPE
    SYNTAX      INTEGER {
                    sav(1),
                    shv(2),
                    off(3)
                }
    MAX-ACCESS  read-write
    STATUS      current
    DESCRIPTION
        "This object identifies the MA Table Address Type for this port

         sav   - security is sav, strict is FALSE
                 Only unknown MAC is treated as violation on all security configured ports.
         shv   - security is shv, strict is TRUE
                 Configured MAC alone is treated as non violation in all security configured ports.
         off   - disable security."

    DEFVAL { 3 }
    ::= { dot1qFutureVlanPortEntry 15 }

dot1qFuturePortPacketReflectionStatus OBJECT-TYPE 
   SYNTAX      TruthValue 
   MAX-ACCESS  read-write 
   STATUS      current 
   DESCRIPTION 
         " Port Packet Reflection feature allows switching of packets received 
           on an ingress port back on the same port on which packet was received,
           if the MAC Destination Address is on the same port. The default behavior 
           of the switch is not to switch packets back on the same ingress port."

   DEFVAL  {false} 
   ::= { dot1qFutureVlanPortEntry 16 } 

dot1qFutureVlanPortProtectedStatic  OBJECT-TYPE
   SYNTAX      TruthValue
   MAX-ACCESS  read-only
   STATUS      current
   DESCRIPTION
      "The static Split Horizon property of the port. If set to true, frames 
       that are received on any other port that has the same property set to
       true will not be forwarded on this port."

   ::= { dot1qFutureVlanPortEntry 17 }

-- ---------------------------------------------------------------------------- 
-- Future Vlan Mac Map Table 
-- ---------------------------------------------------------------------------- 
 
dot1qFutureVlanPortMacMapTable OBJECT-TYPE 
   SYNTAX      SEQUENCE OF Dot1qFutureVlanPortMacMapEntry 
   MAX-ACCESS  not-accessible 
   STATUS      current 
   DESCRIPTION 
      "A table that contains information on VLAN-MAC address 
      mapping." 
   ::= { dot1qFutureVlan 11 } 
 
dot1qFutureVlanPortMacMapEntry OBJECT-TYPE
   SYNTAX      Dot1qFutureVlanPortMacMapEntry
   MAX-ACCESS  not-accessible 
   STATUS      current 
   DESCRIPTION 
      "This object specifies the entry that contains VLAN-MAC address mapping." 
   INDEX { dot1qFutureVlanPort, dot1qFutureVlanPortMacMapAddr }
   ::= { dot1qFutureVlanPortMacMapTable 1 }
    
Dot1qFutureVlanPortMacMapEntry ::=
   SEQUENCE { 
      dot1qFutureVlanPortMacMapAddr MacAddress,
      dot1qFutureVlanPortMacMapVid  VlanId,
      dot1qFutureVlanPortMacMapName DisplayString,
      dot1qFutureVlanPortMacMapMcastBcastOption INTEGER,
      dot1qFutureVlanPortMacMapRowStatus RowStatus
   } 
 
dot1qFutureVlanPortMacMapAddr OBJECT-TYPE
   SYNTAX      MacAddress  
   MAX-ACCESS  not-accessible 
   STATUS      current 
   DESCRIPTION 
      "This object specifies the MAC address for which the VLAN mapping is
       present in the entry." 
   ::= { dot1qFutureVlanPortMacMapEntry 1 }
 
dot1qFutureVlanPortMacMapVid OBJECT-TYPE
   SYNTAX      VlanId 
   MAX-ACCESS  read-write 
   STATUS      current 
   DESCRIPTION 
      "This object specifies the VLAN to which the MAC address of this entry is
       mapped to." 
   ::= { dot1qFutureVlanPortMacMapEntry 2 }
 
dot1qFutureVlanPortMacMapName OBJECT-TYPE
   SYNTAX      DisplayString 
   MAX-ACCESS  read-write 
   STATUS      current 
   DESCRIPTION 
      "This object specifies the name given to the mac-VLAN entry." 
   ::= { dot1qFutureVlanPortMacMapEntry 3 }
 
dot1qFutureVlanPortMacMapMcastBcastOption OBJECT-TYPE
   SYNTAX      INTEGER { allow(1), suppress(2) }
   MAX-ACCESS  read-write
   STATUS      current
   DESCRIPTION 
       "Configurable option for discarding/allowing Multicast/Broadcast untagged
        frames. The value allow (1) indicates that Multicast/Broadcast frames
        with source MAC address as in the MAC VLAN entry will be dropped if MAC
        based VLAN is enabled on that port. The value suppress (2) indicates that
        Multicast/Broadcast frames with source MAC address as in the MAC VLAN
        entry will be processed if MAC based VLAN is enabled on that port."
    DEFVAL { allow }
    ::= { dot1qFutureVlanPortMacMapEntry 4 }
 
dot1qFutureVlanPortMacMapRowStatus OBJECT-TYPE
   SYNTAX      RowStatus 
   MAX-ACCESS  read-write 
   STATUS      current 
   DESCRIPTION 
      "The row status of the entry."  
   ::= { dot1qFutureVlanPortMacMapEntry 5 }

-- ---------------------------------------------------------------------------- 
-- Future Vlan Vlan-Fid Map Table 
-- ---------------------------------------------------------------------------- 
 
dot1qFutureVlanFidMapTable OBJECT-TYPE 
   SYNTAX      SEQUENCE OF Dot1qFutureVlanFidMapEntry 
   MAX-ACCESS  not-accessible 
   STATUS      current 
   DESCRIPTION 
      "This table contains information about the filtering database identifier
      (FID) used by VLAN's to make forwarding decisions. VLAN's can be mapped 
      to use the same FID to share filtering information among them. This will
      cause the mapped VLAN's to operate in shared VLAN learning (SVL) mode.
      VLAN's mapped to a unique FID will operate in independent VLAN learning
      mode (IVL). A SET operation on this table is allowed only when 
      dot1qFutureVlanLearningMode is hybrid. By default, all VLAN's will be 
      mapped to the FID equal to their VLAN id when 
      dot1qFutureVlanHybridTypeDefault is IVL. If the value of 
      dot1qFutureVlanHybridTypeDefault is SVL, all VLAN's are mapped to 
      filtering database id 1."

   ::= { dot1qFutureVlan 12 } 
 
dot1qFutureVlanFidMapEntry OBJECT-TYPE 
   SYNTAX      Dot1qFutureVlanFidMapEntry 
   MAX-ACCESS  not-accessible 
   STATUS      current 
   DESCRIPTION 
      "Entry mapping VlanId to Filtering database id."
   INDEX { dot1qFutureVlanIndex } 
   ::= { dot1qFutureVlanFidMapTable 1 } 
    
Dot1qFutureVlanFidMapEntry ::= 
   SEQUENCE { 
      dot1qFutureVlanIndex Unsigned32,
      dot1qFutureVlanFid Unsigned32 
   } 
   
 dot1qFutureVlanIndex OBJECT-TYPE
    SYNTAX      Unsigned32 (1..4094)
    MAX-ACCESS  read-only  
    STATUS      current
    DESCRIPTION
        "VLAN ID for which filtering database information is available."
    ::= { dot1qFutureVlanFidMapEntry 1 }

 dot1qFutureVlanFid OBJECT-TYPE 
    SYNTAX      Unsigned32 (1..4094)
    MAX-ACCESS  read-write
    STATUS      current 
    DESCRIPTION 
       "This object specifies the filtering database id (FID) that will be used
        by the VLAN."
    ::= { dot1qFutureVlanFidMapEntry 2 } 

 -- dot1qFutureVlanTunnelConfig group 
 
-- SCALAR BEGIN 

dot1qFutureVlanOperStatus OBJECT-TYPE 
   SYNTAX      EnabledStatus 
   MAX-ACCESS  read-only 
   STATUS      current 
   DESCRIPTION 
      "This object specifies the operational status of the VLAN module. 
      The value enabled(1) indicates that VLAN module is currently enabled  
      in the device. 
      The value disabled(2) indicates that VLAN module is currently disabled 
      in the device." 
   ::= { dot1qFutureVlan 13 } 

dot1qFutureGvrpOperStatus OBJECT-TYPE 
   SYNTAX      EnabledStatus 
   MAX-ACCESS  read-only 
   STATUS      current 
   DESCRIPTION 
      "The operational status of the GVRP module. 
      The value enabled(1) indicates that GVRP module is currently enabled  
      in the device. 
      The value disabled(2) indicates that GVRP module is currently disabled 
      in the device." 
   ::= { dot1qFutureVlan 14 } 

dot1qFutureGmrpOperStatus OBJECT-TYPE 
   SYNTAX      EnabledStatus 
   MAX-ACCESS  read-only 
   STATUS      current 
   DESCRIPTION 
      "The operational status of the GMRP module. 
      The value enabled(1) indicates that GMRP module is currently enabled  
      in the device. 
      The value disabled(2) indicates that GMRP module is currently disabled 
      in the device." 
   ::= { dot1qFutureVlan 15 } 

-- SCALAR END

-- SCALAR BEGIN 

dot1qFutureVlanBridgeMode OBJECT-TYPE
   SYNTAX      INTEGER {
                  customerBridge (1),
                  providerBridge (2),
                  providerCoreBridge (3),
                  providerEdgeBridge (4)
               }
   MAX-ACCESS  read-write
   STATUS      deprecated
   DESCRIPTION
      
      "This object specifies the bridge mode of the switch.
      
      Setting this to 'customerBridge' means that the switch will operate 
      as a 802.1Q VLAN Bridge.

      Setting this to 'providerBridge' means that the Bridge will operate as 
      a normal Q-in-Q Bridge.

      Setting this to 'providerCoreBridge' means that the switch will operate 
      as a 802.1ad compliant provider bridge with only S-VLAN component.

      Setting this to 'providerEdgeBridge' means that the switch will operate 
      as a 802.1ad provider edge bridge with S-VLAN component and atleast 
      one C-VLAN component.
      
      For changing the bridge mode, GARP and STP modules should be shutdown."

   ::= { dot1qFutureVlanTunnelConfig 1 }


dot1qFutureVlanTunnelBpduPri OBJECT-TYPE
    SYNTAX      Integer32 (0..7)
    MAX-ACCESS  read-write
    STATUS      deprecated
    DESCRIPTION
        "This object specifies the default user priority for all the tunneled Layer 2
        BPDU's received on tunnel ports."
    DEFVAL { 7 }
    ::= { dot1qFutureVlanTunnelConfig 2 }

-- SCALAR END

-- ---------------------------------------------------------------------------- 
-- Future Vlan Tunnel Table 
-- ---------------------------------------------------------------------------- 
 
dot1qFutureVlanTunnelTable OBJECT-TYPE 
   SYNTAX      SEQUENCE OF Dot1qFutureVlanTunnelEntry 
   MAX-ACCESS  not-accessible 
   STATUS      deprecated
   DESCRIPTION 
      "This table contains information about the dot1q tunnel ports. A walk on 
      this table will show only those interfaces that are configured for
      tunneling.
      This table is supported only when the bridge is configured in Provider 
      Bridge (Q-in-Q) mode.
      For Provider Core or Edge bridges, the tunnel configuration objects 
      are defined in fspb.mib"
      
   ::= { dot1qFutureVlanTunnelConfig 3 } 
 
dot1qFutureVlanTunnelEntry OBJECT-TYPE 
   SYNTAX      Dot1qFutureVlanTunnelEntry 
   MAX-ACCESS  not-accessible 
   STATUS      deprecated
   DESCRIPTION 
      "Entry indicating the tunnel information of the port."
   INDEX { dot1qFutureVlanPort } 
   ::= { dot1qFutureVlanTunnelTable 1 } 
    
Dot1qFutureVlanTunnelEntry ::= 
   SEQUENCE { 
      dot1qFutureVlanTunnelStatus EnabledStatus 
   } 
 
dot1qFutureVlanTunnelStatus OBJECT-TYPE 
   SYNTAX      EnabledStatus
   MAX-ACCESS  read-write
   STATUS      deprecated
   DESCRIPTION 
      "Indicates whether dot1qTunnelling is enabled on disabled on this port.
      dot1qFutureVlanTunnelStatus can be set to 'enabled' if and only if
      the Bridge mode is set to be 'Provider Bridge Mode' and VLAN port
      type is set to 'accessPort'. Tunneling can be enabled only on ports 
      which are in 'dot1x force-authorised' state.
      All tunnel ports should be set as untagged members for the access VLAN's
      configured for that customer."
   DEFVAL      { disabled }
   ::= { dot1qFutureVlanTunnelEntry 1 } 


-- ---------------------------------------------------------------------------- 
-- Future Vlan Tunnel Protocol Table 
-- ---------------------------------------------------------------------------- 
 
dot1qFutureVlanTunnelProtocolTable OBJECT-TYPE 
   SYNTAX      SEQUENCE OF Dot1qFutureVlanTunnelProtocolEntry 
   MAX-ACCESS  not-accessible 
   STATUS      deprecated
   DESCRIPTION 
      "This table contains information/statistics about the customer STP/GVRP BPDU's and
      IGMP packets being tunneled inside the service provider network. A walk on this
      table will show only those interfaces in which tunneling is enabled.

      This table is supported only when the bridge is configured in Provider 
      Bridge (Q-in-Q) mode.
      For Provider Core or Edge bridges, the tunnel protocol configuration
      objects are defined in fspb.mib."
   ::= { dot1qFutureVlanTunnelConfig 4 }
 
dot1qFutureVlanTunnelProtocolEntry OBJECT-TYPE 
   SYNTAX      Dot1qFutureVlanTunnelProtocolEntry 
   MAX-ACCESS  not-accessible 
   STATUS      deprecated
   DESCRIPTION 
      "Entry indicating the tunneling of STP/GVRP BPDU's and IGMP Packets on this port."
   INDEX { dot1qFutureVlanPort } 
   ::= { dot1qFutureVlanTunnelProtocolTable 1 } 
    
Dot1qFutureVlanTunnelProtocolEntry ::= 
   SEQUENCE { 
      dot1qFutureVlanTunnelStpPDUs      EnabledStatus,
      dot1qFutureVlanTunnelStpPDUsRecvd Counter32,
      dot1qFutureVlanTunnelStpPDUsSent    Counter32,
      dot1qFutureVlanTunnelGvrpPDUs       EnabledStatus,
      dot1qFutureVlanTunnelGvrpPDUsRecvd  Counter32,
      dot1qFutureVlanTunnelGvrpPDUsSent   Counter32,
      dot1qFutureVlanTunnelIgmpPkts        EnabledStatus,
      dot1qFutureVlanTunnelIgmpPktsRecvd   Counter32,
      dot1qFutureVlanTunnelIgmpPktsSent    Counter32
   } 
 
dot1qFutureVlanTunnelStpPDUs OBJECT-TYPE 
   SYNTAX      EnabledStatus
   MAX-ACCESS  read-write
   STATUS      deprecated
   DESCRIPTION 
      "Indicates whether tunneling of STP BPDUs is enabled or not."
   DEFVAL      { disabled }
   ::= { dot1qFutureVlanTunnelProtocolEntry 1 } 

dot1qFutureVlanTunnelStpPDUsRecvd OBJECT-TYPE 
   SYNTAX      Counter32
   MAX-ACCESS  read-only
   STATUS      deprecated
   DESCRIPTION 
      "The number of tunneled ingress STP PDU's."
   ::= { dot1qFutureVlanTunnelProtocolEntry 2 } 

dot1qFutureVlanTunnelStpPDUsSent OBJECT-TYPE 
   SYNTAX      Counter32
   MAX-ACCESS  read-only
   STATUS      deprecated
   DESCRIPTION 
      "The number of tunneled egress STP PDU's."
   ::= { dot1qFutureVlanTunnelProtocolEntry 3 } 

dot1qFutureVlanTunnelGvrpPDUs OBJECT-TYPE 
   SYNTAX      EnabledStatus
   MAX-ACCESS  read-write
   STATUS      deprecated
   DESCRIPTION 
      "Indicates whether tunneling of GVRP BPDUs is enabled or not."
   DEFVAL      { enabled }
   ::= { dot1qFutureVlanTunnelProtocolEntry 4 } 

dot1qFutureVlanTunnelGvrpPDUsRecvd OBJECT-TYPE 
   SYNTAX      Counter32
   MAX-ACCESS  read-only
   STATUS      deprecated
   DESCRIPTION 
      "The number of tunneled ingress GVRP PDU's."
   ::= { dot1qFutureVlanTunnelProtocolEntry 5 } 

dot1qFutureVlanTunnelGvrpPDUsSent OBJECT-TYPE 
   SYNTAX      Counter32
   MAX-ACCESS  read-only
   STATUS      deprecated
   DESCRIPTION 
      "The number of tunneled egress GVRP PDU's."
   ::= { dot1qFutureVlanTunnelProtocolEntry 6 } 

dot1qFutureVlanTunnelIgmpPkts OBJECT-TYPE 
   SYNTAX      EnabledStatus
   MAX-ACCESS  read-write
   STATUS      deprecated
   DESCRIPTION 
      "Indicates whether tunneling of IGMP Packets is enabled or not."
   DEFVAL      { enabled }
   ::= { dot1qFutureVlanTunnelProtocolEntry 7 } 

dot1qFutureVlanTunnelIgmpPktsRecvd OBJECT-TYPE 
   SYNTAX      Counter32
   MAX-ACCESS  read-only
   STATUS      deprecated
   DESCRIPTION 
      "The number of tunneled ingress IGMP Packets."
   ::= { dot1qFutureVlanTunnelProtocolEntry 8 } 

dot1qFutureVlanTunnelIgmpPktsSent OBJECT-TYPE 
   SYNTAX      Counter32
   MAX-ACCESS  read-only
   STATUS      deprecated
   DESCRIPTION 
      "The number of tunneled egress IGMP Packets."
   ::= { dot1qFutureVlanTunnelProtocolEntry 9 } 

dot1qFutureVlanCounterTable OBJECT-TYPE
   SYNTAX      SEQUENCE OF Dot1qFutureVlanCounterEntry
   MAX-ACCESS  not-accessible
   STATUS      current
   DESCRIPTION
             "The table contains the statistics on a per VLAN basis.
              It contains number of unicast, broadcast and unknown unicast
              packets flooded per VLAN."
   ::= { dot1qFutureVlan 16 }

dot1qFutureVlanCounterEntry OBJECT-TYPE
   SYNTAX      Dot1qFutureVlanCounterEntry
   MAX-ACCESS  not-accessible
   STATUS      current
   DESCRIPTION
              "This object specifies the entry contains the VLAN statistics."
   INDEX { dot1qFutureVlanIndex }
   ::= { dot1qFutureVlanCounterTable 1 }
Dot1qFutureVlanCounterEntry ::=
   SEQUENCE {
             dot1qFutureVlanCounterRxUcast         Counter32,
             dot1qFutureVlanCounterRxMcastBcast    Counter32,
             dot1qFutureVlanCounterTxUnknUcast     Counter32,
             dot1qFutureVlanCounterTxUcast         Counter32,
             dot1qFutureVlanCounterTxBcast         Counter32,
             dot1qFutureVlanCounterRxFrames        Counter32,
             dot1qFutureVlanCounterRxBytes         Counter32,
             dot1qFutureVlanCounterTxFrames        Counter32,
             dot1qFutureVlanCounterTxBytes         Counter32,
             dot1qFutureVlanCounterDiscardFrames   Counter32,
             dot1qFutureVlanCounterDiscardBytes    Counter32,
             dot1qFutureVlanCounterStatus          EnabledStatus          
            }

dot1qFutureVlanCounterRxUcast OBJECT-TYPE
   SYNTAX      Counter32
   MAX-ACCESS  read-only
   STATUS      current
   DESCRIPTION
            "This object specifies the number of unicast packets received in
             this VLAN."
   ::= { dot1qFutureVlanCounterEntry 1 }

dot1qFutureVlanCounterRxMcastBcast OBJECT-TYPE
   SYNTAX      Counter32
   MAX-ACCESS  read-only
   STATUS      current
   DESCRIPTION
            "This object specifies the number of multicast/broadcast packets
             received in this VLAN."
   ::= { dot1qFutureVlanCounterEntry 2 }

dot1qFutureVlanCounterTxUnknUcast OBJECT-TYPE
   SYNTAX      Counter32
   MAX-ACCESS  read-only
   STATUS      current
   DESCRIPTION
             "This object specifies the number of unknown unicast packets
              flooded in this VLAN."
   ::= { dot1qFutureVlanCounterEntry 3 }

dot1qFutureVlanCounterTxUcast OBJECT-TYPE
   SYNTAX      Counter32
   MAX-ACCESS  read-only
   STATUS      current
   DESCRIPTION
            "This object specifies the number of known unicast packets forwarded
            in this VLAN."
   ::= { dot1qFutureVlanCounterEntry 4 }

dot1qFutureVlanCounterTxBcast OBJECT-TYPE
   SYNTAX      Counter32
   MAX-ACCESS  read-only
   STATUS      current
   DESCRIPTION
            "This object specifies the number of broadcast packets forwarded in
             this VLAN."
   ::= { dot1qFutureVlanCounterEntry 5 }

dot1qFutureVlanCounterRxFrames OBJECT-TYPE
   SYNTAX      Counter32
   MAX-ACCESS  read-only
   STATUS      current
   DESCRIPTION
            "This object displays the total number of unicast, multicast and
             broadcast packets received in the VLAN."
   ::= { dot1qFutureVlanCounterEntry 6 }

dot1qFutureVlanCounterRxBytes OBJECT-TYPE
   SYNTAX      Counter32
   MAX-ACCESS  read-only
   STATUS      current
   DESCRIPTION
            "This object displays the total number of unicast, multicast and broadcast bytes received 
              in the VLAN."
   ::= { dot1qFutureVlanCounterEntry 7 }

dot1qFutureVlanCounterTxFrames OBJECT-TYPE
   SYNTAX      Counter32
   MAX-ACCESS  read-only
   STATUS      current
   DESCRIPTION
            "This object displays the total number of unicast, multicast and broadcast packets transmitted
              by the VLAN."
   ::= { dot1qFutureVlanCounterEntry 8 }

dot1qFutureVlanCounterTxBytes OBJECT-TYPE
   SYNTAX      Counter32
   MAX-ACCESS  read-only
   STATUS      current
   DESCRIPTION
             "This object displays the total number of unicast, multicast and broadcast bytes transmitted 
              by the VLAN."
   ::= { dot1qFutureVlanCounterEntry 9 }

dot1qFutureVlanCounterDiscardFrames OBJECT-TYPE
   SYNTAX      Counter32
   MAX-ACCESS  read-only
   STATUS      current
   DESCRIPTION
            "This object displays the number of packets dropped by the VLAN."
   ::= { dot1qFutureVlanCounterEntry 10 }

dot1qFutureVlanCounterDiscardBytes OBJECT-TYPE
   SYNTAX      Counter32
   MAX-ACCESS  read-only
   STATUS      current
   DESCRIPTION
            "This object displays the number of bytes dropped by the VLAN."
   ::= { dot1qFutureVlanCounterEntry 11 }

dot1qFutureVlanCounterStatus OBJECT-TYPE
   SYNTAX      EnabledStatus
   MAX-ACCESS  read-write
   STATUS      current
   DESCRIPTION
      "A truth value indicating the statistics collection is enabled/disabled
       for this VLAN.

       When statistics collection is set to disabled, VLAN stops collecting
       statistics on this specific VLAN.
       When statistics collection is set to enabled, VLAN start collecting
       statistics on this specific VLAN"
   DEFVAL   { disabled }       
   ::= { dot1qFutureVlanCounterEntry 12 }

dot1qFutureVlanUnicastMacControlTable OBJECT-TYPE
    SYNTAX      SEQUENCE OF Dot1qFutureVlanUnicastMacControlEntry
    MAX-ACCESS  not-accessible
    STATUS      current
    DESCRIPTION
        "A table containing per VLAN Unicast MAC address control information. 
        The control information includes the status of unicast MAC address 
        learning as well as restricting the number of unique entries learnt to 
        a specified limit for the specified VLAN."
    ::= { dot1qFutureVlan 17 }

dot1qFutureVlanUnicastMacControlEntry OBJECT-TYPE
    SYNTAX      Dot1qFutureVlanUnicastMacControlEntry
    MAX-ACCESS  not-accessible
    STATUS      current
    DESCRIPTION
        "Information controlling the number of distinct unicast MAC addresses 
         that can be learnt by a VLAN depending on whether learning is enabled
         or disabled for the specified VLAN."
    INDEX { dot1qFutureVlanIndex }
    ::= { dot1qFutureVlanUnicastMacControlTable 1 }

Dot1qFutureVlanUnicastMacControlEntry ::=
    SEQUENCE {
        dot1qFutureVlanUnicastMacLimit              Unsigned32,
        dot1qFutureVlanAdminMacLearningStatus       MacLearningStatus,
        dot1qFutureVlanOperMacLearningStatus        EnabledStatus,
        dot1qFutureVlanPortFdbFlush                 TruthValue
    }

dot1qFutureVlanUnicastMacLimit OBJECT-TYPE
    SYNTAX      Unsigned32 (0..4294967295)
    MAX-ACCESS  read-write
    STATUS      current
    DESCRIPTION
        "The limiting value on the number of distinct unicast MAC addresses 
         learnt in a VLAN. The lower limit and upper limit value that
         can be SET for this object is determined by the underlying hardware."
        
    ::= { dot1qFutureVlanUnicastMacControlEntry 1 }

dot1qFutureVlanAdminMacLearningStatus OBJECT-TYPE
    SYNTAX      MacLearningStatus
    MAX-ACCESS  read-write
    STATUS      current
    DESCRIPTION
       "A truth value used to configure the unicast MAC learning admin status of
          the VLAN to be enabled (1) or disabled (2) or default (3).
          Configuring this object to default behavior is governed by value 
          configured for dot1qFutureVlanGlobalMacLearningStatus."

    DEFVAL { default }
    ::= { dot1qFutureVlanUnicastMacControlEntry 2 }

dot1qFutureVlanOperMacLearningStatus OBJECT-TYPE
    SYNTAX      EnabledStatus
    MAX-ACCESS  read-only
    STATUS      current
    DESCRIPTION
        "A truth value indicating the unicast MAC learning enabled/disabled.
         Operational status for the specified VLAN.
         If the VLAN does not have any member port, then the MAC Learning
         Status for this VLAN will always be disabled, Otherwise
         the Mac learning status for this VLAN will take value from Admin Mac
         Learning status."
    ::= { dot1qFutureVlanUnicastMacControlEntry 3 }

dot1qFutureVlanPortFdbFlush OBJECT-TYPE
    SYNTAX      TruthValue
    MAX-ACCESS  read-write
    STATUS      current
    DESCRIPTION
      "If this object is set as 'true', then all the dynamically
       learnt MAC addresses in specified VLAN will be removed. After flush,
       this object is set to 'false'."
    DEFVAL  {false}
    ::= { dot1qFutureVlanUnicastMacControlEntry 4 }

dot1qFutureGarpDebug OBJECT-TYPE 
   SYNTAX      Integer32 (0..1048575)
   MAX-ACCESS  read-write 
   STATUS      current 
   DESCRIPTION 
      "Enables the tracing in the selected submodule in GARP. A 32 bit integer
      is used to store the tracing level in the specified module.
       Different Tracing Levels -
         BIT 0 - Initialization and Shutdown Trace.
         BIT 1 - Management trace.
         BIT 2 - Data path trace.
         BIT 3 - Control Plane trace.
         BIT 4 - Packet Dump.
         BIT 5 - OS Resource trace.
         BIT 6 - All Failure trace (All failures including Packet Validation)
         BIT 7 - Buffer Trace.

       Different submodule Tracing -
         BIT 16 - Tracing in GARP module.   
         BIT 17 - Tracing in GMRP module.  
         BIT 18 - Tracing in GVRP module.   
         BIT 19 - Tracing in GARP redundancy module.   

       The remaining bits are reserved. The combinations of levels and submodules 
       are allowed i.e. tracing can be allowed at all failure and data path 
       level in all sub modules by setting the bit appropriately.
       For Example, setting the debug value to the following bit stream, 
          00000000000000010000000000000100 will enable data path trace 
       prints in GARP module. Multiple sub modules and multiple levels can
       be combined by setting the corresponding bits.
       For example, setting the debug value to the following bit stream,
          00000000000001010000000000001100 will enable data path and 
       control plane trace prints in GARP and GVRP modules.
       
       Note : BIT0 is the least significant bit and BIT31 is the most
       significant bit."
   DEFVAL   { 0 }
   ::= { dot1qFutureVlan 18 } 

-- -------------------------------------------------------------
-- dot1qFutureVlanTpFdbTable
-- -------------------------------------------------------------
 dot1qFutureVlanTpFdbTable OBJECT-TYPE
    SYNTAX      SEQUENCE OF Dot1qFutureVlanTpFdbEntry
    MAX-ACCESS  not-accessible
    STATUS      current
    DESCRIPTION
        "An extension to the dot1qTpFdbTable contains information
        about unicast entries only learned via pseudowire
        for which the device has forwarding and/or filtering
        information. This information is used by the
        transparent bridging function in determining how to
        propagate a received frame."
    REFERENCE
        ""
    ::= { dot1qFutureVlan 19 }

dot1qFutureVlanTpFdbEntry OBJECT-TYPE
    SYNTAX      Dot1qFutureVlanTpFdbEntry
    MAX-ACCESS  not-accessible
    STATUS      current
    DESCRIPTION
        "Information about the pseudowire on which MAC address was
        learned"
    AUGMENTS    { dot1qTpFdbEntry }
    ::= { dot1qFutureVlanTpFdbTable 1 }

Dot1qFutureVlanTpFdbEntry ::=
    SEQUENCE {
        dot1qFutureVlanTpFdbPw
            Unsigned32,
        dot1qTpOldFdbPort
            INTEGER,
        dot1qFutureConnectionIdentifier
            MacAddress
    }

dot1qFutureVlanTpFdbPw OBJECT-TYPE
    SYNTAX      Unsigned32
    MAX-ACCESS  read-only
    STATUS      current
    DESCRIPTION
        "Either the value '0', or the pseudowire number on
        which a frame having a source address equal to the value
        of the corresponding instance of dot1qTpFdbAddress has
        been seen. A value of '0' indicates that the entry was
        learned via the layer2 port. Non-zero value indicates
        that this value must be used for forwarding irrespective
        of dot1qTpFdbPort"
    ::= { dot1qFutureVlanTpFdbEntry 1 }

dot1qTpOldFdbPort OBJECT-TYPE
    SYNTAX     INTEGER (0..65535) 
    MAX-ACCESS  read-only
    STATUS      current
    DESCRIPTION
         "This object is useful for generating the source relearning trap.
         When a get is performed on this object, it returns the value of
         zero(0), so that ISS walk doesn't break. It indicates the port 
         through which the MAC address was learnt previously, while generating
         the source relearning trap."
    ::= { dot1qFutureVlanTpFdbEntry 2 }

dot1qFutureConnectionIdentifier OBJECT-TYPE
    SYNTAX      MacAddress
    MAX-ACCESS  read-only
    STATUS      current
    DESCRIPTION
         "This object is to associate the backbone MAC address of the peer
         backbone edge bridge with customer MAC addresses that can be reached
         through the peer backbone edge bridge."
    ::= { dot1qFutureVlanTpFdbEntry 3 }


dot1qFutureVlanWildCardTable OBJECT-TYPE
    SYNTAX      SEQUENCE OF Dot1qFutureVlanWildCardEntry
    MAX-ACCESS  not-accessible
    STATUS      current
    DESCRIPTION
        "Wild card VLAN (Id : 0xFFF) static filtering information 
        will be used for all VLANs for which there is no specific 
        static filtering exists in dot1qStaticUnicastTable or 
        dot1qStaticMulticastTable."
    REFERENCE
        ""
    ::= { dot1qFutureVlan 20 }
    
dot1qFutureVlanWildCardEntry OBJECT-TYPE
    SYNTAX      Dot1qFutureVlanWildCardEntry
    MAX-ACCESS  not-accessible
    STATUS      current
    DESCRIPTION
    "WildCard VLAN filtering information configured into device by
    management specifying set of ports to which frames received
    from any port and for any VLAN containing this wild card MAC
    address as destination address and for which there is no
    static filtering information are allowed to be forwarded."
    INDEX { dot1qFutureVlanWildCardMacAddress }
    ::= { dot1qFutureVlanWildCardTable 1 }

Dot1qFutureVlanWildCardEntry ::=
    SEQUENCE {
        dot1qFutureVlanWildCardMacAddress
        MacAddress,
        dot1qFutureVlanWildCardEgressPorts
        PortList,
        dot1qFutureVlanWildCardRowStatus
        RowStatus
    }

dot1qFutureVlanWildCardMacAddress OBJECT-TYPE
    SYNTAX      MacAddress
    MAX-ACCESS  not-accessible 
    STATUS      current
    DESCRIPTION
        "The destination MAC address in a frame to which this entry's 
        filtering information applies. This object must take the 
        value of a Unicast, Multicast or Broadcast address."
    ::= { dot1qFutureVlanWildCardEntry 1 }

dot1qFutureVlanWildCardEgressPorts OBJECT-TYPE
    SYNTAX      PortList
    MAX-ACCESS  read-write
    STATUS      current
    DESCRIPTION
        "The set of ports to which frames received from a specific port
        and destined for dot1qFutureVlanWildCardMacAddress address must
        be forwarded, if there is no specific static filtering entry
        exist for this MAC."
    ::= { dot1qFutureVlanWildCardEntry 2 }

dot1qFutureVlanWildCardRowStatus OBJECT-TYPE
   SYNTAX      RowStatus 
   MAX-ACCESS  read-write 
   STATUS      current 
   DESCRIPTION 
      "The row status of the entry."  
   ::= { dot1qFutureVlanWildCardEntry 3 }

-- -------------------------------------------------------------
-- The Static (Destination-Address Filtering) Database
-- -------------------------------------------------------------

dot1qFutureStaticUnicastExtnTable OBJECT-TYPE
    SYNTAX      SEQUENCE OF Dot1qFutureStaticUnicastExtnEntry
    MAX-ACCESS  not-accessible
    STATUS      current
    DESCRIPTION
        "A table containing filtering information for Unicast
        MAC addresses for each Filtering Database, configured
        into the device by (local or network) management
        specifying the set of ports to which frames received
        from specific ports and containing specific unicast
        destination addresses are allowed to be forwarded. A
        value of zero in this table as the port number from
        which frames with a specific destination address are
        received, is used to specify all ports for which there
        is no specific entry in this table for that particular
        destination address. Entries are valid for unicast
        addresses only."
    REFERENCE
        "IEEE 802.1Q/D11 Section 12.7.7,
        ISO/IEC 15802-3 Section 7.9.1."
    ::= { dot1qFutureVlan 21 }

dot1qFutureStaticUnicastExtnEntry OBJECT-TYPE
    SYNTAX      Dot1qFutureStaticUnicastExtnEntry
    MAX-ACCESS  not-accessible
    STATUS      current
    DESCRIPTION
        "Filtering information configured into the device by
        (local or network) management specifying the set of
        ports to which frames received from a specific port and
        containing a specific unicast destination address are
        allowed to be forwarded."
    AUGMENTS { dot1qStaticUnicastEntry }
    ::= { dot1qFutureStaticUnicastExtnTable 1 }

Dot1qFutureStaticUnicastExtnEntry ::=
    SEQUENCE {
        dot1qFutureStaticConnectionIdentifier
            MacAddress
    }

dot1qFutureStaticConnectionIdentifier OBJECT-TYPE
    SYNTAX      MacAddress
    MAX-ACCESS  read-write
    STATUS      current
    DESCRIPTION
         "This object is to associate the backbone MAC address of the peer
         backbone edge bridge with customer MAC addresses that can be reached 
         through the peer backbone edge bridge."
    ::= { dot1qFutureStaticUnicastExtnEntry 1 }

-- scalar begin

dot1qFutureUnicastMacLearningLimit OBJECT-TYPE
    SYNTAX      Unsigned32 (0..4294967295) 
    MAX-ACCESS  read-write
    STATUS      current
    DESCRIPTION
       "This object specifies the limiting value on the number of distinct
        unicast MAC addresses that can be learnt in the device.

       The upper limit value that can be SET for this object is determined 
       by the underlying hardware. The value that can be SET for this object 
       cannot be less than the value set for the UnicastMacLimit per VLAN for 
       any of the VLANs in the device."
    ::= { dot1qFutureVlan 22 }

dot1qFutureVlanBaseBridgeMode OBJECT-TYPE
   SYNTAX      INTEGER
                {
                 dot1dTransparentMode(1),
                 dot1qVlanMode(2)
                }

   MAX-ACCESS  read-write
   STATUS      current
   DESCRIPTION
     "This object specifies base Bridge-Mode of the Switch.
      Setting the value to transparent mode will make
      switch behave according to IEEE 802.1d implementation.
      Setting the value to VLAN mode will make switch behave
      according to IEEE 802.1q implementation"
   ::= { dot1qFutureVlan 23 }

dot1qFutureVlanSubnetBasedOnAllPorts OBJECT-TYPE 
   SYNTAX      EnabledStatus
   MAX-ACCESS  read-write
   STATUS      current
   DESCRIPTION 
      "This object is used to enable/disable the subnet based VLAN classification
       on all ports of dot1qFutureVlanPortSubnetBasedClassification. On setting
       this object to enable/disable status, Subnet based VLAN classification 
       will be enabled/disabled on all the ports."
   ::= { dot1qFutureVlan 24 }

-- scalar end

-- ---------------------------------------------------------------------------- 
-- Future Vlan Subnet Map Table 
-- ---------------------------------------------------------------------------- 
 
dot1qFutureVlanPortSubnetMapTable OBJECT-TYPE 
   SYNTAX      SEQUENCE OF Dot1qFutureVlanPortSubnetMapEntry 
   MAX-ACCESS  not-accessible 
   STATUS      current 
   DESCRIPTION 
      "Subnet based VLAN classification - The source IP-subnet address in
       the incoming packets is used to classify VLAN membership. 
       Subnet based VLAN is applied only on IP/ARP packets.
       This table contains information on Subnet-VlanId address mapping.
       In case of BCM, the dot1qFutureVlanPort index should always be 0 since
       BCM supports Subnet based VLAN globally (not on per port)." 
   ::= { dot1qFutureVlan 25 } 
 
dot1qFutureVlanPortSubnetMapEntry OBJECT-TYPE
   SYNTAX      Dot1qFutureVlanPortSubnetMapEntry
   MAX-ACCESS  not-accessible 
   STATUS      current 
   DESCRIPTION 
      "This object specifies an entry that contains VLAN-Subnet address mapping." 
   INDEX { dot1qFutureVlanPort,
           dot1qFutureVlanPortSubnetMapAddr}
   ::= { dot1qFutureVlanPortSubnetMapTable 1 }
    
Dot1qFutureVlanPortSubnetMapEntry ::=
   SEQUENCE { 
      dot1qFutureVlanPortSubnetMapAddr IpAddress,
      dot1qFutureVlanPortSubnetMapVid  VlanId,
      dot1qFutureVlanPortSubnetMapARPOption INTEGER,
      dot1qFutureVlanPortSubnetMapRowStatus RowStatus
   } 
 
dot1qFutureVlanPortSubnetMapAddr OBJECT-TYPE
   SYNTAX      IpAddress
   MAX-ACCESS  not-accessible 
   STATUS      current 
   DESCRIPTION 
      "This object specifies the the source IP-Subnet address for which the VLAN
       mapping is present in the entry." 
   ::= { dot1qFutureVlanPortSubnetMapEntry 1 }

dot1qFutureVlanPortSubnetMapVid OBJECT-TYPE
   SYNTAX      VlanId 
   MAX-ACCESS  read-write 
   STATUS      current 
   DESCRIPTION 
      "This object specifies the VLAN to which the source IP-Subnet address of
       this entry is mapped to." 
   ::= { dot1qFutureVlanPortSubnetMapEntry 2 }
 
dot1qFutureVlanPortSubnetMapARPOption OBJECT-TYPE
   SYNTAX      INTEGER { allow(1), suppress(2) }
   MAX-ACCESS  read-write
   STATUS      current
   DESCRIPTION 
       "Configurable option for discarding/allowing ARP Untagged frames on
        the VLAN. The value allow (1) indicates that ARP frames with source 
        IP-subnet address matching the dot1qFutureVlanPortSubnetMapEntry 
        will be classified to VLAN based on dot1qFutureVlanPortSubnetMapEntry.
        The value suppress (2) indicates that ARP frames with source IP-Subnet
        address matching the dot1qFutureVlanPortSubnetMapEntry will not be
        classified to VLAN based on dot1qFutureVlanPortSubnetMapEntry. The
        VLAN classification will be based on next subsequent classification 
        mechanism."
    DEFVAL { allow }
    ::= { dot1qFutureVlanPortSubnetMapEntry 3 }
 
dot1qFutureVlanPortSubnetMapRowStatus OBJECT-TYPE
   SYNTAX      RowStatus 
   MAX-ACCESS  read-write 
   STATUS      current 
   DESCRIPTION 
      "The row status of the entry."  
   ::= { dot1qFutureVlanPortSubnetMapEntry 4 }
-- ---------------------------------------------------------------------------- 
-- Future Vlan Extension Table
-- ---------------------------------------------------------------------------- 

dot1qFutureStVlanExtTable OBJECT-TYPE 
   SYNTAX      SEQUENCE OF Dot1qFutureStVlanExtEntry 
   MAX-ACCESS  not-accessible 
   STATUS      current 
   DESCRIPTION 
        "An extension to dot1qVlanStaticTable VLAN table."
   ::= { dot1qFutureVlan 29 } 
 
dot1qFutureStVlanExtEntry OBJECT-TYPE
   SYNTAX      Dot1qFutureStVlanExtEntry
   MAX-ACCESS  not-accessible 
   STATUS      current 
   DESCRIPTION 
        "This object specifies each entry which specifies the VLAN
         configuration done for a given VLAN."
   AUGMENTS { dot1qVlanStaticEntry }
   ::= { dot1qFutureStVlanExtTable 1 }
    
Dot1qFutureStVlanExtEntry ::=
   SEQUENCE { 
      dot1qFutureStVlanType INTEGER,
      dot1qFutureStVlanVid VlanIdOrNone,
      dot1qFutureStVlanEgressEthertype Integer32
   } 
 
dot1qFutureStVlanType OBJECT-TYPE
    SYNTAX      INTEGER {
                          normal (1)
                        }
    MAX-ACCESS  read-only
    STATUS      current
    DESCRIPTION
    "Indicates the VLAN type of the static VLAN.
    This object is being retained for backward compatibility of OID's
    of the remaining objects in this table. "
    ::= { dot1qFutureStVlanExtEntry 1 }

dot1qFutureStVlanVid OBJECT-TYPE
   SYNTAX      VlanIdOrNone
   MAX-ACCESS  read-only
   STATUS      current 
   DESCRIPTION 
   
   "This object is being retained for backward compatibility of OID's of the
   remaining objects in this table. "

   ::= { dot1qFutureStVlanExtEntry 2 }

dot1qFutureStVlanEgressEthertype OBJECT-TYPE
    SYNTAX      Integer32 (0..65535)
    MAX-ACCESS  read-write
    STATUS      current
    DESCRIPTION
        "This object sets the value for the Egress Ether type of a packet.
         The value set for this object is applicable for a port present in
         this VLAN only when the value of dot1qFutureVlanPortEgressTPIDType is set
         to VLANbased(2) for a egress port.
         The configurable values are C-TAG, S-TAG ,Q-IN-Q and Userdefined
         TPID defined by object dot1qFutureVlanUserDefinedTPID.

         For a customer bridge, the default value is C-VLAN tag and for a
         Provider-edge bridge, the default is S-VLAN tag."

    DEFVAL { 33024 }
    ::= { dot1qFutureStVlanExtEntry 3}

--scalar begin

dot1qFutureVlanGlobalMacLearningStatus OBJECT-TYPE
   SYNTAX      EnabledStatus
   MAX-ACCESS  read-write
   STATUS      current
   DESCRIPTION
         "This object specifies the global  MAC learning status of the
          switch. The default value of global MAC learning status of
          the switch is enabled.
          This object can take only two values enabled or disabled.
          The value as specified by this object will be applied
          for a newly created VLAN. The configuration of this object 
          will override the value of dot1qFutureVlanAdminMacLearningStatus
          provided  the value of dot1qFutureVlanAdminMacLearningStatus is
          default only."
   DEFVAL  {enabled}
   ::= { dot1qFutureVlan 26 }

dot1qFutureVlanApplyEnhancedFilteringCriteria OBJECT-TYPE
   SYNTAX      TruthValue
   MAX-ACCESS  read-write
   STATUS      current
   DESCRIPTION
   "If this object is set as 'false', then only default filtering
   utility criteria will be applied on all ports.
   Otherwise the filtering criteria to be used for the ports 
   will be taken from dot1qFutureVlanFilteringUtilityCriteria 
   for the respective ports.
    - It is recommended to configure this object before any VLAN configuration
    is done in the system.
    - It is recommended to configure this object in the following sequence:
            -Configure this object
            -Save the configuration into permanent database
            -Restart the system."
   DEFVAL  {true}
   ::= { dot1qFutureVlan 27 }


dot1qFutureVlanSwStatsEnabled OBJECT-TYPE
   SYNTAX      TruthValue
   MAX-ACCESS  read-write
   STATUS      current
   DESCRIPTION
   "If set to 'true', statistics collection will be done and stored in 
    software. This object can be set to 'true' only if the data switching
    is done by software.
    If set to 'false', the statistics collection will be done by the 
    hardware and will not be stored in software.
    If data switching is done by software, then the default value of this
    object will be 'true'. Otherwise, the default value will be 'false'.
    - It is recommended to configure this object before any VLAN configuration
    is done in the system.
    - It is recommended to configure this object in the following sequence:
            -Configure this object
            -Save the configuration into permanent database
            -Restart the system."
   ::= { dot1qFutureVlan 28 }



--scalar end

--table ends

dot1qVlanTraps OBJECT IDENTIFIER ::= { dot1qFutureVlanTraps 0 }

dot1qFutureMacThresholdTrap  NOTIFICATION-TYPE
    OBJECTS {
        dot1qFutureVlanIndex,
        dot1qFutureVlanUnicastMacLimit
        }
    STATUS     current
    DESCRIPTION
         "This trap is generated when the unicast MAC limit threshold is 
         exceeded for a particular VLAN.The generated trap will carry 
         information regarding the VLAN Id whose MAC address limit has exceeded 
         and the Mac address threshold that was configured for this VLAN."
    ::= { dot1qVlanTraps 1 }

dot1qFutureSrcRelearnTrap NOTIFICATION-TYPE
    OBJECTS {
        dot1qFutureVlanFid,
        dot1qTpFdbPort,
        dot1qTpOldFdbPort
        }
    STATUS     current
    DESCRIPTION
         "This trap is generated whenever source relearning happens in a VLAN.
          The generated trap will contain information about the VLAN for which 
          the source relearning happened, MAC address and port number through
          which this MAC address has been learnt now."
    ::= { dot1qVlanTraps 2 }

dot1qFutureSwitchMacLimitTrap NOTIFICATION-TYPE
    OBJECTS {
        dot1qFutureUnicastMacLearningLimit
        }
    STATUS     current
    DESCRIPTION
         "This trap is generated when the unicast MAC limit threshold is
         exceeded for the device. The generated trap will carry
         information regarding the MAC address threshold that was configured
         for this device."
    ::= { dot1qVlanTraps 3 }

-- ---------------------------------------------------------------------------- 
-- Vlan Subnet Extension Table 
-- ---------------------------------------------------------------------------- 

dot1qFutureVlanPortSubnetMapExtTable OBJECT-TYPE 
   SYNTAX      SEQUENCE OF Dot1qFutureVlanPortSubnetMapExtEntry 
   MAX-ACCESS  not-accessible 
   STATUS      current 
   DESCRIPTION 
      "Subnet based VLAN classification - The source IP-subnet address in
       the incoming packets is used to classify VLAN membership. 
       Subnet based VLAN is applied only on IP/ARP packets.
       This table contains information on Subnet-VlanId address mapping."
   ::= { dot1qFutureVlan 30 } 

dot1qFutureVlanPortSubnetMapExtEntry OBJECT-TYPE
   SYNTAX      Dot1qFutureVlanPortSubnetMapExtEntry
   MAX-ACCESS  not-accessible 
   STATUS      current 
   DESCRIPTION 
      "This object specifies the entry that contains VLAN-Subnet address mapping." 
   INDEX { dot1qFutureVlanPort,
           dot1qFutureVlanPortSubnetMapExtAddr,
           dot1qFutureVlanPortSubnetMapExtMask }
   ::= { dot1qFutureVlanPortSubnetMapExtTable 1 }

Dot1qFutureVlanPortSubnetMapExtEntry ::=
   SEQUENCE { 
      dot1qFutureVlanPortSubnetMapExtAddr IpAddress,
      dot1qFutureVlanPortSubnetMapExtMask IpAddress,
      dot1qFutureVlanPortSubnetMapExtVid  VlanId,
      dot1qFutureVlanPortSubnetMapExtARPOption INTEGER,
      dot1qFutureVlanPortSubnetMapExtRowStatus RowStatus
   } 

dot1qFutureVlanPortSubnetMapExtAddr OBJECT-TYPE
   SYNTAX      IpAddress
   MAX-ACCESS  not-accessible 
   STATUS      current 
   DESCRIPTION 
      "This object specifies the Source IP address for which the VLAN mapping is
       present in the entry." 
   ::= { dot1qFutureVlanPortSubnetMapExtEntry 1 }

dot1qFutureVlanPortSubnetMapExtMask OBJECT-TYPE
   SYNTAX      IpAddress
   MAX-ACCESS  not-accessible 
   STATUS      current 
   DESCRIPTION 
      "This object specifies the Subnet Mask for which the VLAN mapping is
       present in the entry." 
   ::= { dot1qFutureVlanPortSubnetMapExtEntry 2 }

dot1qFutureVlanPortSubnetMapExtVid OBJECT-TYPE
   SYNTAX      VlanId 
   MAX-ACCESS  read-write 
   STATUS      current 
   DESCRIPTION 
      "This object specifies the VLAN to which the Source IP-Subnet address of
       this entry is mapped to."    
   ::= { dot1qFutureVlanPortSubnetMapExtEntry 3 }

dot1qFutureVlanPortSubnetMapExtARPOption OBJECT-TYPE
   SYNTAX      INTEGER { allow(1), suppress(2) }
   MAX-ACCESS  read-write
   STATUS      current
   DESCRIPTION 
       "This object specifies the configurable option for discarding/allowing
       ARP untagged frames on the VLAN. The value allow (1) indicates that ARP
       frames with source IP-subnet address matching the
       dot1qFutureVlanPortSubnetMapExtEntry will be classified to VLAN based on 
        dot1qFutureVlanPortSubnetMapExtEntry. The value suppress (2) indicates 
        that ARP frames with source IP-Subnet address matching the 
        dot1qFutureVlanPortSubnetMapExtEntry will not be classified to VLAN
        based on dot1qFutureVlanPortSubnetMapExtEntry. The VLAN classification 
        will be based on next subsequent classification mechanism."
    DEFVAL { allow }
    ::= { dot1qFutureVlanPortSubnetMapExtEntry 4 }

dot1qFutureVlanPortSubnetMapExtRowStatus OBJECT-TYPE
   SYNTAX      RowStatus 
   MAX-ACCESS  read-write 
   STATUS      current 
   DESCRIPTION 
      "The row status of the entry."  
   ::= { dot1qFutureVlanPortSubnetMapExtEntry 5 }

--table ends   

dot1qFutureVlanGlobalsFdbFlush OBJECT-TYPE
   SYNTAX      TruthValue
   MAX-ACCESS  read-write
   STATUS      current
   DESCRIPTION
     "If this object is set as 'true', then all the dynamically learnt
      MAC addresses will be removed. After flush, this object
      is set to 'false'."
   ::= { dot1qFutureVlan 31 }

dot1qFutureVlanUserDefinedTPID OBJECT-TYPE
    SYNTAX      Integer32 (0..65535)
    MAX-ACCESS  read-write
    STATUS      current
    DESCRIPTION
        "This object sets the value for the user defined TPID configurable
         for an ingress port or for a VLAN egress Ethertype.

        A value ZERO deletes the configured entry."

    DEFVAL { 0 }
    ::= { dot1qFutureVlan 32 }

-- ---------------------------------------------------------------------------- 
-- Service level loopback Table 
-- ---------------------------------------------------------------------------- 
dot1qFutureVlanLoopbackTable OBJECT-TYPE
   SYNTAX      SEQUENCE OF Dot1qFutureVlanLoopbackEntry
   MAX-ACCESS  not-accessible
   STATUS      current
   DESCRIPTION
             "This table contains the Loopback Status for all VLANs."
   ::= { dot1qFutureVlan 33 }

dot1qFutureVlanLoopbackEntry OBJECT-TYPE
   SYNTAX      Dot1qFutureVlanLoopbackEntry
   MAX-ACCESS  not-accessible
   STATUS      current
   DESCRIPTION
              "This entry contains the VLAN loopback Status."
   INDEX { dot1qFutureVlanIndex }
   ::= { dot1qFutureVlanLoopbackTable 1 }
Dot1qFutureVlanLoopbackEntry ::=
   SEQUENCE {
             dot1qFutureVlanLoopbackStatus EnabledStatus
            }

dot1qFutureVlanLoopbackStatus OBJECT-TYPE
   SYNTAX      EnabledStatus
   MAX-ACCESS  read-write
   STATUS      current
   DESCRIPTION
      "This object specifies the loopback status for the VLAN.

       When Loopback is enabled, all data packets received
       in the VLAN will be sent back in the same port from which the packets
       are received."

   DEFVAL   { disabled }
   ::= { dot1qFutureVlanLoopbackEntry 1 }

-- ---------------------------------------------------------------------------- 
-- Voice VLAN objects            
-- ---------------------------------------------------------------------------- 

dot1qFutureVlanVoiceVlan OBJECT-TYPE
   SYNTAX      VlanIdOrNone 
   MAX-ACCESS  read-write 
   STATUS      current 
   DESCRIPTION 
      "The default voice VLAN. A non-zero value indicates
      that automated VoIP device discovery and/or voice 
      VLAN-related configuration can be performed using
      this value (if applicable). A zero value indicates
      that a default voice VLAN has not been defined." 

   ::= { dot1qFutureVlan 34 }
 
dot1qFutureVlanVoicePriority OBJECT-TYPE
   SYNTAX      Integer32 (0..7) 
   MAX-ACCESS  read-write 
   STATUS      current 
   DESCRIPTION 
      "The default voice VLAN 802.1p user priority."

   DEFVAL { 6 }
   ::= { dot1qFutureVlan 35 }
 
dot1qFutureVlanVoiceDscp OBJECT-TYPE
   SYNTAX      Integer32 (0..63) 
   MAX-ACCESS  read-write 
   STATUS      current 
   DESCRIPTION 
      "The default voice VLAN DSCP."

   DEFVAL { 46 }
   ::= { dot1qFutureVlan 36 }
 
dot1qFutureVlanVoiceVlanTagging OBJECT-TYPE
   SYNTAX      INTEGER {
                   tagged(1),
                   untagged(2)
               }
   MAX-ACCESS  read-write 
   STATUS      current 
   DESCRIPTION 
      "The default voice VLAN tagging status. Voice
      traffic is considered tagged by default. A value
      of 'untagged(2)' indicates that voice traffic will 
      be untagged (port PVID set to the voice VLAN)."

   DEFVAL { tagged }
   ::= { dot1qFutureVlan 37 }
 
dot1qFutureVlanVoiceDataVlan OBJECT-TYPE
   SYNTAX      VlanIdOrNone 
   MAX-ACCESS  read-write 
   STATUS      current 
   DESCRIPTION 
      "The data VLAN that is associated with the default 
      voice VLAN."

   DEFVAL { 0 }
   ::= { dot1qFutureVlan 38 }
 
dot1qFutureVlanVoiceDataVlanTagging OBJECT-TYPE
   SYNTAX      INTEGER {
                   tagged(1),
                   untagged(2)
               }
   MAX-ACCESS  read-write 
   STATUS      current 
   DESCRIPTION 
      "The tagging status for the data VLAN that is
      associated with the default voice VLAN. Data
      traffic is considered untagged by default. A value
      of 'tagged(1)' indicates that data traffic will 
      be tagged (port PVID is not set to the data VLAN).

      If voice traffic is untagged, the data VLAN
      tagging status is ignored."

   DEFVAL { untagged }
   ::= { dot1qFutureVlan 39 }
 
dot1qFutureVlanVoiceUplink OBJECT-TYPE
   SYNTAX      SnmpAdminString (SIZE (0..7))
   MAX-ACCESS  read-write
   STATUS      current
   DESCRIPTION
       "Specifies an interface to be considered for
       VLAN membership updates when VLAN membership
       updates are initiated by the VLAN voice support.

       An uplink interface is specified using interface
       type and value notation in a string format
       (e.g., 'gi0/9', 'po1234'). A maximum of 1 voice
       uplink can be specified.

       A zero-length string indicates that no uplink
       data is specified."

   ::= { dot1qFutureVlan 40 }

END
