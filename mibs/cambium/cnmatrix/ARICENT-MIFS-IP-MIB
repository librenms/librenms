-- Copyright (C) 2009-2012 Aricent Group . All Rights Reserved

ARICENT-MIFS-IP-MIB DEFINITIONS ::= BEGIN 
 
 IMPORTS 
    OBJECT-TYPE, MODULE-IDENTITY, IpAddress, 
    Counter32, Integer32,
    enterprises            FROM SNMPv2-SMI
    DisplayString,
    TruthValue, RowStatus  FROM SNMPv2-TC
    fsMIStdIpContextId     FROM ARICENT-MISTD-IPVX-MIB; 

fsMIFsIp MODULE-IDENTITY
     LAST-UPDATED "201209050000Z"
     ORGANIZATION "ARICENT COMMUNICATIONS SOFTWARE"
     CONTACT-INFO "support@aricent.com"
     DESCRIPTION " This mib module is for IP module with virtual routing
     and forwarding support."
     REVISION "201209050000Z"
     DESCRIPTION " This mib module is for IP module with virtual routing
     and forwarding support."
::= { enterprises aricent-communication-holding-ltd(29601) iss(2) 38 }

--
--SCALAR_TABLE_BEGIN 
--
   fsMIFsIpGlobalDebug OBJECT-TYPE
      SYNTAX  Integer32
      MAX-ACCESS read-write
      STATUS  current
      DESCRIPTION
          "Enables the tracing in the selected submodule in IP. A 32 bit integer
           is used to store the Tracing level in the specified module.
           Different Tracing Levels -
           BIT 0 - Initialisation and Shutdown Trace.
           BIT 5 - OS Resource trace.
           BIT 7 - Buffer Trace.
     
           Different submodule Tracing -
           BIT 16 - Tracing in IP module.
           BIT 17 - Tracing in ICMP submodule.
           BIT 19 - Tracing in RIP submodule.
           BIT 20 - Tracing in ARP submodule.
           BIT 21 - Tracing in BOOTP submodule.
           BIT 22 - Tracing in UDP submodule.
     
           The remaining bits are used.The combination of levels and submodules 
           are allowed i.e. Tracing can be allowed at all failure and data path 
           level in All submodules by setting the BIT appropriately.
           For Example, setting the debug valut to 
           0b00000000000000010000000001000000 will enable all failure trace 
           prints in IP module."
   ::= { fsMIFsIp 1 }

--
-- FsMiIP Tables
--

fsMIFsIpGlobalTable OBJECT-TYPE
    SYNTAX SEQUENCE OF FsMIFsIpGlobalEntry
    MAX-ACCESS not-accessible
    STATUS     current
    DESCRIPTION
        "Table to store the virtual router specific IP configurations"
    ::= { fsMIFsIp 2 }

fsMIFsIpGlobalEntry OBJECT-TYPE
    SYNTAX     FsMIFsIpGlobalEntry
    MAX-ACCESS not-accessible
    STATUS     current
    DESCRIPTION
        "Each entry has IP configuration information for the Virtual router"
    INDEX { fsMIStdIpContextId }
    ::= { fsMIFsIpGlobalTable 1 }

FsMIFsIpGlobalEntry ::= SEQUENCE {
        fsMIFsIpInLengthErrors        Counter32,
        fsMIFsIpInCksumErrors         Counter32,
        fsMIFsIpInVersionErrors       Counter32,
        fsMIFsIpInTTLErrors           Counter32,
        fsMIFsIpInOptionErrors        Counter32,
        fsMIFsIpInBroadCasts          Counter32,
        fsMIFsIpOutGenErrors          Counter32,
        fsMIFsIpOptProcEnable         INTEGER,
        fsMIFsIpNumMultipath          Integer32,
        fsMIFsIpLoadShareEnable       INTEGER,
        fsMIFsIpEnablePMTUD           INTEGER,
        fsMIFsIpPmtuEntryAge          Integer32,
        fsMIFsIpContextDebug          Integer32
    }

fsMIFsIpInLengthErrors  OBJECT-TYPE
    SYNTAX     Counter32
    MAX-ACCESS read-only
    STATUS     current
    DESCRIPTION
           "Total number of packets received by IP with length less
            than IP header length in the specific context."
    ::= { fsMIFsIpGlobalEntry 1 }

fsMIFsIpInCksumErrors  OBJECT-TYPE
    SYNTAX     Counter32
    MAX-ACCESS read-only
    STATUS     current
    DESCRIPTION
           "Total Number of received packets those failed to pass
            checksum verification in a specific context."
    ::= { fsMIFsIpGlobalEntry 2 }

fsMIFsIpInVersionErrors  OBJECT-TYPE
    SYNTAX     Counter32
    MAX-ACCESS read-only
    STATUS     current
    DESCRIPTION
           "Total number of received packets with different IP
            version from this entity in a specific context."
    ::= { fsMIFsIpGlobalEntry 3 }

fsMIFsIpInTTLErrors  OBJECT-TYPE
    SYNTAX     Counter32
    MAX-ACCESS read-only
    STATUS     current
    DESCRIPTION
           "Number of IP packets received at this entity with
            'Time to Live' field equal to ZERO"
    ::= { fsMIFsIpGlobalEntry 4 }

fsMIFsIpInOptionErrors  OBJECT-TYPE
    SYNTAX     Counter32
    MAX-ACCESS read-only
    STATUS     current
    DESCRIPTION
           "Number of IP packets received with improper options."
    ::= { fsMIFsIpGlobalEntry 5 }

fsMIFsIpInBroadCasts  OBJECT-TYPE
    SYNTAX     Counter32
    MAX-ACCESS read-only
    STATUS     current
    DESCRIPTION
           "Total number of IP broadcast packets received at this
            entity."
    ::= { fsMIFsIpGlobalEntry 6 }

fsMIFsIpOutGenErrors  OBJECT-TYPE
    SYNTAX     Counter32
    MAX-ACCESS read-only
    STATUS     current
    DESCRIPTION
           "Number of outgoing IP packets rejected due to general
            problems like interface down, forwarding disabled etc."
    ::= { fsMIFsIpGlobalEntry 7 } 

fsMIFsIpOptProcEnable OBJECT-TYPE
    SYNTAX     INTEGER   {
                    enabled (1),
                    disabled (2)
               }
    MAX-ACCESS read-write
    STATUS     current
    DESCRIPTION
           "Indication as to if Option processing is active."
    DEFVAL     { enabled }
    ::= { fsMIFsIpGlobalEntry 8 }

fsMIFsIpNumMultipath OBJECT-TYPE
    SYNTAX     Integer32 (1..16)
    MAX-ACCESS read-write
    STATUS     current
    DESCRIPTION
           "The number of multi-paths in the routing table."
    DEFVAL     { 2 }
    ::= { fsMIFsIpGlobalEntry 9 }

fsMIFsIpLoadShareEnable OBJECT-TYPE
    SYNTAX     INTEGER {
                    enabled (1),
                    disabled (2)
               }   
    MAX-ACCESS read-write
    STATUS      current
    DESCRIPTION
           "Enabling this will distribute the load among
            available equal cost multi-paths."
    DEFVAL  { disabled }
    ::= { fsMIFsIpGlobalEntry 10 }

fsMIFsIpEnablePMTUD OBJECT-TYPE
    SYNTAX     INTEGER {
                    enabled     (1),
                    disabled    (2)
               }
    MAX-ACCESS read-write
    STATUS     current
    DESCRIPTION
           "This Object Enables or Disables PMTU-D in the context. 
            This MIB Object overrides the route-based and
            application-level requests for PMTU-D. When this object
            is set to disabled (2), PMTU-D is not done even if the
            application requests to do so."
    DEFVAL { disabled }
    ::= { fsMIFsIpGlobalEntry 11 }

fsMIFsIpPmtuEntryAge OBJECT-TYPE
    SYNTAX     Integer32 (5..255)
    MAX-ACCESS read-write
    STATUS     current
    DESCRIPTION
           "This object specifies the timeout in minutes, after which
            the estimate of a PMTU is considered stale. After the
            configured minutes the estimate of the PMTU is increased.
            When Set to inifinity (255), detection in increase of
            PMTU is not done."
    DEFVAL { 10 }
    ::= { fsMIFsIpGlobalEntry 12 }

fsMIFsIpContextDebug OBJECT-TYPE
   SYNTAX  Integer32
   MAX-ACCESS read-write
   STATUS  current
   DESCRIPTION
          "Enables the tracing in the selected submodule in IP. A 32 bit integer
           is used to store the Tracing level in the specified module.
           Different Tracing Levels -
           BIT 0 - Initialisation and Shutdown Trace.
           BIT 1 - Management trace.
           BIT 2 - Data path trace.
           BIT 3 - Control Plane trace.
           BIT 4 - Packet Dump.
           BIT 5 - OS Resource trace.
           BIT 6 - All Failure trace (All failures including Packet Validation)
           BIT 7 - Buffer Trace.
     
           Different submodule Tracing -
           BIT 16 - Tracing in IP module.
           BIT 17 - Tracing in ICMP submodule.
           BIT 19 - Tracing in RIP submodule.
           BIT 20 - Tracing in ARP submodule.
           BIT 21 - Tracing in BOOTP submodule.
           BIT 22 - Tracing in UDP submodule.
     
           The remaining bits are used.The combination of levels and submodules 
           are allowed i.e. Tracing can be allowed at all failure and data path 
           level in All submodules by setting the BIT appropriately.
           For Example, setting the debug valut to 
           0b00000000000000010000000001000000 will enable all failure trace 
           prints in IP module."
   ::= { fsMIFsIpGlobalEntry 13 }

--
-- Trace route config table 
--

fsMIFsIpTraceConfigTable  OBJECT-TYPE
  SYNTAX  SEQUENCE OF FsMIFsIpTraceConfigEntry
  MAX-ACCESS  not-accessible
  STATUS  current
  DESCRIPTION
  "This entity's IP Traceroute Configuration Table."
  ::= { fsMIFsIp 3 }

fsMIFsIpTraceConfigEntry  OBJECT-TYPE
   SYNTAX  FsMIFsIpTraceConfigEntry
   MAX-ACCESS  not-accessible
   STATUS  current
   DESCRIPTION
   "Contains the configuration information about a
   particular IP
   traceroute Operation."
   INDEX  { fsMIFsIpTraceConfigDest }
   ::= { fsMIFsIpTraceConfigTable 1 }

FsMIFsIpTraceConfigEntry ::=
               SEQUENCE {
   fsMIFsIpTraceConfigDest  IpAddress,
   fsMIFsIpTraceConfigAdminStatus  INTEGER,
   fsMIFsIpTraceConfigMaxTTL  Integer32,
   fsMIFsIpTraceConfigMinTTL  Integer32,
   fsMIFsIpTraceConfigOperStatus INTEGER,
   fsMIFsIpTraceConfigTimeout  Integer32,
   fsMIFsIpTraceConfigMtu  Integer32
   }

fsMIFsIpTraceConfigDest  OBJECT-TYPE
   SYNTAX  IpAddress
   MAX-ACCESS  not-accessible
   STATUS  current
   DESCRIPTION
   "The destination IP address to which a route has to
   be traced."
   ::= { fsMIFsIpTraceConfigEntry 1 }
  
fsMIFsIpTraceConfigAdminStatus  OBJECT-TYPE
   SYNTAX  INTEGER {
   on  (1),
   off  (2)
   }
   MAX-ACCESS  read-write
   STATUS  current
   DESCRIPTION
   "The desired status for the traceroute operation.
    This variable has to be made on (from off) for
    starting the operation. If this variable is set to
    on when fsMIFsIpTraceConfigOperStatus is inprogress,
    then GEN_ERROR is returned. This variable is set
    to off when the fsMIFsIpTraceConfigOperStatus becomes
    not inprogress."
   DEFVAL { on }
   ::= { fsMIFsIpTraceConfigEntry 2 }


fsMIFsIpTraceConfigMaxTTL  OBJECT-TYPE
   SYNTAX  Integer32 (1..99)
   MAX-ACCESS  read-write
   STATUS  current
   DESCRIPTION
   "The maximum value of the TTL field to be filled up
   in the IP packets used for the traceroute."
   DEFVAL  { 15 }
   ::= { fsMIFsIpTraceConfigEntry 3 }
 

fsMIFsIpTraceConfigMinTTL  OBJECT-TYPE
   SYNTAX  Integer32 (1..99)
   MAX-ACCESS  read-write
   STATUS  current
   DESCRIPTION
   "The minimum value of the TTL field to be filled up
   in the IP packets used for the traceroute."
   DEFVAL  { 1 }
   ::= { fsMIFsIpTraceConfigEntry 4 }


fsMIFsIpTraceConfigOperStatus OBJECT-TYPE
   SYNTAX  INTEGER {
   inprogress  (1),
   notinprogress  (2)
   }
   MAX-ACCESS  read-only
   STATUS  current
   DESCRIPTION "The current status for the traceroute operation."
   ::= { fsMIFsIpTraceConfigEntry 5 }

fsMIFsIpTraceConfigTimeout OBJECT-TYPE
   SYNTAX  Integer32 (0..2147483647)
   MAX-ACCESS  read-write
   STATUS  current
   DESCRIPTION
   "Interval between (in seconds) consecutive trace
   requests."
   ::= { fsMIFsIpTraceConfigEntry 6 }
 
fsMIFsIpTraceConfigMtu OBJECT-TYPE
   SYNTAX  Integer32 (0..2147483647)
   MAX-ACCESS  read-write
   STATUS  current
   DESCRIPTION
   "Number of octets of data to be sent in trace
   packets."
   ::= { fsMIFsIpTraceConfigEntry 7 }
  
--
--Trace Table
--

fsMIFsIpTraceTable  OBJECT-TYPE
   SYNTAX  SEQUENCE OF FsIpTraceEntry
   MAX-ACCESS  not-accessible
   STATUS  current
   DESCRIPTION
   "This entity's IP Traceroute Table containing the
   results of the traceroute operation(s)."
   ::= { fsMIFsIp 4 }
 
fsMIFsIpTraceEntry  OBJECT-TYPE
   SYNTAX  FsIpTraceEntry
   MAX-ACCESS  not-accessible
   STATUS  current
   DESCRIPTION
   "Contains the information about a particular
   intermediate node on the way to the destination."
   INDEX  { fsMIFsIpTraceDest,
     fsMIFsIpTraceHopCount }
  ::= { fsMIFsIpTraceTable 1 }

FsIpTraceEntry  ::=  SEQUENCE {
   fsMIFsIpTraceDest  IpAddress,
   fsMIFsIpTraceHopCount Integer32,
   fsMIFsIpTraceIntermHop  IpAddress,
   fsMIFsIpTraceReachTime1  Integer32,
   fsMIFsIpTraceReachTime2  Integer32,
   fsMIFsIpTraceReachTime3  Integer32
   }
 
fsMIFsIpTraceDest  OBJECT-TYPE
   SYNTAX  IpAddress
   MAX-ACCESS  not-accessible
   STATUS  current
   DESCRIPTION
   "The destination IP address to which a route was
   traced."
   ::= { fsMIFsIpTraceEntry 1 }
  
fsMIFsIpTraceHopCount OBJECT-TYPE
   SYNTAX  Integer32 (0..2147483647)
   MAX-ACCESS  not-accessible
   STATUS  current
   DESCRIPTION
   "The count of the number of hops required to reach
   this intermediate node."
   ::= { fsMIFsIpTraceEntry 2 }
 
fsMIFsIpTraceIntermHop  OBJECT-TYPE
   SYNTAX  IpAddress
   MAX-ACCESS  read-only
   STATUS  current
   DESCRIPTION
   "The IP address of the intermediate node/destination."
   ::= { fsMIFsIpTraceEntry 3 }
  
fsMIFsIpTraceReachTime1  OBJECT-TYPE
   SYNTAX  Integer32 (0..2147483647)
   MAX-ACCESS  read-only
   STATUS  current
   DESCRIPTION
   "The time in seconds required to reach this
   intermediate node.The value of '-1' denotes that the
   response was not received from this node"
   ::= { fsMIFsIpTraceEntry 4 }
 
fsMIFsIpTraceReachTime2  OBJECT-TYPE
  SYNTAX  Integer32 (0..2147483647)
  MAX-ACCESS  read-only
  STATUS  current
  DESCRIPTION
  "The time in seconds required to reach this
  intermediate node for the second time. The value of
  '-1' denotes that the response was not received
  from this node"
  ::= { fsMIFsIpTraceEntry 5 }

fsMIFsIpTraceReachTime3  OBJECT-TYPE
  SYNTAX  Integer32 (0..2147483647)
  MAX-ACCESS  read-only
  STATUS  current
  DESCRIPTION
  "The time in seconds required to reach this
  intermediate node for the third time. The value of
  '-1' denotes that the response was not received from
  this node"
  ::= { fsMIFsIpTraceEntry 6 }

--
-- IP address table
--

fsMIFsIpAddressTable   OBJECT-TYPE
    SYNTAX  SEQUENCE OF FsMIFsIpAddressEntry
    MAX-ACCESS   not-accessible
    STATUS   current
    DESCRIPTION
     "The table of IP addresses on every Interface."
    ::= { fsMIFsIp 5 }

fsMIFsIpAddressEntry   OBJECT-TYPE
    SYNTAX   FsMIFsIpAddressEntry
    MAX-ACCESS   not-accessible
    STATUS   current
    DESCRIPTION
     "The individual entry in the above table."
    INDEX   { fsMIStdIpContextId, fsMIFsIpAddrTabAddress }
    ::= { fsMIFsIpAddressTable 1 }

FsMIFsIpAddressEntry  ::=
    SEQUENCE {
    fsMIFsIpAddrTabAddress
 IpAddress,
    fsMIFsIpAddrTabIfaceId
 Integer32,
    fsMIFsIpAddrTabAdvertise
 TruthValue,
    fsMIFsIpAddrTabPreflevel
 Integer32,
    fsMIFsIpAddrTabStatus
 RowStatus
    }

fsMIFsIpAddrTabAddress OBJECT-TYPE
    SYNTAX IpAddress
    MAX-ACCESS not-accessible
    STATUS current
    DESCRIPTION
      "One of the router's IP addresses."
    ::= { fsMIFsIpAddressEntry 1 }

fsMIFsIpAddrTabIfaceId OBJECT-TYPE
    SYNTAX Integer32 (0..2147483647)
    MAX-ACCESS read-only
    STATUS current
    DESCRIPTION
      "The interface number to which the IP address
      belongs to."
    ::= { fsMIFsIpAddressEntry 2 }


fsMIFsIpAddrTabAdvertise OBJECT-TYPE
    SYNTAX TruthValue
    MAX-ACCESS read-write
    STATUS current
    DESCRIPTION
      "A flag indicating whether or not the address is
      to be advertised."
    ::= { fsMIFsIpAddressEntry 3 }

fsMIFsIpAddrTabPreflevel OBJECT-TYPE
    SYNTAX Integer32 (0..2147483647)
    MAX-ACCESS read-write
    STATUS current
    DESCRIPTION
      "The preferability of the address as a default
      router address, relative to other router addresses on
      the same subnet. A 32-bit, signed, twos-complement
      integer, with higher values meaning more preferable."
    ::= { fsMIFsIpAddressEntry 4 }

fsMIFsIpAddrTabStatus OBJECT-TYPE
    SYNTAX RowStatus
    MAX-ACCESS read-only
    STATUS current
    DESCRIPTION
      "The status of this row, by which new entries may be
      created, or old entries deleted from this table."
    ::= { fsMIFsIpAddressEntry 5 }
--
--List of Default Routers.
--

fsMIFsIpRtrLstTable OBJECT-TYPE
    SYNTAX  SEQUENCE OF FsMIFsIpRtrLstEntry
    MAX-ACCESS  not-accessible
    STATUS  current
    DESCRIPTION
      "List of default router addresses. Used when system
      functions as a host.Maintained as per RFC 1122."
    ::= { fsMIFsIp 6 }

fsMIFsIpRtrLstEntry  OBJECT-TYPE
    SYNTAX   FsMIFsIpRtrLstEntry
    MAX-ACCESS   not-accessible
    STATUS   current
    DESCRIPTION
     "The individual entry in the above table."
    INDEX   { fsMIFsIpRtrLstAddress }
    ::= { fsMIFsIpRtrLstTable 1 }

FsMIFsIpRtrLstEntry ::=
    SEQUENCE {
     fsMIFsIpRtrLstIface
    Integer32,
     fsMIFsIpRtrLstAddress
    IpAddress,
     fsMIFsIpRtrLstPreflevel
    Integer32,
     fsMIFsIpRtrLstStatic
    TruthValue,
     fsMIFsIpRtrLstStatus
    RowStatus
     }

fsMIFsIpRtrLstIface OBJECT-TYPE
    SYNTAX Integer32 (0..2147483647)
    MAX-ACCESS read-write
    STATUS current
    DESCRIPTION
      "The interface via which the router could be
      reached."
    ::= { fsMIFsIpRtrLstEntry 1 }

fsMIFsIpRtrLstAddress OBJECT-TYPE
    SYNTAX IpAddress
    MAX-ACCESS not-accessible
    STATUS current
    DESCRIPTION
      "An IP address of a default router."
    ::= { fsMIFsIpRtrLstEntry 2 }

fsMIFsIpRtrLstPreflevel OBJECT-TYPE
    SYNTAX Integer32 (0..2147483647)
    MAX-ACCESS read-write
    STATUS current
    DESCRIPTION
      "The preferability of the RouterAddress as a default
      router address, relative to other router addresses
      on the same subnet."
    ::= { fsMIFsIpRtrLstEntry 3 }

fsMIFsIpRtrLstStatic OBJECT-TYPE
    SYNTAX TruthValue
    MAX-ACCESS read-only
    STATUS current
    DESCRIPTION
      "This entry states how the default router address
      was learned."
    ::= { fsMIFsIpRtrLstEntry 4 }

fsMIFsIpRtrLstStatus OBJECT-TYPE
    SYNTAX RowStatus
    MAX-ACCESS read-create
    STATUS current
    DESCRIPTION
      "The status of this row, by which new entries may be
      created, or old entries deleted from this table."
    ::= { fsMIFsIpRtrLstEntry 5 }

--
--PMTU Table
--

fsMIFsIpPathMtuTable OBJECT-TYPE
    SYNTAX  SEQUENCE OF FsMIFsIpPathMtuEntry  
    MAX-ACCESS not-accessible
    STATUS     current
    DESCRIPTION
           "This Table shows the PMTU-D information for every path. 
            Administrator can enable or disable PMTU-D per 
            destination basis. This overrides the request from the 
            application."
    ::= { fsMIFsIp 7 }

fsMIFsIpPathMtuEntry OBJECT-TYPE
    SYNTAX  FsMIFsIpPathMtuEntry
    MAX-ACCESS not-accessible
    STATUS current
    DESCRIPTION
           "This object forms the conceptual row of the PMTU Table."
    INDEX { fsMIStdIpContextId, fsMIFsIpPmtuDestination, fsMIFsIpPmtuTos }
    ::= { fsMIFsIpPathMtuTable 1 }

FsMIFsIpPathMtuEntry ::= SEQUENCE {
        fsMIFsIpPmtuDestination   IpAddress,
        fsMIFsIpPmtuTos           Integer32,
        fsMIFsIpPathMtu           Integer32,
        fsMIFsIpPmtuDisc          INTEGER,
        fsMIFsIpPmtuEntryStatus   RowStatus
        }

fsMIFsIpPmtuDestination OBJECT-TYPE
    SYNTAX     IpAddress
    MAX-ACCESS not-accessible
    STATUS     current
    DESCRIPTION
           "Specifies the Destination IP address of the Path for 
            which the discovery is made."
    ::= { fsMIFsIpPathMtuEntry 1 }

fsMIFsIpPmtuTos OBJECT-TYPE
    SYNTAX     Integer32 (0..2147483647)
    MAX-ACCESS not-accessible
    STATUS     current
    DESCRIPTION
           "Specifies the type of service of the path."
    ::= { fsMIFsIpPathMtuEntry 2 }

fsMIFsIpPathMtu OBJECT-TYPE
    SYNTAX     Integer32 (68 .. 65535)
    MAX-ACCESS read-write
    STATUS     current
    DESCRIPTION
           "Value of the path mtu discovered. If the admin changes 
            this value, PMTU discovery on that path is stopped."
    ::= { fsMIFsIpPathMtuEntry 3 }

fsMIFsIpPmtuDisc OBJECT-TYPE
    SYNTAX     INTEGER {
                    enabled   (1),
                    disabled  (2)
               }
    MAX-ACCESS read-write
    STATUS     current
    DESCRIPTION
           "Enables or Disables PMTU discovery for the given path.
            This overrides the application request wrt to PMTU-D."
    ::= { fsMIFsIpPathMtuEntry 4 }

fsMIFsIpPmtuEntryStatus OBJECT-TYPE
    SYNTAX     RowStatus
    MAX-ACCESS read-write
    STATUS     current
    DESCRIPTION
           "Entry Status of the row in the PMTU table."
    ::= { fsMIFsIpPathMtuEntry 5 }

-- fsMIFsIpCommonRoutingTable

fsMIFsIpCommonRoutingTable OBJECT-TYPE
    SYNTAX  SEQUENCE OF FsMIFsIpCommonRoutingEntry
    MAX-ACCESS not-accessible
    STATUS   current
    DESCRIPTION
    "Common routing Table which contains all the routing entries
              for a particular destination."
         ::= { fsMIFsIp 8 }

fsMIFsIpCommonRoutingEntry OBJECT-TYPE
    SYNTAX   FsMIFsIpCommonRoutingEntry
    MAX-ACCESS not-accessible
    STATUS   current
    DESCRIPTION
 "A particular route to     a particular destina-
 tion, under a particular policy."
    INDEX {
            fsMIStdIpContextId,
            fsMIFsIpRouteDest,
            fsMIFsIpRouteMask,
            fsMIFsIpRouteTos,
            fsMIFsIpRouteNextHop,
            fsMIFsIpRouteProto
   }
    ::= { fsMIFsIpCommonRoutingTable 1 }

FsMIFsIpCommonRoutingEntry ::=
    SEQUENCE {
  fsMIFsIpRouteDest
      IpAddress,
  fsMIFsIpRouteMask
      IpAddress,
  fsMIFsIpRouteTos
       Integer32,
  fsMIFsIpRouteNextHop
      IpAddress,
  fsMIFsIpRouteProto
      INTEGER,
  fsMIFsIpRouteProtoInstanceId
      Integer32,
  fsMIFsIpRouteIfIndex
      Integer32,
  fsMIFsIpRouteType
      INTEGER,
  fsMIFsIpRouteAge
      Integer32,
  fsMIFsIpRouteNextHopAS
      Integer32,
  fsMIFsIpRouteMetric1
      Integer32,
  fsMIFsIpRoutePreference
      Integer32,
  fsMIFsIpRouteStatus
                  RowStatus
 }

fsMIFsIpRouteDest OBJECT-TYPE
    SYNTAX   IpAddress
    MAX-ACCESS not-accessible
    STATUS   current
    DESCRIPTION
 "The destination IP address of this route.This object may not 
              take a Multicast (Class  D)address value.Any assignment 
              (implicit or  otherwise)  of  an instance  of  this  object ,
              to a value x must be rejected if the bitwise logical-AND of
          x  with the  value of the corresponding instance of the 
              fsMIFsIpRouteMask object is not equal to x." 
          ::= { fsMIFsIpCommonRoutingEntry 1 }

fsMIFsIpRouteMask OBJECT-TYPE
    SYNTAX   IpAddress
    MAX-ACCESS not-accessible
    STATUS   current
    DESCRIPTION
 "Indicate the mask to be logical-ANDed with the
 destination  address  before  being compared to
 the value  in the  fsMIFsIpRouteDest  field.   For
 those systems  that  do  not support arbitrary
 subnet masks, an agent constructs the value  of
 the  fsMIFsIpRouteMask  by  reference to the IP Ad-
 dress Class.

 Any assignment (implicit or  otherwise)  of  an
 instance  of  this  object to a value x must be
 rejected if the bitwise logical-AND of x  with
 the  value of the corresponding instance of the
 fsMIFsIpRouteDest object is not equal to fsIpRoute-
 Dest."
      ::= { fsMIFsIpCommonRoutingEntry 2 }

-- The following convention is included for specification
-- of TOS Field contents.  At this time, the Host Requirements
-- and the Router Requirements documents disagree on the width
-- of the TOS field.  This mapping describes the Router
-- Requirements mapping, and leaves room to widen the TOS field
-- without impact to fielded systems.

fsMIFsIpRouteTos OBJECT-TYPE
    SYNTAX   Integer32 (0..2147483647) 
    MAX-ACCESS not-accessible
    STATUS   current
    DESCRIPTION
 "The policy specifier is the IP TOS Field.  The encoding
 of IP TOS is as specified  by    the  following convention.
 Zero indicates the default path if no more  specific
 policy applies.

 +-----+-----+-----+-----+-----+-----+-----+-----+
 |           |      |  |
 |   PRECEDENCE       |    TYPE OF SERVICE    |  0  |
 |           |      |  |
 +-----+-----+-----+-----+-----+-----+-----+-----+

  IP TOS        IP TOS
     Field     Policy       Field     Policy
     Contents     Code       Contents    Code
     0 0 0 0  ==>   0       0 0 0 1  ==>      2
     0 0 1 0  ==>   4       0 0 1 1  ==>      6
     0 1 0 0  ==>   8       0 1 0 1  ==>     10
     0 1 1 0  ==>  12       0 1 1 1  ==>     14
     1 0 0 0  ==>  16       1 0 0 1  ==>     18
     1 0 1 0  ==>  20       1 0 1 1  ==>     22
     1 1 0 0  ==>  24       1 1 0 1  ==>     26
     1 1 1 0  ==>  28       1 1 1 1  ==>     30"
                 ::= { fsMIFsIpCommonRoutingEntry 3 }

  fsMIFsIpRouteNextHop OBJECT-TYPE
      SYNTAX   IpAddress
      MAX-ACCESS not-accessible
      STATUS   current
      DESCRIPTION
 "On remote routes, the address of the next sys-
 tem en route; Otherwise, 0.0.0.0."
      ::= { fsMIFsIpCommonRoutingEntry 4 }

  fsMIFsIpRouteProto OBJECT-TYPE
      SYNTAX   INTEGER {
  other        (1),  -- not specified
  local        (2),  -- local interface
  netmgmt   (3),  -- static route
  icmp        (4),  -- result of ICMP Redirect

  -- the following are all dynamic
  -- routing protocols
  egp         (5),  -- Exterior Gateway Protocol
  ggp         (6),  -- Gateway-Gateway Protocol
  hello         (7),  -- FuzzBall HelloSpeak
  rip         (8),  -- Berkeley RIP or RIP-II
  isIs         (9),  -- Dual IS-IS
  esIs         (10), -- ISO 9542
  ciscoIgrp  (11), -- Cisco IGRP
  bbnSpfIgp  (12), -- BBN SPF IGP
  ospf         (13), -- Open Shortest Path First
  bgp         (14), -- Border Gateway Protocol
  idpr         (15), -- InterDomain Policy Routing
          ciscoEigrp (16)  -- Cisco EIGRP
           }
      MAX-ACCESS not-accessible
      STATUS   current
      DESCRIPTION
 "The routing mechanism via which this route was
 learned.  Inclusion of values for gateway rout-
 ing protocols is not  intended     to  imply  that
 hosts should support those protocols."
      ::= { fsMIFsIpCommonRoutingEntry 5 }

fsMIFsIpRouteProtoInstanceId OBJECT-TYPE
            SYNTAX   Integer32
    MAX-ACCESS read-only
    STATUS   current
    DESCRIPTION
  "Instance Id of the dynamic routing protocol. This supports 
                 multiple instantiation of dynamic protocols."
      ::= { fsMIFsIpCommonRoutingEntry 6 }


  fsMIFsIpRouteIfIndex OBJECT-TYPE
      SYNTAX   Integer32 
      MAX-ACCESS read-write
      STATUS   current
      DESCRIPTION
 "The ifIndex value which identifies the local interface  
                through  which,the next hop of this route should be reached."
      ::= { fsMIFsIpCommonRoutingEntry 7 }

  fsMIFsIpRouteType OBJECT-TYPE
      SYNTAX   INTEGER {
  other       (1), -- not specified by this MIB
  reject   (2), -- route which discards traffic
  local       (3), -- local interface
  remote   (4)    -- remote destination
       }
    MAX-ACCESS read-write
    STATUS   current
    DESCRIPTION
 "The type of route.  Note that local(3)  refers
 to  a route for which the next hop is the final
 destination; remote(4) refers to  a  route  for
 which the  next  hop is not the final destina-
 tion.

 Routes which do not result in traffic forwarding or
 rejection should not be displayed even if the
 implementation keeps them stored internally.
 reject (2) refers to a route which, if matched, discards
 the message as unreachable. This is used in some
 protocols as a means of correctly aggregating routes."
    ::= { fsMIFsIpCommonRoutingEntry 8 }


fsMIFsIpRouteAge OBJECT-TYPE
    SYNTAX   Integer32 
    MAX-ACCESS read-only
    STATUS   current
    DESCRIPTION
 "The number of seconds     since    this  route  was
 last  updated    or  otherwise  determined  to be
 correct.  Note that no semantics of  `too  old'
 can  be implied except through knowledge of the
 routing  protocol  by    which  the   route   was
 learned."
    DEFVAL  { 0 }
    ::= { fsMIFsIpCommonRoutingEntry 9 }

fsMIFsIpRouteNextHopAS OBJECT-TYPE
    SYNTAX   Integer32 
    MAX-ACCESS read-write
    STATUS   current
    DESCRIPTION
 "The Autonomous System Number of the Next  Hop.
 The  semantics of this object are determined by
 the routing-protocol specified in  the     route's
 fsMIFsIpRouteProto  value. When    this object is
 unknown or not relevant its value should be set
 to zero."
     DEFVAL { 0 }
     ::= { fsMIFsIpCommonRoutingEntry 10 }

 fsMIFsIpRouteMetric1 OBJECT-TYPE
         SYNTAX   Integer32 
     MAX-ACCESS read-only
     STATUS   current
     DESCRIPTION
  "The primary routing  metric  for  this  route.
  The  semantics of this metric are determined by
  the routing-protocol specified in  the     route's
  fsMIFsIpRouteProto  value.   If    this metric is not
  used, its value should be set to -1."
     DEFVAL { -1 }
     ::= { fsMIFsIpCommonRoutingEntry 11 }

 fsMIFsIpRoutePreference OBJECT-TYPE
         SYNTAX   Integer32 (0.. 255)
     MAX-ACCESS read-write
     STATUS   current
     DESCRIPTION
  "The preference for the method by which this route was learned.
               This value will be used by the forwarding algorithm to choose
               the best route."
     ::= { fsMIFsIpCommonRoutingEntry 12 }

fsMIFsIpRouteStatus  OBJECT-TYPE
             SYNTAX   RowStatus
             MAX-ACCESS read-create
           STATUS   current
               DESCRIPTION
           "The row status variable, used according to
                row installation and removal conventions."
      ::= { fsMIFsIpCommonRoutingEntry 13 }

-- IPIF table 

fsMIFsIpifTable OBJECT-TYPE
   SYNTAX  SEQUENCE OF FsMIFsIpifEntry
   MAX-ACCESS not-accessible
   STATUS   current
   DESCRIPTION
          "IP interface table which maintains the interface specific
           configurable parameters of IP."
   ::= { fsMIFsIp 9 }

fsMIFsIpifEntry OBJECT-TYPE
      SYNTAX   FsMIFsIpifEntry
      MAX-ACCESS not-accessible
      STATUS   current
      DESCRIPTION
               "A particular interface specific IP information."
      INDEX {
  fsMIFsIpifIndex
  }
      ::= { fsMIFsIpifTable 1 }

FsMIFsIpifEntry ::=
    SEQUENCE {
  fsMIFsIpifIndex
      Integer32,
  fsMIFsIpifMaxReasmSize
      Integer32,
  fsMIFsIpifIcmpRedirectEnable
      INTEGER,
  fsMIFsIpifDrtBcastFwdingEnable
      INTEGER,
  fsMIFsIpifContextId 
      Integer32,
  fsMIFsIpifProxyArpAdminStatus    
      INTEGER,
  fsMIFsIpifLocalProxyArpAdminStatus
      INTEGER
    }

fsMIFsIpifIndex   OBJECT-TYPE
    SYNTAX  Integer32 (0..2147483647)
    MAX-ACCESS  not-accessible
    STATUS  current
    DESCRIPTION
      "The index value which identifies the
       interface to which this entry is applicable. The
       interface identified by a particular value of this
       index is the same interface as identified by the same
       value of ifIndex in MIB II."
    ::= { fsMIFsIpifEntry 1 }

    fsMIFsIpifMaxReasmSize OBJECT-TYPE
       SYNTAX  Integer32 (1024..33280)
       MAX-ACCESS read-write
       STATUS  current
       DESCRIPTION
               "The maximum size of the fragmented IP datagram received 
          on this interface that can be considered for reassembly." 
          ::= { fsMIFsIpifEntry 2 }


fsMIFsIpifIcmpRedirectEnable   OBJECT-TYPE
     SYNTAX   INTEGER {
                enabled(1),
                disabled(2)
              }
     MAX-ACCESS read-write
     STATUS   current
     DESCRIPTION
             "Enabling or Diabling of the ICMP redirect messages on an 
     interface basis."
     ::= { fsMIFsIpifEntry 3 }

    fsMIFsIpifDrtBcastFwdingEnable  OBJECT-TYPE
      SYNTAX   INTEGER {
                 enabled(1),
                 disabled(2)
               }
      MAX-ACCESS read-write
      STATUS    current
      DESCRIPTION
             "Enabling of Directed broadcast forwarding on that 
      interface."
      ::= { fsMIFsIpifEntry 4 }


fsMIFsIpifContextId OBJECT-TYPE
    SYNTAX     Integer32
    MAX-ACCESS read-only
    STATUS     current
    DESCRIPTION
           "The context to which the interface is mapped."
    ::= { fsMIFsIpifEntry 5 }

     fsMIFsIpifProxyArpAdminStatus OBJECT-TYPE
       SYNTAX      INTEGER {
                     enabled(1),
                     disabled(2)
                    }
       MAX-ACCESS  read-write
       STATUS      current
       DESCRIPTION
                  "Enables or Disables Proxy ARP Feature for that
                   interface. By default, this object
                   should have the value enabled(1)."
     DEFVAL     { disabled }
     ::= { fsMIFsIpifEntry 6 }

     fsMIFsIpifLocalProxyArpAdminStatus OBJECT-TYPE
        SYNTAX INTEGER {
                 enabled     (1),
                 disabled    (2)
        }
        MAX-ACCESS read-write
        STATUS current
        DESCRIPTION
                "This Object Enables or Disables Proxy ARP feature
                 in local subnet.
                 When this object is set to enabled (1),
                 ISS will act as ARP proxy for target address which
                 is in same subnet also. When this object is set to
                 disabled (2) ISS will not act as ARP proxy for target
                 address which is in same subnet."
        DEFVAL { disabled }
        ::= { fsMIFsIpifEntry 7 }

--
--ICMP Context specific global configuration 
--

    fsMIFsIcmpGlobalTable OBJECT-TYPE
    SYNTAX SEQUENCE OF FsMIFsIcmpGlobalEntry
    MAX-ACCESS not-accessible
    STATUS     current
    DESCRIPTION
        "Table to store the virtual router specific ICMP configurations"
    ::= { fsMIFsIp 10 }

    fsMIFsIcmpGlobalEntry OBJECT-TYPE
    SYNTAX     FsMIFsIcmpGlobalEntry
    MAX-ACCESS not-accessible
    STATUS     current
    DESCRIPTION
        "Each entry has ICMP configuration information for the Virtual router"
    INDEX {fsMIStdIpContextId}
    ::= {fsMIFsIcmpGlobalTable 1}

    FsMIFsIcmpGlobalEntry ::= SEQUENCE {
        fsMIFsIcmpSendRedirectEnable      INTEGER,
        fsMIFsIcmpSendUnreachableEnable   INTEGER,
        fsMIFsIcmpSendEchoReplyEnable     INTEGER,
        fsMIFsIcmpNetMaskReplyEnable      INTEGER,
        fsMIFsIcmpTimeStampReplyEnable    INTEGER,
        fsMIFsIcmpInDomainNameRequests        Counter32,
        fsMIFsIcmpInDomainNameReply           Counter32,
        fsMIFsIcmpOutDomainNameRequests       Counter32,
        fsMIFsIcmpOutDomainNameReply          Counter32,
        fsMIFsIcmpDirectQueryEnable       INTEGER,
        fsMIFsIcmpDomainName              DisplayString,
        fsMIFsIcmpTimeToLive              Integer32,
        fsMIFsIcmpInSecurityFailures      Counter32,
        fsMIFsIcmpOutSecurityFailures     Counter32,
        fsMIFsIcmpSendSecurityFailuresEnable INTEGER,
        fsMIFsIcmpRecvSecurityFailuresEnable INTEGER
}

fsMIFsIcmpSendRedirectEnable OBJECT-TYPE
    SYNTAX     INTEGER   {
                    enabled    (1),
                    disabled   (2)
               }
    MAX-ACCESS read-write
    STATUS     current
    DESCRIPTION 
           " Allow sending ICMP Redirect Message "
    DEFVAL     { enabled }
    ::= { fsMIFsIcmpGlobalEntry 1 }

fsMIFsIcmpSendUnreachableEnable OBJECT-TYPE
    SYNTAX     INTEGER  {
                    enabled    (1),
                    disabled   (2)
               }
    MAX-ACCESS read-write
    STATUS     current
    DESCRIPTION 
           " Allow sending ICMP Unreachable Message "
    DEFVAL     { enabled }
    ::= { fsMIFsIcmpGlobalEntry 2 }

fsMIFsIcmpSendEchoReplyEnable OBJECT-TYPE
    SYNTAX     INTEGER  {
                    enabled    (1),
                    disabled   (2)
               }
    MAX-ACCESS read-write
    STATUS     current
    DESCRIPTION 
            " Allow sending ICMP Echo Reply Message "
    DEFVAL     { enabled }
    ::= { fsMIFsIcmpGlobalEntry 3 }

fsMIFsIcmpNetMaskReplyEnable OBJECT-TYPE
    SYNTAX     INTEGER  {
                    enabled    (1),
                    disabled   (2)
               }
    MAX-ACCESS read-write
    STATUS     current
    DESCRIPTION 
           " Allow sending ICMP Net Mask Reply Message "
    DEFVAL     { enabled }
      ::= { fsMIFsIcmpGlobalEntry 4 }

fsMIFsIcmpTimeStampReplyEnable OBJECT-TYPE
    SYNTAX     INTEGER  {
                    enabled    (1),
                    disabled   (2)
               }
    MAX-ACCESS read-write
    STATUS     current
    DESCRIPTION 
           " Allow sending ICMP Time stamp reply Message "
    DEFVAL     { enabled }
    ::= { fsMIFsIcmpGlobalEntry 5 }

fsMIFsIcmpInDomainNameRequests OBJECT-TYPE
    SYNTAX  Counter32
    MAX-ACCESS  read-only
    STATUS  current
    DESCRIPTION
      "The number of ICMP Domain Name Requests
      received."
    ::= { fsMIFsIcmpGlobalEntry 6 }

fsMIFsIcmpInDomainNameReply OBJECT-TYPE
    SYNTAX  Counter32
    MAX-ACCESS  read-only
    STATUS  current
    DESCRIPTION
      "The number of ICMP Domain Name Replies
      received."
    ::= { fsMIFsIcmpGlobalEntry 7 }

fsMIFsIcmpOutDomainNameRequests OBJECT-TYPE
    SYNTAX  Counter32
    MAX-ACCESS  read-only
    STATUS  current
    DESCRIPTION
      "The number of ICMP Domain Name Requests
      send."
    ::= { fsMIFsIcmpGlobalEntry 8 }

fsMIFsIcmpOutDomainNameReply OBJECT-TYPE
    SYNTAX  Counter32
    MAX-ACCESS  read-only
    STATUS  current
    DESCRIPTION
      "The number of ICMP Domain Name Replies
      send."
    ::= { fsMIFsIcmpGlobalEntry 9 }

fsMIFsIcmpDirectQueryEnable OBJECT-TYPE
    SYNTAX     INTEGER {
                    enabled     (1),
                    disabled    (2)
               }
    MAX-ACCESS read-write
    STATUS     current
    DESCRIPTION
           "DNS Direct Query will be enabled or disabled
            accordingly"
    DEFVAL { disabled }
      ::= { fsMIFsIcmpGlobalEntry 10 }

fsMIFsIcmpDomainName OBJECT-TYPE
    SYNTAX DisplayString
    MAX-ACCESS read-write
    STATUS current
    DESCRIPTION
      "Domain Name of the system, used to send when
      replies to DNS Direct Query."
    ::= { fsMIFsIcmpGlobalEntry 11 }

fsMIFsIcmpTimeToLive OBJECT-TYPE
    SYNTAX Integer32 (0..2147483647)
    MAX-ACCESS read-write
    STATUS current
    DESCRIPTION
      "The number of seconds untill which the name
      can be cached."
    ::= { fsMIFsIcmpGlobalEntry 12 }

fsMIFsIcmpInSecurityFailures OBJECT-TYPE
    SYNTAX Counter32
    MAX-ACCESS read-only
    STATUS current
    DESCRIPTION
      "The number of ICMP Security Failure messages
      received."
    ::= { fsMIFsIcmpGlobalEntry 13 }

fsMIFsIcmpOutSecurityFailures OBJECT-TYPE
    SYNTAX Counter32
    MAX-ACCESS read-only
    STATUS current
    DESCRIPTION
      "The number of ICMP Security Failure messages
      sent."
    ::= { fsMIFsIcmpGlobalEntry 14 }

fsMIFsIcmpSendSecurityFailuresEnable OBJECT-TYPE
    SYNTAX INTEGER {
enabled (1),
disabled (2)
    }
    MAX-ACCESS read-write
    STATUS current
    DESCRIPTION
      "Allow sending Security Failure messages."
    DEFVAL { enabled }
    ::= { fsMIFsIcmpGlobalEntry 15 }

fsMIFsIcmpRecvSecurityFailuresEnable OBJECT-TYPE
    SYNTAX INTEGER {
enabled (1),
disabled (2)
    }
    MAX-ACCESS    read-write
    STATUS    current
    DESCRIPTION
      "Allow Recieving Security Failure messages."
    DEFVAL { enabled }
      ::= { fsMIFsIcmpGlobalEntry 16 }


fsMIFsUdpGlobalTable OBJECT-TYPE
    SYNTAX SEQUENCE OF FsMIFsUdpGlobalEntry
    MAX-ACCESS not-accessible
    STATUS     current
    DESCRIPTION
        "Table to store the virtual router specific ICMP configurations"
    ::= { fsMIFsIp 11 }

    fsMIFsUdpGlobalEntry OBJECT-TYPE
    SYNTAX     FsMIFsUdpGlobalEntry
    MAX-ACCESS not-accessible
    STATUS     current
    DESCRIPTION
        "Each entry has ICMP configuration information for the Virtual router"
    INDEX {fsMIStdIpContextId}
    ::= {fsMIFsUdpGlobalTable 1}

    FsMIFsUdpGlobalEntry ::= SEQUENCE {
        fsMIFsUdpInNoCksum      Counter32,
        fsMIFsUdpInIcmpErr      Counter32,
        fsMIFsUdpInErrCksum     Counter32,
        fsMIFsUdpInBcast        Counter32
    }
 

fsMIFsUdpInNoCksum OBJECT-TYPE
SYNTAX      Counter32
MAX-ACCESS      read-only
STATUS      current
DESCRIPTION " Number of UDP datagrams received without
    checksum "
::= { fsMIFsUdpGlobalEntry 1 }

fsMIFsUdpInIcmpErr OBJECT-TYPE
SYNTAX      Counter32
MAX-ACCESS      read-only
STATUS      current
DESCRIPTION " Number of ICMP error packets received "
::= { fsMIFsUdpGlobalEntry 2 }

fsMIFsUdpInErrCksum OBJECT-TYPE
SYNTAX      Counter32
MAX-ACCESS      read-only
STATUS      current
DESCRIPTION " Number of UDP packets received with wrong
     checksum "
::= { fsMIFsUdpGlobalEntry 3 }

fsMIFsUdpInBcast OBJECT-TYPE
SYNTAX      Counter32
MAX-ACCESS      read-only
STATUS      current
DESCRIPTION " Number of UDP packets received in broadcast mode "
::= { fsMIFsUdpGlobalEntry 4 }

--
--CIDR Agg Table
--

fsMIFsIpCidrAggTable OBJECT-TYPE
    SYNTAX     SEQUENCE OF FsMIFsIpCidrAggEntry
    MAX-ACCESS not-accessible
    STATUS     current
    DESCRIPTION
           "The (conceptual) table listing the router's
            supernet routes.RIP advertises only supernet
            routes on the speicified interface. And it
            suppresses all routes which are subset of the supernet."
    ::= { fsMIFsIp 12 }

fsMIFsIpCidrAggEntry OBJECT-TYPE
    SYNTAX     FsMIFsIpCidrAggEntry
    MAX-ACCESS not-accessible
    STATUS     current
    DESCRIPTION
           "An entry (conceptual row) in the
            fsMIFsIpCidrAggTable representing supertnet route for
            the domain."
    INDEX  { 
        fsMIStdIpContextId, 
        fsMIFsIpCidrAggAddress, 
        fsMIFsIpCidrAggAddressMask 
        }
    ::= { fsMIFsIpCidrAggTable 1 }

FsMIFsIpCidrAggEntry ::=
    SEQUENCE {
             fsMIFsIpCidrAggAddress        IpAddress,
             fsMIFsIpCidrAggAddressMask    IpAddress,
             fsMIFsIpCidrAggStatus         RowStatus
    }

fsMIFsIpCidrAggAddress OBJECT-TYPE
    SYNTAX     IpAddress
    MAX-ACCESS not-accessible
    STATUS     current
    DESCRIPTION
           "The aggregated address which when combined with the
            corresponding value of fsMIFsIpCidrAggAddressMask
            identifies the supernet route for this domain."
    ::= { fsMIFsIpCidrAggEntry 1 }

fsMIFsIpCidrAggAddressMask OBJECT-TYPE
    SYNTAX     IpAddress
    MAX-ACCESS not-accessible
    STATUS     current
    DESCRIPTION
           "The aggregated address mask which when combined with
            the corresponding value of fsMIFsIpCidrAggAddress
            identifies the supernet route for the domain."
    ::= { fsMIFsIpCidrAggEntry 2 }

fsMIFsIpCidrAggStatus OBJECT-TYPE
    SYNTAX     RowStatus
    MAX-ACCESS read-write
    STATUS     current
    DESCRIPTION
           "The status of this row, by which new entries may be
            created, or old entries deleted from this table."
    ::= { fsMIFsIpCidrAggEntry 3 }

fsMIFsCidrAdvertTable OBJECT-TYPE
    SYNTAX     SEQUENCE OF FsMIFsCidrAdvertEntry
    MAX-ACCESS not-accessible
    STATUS     current
    DESCRIPTION
      "The (conceptual) table listing the routes that are to
      be explicitly advertised on a specific interface,
      for multi-homed reasons, or policy reasons "
    ::= { fsMIFsIp 13 }

fsMIFsCidrAdvertEntry OBJECT-TYPE
    SYNTAX     FsMIFsCidrAdvertEntry
    MAX-ACCESS not-accessible
    STATUS     current
    DESCRIPTION
           "An entry (conceptual row) in the
            fsMIFsCidrAdvertTable representing a route to be explicitly
            advertised on a specific interface."
    INDEX  { 
        fsMIStdIpContextId, 
        fsMIFsCidrAdvertAddress, 
        fsMIFsCidrAdvertAddressMask 
        }
    ::= { fsMIFsCidrAdvertTable 1 }

FsMIFsCidrAdvertEntry ::= 
    SEQUENCE {
              fsMIFsCidrAdvertAddress      IpAddress,
              fsMIFsCidrAdvertAddressMask  IpAddress,
              fsMIFsCidrAdvertStatus       RowStatus
    }

fsMIFsCidrAdvertAddress OBJECT-TYPE
    SYNTAX     IpAddress
    MAX-ACCESS not-accessible
    STATUS     current
    DESCRIPTION
           "The network address which when combined with the
            corresponding value of fsMIFsCidrAdvertAddressMask
            identifies the route that is to be explicitly advertised."
    ::= { fsMIFsCidrAdvertEntry 1 }

fsMIFsCidrAdvertAddressMask OBJECT-TYPE
    SYNTAX     IpAddress
    MAX-ACCESS not-accessible
    STATUS     current
    DESCRIPTION
           "The destination network address mask which when
            combined with the corresponding value of
            fsMIFsCidrAdvertAddress identifies the route to be
            explicitly advertised."
    ::= { fsMIFsCidrAdvertEntry 2 }

fsMIFsCidrAdvertStatus OBJECT-TYPE
    SYNTAX     RowStatus
    MAX-ACCESS read-write
    STATUS     current
    DESCRIPTION
           "The status of this row, by which new entries may be
            created, or old entries deleted from this table."
    ::= { fsMIFsCidrAdvertEntry 3 }


fsMIFsIrdpInAdvertisements OBJECT-TYPE
     SYNTAX Counter32
     MAX-ACCESS read-only
     STATUS current
     DESCRIPTION
             "The total number of ICMP Router Advertisements  received."
     ::= { fsMIFsIp 14 }

 fsMIFsIrdpInSolicitations OBJECT-TYPE
     SYNTAX  Counter32
     MAX-ACCESS  read-only
     STATUS  current
     DESCRIPTION
       "The total number of ICMP Router Solicitations
       received."
     ::= { fsMIFsIp 15 }

 fsMIFsIrdpOutAdvertisements OBJECT-TYPE
     SYNTAX  Counter32
     MAX-ACCESS  read-only
     STATUS  current
     DESCRIPTION
       "The number of ICMP Router Advertisements
       sent."
     ::= { fsMIFsIp 16 }

 fsMIFsIrdpOutSolicitations OBJECT-TYPE
     SYNTAX  Counter32
     MAX-ACCESS  read-only
     STATUS  current
     DESCRIPTION
       "The number of ICMP Router Solicitations
       sent."
     ::= { fsMIFsIp 17 }

 fsMIFsIrdpSendAdvertisementsEnable OBJECT-TYPE
     SYNTAX INTEGER {

 enabled (1),
 disabled (2)
     }
     MAX-ACCESS read-write
     STATUS current
     DESCRIPTION
       "Allow sending Router Advertisements."
     DEFVAL { enabled }
     ::= { fsMIFsIp 18 }

--SCALAR_TABLE_END fsirdp

 fsMIFsIrdpIfConfTable OBJECT-TYPE
     SYNTAX SEQUENCE OF FsMIFsIrdpIfConfEntry
     MAX-ACCESS not-accessible
     STATUS current
     DESCRIPTION
       "This table has interface specific irdp configurable
       objects."
     ::= { fsMIFsIp 19 }

 fsMIFsIrdpIfConfEntry OBJECT-TYPE
     SYNTAX FsMIFsIrdpIfConfEntry
     MAX-ACCESS not-accessible
     STATUS current
     DESCRIPTION
       "The individual entry in the above table."
     INDEX {
        fsMIFsIrdpIfConfIfNum,
        fsMIFsIrdpIfConfSubref
     }
::= { fsMIFsIrdpIfConfTable 1 }

 FsMIFsIrdpIfConfEntry ::=
     SEQUENCE {
          fsMIFsIrdpIfConfIfNum
          Integer32,
          fsMIFsIrdpIfConfSubref
          Integer32,
          fsMIFsIrdpIfConfAdvertisementAddress
 IpAddress,
 fsMIFsIrdpIfConfMaxAdvertisementInterval
 Integer32,
 fsMIFsIrdpIfConfMinAdvertisementInterval
 Integer32,
 fsMIFsIrdpIfConfAdvertisementLifetime
 Integer32,
 fsMIFsIrdpIfConfPerformRouterDiscovery
 TruthValue,
 fsMIFsIrdpIfConfSolicitationAddress
 IpAddress
     }

 fsMIFsIrdpIfConfIfNum    OBJECT-TYPE
     SYNTAX    Integer32 (0..2147483647)
     MAX-ACCESS    not-accessible
     STATUS    current
     DESCRIPTION
     "The number of interfaces present in this system."
     ::= { fsMIFsIrdpIfConfEntry 1 }

 fsMIFsIrdpIfConfSubref     OBJECT-TYPE
     SYNTAX    Integer32 (0..2147483647)
     MAX-ACCESS    not-accessible
     STATUS    current
     DESCRIPTION
     "The subreference of this interface."
     ::= { fsMIFsIrdpIfConfEntry 2 }

 fsMIFsIrdpIfConfAdvertisementAddress OBJECT-TYPE
     SYNTAX IpAddress 
     MAX-ACCESS read-write
     STATUS current
     DESCRIPTION
       "The IP destination address to be used for
       multicast Rourter Advertisements sent from the
       interface. The only permissible values are the
       all-systems multicast address, 224.0.0.1, or
       limited-broadcast address, 255.255.255.255. "
           DEFVAL { 'e0000001'H }
     ::= { fsMIFsIrdpIfConfEntry 3 }

 fsMIFsIrdpIfConfMaxAdvertisementInterval OBJECT-TYPE
     SYNTAX Integer32 (4..1800)
     MAX-ACCESS read-write
     STATUS current
     DESCRIPTION
       "The maximum time allowed between sending multicast
       Advertisements from the interface, in seconds."
     DEFVAL { 600 }
     ::= { fsMIFsIrdpIfConfEntry 4 }

 fsMIFsIrdpIfConfMinAdvertisementInterval OBJECT-TYPE
     SYNTAX Integer32 (4..1800)
     MAX-ACCESS read-write
     STATUS current
     DESCRIPTION
       "The minimum time allowed between sending unsolicited
       multicast Router Advertisements from the interface,
       in seconds."
     DEFVAL { 450 }
     ::= { fsMIFsIrdpIfConfEntry 5 }

 fsMIFsIrdpIfConfAdvertisementLifetime OBJECT-TYPE
     SYNTAX Integer32 (1800..9000)
     MAX-ACCESS read-write
     STATUS current
     DESCRIPTION
       "The value to be placed in the Lifetim efield of Router
       Advertisements sent from the interface, in seconds."
     DEFVAL { 1800 }
     ::= { fsMIFsIrdpIfConfEntry 6 }

 fsMIFsIrdpIfConfPerformRouterDiscovery OBJECT-TYPE
     SYNTAX TruthValue
     MAX-ACCESS read-write
     STATUS current
     DESCRIPTION
       "A flag indicating whether or not the host is to perform
       ICMP router discovery on the interface."
           DEFVAL { true }
     ::= { fsMIFsIrdpIfConfEntry 7 }

 fsMIFsIrdpIfConfSolicitationAddress OBJECT-TYPE
     SYNTAX IpAddress 
     MAX-ACCESS read-write
     STATUS current
     DESCRIPTION
       "The IP destination address to be used for sending
       Router Solicitations from the interface. The only
       permissible values are the all-routers multicast
       address, 224.0.0.2, or the limited-broadcast
       address, 255.255.255.255."
           DEFVAL { 'e0000002'H }
     ::= { fsMIFsIrdpIfConfEntry 8 }

--
-- RARP Client Scalars
--

 fsMIFsRarpClientRetransmissionTimeout OBJECT-TYPE
     SYNTAX   Integer32 (30..3000)
     MAX-ACCESS   read-write
     STATUS   current
     DESCRIPTION
             "The interval (in seconds) after which an unanswered RARP
       request should be retransmitted."
     DEFVAL {100}
     ::= { fsMIFsIp 20 }

 fsMIFsRarpClientMaxRetries OBJECT-TYPE
     SYNTAX Integer32 (2..10)
     MAX-ACCESS read-write
     STATUS current
     DESCRIPTION
             "The maximum number of retransmissions of RARP request
       packet after which no request should be sent."
     DEFVAL {4}
     ::= { fsMIFsIp 21 }



 fsMIFsRarpClientPktsDiscarded OBJECT-TYPE
     SYNTAX Counter32
     MAX-ACCESS read-only
     STATUS current
     DESCRIPTION
             "Total number of RARP Reply packets discarded 
                   by this client."
     ::= { fsMIFsIp 22 }

--
-- RARP server scalars
--

 fsMIFsRarpServerStatus OBJECT-TYPE
     SYNTAX INTEGER {
              enabled (1),
              disabled (2)
     }
     MAX-ACCESS read-write
     STATUS current
     DESCRIPTION
             "Enables or Disables the RARP Server."
     DEFVAL { disabled }
     ::= { fsMIFsIp 23 }

 fsMIFsRarpServerPktsDiscarded OBJECT-TYPE
     SYNTAX Counter32
     MAX-ACCESS read-only
     STATUS current
     DESCRIPTION
             "Total number of RARP request packets discarded 
                   by this server."
     ::= { fsMIFsIp 24 }


       fsMIFsRarpServerTableMaxEntries OBJECT-TYPE
          SYNTAX Integer32(0..25)
          MAX-ACCESS read-write
          STATUS current
          DESCRIPTION
                  "Maximum number of entries in the RARP server table."
          ::= { fsMIFsIp 25 }
    
fsMIFsRarpServerDatabaseTable OBJECT-TYPE
     SYNTAX SEQUENCE OF FsMIFsRarpServerDatabaseEntry
     MAX-ACCESS not-accessible
     STATUS current
     DESCRIPTION
             "The Server database which maps the Client's 
                   hardware Address to IP Address ."
     ::= { fsMIFsIp 26 }

 fsMIFsRarpServerDatabaseEntry OBJECT-TYPE
     SYNTAX FsMIFsRarpServerDatabaseEntry
     MAX-ACCESS not-accessible
     STATUS current
     DESCRIPTION
             "Contains entry for a particular client."
     INDEX { fsMIFsHardwareAddress }
     ::= { fsMIFsRarpServerDatabaseTable 1 }

 FsMIFsRarpServerDatabaseEntry ::=
     SEQUENCE {
  fsMIFsHardwareAddress OCTET STRING,
  fsMIFsHardwareAddrLen Integer32 ,
  fsMIFsProtocolAddress IpAddress,
  fsMIFsEntryStatus RowStatus
     }

 fsMIFsHardwareAddress OBJECT-TYPE
     SYNTAX OCTET STRING (SIZE(6))
     MAX-ACCESS not-accessible
     STATUS current
     DESCRIPTION
       "The Hardware address of the client."
     ::= { fsMIFsRarpServerDatabaseEntry 1 }

 fsMIFsHardwareAddrLen OBJECT-TYPE
     SYNTAX Integer32 (1..6)
     MAX-ACCESS read-write   STATUS current
     DESCRIPTION
       "The hardware address length of the spceified index."
     ::= { fsMIFsRarpServerDatabaseEntry 2 }

 fsMIFsProtocolAddress OBJECT-TYPE
     SYNTAX IpAddress
     MAX-ACCESS read-write
     STATUS current
     DESCRIPTION
       "IP Address corresponding to the client's 
                   Hardware Address."
     ::= { fsMIFsRarpServerDatabaseEntry 3 }

 fsMIFsEntryStatus OBJECT-TYPE
     SYNTAX RowStatus
     MAX-ACCESS read-write
     STATUS current
     DESCRIPTION
       "The status of this row,by which new entries may 
                   be created or old entries can be deleted from 
                   this server table as per SMIv2."
     ::= { fsMIFsRarpServerDatabaseEntry 4 }


 fsMIFsIpProxyArpSubnetOption OBJECT-TYPE
      SYNTAX INTEGER {
            enabled     (1),
            disabled    (2)
      }
      MAX-ACCESS read-write
      STATUS     obsolete
      DESCRIPTION
          "This Object Enables or Disables Subnet Check in Proxy 
           ARP feature.When this object is set to enabled (1), 
           ISS will act as ARP proxy for target address which
           is in different subnet.When this object is set to
           disabled (2) ISS will act as ARP proxy for target 
           address which is in same and different subnet which
           is used in IP-DSLAM case."
      DEFVAL { enabled }
     ::= { fsMIFsIp 27 }

END
