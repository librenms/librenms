-- Copyright (C) 2009-2012 Aricent Group . All Rights Reserved

ARICENT-TACACS-EXT-MIB DEFINITIONS ::= BEGIN

IMPORTS
    MODULE-IDENTITY, OBJECT-TYPE,
    Integer32, Unsigned32, enterprises,
    Counter32                        FROM SNMPv2-SMI
    DisplayString, RowStatus         FROM SNMPv2-TC
    InetAddressType, InetAddress     FROM INET-ADDRESS-MIB;

futureTacacsClientExtMIB MODULE-IDENTITY
    LAST-UPDATED "202210190000Z"
    ORGANIZATION "ARICENT COMMUNICATIONS SOFTWARE"
    CONTACT-INFO "support@aricent.com"
	 DESCRIPTION
         "The MIB for ISSAcessControl."
	 REVISION "202210190000Z"
         DESCRIPTION
         "Added fsTacClntServerKeyType"
	 REVISION "201209050000Z"
         DESCRIPTION
         "The MIB for ISSAcessControl."
         ::= { enterprises  aricent-communication-holding-ltd(29601) iss(2) 29 }


futureTacacsClientExtScalarGroup   OBJECT IDENTIFIER 
                                                ::= { futureTacacsClientExtMIB 1 }
futureTacacsClientExtTableGroup   OBJECT IDENTIFIER 
                                                ::= { futureTacacsClientExtMIB 2 }

-- Scalar MIB definitions 
-- ***********************

fsTacClntExtActiveServerAddressType OBJECT-TYPE
   SYNTAX      InetAddressType
   MAX-ACCESS  read-write 
   STATUS      current
   DESCRIPTION
   "The address type of active server.This can be IPv4 or IPv6."
    ::= { futureTacacsClientExtScalarGroup 1 }


fsTacClntExtActiveServer   OBJECT-TYPE
    SYNTAX      InetAddress 
    MAX-ACCESS  read-write
    STATUS      current
    DESCRIPTION
      "Maximum of 5 server's(IPv4 or IPv6) information could be configured 
      for TACACS. This object indicates the active server among 
      those 5 servers. The TACACS+ client interacts with the server 
      having this IP address . Setting this object to zero disables 
      the active server concept."
    ::= { futureTacacsClientExtScalarGroup 2 }


fsTacClntExtTraceLevel   OBJECT-TYPE
    SYNTAX      Unsigned32
    MAX-ACCESS  read-write
    STATUS      current
    DESCRIPTION
      "The debug trace level for TACACS+ client implementation. This is a bit
      mapped data. Each bit of this object represents a trace level.
       0x00000001 - Information
       0x00000002 - Errors
       0x00000004 - Tx. packet dump
       0x00000008 - Rx. packet dump
       0xffffffff - All of the above
       0x00000000 - No trace"
    ::= { futureTacacsClientExtScalarGroup 3 }

fsTacClntExtRetransmit   OBJECT-TYPE
    SYNTAX      Integer32 (1..100)
    MAX-ACCESS  read-write
    STATUS      current
    DESCRIPTION
      " Number of times the TACACS+ client searches the list of Maximum number of  TACACS+ servers(IPv4 or IPv6)i.e 5 as of now"
    DEFVAL { 2 }
    ::= { futureTacacsClientExtScalarGroup 4 }

-- ----------------------------------
-- Statistics scalar MIB definitions
-- ----------------------------------

fsTacClntExtStatisticsGroup   OBJECT IDENTIFIER 
                                        ::= { futureTacacsClientExtScalarGroup 5 }

fsTacClntExtAuthenStartRequests   OBJECT-TYPE
    SYNTAX      Counter32
    MAX-ACCESS  read-only
    STATUS      current
    DESCRIPTION
      "Number of authentication start requests sent to the server(IPv4 or IPv6)."
    ::= { fsTacClntExtStatisticsGroup 1 }

fsTacClntExtAuthenContinueRequests   OBJECT-TYPE
    SYNTAX      Counter32
    MAX-ACCESS  read-only
    STATUS      current
    DESCRIPTION
      "Number of authentication continue requests sent to the server(IPv4 or IPv6)."
    ::= { fsTacClntExtStatisticsGroup 2 }

fsTacClntExtAuthenEnableRequests   OBJECT-TYPE
    SYNTAX      Counter32
    MAX-ACCESS  read-only
    STATUS      current
    DESCRIPTION
      "Number of authentication enable requests sent to the server(IPv4 or IPv6)."
    ::= { fsTacClntExtStatisticsGroup 3 }

fsTacClntExtAuthenAbortRequests   OBJECT-TYPE
    SYNTAX      Counter32
    MAX-ACCESS  read-only
    STATUS      current
    DESCRIPTION
      "Number of authentication abort requests sent to the server(IPv4 or IPv6)."
    ::= { fsTacClntExtStatisticsGroup 4 }

fsTacClntExtAuthenPassReceived   OBJECT-TYPE
    SYNTAX      Counter32
    MAX-ACCESS  read-only
    STATUS      current
    DESCRIPTION
      "Number of authentication passes received from the server(IPv4 or IPv6)."
    ::= { fsTacClntExtStatisticsGroup 5 }

fsTacClntExtAuthenFailReceived   OBJECT-TYPE
    SYNTAX      Counter32
    MAX-ACCESS  read-only
    STATUS      current
    DESCRIPTION
      "Number of authentication fails received from the server(IPv4 or IPv6)."
    ::= { fsTacClntExtStatisticsGroup 6 }

fsTacClntExtAuthenGetUserReceived   OBJECT-TYPE
    SYNTAX      Counter32
    MAX-ACCESS  read-only
    STATUS      current
    DESCRIPTION
      "Number of authentication get users received from the server(IPv4 or IPv6)."
    ::= { fsTacClntExtStatisticsGroup 7 }

fsTacClntExtAuthenGetPassReceived   OBJECT-TYPE
    SYNTAX      Counter32
    MAX-ACCESS  read-only
    STATUS      current
    DESCRIPTION
      "Number of authentication get passwords received from the server(IPv4 or IPv6)."
    ::= { fsTacClntExtStatisticsGroup 8 }

fsTacClntExtAuthenGetDataReceived   OBJECT-TYPE
    SYNTAX      Counter32
    MAX-ACCESS  read-only
    STATUS      current
    DESCRIPTION
      "Number of authentication get data received from the  server(IPv4 or IPv6)."
    ::= { fsTacClntExtStatisticsGroup 9 }

fsTacClntExtAuthenErrorReceived   OBJECT-TYPE
    SYNTAX      Counter32
    MAX-ACCESS  read-only
    STATUS      current
    DESCRIPTION
      "Number of authentication errors received from the server(IPv4 or IPv6)."
    ::= { fsTacClntExtStatisticsGroup 10 }

fsTacClntExtAuthenFollowReceived   OBJECT-TYPE
    SYNTAX      Counter32
    MAX-ACCESS  read-only
    STATUS      current
    DESCRIPTION
      "Number of authentication follows received from the server(IPv4 or IPv6)."
    ::= { fsTacClntExtStatisticsGroup 11 }

fsTacClntExtAuthenRestartReceived   OBJECT-TYPE
    SYNTAX      Counter32
    MAX-ACCESS  read-only
    STATUS      current
    DESCRIPTION
      "Number of authentication re-starts received from the server(IPv4 or IPv6)."
    ::= { fsTacClntExtStatisticsGroup 12 }

fsTacClntExtAuthenSessionTimouts   OBJECT-TYPE
    SYNTAX      Counter32
    MAX-ACCESS  read-only
    STATUS      current
    DESCRIPTION
      "Number of authentication session time outs"
    ::= { fsTacClntExtStatisticsGroup 13 }

fsTacClntExtAuthorRequests   OBJECT-TYPE
    SYNTAX      Counter32
    MAX-ACCESS  read-only
    STATUS      current
    DESCRIPTION
      "Number of authorization requests sent to the server(IPv4 or IPv6)."
    ::= { fsTacClntExtStatisticsGroup 14 }

fsTacClntExtAuthorPassAddReceived   OBJECT-TYPE
    SYNTAX      Counter32
    MAX-ACCESS  read-only
    STATUS      current
    DESCRIPTION
      "Number of authorization pass adds received from  the server(IPv4 or IPv6)."
    ::= { fsTacClntExtStatisticsGroup 15 }

fsTacClntExtAuthorPassReplReceived   OBJECT-TYPE
    SYNTAX      Counter32
    MAX-ACCESS  read-only
    STATUS      current
    DESCRIPTION
      "Number of authorization pass replaces received from the server(IPv4 or IPv6)."
    ::= { fsTacClntExtStatisticsGroup 16 }

fsTacClntExtAuthorFailReceived   OBJECT-TYPE
    SYNTAX      Counter32
    MAX-ACCESS  read-only
    STATUS      current
    DESCRIPTION
      "Number of authorization fails received from the server(IPv4 or IPv6)."
    ::= { fsTacClntExtStatisticsGroup 17 }

fsTacClntExtAuthorErrorReceived   OBJECT-TYPE
    SYNTAX      Counter32
    MAX-ACCESS  read-only
    STATUS      current
    DESCRIPTION
      "Number of authorization errors received from the server(IPv4 or IPv6)."
    ::= { fsTacClntExtStatisticsGroup 18 }

fsTacClntExtAuthorFollowReceived   OBJECT-TYPE
    SYNTAX      Counter32
    MAX-ACCESS  read-only
    STATUS      current
    DESCRIPTION
      "Number of authorization follow received from the server(IPv4 or IPv6)."
    ::= { fsTacClntExtStatisticsGroup 19 }

fsTacClntExtAuthorSessionTimeouts   OBJECT-TYPE
    SYNTAX      Counter32
    MAX-ACCESS  read-only
    STATUS      current
    DESCRIPTION
      "Number of authorization session time outs"
    ::= { fsTacClntExtStatisticsGroup 20 }

fsTacClntExtAcctStartRequests   OBJECT-TYPE
    SYNTAX      Counter32
    MAX-ACCESS  read-only
    STATUS      current
    DESCRIPTION
      "Number of accounting start requests sent to the server(IPv4 or IPv6)."
    ::= { fsTacClntExtStatisticsGroup 21 }

fsTacClntExtAcctWdRequests   OBJECT-TYPE
    SYNTAX      Counter32
    MAX-ACCESS  read-only
    STATUS      current
    DESCRIPTION
      "Number of accounting watch dog requests sent to the server(IPv4 or IPv6)."
    ::= { fsTacClntExtStatisticsGroup 22 }

fsTacClntExtAcctStopRequests   OBJECT-TYPE
    SYNTAX      Counter32
    MAX-ACCESS  read-only
    STATUS      current
    DESCRIPTION
      "Number of accounting stop requests sent to the server(IPv4 or IPv6)."
    ::= { fsTacClntExtStatisticsGroup 23 }

fsTacClntExtAcctSuccessReceived   OBJECT-TYPE
    SYNTAX      Counter32
    MAX-ACCESS  read-only
    STATUS      current
    DESCRIPTION
      "Number of accounting successes received from the server(IPv4 or IPv6)."
    ::= { fsTacClntExtStatisticsGroup 24 }

fsTacClntExtAcctErrorReceived   OBJECT-TYPE
    SYNTAX      Counter32
    MAX-ACCESS  read-only
    STATUS      current
    DESCRIPTION
      "Number of accounting errors received from the server(IPv4 or IPv6)."
    ::= { fsTacClntExtStatisticsGroup 25 }

fsTacClntExtAcctFollowReceived   OBJECT-TYPE
    SYNTAX      Counter32
    MAX-ACCESS  read-only
    STATUS      current
    DESCRIPTION
      "Number of accounting follows  received from the server(IPv4 or IPv6)."
    ::= { fsTacClntExtStatisticsGroup 26 }

fsTacClntExtAcctSessionTimeouts   OBJECT-TYPE
    SYNTAX      Counter32
    MAX-ACCESS  read-only
    STATUS      current
    DESCRIPTION
      "Number of accounting session time outs."
    ::= { fsTacClntExtStatisticsGroup 27 }

fsTacClntExtMalformedPktsReceived   OBJECT-TYPE
    SYNTAX      Counter32
    MAX-ACCESS  read-only
    STATUS      current
    DESCRIPTION
      "Number of Malformed packets received from the server(IPv4 or IPv6)."
    ::= { fsTacClntExtStatisticsGroup 28 }

fsTacClntExtSocketFailures   OBJECT-TYPE
    SYNTAX      Counter32
    MAX-ACCESS  read-only
    STATUS      current
    DESCRIPTION
      "Number of socket failures occured."
    ::= { fsTacClntExtStatisticsGroup 29 }

fsTacClntExtConnectionFailures   OBJECT-TYPE
    SYNTAX      Counter32
    MAX-ACCESS  read-only
    STATUS      current
    DESCRIPTION
      "Number of connection failures occurred."
    ::= { fsTacClntExtStatisticsGroup 30 }

-- Tabular MIB definitions 
-- ***********************

-- ----------------------------------
-- Table 1: TACACS+ Server Table
-- ----------------------------------

fsTacClntExtServerTable   OBJECT-TYPE
    SYNTAX SEQUENCE OF FsTacClntExtServerEntry
    MAX-ACCESS not-accessible
    STATUS     current
    DESCRIPTION
      "The TACACS+ server(IPv4 or IPv6) table of server information entries. The entries have
      server information such as server IP address, secret key, port no and timeout."
   ::= { futureTacacsClientExtTableGroup 1 }

fsTacClntExtServerEntry OBJECT-TYPE
   SYNTAX      FsTacClntExtServerEntry
   MAX-ACCESS  not-accessible
   STATUS      current
   DESCRIPTION
      "The entry has server address type, server IP address, port no. secret key and timeout."
   INDEX {fsTacClntExtServerAddressType, fsTacClntExtServerAddress }
   ::= { fsTacClntExtServerTable 1 }
      
FsTacClntExtServerEntry ::= SEQUENCE {
      fsTacClntExtServerAddressType
         InetAddressType,
      fsTacClntExtServerAddress
         InetAddress, 
      fsTacClntExtServerStatus
         RowStatus,
      fsTacClntExtServerSingleConnect
         INTEGER,
      fsTacClntExtServerPort
         Integer32,
      fsTacClntExtServerTimeout
         Integer32,
      fsTacClntExtServerKey
         DisplayString,
      fsTacClntExtServerKeyType
         INTEGER
      }

fsTacClntExtServerAddressType OBJECT-TYPE
   SYNTAX      InetAddressType
   MAX-ACCESS  not-accessible
   STATUS      current
   DESCRIPTION
   "The type of IP address used.This can be IPv4 or IPv6."
   ::= { fsTacClntExtServerEntry 1 }

fsTacClntExtServerAddress OBJECT-TYPE
    SYNTAX      InetAddress 
    MAX-ACCESS  not-accessible
    STATUS      current
    DESCRIPTION
      "Server IP address"
   ::= { fsTacClntExtServerEntry 2 }

fsTacClntExtServerStatus OBJECT-TYPE
    SYNTAX      RowStatus
    MAX-ACCESS  read-create
    STATUS      current
    DESCRIPTION
      "Row status of the server(IPv4 or IPv6) entry."
   ::= { fsTacClntExtServerEntry 3 }

fsTacClntExtServerSingleConnect   OBJECT-TYPE
    SYNTAX      INTEGER {
                        yes(1), 
                        no(2) 
                        }
    MAX-ACCESS  read-create
    STATUS      current
    DESCRIPTION
      " Multiple sessions are handled over single TCP, when single connect support is enabled.
        When single connect is disabled multiple TCP connections established by server."
    DEFVAL { no }
   ::= { fsTacClntExtServerEntry 4 }

fsTacClntExtServerPort OBJECT-TYPE
    SYNTAX      Integer32 (0..65535)
    MAX-ACCESS  read-create
    STATUS      current
    DESCRIPTION
      "Server port no. for TACACS+ protocol. The default value is 49."
    DEFVAL { 49 }
   ::= { fsTacClntExtServerEntry 5 }

fsTacClntExtServerTimeout OBJECT-TYPE
    SYNTAX      Integer32 (1..255)
    MAX-ACCESS  read-create
    STATUS      current
    DESCRIPTION
      "The time out value within which a response is expected from server(IPv4 or IPv6). The session will be released, 
      if the response is not received within this time out."
    DEFVAL { 5 }
   ::= { fsTacClntExtServerEntry 6 }

fsTacClntExtServerKey OBJECT-TYPE
    SYNTAX      DisplayString
    MAX-ACCESS  read-create
    STATUS      current
    DESCRIPTION
      "Secret key shared between the client and server(IPv4 or IPv6) for encryption and
      decryption"
   ::= { fsTacClntExtServerEntry 7 }

fsTacClntExtServerKeyType OBJECT-TYPE
    SYNTAX      INTEGER {
                            unencrypted-password (0),
                            type-7 (7)
                        }
    MAX-ACCESS  read-create
    STATUS      current
    DESCRIPTION
      "This is used to indicate how the secret key must be interpreted."
    DEFVAL { unencrypted-password }
   ::= { fsTacClntExtServerEntry 8 }
END
