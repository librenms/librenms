CAMBIUM-NETWORKS-RPS-MIB DEFINITIONS ::= BEGIN

IMPORTS
    MODULE-IDENTITY, NOTIFICATION-TYPE, OBJECT-TYPE,
    Unsigned32, Integer32, Counter32, enterprises
            FROM SNMPv2-SMI
    MODULE-COMPLIANCE, OBJECT-GROUP
            FROM SNMPv2-CONF
    SnmpAdminString
            FROM SNMP-FRAMEWORK-MIB
    ifIndex
            FROM IF-MIB
    RowStatus, TruthValue
            FROM SNMPv2-TC;

cnRPSMib MODULE-IDENTITY
    LAST-UPDATED "202209082000Z" -- September 08, 2022
    ORGANIZATION "Cambium Networks, Inc."
    CONTACT-INFO "cambiumnetworks.com"
    DESCRIPTION
        "This MIB module contains objects related to the
        Removable Power Supply support."

    REVISION    "202209082000Z" -- September 08, 2022
    DESCRIPTION "Ver 2: Add cnRPSCurrentInputVoltage"
    REVISION    "202007030000Z" -- July 03, 2020
    DESCRIPTION "Ver 1: Initial version."

    ::= { enterprises 17713 24 6 }

--
-- Removable Power Supply attributes
--

cnRPSTable OBJECT-TYPE
    SYNTAX         SEQUENCE OF CnRPSTableEntry
    MAX-ACCESS     not-accessible
    STATUS         current
    DESCRIPTION
        "RPS entry"

    ::= { cnRPSMib 1 }

cnRPSTableEntry OBJECT-TYPE
    SYNTAX         CnRPSTableEntry
    MAX-ACCESS     not-accessible
    STATUS         current
    DESCRIPTION
        "Port-specific data related to the transceivers"

    INDEX { cnRPSIndex }
    ::= { cnRPSTable 1 }

CnRPSTableEntry ::= SEQUENCE {
    cnRPSIndex                  Integer32,
    cnRPSMaximumVoltage         Integer32,
    cnRPSMaximumCurrent         Integer32,
    cnRPSMaximumWatts           Integer32,
    cnRPSStatus                 INTEGER,
    cnRPSCurrentInputVoltage    Integer32
}

cnRPSIndex OBJECT-TYPE
    SYNTAX         Integer32(1..2)
    MAX-ACCESS     read-only
    STATUS         current
    DESCRIPTION
        "RPS index identifier attribute"

    ::= { cnRPSTableEntry 1 }

cnRPSMaximumVoltage OBJECT-TYPE
    SYNTAX         Integer32
    UNITS          "volts"
    MAX-ACCESS     read-only
    STATUS         current
    DESCRIPTION
        "Maximum voltage of power supply."

    ::= { cnRPSTableEntry 2 }

cnRPSMaximumCurrent OBJECT-TYPE
    SYNTAX         Integer32
    UNITS          "amps"
    MAX-ACCESS     read-only
    STATUS         current
    DESCRIPTION
        "Maximum current of power supply."

    ::= { cnRPSTableEntry 3 }

cnRPSMaximumWatts OBJECT-TYPE
    SYNTAX         Integer32
    UNITS          "watts"
    MAX-ACCESS     read-only
    STATUS         current
    DESCRIPTION
        "Maximum watts of power supply."

    ::= { cnRPSTableEntry 4 }

cnRPSStatus OBJECT-TYPE
    SYNTAX         INTEGER{
                       ok(1),
                       error(2),
                       notpresent(3)
                   }
    MAX-ACCESS     read-only
    STATUS         current
    DESCRIPTION
        "Status of power supply."

    ::= { cnRPSTableEntry 5 }

cnRPSCurrentInputVoltage OBJECT-TYPE
    SYNTAX         Integer32
    UNITS          "volts"
    MAX-ACCESS     read-only
    STATUS         current
    DESCRIPTION
        "Current input voltage applied to the power supply."

    ::= { cnRPSTableEntry 6 }

cnRPSTrapMsg NOTIFICATION-TYPE
     OBJECTS      {
                    cnRPSMaximumWatts,
                    cnRPSStatus,
                    cnRPSIndex
                  }
     STATUS       current
     DESCRIPTION
         "This notification is sent out whenever a status change occurs on a power supply."
     ::= { cnRPSMib 2 }

END
