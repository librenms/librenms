CAMBIUM-PTP500-MIB DEFINITIONS ::= BEGIN

   IMPORTS
      IpAddress, enterprises
         FROM RFC1155-SMI
      OBJECT-TYPE
         FROM RFC-1212
      DisplayString
         FROM RFC1213-MIB
      TRAP-TYPE
         FROM RFC-1215;

   -- Define the Cambium PTP object identifier
   cambium            OBJECT IDENTIFIER ::= { enterprises 17713 }

   -- Groups in cambium
   ptp                OBJECT IDENTIFIER ::= { cambium 1 }
   ptmp               OBJECT IDENTIFIER ::= { cambium 2 }
   ptp500             OBJECT IDENTIFIER ::= { cambium 5 }

   -- Groups in ptp500
   dfs                OBJECT IDENTIFIER ::= { ptp500 3 }
   configuration      OBJECT IDENTIFIER ::= { ptp500 5 }
   ethernet           OBJECT IDENTIFIER ::= { ptp500 6 }
   telecom            OBJECT IDENTIFIER ::= { ptp500 7 }
   licence            OBJECT IDENTIFIER ::= { ptp500 8 }
   management         OBJECT IDENTIFIER ::= { ptp500 9 }
   phyControl         OBJECT IDENTIFIER ::= { ptp500 10 }
   phyStatus          OBJECT IDENTIFIER ::= { ptp500 12 }
   alarms             OBJECT IDENTIFIER ::= { ptp500 13 }
   smtp               OBJECT IDENTIFIER ::= { ptp500 15 }
   snmpControl        OBJECT IDENTIFIER ::= { ptp500 16 }
   sntp               OBJECT IDENTIFIER ::= { ptp500 17 }
   reset              OBJECT IDENTIFIER ::= { ptp500 18 }
   versions           OBJECT IDENTIFIER ::= { ptp500 19 }
   pubStats           OBJECT IDENTIFIER ::= { ptp500 20 }
   encryption         OBJECT IDENTIFIER ::= { ptp500 22 }
   tDDControl         OBJECT IDENTIFIER ::= { ptp500 23 }
   aAAControl         OBJECT IDENTIFIER ::= { ptp500 25 }
   syslogControl      OBJECT IDENTIFIER ::= { ptp500 24 }
   supplementary      OBJECT IDENTIFIER ::= { ptp500 96 }
   ptpTraps           OBJECT IDENTIFIER ::= { ptp500 99 }
   ptpTrapPrefix      OBJECT IDENTIFIER ::= { ptpTraps 0 }

 
   DfsTableEntry ::=
      SEQUENCE { dfsTableIndex INTEGER
               , dfsMeans INTEGER
               , dfsNineNinePointNinePercentiles INTEGER
               , dfsPeaks INTEGER
      }
 
   dfsTable OBJECT-TYPE
      SYNTAX SEQUENCE OF DfsTableEntry
      ACCESS not-accessible
      STATUS mandatory
      DESCRIPTION 
        " A table storing a snapshot of various DFS measurements for each channel"
      ::= { dfs 2 }
 
   dfsTableEntry OBJECT-TYPE
      SYNTAX DfsTableEntry
      ACCESS not-accessible
      STATUS mandatory
      DESCRIPTION 
        "Table DfsTable"
      INDEX { dfsTableIndex }
      ::= { dfsTable 1 }
 
   VLANPriorityTableEntry ::=
      SEQUENCE { vLANPriorityQueueMapping INTEGER
               , vLANPriorityTableIndex INTEGER
      }
 
   vLANPriorityTable OBJECT-TYPE
      SYNTAX SEQUENCE OF VLANPriorityTableEntry
      ACCESS not-accessible
      STATUS mandatory
      DESCRIPTION 
        " A priority queue mapping table. This is a list of packet queues indexed by VLAN priority."
      ::= { ethernet 15 }
 
   vLANPriorityTableEntry OBJECT-TYPE
      SYNTAX VLANPriorityTableEntry
      ACCESS not-accessible
      STATUS mandatory
      DESCRIPTION 
        "Table VLANPriorityTable"
      INDEX { vLANPriorityTableIndex }
      ::= { vLANPriorityTable 1 }
 
   SNMPTrapTableEntry ::=
      SEQUENCE { sNMPTrapTableIndex INTEGER
               , sNMPTrapIPAddress IpAddress
               , sNMPTrapPortNumber INTEGER
      }
 
   sNMPTrapTable OBJECT-TYPE
      SYNTAX SEQUENCE OF SNMPTrapTableEntry
      ACCESS not-accessible
      STATUS mandatory
      DESCRIPTION 
        " SNMP trap configuration table."
      ::= { snmpControl 4 }
 
   sNMPTrapTableEntry OBJECT-TYPE
      SYNTAX SNMPTrapTableEntry
      ACCESS not-accessible
      STATUS mandatory
      DESCRIPTION 
        "Table SNMPTrapTable"
      INDEX { sNMPTrapTableIndex }
      ::= { sNMPTrapTable 1 }
 
   UserTableEntry ::=
      SEQUENCE { userTableIndex INTEGER
               , userName OCTET STRING
               , userRole INTEGER
               , userEnabled INTEGER
               , userPassword OCTET STRING
      }
 
   userTable OBJECT-TYPE
      SYNTAX SEQUENCE OF UserTableEntry
      ACCESS not-accessible
      STATUS mandatory
      DESCRIPTION 
        " The User Table Control group contains objects specifically for user account management."
      ::= { aAAControl 2 }
 
   userTableEntry OBJECT-TYPE
      SYNTAX UserTableEntry
      ACCESS not-accessible
      STATUS mandatory
      DESCRIPTION 
        "Table UserTable"
      INDEX { userTableIndex }
      ::= { userTable 1 }
 
   -- Dfs group attribute definitions 
   --
   dfsTableNumber OBJECT-TYPE
      SYNTAX INTEGER (1..63)
      ACCESS read-only
      STATUS mandatory
      DESCRIPTION
             "Number of entries in the dfsTable"  
      ::= { dfs 1 } 
 
   -- DfsTable group attribute definitions 
   --
   dfsTableIndex OBJECT-TYPE
      SYNTAX INTEGER (1..63)
      ACCESS not-accessible
      STATUS mandatory
      DESCRIPTION
             "used to index values in the dfsTable."  
      ::= { dfsTableEntry 1 } 
 
   dfsMeans OBJECT-TYPE
      SYNTAX INTEGER
      ACCESS read-only
      STATUS mandatory
      DESCRIPTION
             "Snapshot of DFS means"  
      ::= { dfsTableEntry 2 } 
 
   dfsNineNinePointNinePercentiles OBJECT-TYPE
      SYNTAX INTEGER
      ACCESS read-only
      STATUS mandatory
      DESCRIPTION
             "Snapshot of DFS 99.9 percentiles"  
      ::= { dfsTableEntry 3 } 
 
   dfsPeaks OBJECT-TYPE
      SYNTAX INTEGER
      ACCESS read-only
      STATUS mandatory
      DESCRIPTION
             "Snapshot of DFS peaks"  
      ::= { dfsTableEntry 4 } 
 
   -- Configuration group attribute definitions 
   --
   iPAddress OBJECT-TYPE
      SYNTAX IpAddress
      ACCESS read-write
      STATUS mandatory
      DESCRIPTION
             "Internet protocol (IP) address. This address is used by 
             the family of Internet protocols to uniquely identify the 
             unit on a network. NB: A system reboot is required to 
             activate changes to this attribute."  
      ::= { configuration 1 } 
 
   subnetMask OBJECT-TYPE
      SYNTAX IpAddress
      ACCESS read-write
      STATUS mandatory
      DESCRIPTION
             "A subnet allows the flow of network traffic between 
             hosts to be segregated based on a network configuration. 
             By organizing hosts into logical groups, subnetting can 
             improve network security and performance. NB: A system 
             reboot is required to activate changes to this attribute"  
      ::= { configuration 2 } 
 
   gatewayIPAddress OBJECT-TYPE
      SYNTAX IpAddress
      ACCESS read-write
      STATUS mandatory
      DESCRIPTION
             "The IP address of a computer on the current network that 
             is currently acting as a network gateway. A gateway acts 
             as an entrance / exit to packets from / to other 
             networks. NB: A system reboot is required to activate 
             changes to this attribute"  
      ::= { configuration 3 } 
 
   targetMACAddress OBJECT-TYPE
      SYNTAX OCTET STRING (SIZE(6))
      ACCESS read-only
      STATUS mandatory
      DESCRIPTION
             "MAC address of the PTP wireless unit forming the other 
             end of the PTP link"  
      ::= { configuration 4 } 
 
   masterSlaveMode OBJECT-TYPE
      SYNTAX INTEGER {
                       master(0),
                       slave(1)
                     }
      ACCESS read-only
      STATUS mandatory
      DESCRIPTION
             "The PTP wireless link operates using a master and slave 
             relationship"  
      ::= { configuration 5 } 
 
   maximumTransmitPower OBJECT-TYPE
      SYNTAX INTEGER (-100..27)
      ACCESS read-only
      STATUS mandatory
      DESCRIPTION
             "Maximum transmit power the wireless unit is permitted to 
             use when establishing and maintaining the wireless link"  
      ::= { configuration 6 } 
 
   antennaGain OBJECT-TYPE
      SYNTAX INTEGER (0..610)
      ACCESS read-write
      STATUS mandatory
      DESCRIPTION
             "Antenna Gain. Expressed in 10ths of dBi. NB: This 
             attribute is ignored for variants with an integral 
             antenna."  
      ::= { configuration 7 } 
 
   cableLoss OBJECT-TYPE
      SYNTAX INTEGER (0..255)
      ACCESS read-write
      STATUS mandatory
      DESCRIPTION
             "Loss in the cable between the ODU and the antenna. 
             Expressed in 10ths of dB. NB: This attribute is ignored 
             for variants with an integral antenna."  
      ::= { configuration 8 } 
 
   eIRP OBJECT-TYPE
      SYNTAX INTEGER
      ACCESS read-only
      STATUS mandatory
      DESCRIPTION
             "Effective Isotropic Radiated Power (EIRP) describes the 
             strength of the radio signal leaving the wireless unit. 
             Expressed in 10ths of dBm"  
      ::= { configuration 9 } 
 
   channelBandwidth OBJECT-TYPE
      SYNTAX INTEGER {
                       bw-30-mhz(0),
                       bw-15-mhz(1),
                       bw-10-mhz(2),
                       bw-5-mhz(3),
                       bw-20-mhz(4)
                     }
      ACCESS read-only
      STATUS mandatory
      DESCRIPTION
             "This control sets the bandwidth of the transmit and 
             receive radio channels"  
      ::= { configuration 11 } 
 
   remoteIPAddress OBJECT-TYPE
      SYNTAX IpAddress
      ACCESS read-only
      STATUS mandatory
      DESCRIPTION
             "IP Address of the peer wireless unit"  
      ::= { configuration 12 } 
 
   linkName OBJECT-TYPE
      SYNTAX DisplayString (SIZE(0..63))
      ACCESS read-only
      STATUS mandatory
      DESCRIPTION
             "Name of the PTP link allocated by the System 
             Administrator. Used to establish a connection with the 
             correct PTP wireless unit at the other end of the link. 
             NOTE: The link name MUST be the same at both ends of the 
             PTP link."  
      ::= { configuration 14 } 
 
   siteName OBJECT-TYPE
      SYNTAX DisplayString (SIZE(0..63))
      ACCESS read-write
      STATUS mandatory
      DESCRIPTION
             "This field contains a user-provided description of the 
             site name together with any additional notes"  
      ::= { configuration 15 } 
 
   accessMethod OBJECT-TYPE
      SYNTAX INTEGER {
                       link-access(0),
                       link-name-access(1),
                       group-access(2)
                     }
      ACCESS read-only
      STATUS mandatory
      DESCRIPTION
             "This controls whether the link can be established 
             between pre-paired Master-Slave using MAC addresses (Link 
             Access) or by using link name (Link Name Access)"  
      ::= { configuration 16 } 
 
   groupID OBJECT-TYPE
      SYNTAX INTEGER (0..255)
      ACCESS read-only
      STATUS mandatory
      DESCRIPTION
             "When Access Method is set to Group Access, the Group ID 
             identifies all the units belonging to the same group. 
             Group Access is only supported on some platforms"  
      ::= { configuration 17 } 
 
   -- Ethernet group attribute definitions 
   --
   dataPortAutoNegotiation OBJECT-TYPE
      SYNTAX INTEGER {
                       disabled(0),
                       enabled(1)
                     }
      ACCESS read-write
      STATUS mandatory
      DESCRIPTION
             "This controls whether the local Ethernet interface 
             configuration is automatically negotiated or forced. Do 
             not use a forced setting together with auto negotiation 
             at the Ethernet link partner. If you want to run your 
             Ethernet link at a fixed speed and duplex then you would 
             normally leave auto negotiation enabled and only enable 
             the single Auto Neg Advertisement option that you want 
             the link to run in - FORCING ETHERNET CONFIGURATION IS A 
             LAST RESORT WHICH SHOULD ONLY BE PERFORMED IF YOU ARE 
             HAVING PROBLEMS WITH AUTO NEGOTIATION - AND YOU MUST 
             ENSURE THAT YOU CONFIGURE BOTH THIS UNIT AND THE ETHERNET 
             LINK PARTNER TO WHICH IT IS CONNECTED IDENTICALLY (THE 
             LINK PARTNER MUST NOT HAVE AUTO NEGOTIATION ENABLED 
             EITHER, OTHERWISE A DUPLEX MISMATCH WILL OCCUR). NB: The 
             new setting will only take effect after a system reboot."  
      ::= { ethernet 1 } 
 
   dataPortAutoNegAdvertisement OBJECT-TYPE
      SYNTAX BITS {
                    neg-invalid(2),
                    neg-10-mbps-half-duplex(3),
                    neg-10-mbps-full-duplex(4),
                    neg-100-mbps-half-duplex(5),
                    neg-100-mbps-full-duplex(6),
                    neg-unknown-1(7)
                  }
      ACCESS read-write
      STATUS mandatory
      DESCRIPTION
             "This sets the different Ethernet configurations that 
             will be advertised during auto negotiation. NB: The new 
             setting will only take effect after a system reboot. 
             WARNING: Duplex mismatch may result if both ends of the 
             Ethernet link do not have the same settings. Do not auto 
             negotiation together with a fixed setting at the Ethernet 
             link partner. WARNING: Make sure that you select 
             option(s) that you know your connected equipment can 
             cater for!"  
      ::= { ethernet 2 } 
 
   dataPortAutoMdix OBJECT-TYPE
      SYNTAX INTEGER {
                       disabled(0),
                       enabled(1)
                     }
      ACCESS read-write
      STATUS mandatory
      DESCRIPTION
             "This enables/disables the Auto MDI/MDIX capability. NB: 
             The new setting will only take effect after a system 
             reboot"  
      ::= { ethernet 3 } 
 
   dataPortStatus OBJECT-TYPE
      SYNTAX INTEGER {
                       down(0),
                       copper-link-up(1),
                       fiber-link-up(2)
                     }
      ACCESS read-only
      STATUS mandatory
      DESCRIPTION
             "Current status of the Ethernet link. NB: a change of 
             state may generate an SNMP trap and/or SMTP email alert"  
      ::= { ethernet 4 } 
 
   dataPortSpeedAndDuplex OBJECT-TYPE
      SYNTAX INTEGER {
                       speed-1000-mbps-full-duplex(0),
                       speed-100-mbps-full-duplex(1),
                       speed-100-mbps-half-duplex(2),
                       speed-10-mbps-full-duplex(3),
                       speed-10-mbps-half-duplex(4),
                       speed-unknown-6(5)
                     }
      ACCESS read-only
      STATUS mandatory
      DESCRIPTION
             "The current speed and duplex of the Ethernet link"  
      ::= { ethernet 5 } 
 
   dataPortWirelessDownAlert OBJECT-TYPE
      SYNTAX INTEGER {
                       disabled(0),
                       enabled(1)
                     }
      ACCESS read-write
      STATUS mandatory
      DESCRIPTION
             "When enabled, this causes the Ethernet link to be 
             dropped briefly when the wireless link drops. This is so 
             that spanning tree algorithms can quickly detect that 
             there is a problem."  
      ::= { ethernet 6 } 
 
   useVLANForManagementInterfaces OBJECT-TYPE
      SYNTAX INTEGER {
                       no-vlan-tagging(0),
                       ieee-8021q-tagged-c-tag-type-8100(1),
                       ieee-8021ad-tagged-s-tag-or-b-tag-type-88a8(2)
                     }
      ACCESS read-write
      STATUS mandatory
      DESCRIPTION
             "This controls whether the management interfaces 
             (WWW/SNMP/SMTP/SNTP) use VLAN tags or not. NB: The new 
             setting will only take effect after a system reboot"  
      ::= { ethernet 7 } 
 
   vLANManagementPriority OBJECT-TYPE
      SYNTAX INTEGER (0..7)
      ACCESS read-write
      STATUS mandatory
      DESCRIPTION
             "This VLAN Priority (0-7) will be included in packets 
             generated by the management interfaces. NB: The new 
             setting will only take effect after a system reboot"  
      ::= { ethernet 8 } 
 
   vLANManagementVID OBJECT-TYPE
      SYNTAX INTEGER (0..4094)
      ACCESS read-write
      STATUS mandatory
      DESCRIPTION
             "This VLAN VID (0-4094) will be included in packets 
             generated by the management interfaces. NB: The new 
             setting will only take effect after a system reboot"  
      ::= { ethernet 11 } 
 
   vLANPriorityTableNumber OBJECT-TYPE
      SYNTAX INTEGER (9)
      ACCESS read-only
      STATUS mandatory
      DESCRIPTION
             "Number of entries in the vLANPriorityTable."  
      ::= { ethernet 14 } 
 
   -- VLANPriorityTable group attribute definitions 
   --
   vLANPriorityQueueMapping OBJECT-TYPE
      SYNTAX INTEGER {
                       q0(0),
                       q1(1),
                       q2(2),
                       q3(3),
                       q4(4),
                       q5(5),
                       q6(6),
                       q7(7)
                     }
      ACCESS read-write
      STATUS mandatory
      DESCRIPTION
             "Mapping of VLAN priority flag to packet queue. The 
             higher the queue number the greater its priority."  
      ::= { vLANPriorityTableEntry 1 } 
 
   vLANPriorityTableIndex OBJECT-TYPE
      SYNTAX INTEGER {
                       p0(1),
                       p1(2),
                       p2(3),
                       p3(4),
                       p4(5),
                       p5(6),
                       p6(7),
                       p7(8),
                       untagged(9)
                     }
      ACCESS not-accessible
      STATUS mandatory
      DESCRIPTION
             "VLAN priority flag, used to index values in the 
             vLANPriorityTable."  
      ::= { vLANPriorityTableEntry 2 } 
 
   -- Telecom group attribute definitions 
   --
   telecomsInterface OBJECT-TYPE
      SYNTAX INTEGER {
                       none(0),
                       e1(1),
                       t1(2)
                     }
      ACCESS read-only
      STATUS mandatory
      DESCRIPTION
             "The line interface type. If this is set to 'None' then 
             the telecoms interfaces are disabled, and the telecom 
             group attributes will be ignored."  
      ::= { telecom 1 } 
 
   telecomsChannelStatus OBJECT-TYPE
      SYNTAX INTEGER {
                       disabled(0),
                       no-signal-local(1),
                       no-signal-remote(2),
                       no-signal-local-and-remote(3),
                       up(4),
                       remote-timing(5),
                       no-signal-local-and-remote-timing(6)
                     }
      ACCESS read-only
      STATUS mandatory
      DESCRIPTION
             "Current status of telecoms channel. NB: a change of 
             state may generate an SNMP trap and/or SMTP email alert"  
      ::= { telecom 2 } 
 
   telecomsLineCode OBJECT-TYPE
      SYNTAX INTEGER {
                       ami(0),
                       b8zshdb3(1)
                     }
      ACCESS read-only
      STATUS mandatory
      DESCRIPTION
             "The line code setting of the telecoms interface. This 
             must match the setting of the device connected to this 
             interface"  
      ::= { telecom 4 } 
 
   telecomsCableLength OBJECT-TYPE
      SYNTAX INTEGER {
                       feet-133(0),
                       feet-266(1),
                       feet-399(2),
                       feet-533(3),
                       feet-655(4)
                     }
      ACCESS read-only
      STATUS mandatory
      DESCRIPTION
             "The length of the cable connected to the telecoms 
             interface, measured in feet"  
      ::= { telecom 6 } 
 
   telecomsLoopback OBJECT-TYPE
      SYNTAX INTEGER {
                       none(0),
                       copper(1),
                       wireless(2)
                     }
      ACCESS read-only
      STATUS mandatory
      DESCRIPTION
             "The loopback status of telecoms channel. This is 
             intended for installation testing and should be set to 
             'None' for normal operation. The wire connections to a 
             unit can be tested by applying a 'Copper' loopback to the 
             local unit. The wireless connection to the remote unit 
             can be tested by applying a 'Wireless' loopback to the 
             remote unit with no loopback on the local unit. When 
             applying a wireless loopback, please ensure that the 
             other end of the link has a loopback setting of 'None'. 
             NB: a change of state may generate an SNMP trap and/or 
             SMTP email alert"  
      ::= { telecom 8 } 
 
   -- Licence group attribute definitions 
   --
   regionCode OBJECT-TYPE
      SYNTAX INTEGER {
                       region-code-invalid(0),
                       region-code-1(1),
                       region-code-2(2),
                       region-code-3(3),
                       region-code-4(4),
                       region-code-5(5),
                       region-code-6(6),
                       region-code-7(7),
                       region-code-8(8),
                       region-code-9(9),
                       region-code-10(10),
                       region-code-11(11),
                       region-code-12(12),
                       region-code-13(13),
                       region-code-14(14),
                       region-code-15(15),
                       region-code-16(16),
                       region-code-17(17),
                       region-code-18(18),
                       region-code-19(19),
                       region-code-20(20),
                       region-code-21(21),
                       region-code-22(22),
                       region-code-23(23),
                       region-code-24(24),
                       region-code-25(25),
                       region-code-26(26),
                       region-code-27(27),
                       region-code-28(28),
                       region-code-29(29),
                       region-code-30(30),
                       region-code-31(31)
                     }
      ACCESS read-only
      STATUS mandatory
      DESCRIPTION
             "The region code prohibits the wireless unit from 
             operating outside the regulated limits. An invalid region 
             code indicates a corrupted licence key. NB: a change of 
             state may generate an SNMP trap and/or SMTP email alert"  
      ::= { licence 1 } 
 
   productVariant OBJECT-TYPE
      SYNTAX INTEGER {
                       ptp-xx400-full(0),
                       ptp-xx400-deprecated-1(1),
                       ptp-xx400-deprecated-2(2),
                       ptp-xx400-lite(3),
                       spare-1(4),
                       ptp-xx300(5),
                       spare-2(6),
                       spare-3(7),
                       ptp-xx500-full-deprecated(8),
                       ptp-xx500-lite-deprecated(9),
                       ptp-xx500(10),
                       ptp-xx600-lite(11),
                       ptp-xx600-full(12),
                       spare-5(13),
                       spare-6(14),
                       ptp-800(15)
                     }
      ACCESS read-only
      STATUS mandatory
      DESCRIPTION
             "The product variant"  
      ::= { licence 2 } 
 
   productName OBJECT-TYPE
      SYNTAX DisplayString (SIZE(0..63))
      ACCESS read-only
      STATUS mandatory
      DESCRIPTION
             "Name of the product variant"  
      ::= { licence 3 } 
 
   ethernetFiberSupport OBJECT-TYPE
      SYNTAX INTEGER {
                       disabled(0),
                       enabled(1)
                     }
      ACCESS read-only
      STATUS mandatory
      DESCRIPTION
             "Ethernet fiber support availability on this wireless 
             unit"  
      ::= { licence 4 } 
 
   frequencyVariant OBJECT-TYPE
      SYNTAX INTEGER {
                       freq-5800-mhz(0),
                       freq-5400-mhz(1),
                       freq-4900-mhz(2),
                       freq-2500-mhz(3),
                       freq-5800-mhz2(4),
                       freq-5400-mhz2(5),
                       freq-4500-mhz(6),
                       freq-5900-mhz(7),
                       freq-5200-mhz(8),
                       freq-5100-mhz(9),
                       freq-4800-mhz(10)
                     }
      ACCESS read-only
      STATUS mandatory
      DESCRIPTION
             "Frequency variant of the wireless unit"  
      ::= { licence 5 } 
 
   bandwidthVariant OBJECT-TYPE
      SYNTAX INTEGER {
                       bw-30-mhz(0),
                       bw-15-mhz(1),
                       bw-10-mhz(2),
                       bw-5-mhz(3),
                       bw-20-mhz(4)
                     }
      ACCESS read-only
      STATUS mandatory
      DESCRIPTION
             "Bandwidth variant of the wireless unit"  
      ::= { licence 6 } 
 
   constantPowerSpectralDensity OBJECT-TYPE
      SYNTAX INTEGER {
                       constant(0),
                       full-power(1)
                     }
      ACCESS read-only
      STATUS mandatory
      DESCRIPTION
             "Constant power spectral density mode control"  
      ::= { licence 7 } 
 
   sNMPv3Enable OBJECT-TYPE
      SYNTAX INTEGER {
                       disabled(0),
                       enabled(1)
                     }
      ACCESS read-only
      STATUS mandatory
      DESCRIPTION
             "SNMPv3 availability control"  
      ::= { licence 9 } 
 
   licensedCapacity OBJECT-TYPE
      SYNTAX INTEGER {
                       capacity-25-mbps(0),
                       capacity-52-mbps(1),
                       capacity-105-mbps(2)
                     }
      ACCESS read-only
      STATUS mandatory
      DESCRIPTION
             "Maximum allowable data rate for ethernet frames 
             permitted by the licence key. The actual data rate 
             depends upon the prevailing wireless conditions"  
      ::= { licence 11 } 
 
   -- Management group attribute definitions 
   --
   installStatus OBJECT-TYPE
      SYNTAX INTEGER {
                       ok(0),
                       wrong-peer(1)
                     }
      ACCESS read-only
      STATUS mandatory
      DESCRIPTION
             "A non-zero value indicates that signalling was received 
             with the wrong MAC address or a mismatched link name. NB: 
             It is very unusual to detect this, because units with 
             mis-configured Target MAC Address will normally fail to 
             establish a wireless link. However, rare circumstances 
             may establish a partial wireless link and detect this 
             situation. NB: A non-zero value on start-up, or a change 
             of value during operation, may generate an SNMP trap 
             and/or SMTP email alert"  
      ::= { management 3 } 
 
   installArmState OBJECT-TYPE
      SYNTAX INTEGER {
                       disarmed(0),
                       armed(1)
                     }
      ACCESS read-only
      STATUS mandatory
      DESCRIPTION
             "Indicates if the unit is being installed. NB: a value 
             other than 'disarmed' on startup, or a change of state 
             during operation may generate an SNMP trap and/or SMTP 
             email alert"  
      ::= { management 4 } 
 
   tFTPServerIPAddress OBJECT-TYPE
      SYNTAX IpAddress
      ACCESS read-write
      STATUS mandatory
      DESCRIPTION
             "IP address of the TFTP Server from which the TFTP 
             Software Upgrade File Name will be retrieved"  
      ::= { management 5 } 
 
   tFTPServerPortNumber OBJECT-TYPE
      SYNTAX INTEGER (0..65535)
      ACCESS read-write
      STATUS mandatory
      DESCRIPTION
             "The port number of the TFTP Server from which the TFTP 
             Software Upgrade File Name will be retrieved"  
      ::= { management 6 } 
 
   tFTPSoftwareUpgradeFileName OBJECT-TYPE
      SYNTAX DisplayString (SIZE(0..127))
      ACCESS read-write
      STATUS mandatory
      DESCRIPTION
             "Filename of the Software Upgrade to be loaded from the 
             TFTP Server"  
      ::= { management 7 } 
 
   tFTPStartSoftwareUpgrade OBJECT-TYPE
      SYNTAX INTEGER
      ACCESS read-write
      STATUS mandatory
      DESCRIPTION
             "Write '1' to this attribute to start the TFTP software 
             upgrade process. The attribute will be reset to 0 when 
             the upgrade process has finished"  
      ::= { management 8 } 
 
   tFTPSoftwareUpgradeStatus OBJECT-TYPE
      SYNTAX INTEGER {
                       idle(0),
                       upload-in-progress(1),
                       upload-successful-programming-flash(2),
                       upgrade-successful-reboot-to-run-the-new-software-image(3),
                       upgrade-failed(4)
                     }
      ACCESS read-only
      STATUS mandatory
      DESCRIPTION
             "The current status of the TFTP Software upgrade process"  
      ::= { management 9 } 
 
   tFTPSoftwareUpgradeStatusText OBJECT-TYPE
      SYNTAX DisplayString (SIZE(0..127))
      ACCESS read-only
      STATUS mandatory
      DESCRIPTION
             "Descriptive text describing the status of the TFTP 
             Software upgrade process, including any error details"  
      ::= { management 10 } 
 
   tFTPSoftwareUpgradeStatusAdditionalText OBJECT-TYPE
      SYNTAX DisplayString (SIZE(0..127))
      ACCESS read-only
      STATUS mandatory
      DESCRIPTION
             "Any additional text describing the status of the TFTP 
             Software upgrade process, including any error details"  
      ::= { management 11 } 
 
   hTTPAccessEnabled OBJECT-TYPE
      SYNTAX INTEGER {
                       no(0),
                       yes(1)
                     }
      ACCESS read-write
      STATUS mandatory
      DESCRIPTION
             "This controls whether or not HTTP access is enabled, 
             i.e. if this is disabled (0) then the unit will not 
             respond to any requests on the HTTP port. Remote 
             management via HTTPS is not affected by this setting. Any 
             change in this setting will not take effect until the 
             unit has been rebooted. (Factory default = Enabled)"  
      ::= { management 12 } 
 
   telnetAccessEnabled OBJECT-TYPE
      SYNTAX INTEGER {
                       no(0),
                       yes(1)
                     }
      ACCESS read-write
      STATUS mandatory
      DESCRIPTION
             "This controls whether or not Telnet access is enabled, 
             i.e. if this is disabled (0) then the unit will not 
             respond to any requests on the TELNET port. Any change in 
             this setting will not take effect until the unit has been 
             rebooted. (Factory default = Disabled)"  
      ::= { management 13 } 
 
   hTTPPortNumber OBJECT-TYPE
      SYNTAX INTEGER (0..65535)
      ACCESS read-write
      STATUS mandatory
      DESCRIPTION
             "This controls the port number for HTTP access. A value 
             of zero will use the default port number. Any change in 
             this setting will not take effect until the unit has been 
             rebooted. (Factory default = 80)"  
      ::= { management 14 } 
 
   hTTPSPortNumber OBJECT-TYPE
      SYNTAX INTEGER (0..65535)
      ACCESS read-write
      STATUS mandatory
      DESCRIPTION
             "This controls the port number for HTTPS access. A value 
             of zero will use the default port number. Availability of 
             HTTPS is controlled via the Licence Key. Any change in 
             this setting will not take effect until the unit has been 
             rebooted. (Factory default = 443)"  
      ::= { management 15 } 
 
   telnetPortNumber OBJECT-TYPE
      SYNTAX INTEGER (0..65535)
      ACCESS read-write
      STATUS mandatory
      DESCRIPTION
             "This controls the port number for TELNET access. A value 
             of zero will use the default port number. Any change in 
             this setting will not take effect until the unit has been 
             rebooted. (Factory default = 23)"  
      ::= { management 16 } 
 
   hTTPSAccessEnabled OBJECT-TYPE
      SYNTAX INTEGER {
                       no(0),
                       yes(1)
                     }
      ACCESS read-write
      STATUS mandatory
      DESCRIPTION
             "This controls whether or not HTTPS access is enabled, 
             i.e. if this is disabled (0) then the unit will not 
             respond to any requests on the HTTPS port. Remote 
             management via HTTP is not affected by this setting. Any 
             change in this setting will not take effect until the 
             unit has been rebooted. (Factory default = Enabled)"  
      ::= { management 17 } 
 
   -- PhyControl group attribute definitions 
   --
   linkSymmetry OBJECT-TYPE
      SYNTAX INTEGER {
                       symmetry-adaptive(0),
                       symmetry-3-to-1(1),
                       symmetry-1-to-1(2),
                       symmetry-1-to-3(3)
                     }
      ACCESS read-only
      STATUS mandatory
      DESCRIPTION
             "In fixed asymmetric mode (3 to 1) the transmit time is 
             three times as long as the receive time. In fixed 
             symmetric mode (1 to 1) the unit spends an equal amount 
             of time transmitting and receiving. In fixed asymmetric 
             mode (1 to 3) the receive time is three times as long as 
             the transmit time. In adaptive mode the transmit and 
             receive periods adjust with applied load. NB: only 
             applicable for master nodes."  
      ::= { phyControl 1 } 
 
   linkModeOptimisation OBJECT-TYPE
      SYNTAX INTEGER {
                       ip-traffic(0),
                       tdm-traffic(1)
                     }
      ACCESS read-only
      STATUS mandatory
      DESCRIPTION
             "Optimises the wireless link behavior for the type of 
             traffic to be carried. In 'IP Traffic' mode, the wireless 
             link will minimise transmission errors by automatically 
             adapting the modulation mode. In 'TDM Traffic' mode, the 
             wireless link will minimise transmission latency and 
             preserve throughput by maintaining a higher modulation 
             mode in the presence of a limited number of errors. The 
             'TDM Traffic' mode is recommended for E1/T1 applications 
             and connectionless protocols."  
      ::= { phyControl 2 } 
 
   userConfiguredMaxModulationMode OBJECT-TYPE
      SYNTAX INTEGER {
                       mod-bpsk-50-percent(0),
                       mod-qpsk-50-percent(1),
                       mod-qpsk-75-percent(2),
                       mod-16qam-50-percent(3),
                       mod-16qam-75-percent(4),
                       mod-64qam-67-percent(5),
                       mod-64qam-83-percent(6)
                     }
      ACCESS read-write
      STATUS mandatory
      DESCRIPTION
             "The maximum receive modulation mode controls the MAX 
             mode used for adaptive modulation. NOTE: This attribute 
             is automatically disabled when the installation agent is 
             armed. To disarm the installation agent use the 
             installation wizard"  
      ::= { phyControl 3 } 
 
   remoteMaximumTransmitPower OBJECT-TYPE
      SYNTAX INTEGER (-100..27)
      ACCESS read-only
      STATUS mandatory
      DESCRIPTION
             "Maximum transmit power the remote wireless unit is 
             permitted to use when establishing and maintaining the 
             wireless link"  
      ::= { phyControl 4 } 
 
   -- PhyStatus group attribute definitions 
   --
   receivePower OBJECT-TYPE
      SYNTAX INTEGER
      ACCESS read-only
      STATUS mandatory
      DESCRIPTION
             "Receive power expressed in tenths of a dBm"  
      ::= { phyStatus 1 } 
 
   vectorError OBJECT-TYPE
      SYNTAX INTEGER
      ACCESS read-only
      STATUS mandatory
      DESCRIPTION
             "The vector error measurement compares the received 
             signal's IQ modulation characteristics to an ideal signal 
             to determine the composite error vector magnitude. The 
             value represented by this attribute is the average vector 
             error over the previous second expressed in tenths of a 
             dB"  
      ::= { phyStatus 2 } 
 
   transmitPower OBJECT-TYPE
      SYNTAX INTEGER
      ACCESS read-only
      STATUS mandatory
      DESCRIPTION
             "Transmit power expressed in tenths of a dBm"  
      ::= { phyStatus 3 } 
 
   range OBJECT-TYPE
      SYNTAX INTEGER
      ACCESS read-only
      STATUS mandatory
      DESCRIPTION
             "Distance between the two peer wireless units expressed 
             in tenths of a kilometer"  
      ::= { phyStatus 4 } 
 
   linkLoss OBJECT-TYPE
      SYNTAX INTEGER (-500..500)
      ACCESS read-only
      STATUS mandatory
      DESCRIPTION
             "The wireless link loss expressed in tenths of a dB"  
      ::= { phyStatus 5 } 
 
   receiveChannel OBJECT-TYPE
      SYNTAX INTEGER (0..63)
      ACCESS read-only
      STATUS mandatory
      DESCRIPTION
             "Current active receive channel"  
      ::= { phyStatus 6 } 
 
   transmitChannel OBJECT-TYPE
      SYNTAX INTEGER (0..63)
      ACCESS read-only
      STATUS mandatory
      DESCRIPTION
             "Current active transmit channel"  
      ::= { phyStatus 7 } 
 
   receiveModulationMode OBJECT-TYPE
      SYNTAX INTEGER {
                       mod-acquisition(0),
                       mod-bpsk-50-percent(1),
                       mod-qpsk-50-percent-single(2),
                       mod-qpsk-75-percent-single(3),
                       mod-16qam-50-percent-single(4),
                       mod-16qam-75-percent-single(5),
                       mod-64qam-67-percent-single(6),
                       mod-64qam-83-percent-single(7),
                       mod-reserved1(8),
                       mod-qpsk-50-percent-dual(9),
                       mod-qpsk-75-percent-dual(10),
                       mod-16qam-50-percent-dual(11),
                       mod-16qam-75-percent-dual(12),
                       mod-64qam-67-percent-dual(13),
                       mod-64qam-83-percent-dual(14),
                       mod-reserved2(15)
                     }
      ACCESS read-only
      STATUS mandatory
      DESCRIPTION
             "Current active receive modulation mode"  
      ::= { phyStatus 8 } 
 
   transmitModulationMode OBJECT-TYPE
      SYNTAX INTEGER {
                       mod-acquisition(0),
                       mod-bpsk-50-percent(1),
                       mod-qpsk-50-percent-single(2),
                       mod-qpsk-75-percent-single(3),
                       mod-16qam-50-percent-single(4),
                       mod-16qam-75-percent-single(5),
                       mod-64qam-67-percent-single(6),
                       mod-64qam-83-percent-single(7),
                       mod-reserved1(8),
                       mod-qpsk-50-percent-dual(9),
                       mod-qpsk-75-percent-dual(10),
                       mod-16qam-50-percent-dual(11),
                       mod-16qam-75-percent-dual(12),
                       mod-64qam-67-percent-dual(13),
                       mod-64qam-83-percent-dual(14),
                       mod-reserved2(15)
                     }
      ACCESS read-only
      STATUS mandatory
      DESCRIPTION
             "Current active transmit modulation mode"  
      ::= { phyStatus 9 } 
 
   receiveFreqMHz OBJECT-TYPE
      SYNTAX INTEGER (0..5925)
      ACCESS read-only
      STATUS mandatory
      DESCRIPTION
             "Current receive frequency expressed in integer MHz"  
      ::= { phyStatus 11 } 
 
   transmitFreqMHz OBJECT-TYPE
      SYNTAX INTEGER (0..5925)
      ACCESS read-only
      STATUS mandatory
      DESCRIPTION
             "Current transmit frequency expressed in integer MHz"  
      ::= { phyStatus 12 } 
 
   signalStrengthRatio OBJECT-TYPE
      SYNTAX INTEGER
      ACCESS read-only
      STATUS mandatory
      DESCRIPTION
             "Signal strength ratio (Vertical / Horizontal) : the 
             number of dB larger the Vertical antenna input is than 
             the Horizontal antenna input expressed in tenths of a dB"  
      ::= { phyStatus 13 } 
 
   receiveFreqKHz OBJECT-TYPE
      SYNTAX INTEGER (0..5925000)
      ACCESS read-only
      STATUS mandatory
      DESCRIPTION
             "Current receive frequency expressed as KHz"  
      ::= { phyStatus 14 } 
 
   transmitFreqKHz OBJECT-TYPE
      SYNTAX INTEGER (0..5925000)
      ACCESS read-only
      STATUS mandatory
      DESCRIPTION
             "Current transmit frequency expressed as KHz"  
      ::= { phyStatus 15 } 
 
   searchState OBJECT-TYPE
      SYNTAX INTEGER {
                       registering(0),
                       searching(1),
                       acquiring(2),
                       registering-acquiring2(3)
                     }
      ACCESS read-only
      STATUS mandatory
      DESCRIPTION
             "Search status of the wireless modem. 'Registering' means 
             that the modem has locked to an OFDM signal, and the 
             wireless link is up. 'Searching' means that no wireless 
             signal has been detected. 'Acquiring' means that a 
             wireless signal has been detected, but the modem has not 
             locked to an OFDM signal."  
      ::= { phyStatus 16 } 
 
   -- Alarms group attribute definitions 
   --
   unitOutOfCalibration OBJECT-TYPE
      SYNTAX INTEGER {
                       calibrated(0),
                       partial-calibration(1),
                       invalid-calibration(2),
                       bandwidth-variant-unsupported-pas-shutdown(3),
                       out-of-calibration-pas-shutdown(4)
                     }
      ACCESS read-only
      STATUS mandatory
      DESCRIPTION
             "The unit is out of calibration"  
      ::= { alarms 1 } 
 
   incompatibleRegionCodes OBJECT-TYPE
      SYNTAX INTEGER {
                       ok(0),
                       incompatible-licence-keys(1)
                     }
      ACCESS read-only
      STATUS mandatory
      DESCRIPTION
             "The master and slave units have incompatible region 
             codes. NB: Both units must have compatible licence keys"  
      ::= { alarms 4 } 
 
   noWirelessChannelAvailable OBJECT-TYPE
      SYNTAX INTEGER {
                       ok(0),
                       no-wireless-channel-available(1)
                     }
      ACCESS read-only
      STATUS mandatory
      DESCRIPTION
             "Spectrum Management was unable to locate a suitable 
             wireless channel to operate on"  
      ::= { alarms 5 } 
 
   wirelessLinkDisabledWarning OBJECT-TYPE
      SYNTAX INTEGER {
                       ok(0),
                       disabled-by-snmp-ifadminstatus(1)
                     }
      ACCESS read-only
      STATUS mandatory
      DESCRIPTION
             "The SNMP ifAdminStatus of the wireless interface has 
             disabled wireless traffic"  
      ::= { alarms 6 } 
 
   dataPortDisabledWarning OBJECT-TYPE
      SYNTAX INTEGER {
                       ok(0),
                       disabled-by-snmp-ifadminstatus(1)
                     }
      ACCESS read-only
      STATUS mandatory
      DESCRIPTION
             "The SNMP ifAdminStatus of the Ethernet interface has 
             disabled Ethernet traffic"  
      ::= { alarms 7 } 
 
   dataPortConfigurationMismatch OBJECT-TYPE
      SYNTAX INTEGER {
                       no-error(0),
                       mismatch-detected(1)
                     }
      ACCESS read-only
      STATUS mandatory
      DESCRIPTION
             "The detection of Ethernet fragments (runt packets) when 
             the link is in full duplex is an indication of an 
             auto-negotiation or forced configuration mismatch"  
      ::= { alarms 9 } 
 
   incompatibleMasterAndSlave OBJECT-TYPE
      SYNTAX INTEGER {
                       ok(0),
                       incompatible-product-variants(1),
                       different-software-versions-running(2)
                     }
      ACCESS read-only
      STATUS mandatory
      DESCRIPTION
             "A non-zero value indicates that the master and slave 
             ends of a link are different hardware products, or have 
             different software versions. NB: It is very unusual to 
             detect this, because incompatible units will normally 
             fail to establish a wireless link. However, some 
             combinations may establish a partial wireless link and 
             detect this situation. NB: A non-zero value may generate 
             an SNMP trap and/or SMTP email alert"  
      ::= { alarms 10 } 
 
   tDDSynchronizationStatus OBJECT-TYPE
      SYNTAX INTEGER {
                       locked(0),
                       holdover(1),
                       holdover-not-connected(2),
                       acquiring-lock(3),
                       no-timing-reference(4),
                       timing-system-not-connected(5),
                       initialising(6),
                       cluster-timing-master(7),
                       tdd-sync-not-active(8)
                     }
      ACCESS read-only
      STATUS mandatory
      DESCRIPTION
             "An alarm value (displayed in red) indicates that one of 
             the following conditions has not been met (i) An external 
             timing system is connected or internal timing has been 
             configured. (ii) The timing system is providing a useable 
             reference. (iii) The ODU is locked to this reference."  
      ::= { alarms 11 } 
 
   tDDSynchronizationAlarm OBJECT-TYPE
      SYNTAX INTEGER {
                       ok(0),
                       not-synchronized(1),
                       timing-system-failure(2)
                     }
      ACCESS read-only
      STATUS mandatory
      DESCRIPTION
             "Not Synchronized indicates failure of the external 
             timing system for a period greater than the holdover 
             timer. TDD frame timing will have drifted, and this link 
             may cause interference with other links in a synchronized 
             network. Timing System Failure is an early warning, 
             indicating that 80% of the holdover period has expired."  
      ::= { alarms 13 } 
 
   linkModeOptimizationMismatch OBJECT-TYPE
      SYNTAX INTEGER {
                       ok(0),
                       link-mode-optimization-mismatch(1)
                     }
      ACCESS read-only
      STATUS mandatory
      DESCRIPTION
             "The remote node of this link has been configured with a 
             different link mode optimization"  
      ::= { alarms 14 } 
 
   capacityLicenseMismatch OBJECT-TYPE
      SYNTAX INTEGER {
                       ok(0),
                       mismatch-detected(1)
                     }
      ACCESS read-only
      STATUS mandatory
      DESCRIPTION
             "The local and remote units have different licensed 
             capacity and/or the full capacity trial has been 
             activated at only one unit. The wireless link is 
             operating at the capacity of the lowest capacity unit"  
      ::= { alarms 16 } 
 
   -- Smtp group attribute definitions 
   --
   sMTPEmailAlert OBJECT-TYPE
      SYNTAX INTEGER {
                       disabled(0),
                       enabled(1)
                     }
      ACCESS read-write
      STATUS mandatory
      DESCRIPTION
             "Simple Mail Transfer Protocol is used to send equipment 
             alerts via email to a specified email address. This 
             utility can only be configured by the system 
             administrator"  
      ::= { smtp 1 } 
 
   sMTPServerIPAddress OBJECT-TYPE
      SYNTAX IpAddress
      ACCESS read-write
      STATUS mandatory
      DESCRIPTION
             "IP address of the SMTP server"  
      ::= { smtp 2 } 
 
   sMTPServerPortNumber OBJECT-TYPE
      SYNTAX INTEGER (0..65535)
      ACCESS read-write
      STATUS mandatory
      DESCRIPTION
             "Port number of the SMTP server"  
      ::= { smtp 3 } 
 
   sMTPSourceEmailAddress OBJECT-TYPE
      SYNTAX DisplayString (SIZE(0..63))
      ACCESS read-write
      STATUS mandatory
      DESCRIPTION
             "The 'from' email address used when constructing the 
             automatically generated e-mail message"  
      ::= { smtp 4 } 
 
   sMTPDestinationEmailAddress OBJECT-TYPE
      SYNTAX DisplayString (SIZE(0..63))
      ACCESS read-write
      STATUS mandatory
      DESCRIPTION
             "The 'to' email address used when constructing the 
             automatically generated e-mail message"  
      ::= { smtp 5 } 
 
   sMTPEnabledMessages OBJECT-TYPE
      SYNTAX BITS {
                    telecoms-channel-up-down(1),
                    unknown-6(2),
                    data-port-up-down(3),
                    enabled-diagnostic-alarms(4),
                    dfs-impulse-interference(5),
                    channel-change(6),
                    wireless-link-up-down(7)
                  }
      ACCESS read-write
      STATUS mandatory
      DESCRIPTION
             "This controls which SMTP messages the unit will send"  
      ::= { smtp 6 } 
 
   -- SnmpControl group attribute definitions 
   --
   sNMPPortNumber OBJECT-TYPE
      SYNTAX INTEGER (0..65535)
      ACCESS read-write
      STATUS mandatory
      DESCRIPTION
             "The IP port number used to access the SNMP MIB (i.e. 
             Gets and Sets) (default = 161). NB: A system reboot is 
             required to activate changes to this attribute"  
      ::= { snmpControl 1 } 
 
   sNMPCommunityString OBJECT-TYPE
      SYNTAX DisplayString (SIZE(0..63))
      ACCESS read-write
      STATUS mandatory
      DESCRIPTION
             "The SNMP community string. NB: A system reboot is 
             required to activate changes to this attribute"  
      ::= { snmpControl 2 } 
 
   sNMPTrapTableNumber OBJECT-TYPE
      SYNTAX INTEGER (2)
      ACCESS read-only
      STATUS mandatory
      DESCRIPTION
             "Number of entries in the sNMPTrapTable."  
      ::= { snmpControl 3 } 
 
   sNMPTrapVersion OBJECT-TYPE
      SYNTAX INTEGER {
                       v1(0),
                       v2c(1)
                     }
      ACCESS read-write
      STATUS mandatory
      DESCRIPTION
             "The SNMP protocol version to use for SNMP Traps. NB: A 
             system reboot is required to activate changes to this 
             attribute"  
      ::= { snmpControl 5 } 
 
   sNMPEnabledTraps OBJECT-TYPE
      SYNTAX BITS {
                    unknown-8(0),
                    data-port-up-down(1),
                    authentication-failure(2),
                    enabled-diagnostic-alarms(3),
                    dfs-impulse-interference(4),
                    channel-change(5),
                    wireless-link-up-down(6),
                    cold-start(7),
                    telecoms-channel-up-down(15)
                  }
      ACCESS read-write
      STATUS mandatory
      DESCRIPTION
             "This controls which SNMP Traps the unit will send"  
      ::= { snmpControl 6 } 
 
   enabledDiagnosticAlarms OBJECT-TYPE
      SYNTAX BITS {
                    incompatible-master-and-slave(0),
                    incompatible-region-codes(1),
                    unknown-6(2),
                    unknown-5(3),
                    unit-out-of-calibration(4),
                    install-arm-state(5),
                    install-status(6),
                    region-code(7),
                    telecoms-channel-status(8),
                    unknown-15(9),
                    data-port-status(10),
                    data-port-disabled-warning(11),
                    wireless-link-disabled-warning(12),
                    sntp-synchronization-failed(13),
                    no-wireless-channel-available(14),
                    data-port-configuration-mismatch(15),
                    syslog-client-disabled-warning(16),
                    licensed-capacity-mismatch(17),
                    syslog-local-wrapped(18),
                    syslog-local-nearly-full(19),
                    syslog-local-enable-disable(20),
                    link-mode-optimization-mismatch(21),
                    tdd-synchronization-alarm(22),
                    telecoms-channel-loopback(23)
                  }
      ACCESS read-write
      STATUS mandatory
      DESCRIPTION
             "Controls which individual diagnostic alarms are enabled. 
             The unit may be configured to generate SNMP traps and/or 
             SMTP email alerts for these enabled alarms by selecting 
             'Enabled Diagnostic Alarms' on the 'SNMP Enabled Traps' 
             and/or 'SMTP Enabled Messages' attributes"  
      ::= { snmpControl 7 } 
 
   sNMPSendAllTrapsAtStartup OBJECT-TYPE
      SYNTAX INTEGER {
                       disabled(0),
                       enabled(1)
                     }
      ACCESS read-write
      STATUS mandatory
      DESCRIPTION
             "Controls whether cleared traps are reported at start-up 
             as well as raised traps. Only enabled traps will be 
             reported. NB: Traps corresponding to transient events 
             (i.e. not associated with an alarm or status value) are 
             only sent when required and not at start-up."  
      ::= { snmpControl 8 } 
 
   -- SNMPTrapTable group attribute definitions 
   --
   sNMPTrapTableIndex OBJECT-TYPE
      SYNTAX INTEGER (1..2)
      ACCESS not-accessible
      STATUS mandatory
      DESCRIPTION
             "SNMP trap value, used to index the SNMPTrapTable."  
      ::= { sNMPTrapTableEntry 1 } 
 
   sNMPTrapIPAddress OBJECT-TYPE
      SYNTAX IpAddress
      ACCESS read-write
      STATUS mandatory
      DESCRIPTION
             "The IP address to which all SNMP Traps are sent. An IP 
             Address of 0.0.0.0 disables all TRAP generation. NB: A 
             system reboot is required to activate changes to this 
             attribute."  
      ::= { sNMPTrapTableEntry 2 } 
 
   sNMPTrapPortNumber OBJECT-TYPE
      SYNTAX INTEGER (0..65535)
      ACCESS read-write
      STATUS mandatory
      DESCRIPTION
             "Destination port for SNMP Traps (default=162). A value 
             of 0 will disable the trap receiver. NB: A system reboot 
             is required to activate changes to this attribute."  
      ::= { sNMPTrapTableEntry 3 } 
 
   -- Sntp group attribute definitions 
   --
   sNTPState OBJECT-TYPE
      SYNTAX INTEGER {
                       disabled(0),
                       enabled(1)
                     }
      ACCESS read-write
      STATUS mandatory
      DESCRIPTION
             "SNTP control state"  
      ::= { sntp 1 } 
 
   sNTPServerIPAddress OBJECT-TYPE
      SYNTAX IpAddress
      ACCESS read-write
      STATUS mandatory
      DESCRIPTION
             "The IP address of a valid SNTP server"  
      ::= { sntp 2 } 
 
   sNTPServerPortNumber OBJECT-TYPE
      SYNTAX INTEGER (0..65535)
      ACCESS read-write
      STATUS mandatory
      DESCRIPTION
             "The IP port number of the SNTP server. Defaults to port 
             123."  
      ::= { sntp 3 } 
 
   sNTPPollInterval OBJECT-TYPE
      SYNTAX INTEGER (60..43200)
      ACCESS read-write
      STATUS mandatory
      DESCRIPTION
             "The SNTP server polling interval"  
      ::= { sntp 4 } 
 
   sNTPSync OBJECT-TYPE
      SYNTAX INTEGER {
                       no-sync(0),
                       in-sync(1)
                     }
      ACCESS read-only
      STATUS mandatory
      DESCRIPTION
             "If SNTP Sync fails then check the server settings in the 
             Remote Management page, or disable SNTP. NB: a change of 
             state may generate an SNMP trap and/or SMTP email alert"  
      ::= { sntp 5 } 
 
   sNTPLastSync OBJECT-TYPE
      SYNTAX INTEGER
      ACCESS read-only
      STATUS mandatory
      DESCRIPTION
             "Last SNTP sync time"  
      ::= { sntp 6 } 
 
   systemClock OBJECT-TYPE
      SYNTAX INTEGER
      ACCESS read-only
      STATUS mandatory
      DESCRIPTION
             "System clock presented as local time"  
      ::= { sntp 7 } 
 
   timeZone OBJECT-TYPE
      SYNTAX INTEGER {
                       gmt-minus-1200(0),
                       gmt-minus-1130(1),
                       gmt-minus-1100(2),
                       gmt-minus-1030(3),
                       gmt-minus-1000(4),
                       gmt-minus-0930(5),
                       gmt-minus-0900(6),
                       gmt-minus-0830(7),
                       gmt-minus-0800(8),
                       gmt-minus-0730(9),
                       gmt-minus-0700(10),
                       gmt-minus-0630(11),
                       gmt-minus-0600(12),
                       gmt-minus-0530(13),
                       gmt-minus-0500(14),
                       gmt-minus-0430(15),
                       gmt-minus-0400(16),
                       gmt-minus-0330(17),
                       gmt-minus-0300(18),
                       gmt-minus-0230(19),
                       gmt-minus-0200(20),
                       gmt-minus-0130(21),
                       gmt-minus-0100(22),
                       gmt-minus-0030(23),
                       gmt-zero(24),
                       gmt-plus-0030(25),
                       gmt-plus-0100(26),
                       gmt-plus-0130(27),
                       gmt-plus-0200(28),
                       gmt-plus-0230(29),
                       gmt-plus-0300(30),
                       gmt-plus-0330(31),
                       gmt-plus-0400(32),
                       gmt-plus-0430(33),
                       gmt-plus-0500(34),
                       gmt-plus-0530(35),
                       gmt-plus-0600(36),
                       gmt-plus-0630(37),
                       gmt-plus-0700(38),
                       gmt-plus-0730(39),
                       gmt-plus-0800(40),
                       gmt-plus-0830(41),
                       gmt-plus-0900(42),
                       gmt-plus-0930(43),
                       gmt-plus-1000(44),
                       gmt-plus-1030(45),
                       gmt-plus-1100(46),
                       gmt-plus-1130(47),
                       gmt-plus-1200(48),
                       gmt-plus-1230(49),
                       gmt-plus-1300(50)
                     }
      ACCESS read-write
      STATUS mandatory
      DESCRIPTION
             "Time zone offsets from Greenwich Mean Time (GMT)"  
      ::= { sntp 8 } 
 
   daylightSaving OBJECT-TYPE
      SYNTAX INTEGER {
                       disabled(0),
                       enabled(1)
                     }
      ACCESS read-write
      STATUS mandatory
      DESCRIPTION
             "Daylight Saving Time"  
      ::= { sntp 9 } 
 
   -- Reset group attribute definitions 
   --
   systemReset OBJECT-TYPE
      SYNTAX INTEGER {
                       running(0),
                       console-reboot(1)
                     }
      ACCESS read-write
      STATUS mandatory
      DESCRIPTION
             "Setting this attribute to '1' will cause a system 
             reboot. NB: a system reboot will apply any pending new 
             settings held in memory"  
      ::= { reset 1 } 
 
   -- Versions group attribute definitions 
   --
   softwareVersion OBJECT-TYPE
      SYNTAX DisplayString (SIZE(0..63))
      ACCESS read-only
      STATUS mandatory
      DESCRIPTION
             "Current software version"  
      ::= { versions 1 } 
 
   hardwareVersion OBJECT-TYPE
      SYNTAX DisplayString (SIZE(0..63))
      ACCESS read-only
      STATUS mandatory
      DESCRIPTION
             "Hardware platform version"  
      ::= { versions 2 } 
 
   secondarySoftwareVersion OBJECT-TYPE
      SYNTAX DisplayString (SIZE(0..63))
      ACCESS read-only
      STATUS mandatory
      DESCRIPTION
             "Secondary software version, used when the primary 
             software image is invalid or erased"  
      ::= { versions 3 } 
 
   bootVersion OBJECT-TYPE
      SYNTAX DisplayString (SIZE(0..63))
      ACCESS read-only
      STATUS mandatory
      DESCRIPTION
             "Boot code software version"  
      ::= { versions 4 } 
 
   -- PubStats group attribute definitions 
   --
   receiveDataRate OBJECT-TYPE
      SYNTAX INTEGER
      ACCESS read-only
      STATUS mandatory
      DESCRIPTION
             "Average data rate over the last one second interval 
             (kbps)"  
      ::= { pubStats 1 } 
 
   transmitDataRate OBJECT-TYPE
      SYNTAX INTEGER
      ACCESS read-only
      STATUS mandatory
      DESCRIPTION
             "Average data rate over the last one second interval 
             (kbps)"  
      ::= { pubStats 2 } 
 
   aggregateDataRate OBJECT-TYPE
      SYNTAX INTEGER
      ACCESS read-only
      STATUS mandatory
      DESCRIPTION
             "Average data rate over the last one second interval 
             (kbps)"  
      ::= { pubStats 3 } 
 
   wirelessLinkAvailability OBJECT-TYPE
      SYNTAX INTEGER (0..1000000)
      ACCESS read-only
      STATUS mandatory
      DESCRIPTION
             "Link availability calculated since the last reset of the 
             system counters, as a percentage multiplied by 10000 to 
             give four decimal places of precision"  
      ::= { pubStats 4 } 
 
   wirelessLinkStatus OBJECT-TYPE
      SYNTAX INTEGER {
                       up(0),
                       registering(1),
                       acquiring(2),
                       searching(3),
                       radar-cac(4),
                       initialising(5)
                     }
      ACCESS read-only
      STATUS mandatory
      DESCRIPTION
             "Current status of the wireless link"  
      ::= { pubStats 5 } 
 
   byteErrorRatio OBJECT-TYPE
      SYNTAX INTEGER
      ACCESS read-only
      STATUS mandatory
      DESCRIPTION
             "Reciprocal of the byte error ratio calculated since the 
             last reset of the system counters"  
      ::= { pubStats 6 } 
 
   receiveModulationModeDetail OBJECT-TYPE
      SYNTAX INTEGER {
                       running-at-maximum-receive-mode(0),
                       running-at-user-configured-max-modulation-mode(1),
                       restricted-because-installation-is-armed(2),
                       restricted-because-of-byte-errors-on-the-wireless-link(3),
                       restricted-because-the-link-parameters-are-updating(4),
                       restricted-because-channel-change-is-in-progress(5),
                       restricted-due-to-the-low-ethernet-link-speed(6),
                       running-at-maximum-receive-mode-for-channel-bandwidth(7),
                       limited-by-the-wireless-conditions(8)
                     }
      ACCESS read-only
      STATUS mandatory
      DESCRIPTION
             "The reason for the current receive modulation mode"  
      ::= { pubStats 7 } 
 
   -- Encryption group attribute definitions 
   --
   encryptionAlgorithm OBJECT-TYPE
      SYNTAX INTEGER {
                       none(0),
                       aes-rijndael(1),
                       aes-256-bit-rijndael(2)
                     }
      ACCESS read-only
      STATUS mandatory
      DESCRIPTION
             "The Encryption Algorithm used by the wireless link. NB: 
             A system reboot is required to activate changes to this 
             attribute. NB: The same Encryption Algorithm must be 
             configured at BOTH ends of the link for it to function 
             correctly"  
      ::= { encryption 1 } 
 
   -- TDDControl group attribute definitions 
   --
   tDDSynchronizationMode OBJECT-TYPE
      SYNTAX INTEGER {
                       disabled(0),
                       enabled(1)
                     }
      ACCESS read-only
      STATUS mandatory
      DESCRIPTION
             "TDD Synchronization Mode selection"  
      ::= { tDDControl 1 } 
 
   -- AAAControl group attribute definitions 
   --
   userTableNumber OBJECT-TYPE
      SYNTAX INTEGER (1..10)
      ACCESS read-only
      STATUS mandatory
      DESCRIPTION
             "Number of entries in the userTable"  
      ::= { aAAControl 1 } 
 
   -- UserTable group attribute definitions 
   --
   userTableIndex OBJECT-TYPE
      SYNTAX INTEGER (1..10)
      ACCESS not-accessible
      STATUS mandatory
      DESCRIPTION
             "used to index values in the userTable."  
      ::= { userTableEntry 1 } 
 
   userName OBJECT-TYPE
      SYNTAX OCTET STRING
      ACCESS read-only
      STATUS no-config-playback
      DESCRIPTION
             "User name which must be entered, along with the 
             appropriate password, in order to gain access to the 
             system."  
      ::= { userTableEntry 2 } 
 
   userRole OBJECT-TYPE
      SYNTAX INTEGER {
                       read-only(0),
                       system-administrator(1),
                       security-officer(2)
                     }
      ACCESS read-only
      STATUS no-config-playback
      DESCRIPTION
             "Role of the selected user. A Security Officer has access 
             to and can modify all settings. A System Administrator 
             has access to and can modify all non-security settings. A 
             Read Only user can view settings, but cannot make any 
             changes."  
      ::= { userTableEntry 3 } 
 
   userEnabled OBJECT-TYPE
      SYNTAX INTEGER {
                       disabled(0),
                       enabled(1)
                     }
      ACCESS read-only
      STATUS no-config-playback
      DESCRIPTION
             "Enable / Disable the selected user"  
      ::= { userTableEntry 4 } 
 
   userPassword OBJECT-TYPE
      SYNTAX OCTET STRING
      ACCESS read-write
      STATUS no-config-playback
      DESCRIPTION
             "User password, which must be entered in order to gain 
             access to the system."  
      ::= { userTableEntry 5 } 
 
   -- SyslogControl group attribute definitions 
   --
   syslogClient OBJECT-TYPE
      SYNTAX INTEGER {
                       disabled(0),
                       enabled(1)
                     }
      ACCESS read-only
      STATUS mandatory
      DESCRIPTION
             "Enable or disable the syslog client"  
      ::= { syslogControl 1 } 
 
   syslogState OBJECT-TYPE
      SYNTAX INTEGER {
                       disabled(0),
                       enabled(1)
                     }
      ACCESS read-only
      STATUS mandatory
      DESCRIPTION
             "The syslog service has been enabled or disabled"  
      ::= { syslogControl 2 } 
 
   -- Supplementary group attribute definitions 
   --
   longitude OBJECT-TYPE
      SYNTAX DisplayString (SIZE(0..19))
      ACCESS read-write
      STATUS mandatory
      DESCRIPTION
             "The longitude of the unit, measured in decimal degrees. 
             This object is set by the SNMP manager and has no 
             internal function."  
      ::= { supplementary 1 } 
 
   latitude OBJECT-TYPE
      SYNTAX DisplayString (SIZE(0..19))
      ACCESS read-write
      STATUS mandatory
      DESCRIPTION
             "The latitude of the unit, measured in decimal degrees. 
             This object is set by the SNMP manager and has no 
             internal function."  
      ::= { supplementary 2 } 
 
   altitude OBJECT-TYPE
      SYNTAX INTEGER
      ACCESS read-write
      STATUS mandatory
      DESCRIPTION
             "The altitude of the unit, measured in metres. This 
             object is set by the SNMP manager and has no internal 
             function."  
      ::= { supplementary 3 } 
 
   -- Enterprise TRAP definitions
   --

   channelChangeTrap TRAP-TYPE
      ENTERPRISE ptpTraps
      VARIABLES { receiveChannel }
      DESCRIPTION "The PTP radio has changed wireless channel.
                 This has been caused by either
                 i) mandatory radar avoidance,
                    a DFS impulsive interference event will also be
                    detected,
                 or
                 ii) Dynamic Spectrum Optimization, (DSO)
                     DSO improves link performance by selecting the
                     most appropriate transmit and receive channels
                     with the lowest level of interference."
      ::= 1

   dfsImpulsiveInterferenceTrap TRAP-TYPE
      ENTERPRISE ptpTraps
      VARIABLES { receiveChannel }
      DESCRIPTION "DFS impulsive interference detected event"
      ::= 2

   dataPortStatusTrap TRAP-TYPE
      ENTERPRISE ptpTraps
      VARIABLES { dataPortStatus }
      DESCRIPTION
             "Current status of the Ethernet link. NB: a change of 
             state may generate an SNMP trap and/or SMTP email alert"  
      ::= 3

   telecomsChannelStatusTrap TRAP-TYPE
      ENTERPRISE ptpTraps
      VARIABLES { telecomsChannelStatus }
      DESCRIPTION
             "Current status of telecoms channel. NB: a change of 
             state may generate an SNMP trap and/or SMTP email alert"  
      ::= 4

   telecomsLoopbackTrap TRAP-TYPE
      ENTERPRISE ptpTraps
      VARIABLES { telecomsLoopback }
      DESCRIPTION
             "The loopback status of telecoms channel. This is 
             intended for installation testing and should be set to 
             'None' for normal operation. The wire connections to a 
             unit can be tested by applying a 'Copper' loopback to the 
             local unit. The wireless connection to the remote unit 
             can be tested by applying a 'Wireless' loopback to the 
             remote unit with no loopback on the local unit. When 
             applying a wireless loopback, please ensure that the 
             other end of the link has a loopback setting of 'None'. 
             NB: a change of state may generate an SNMP trap and/or 
             SMTP email alert"  
      ::= 6

   regionCodeTrap TRAP-TYPE
      ENTERPRISE ptpTraps
      VARIABLES { regionCode }
      DESCRIPTION
             "The region code prohibits the wireless unit from 
             operating outside the regulated limits. An invalid region 
             code indicates a corrupted licence key. NB: a change of 
             state may generate an SNMP trap and/or SMTP email alert"  
      ::= 8

   installStatusTrap TRAP-TYPE
      ENTERPRISE ptpTraps
      VARIABLES { installStatus }
      DESCRIPTION
             "A non-zero value indicates that signalling was received 
             with the wrong MAC address or a mismatched link name. NB: 
             It is very unusual to detect this, because units with 
             mis-configured Target MAC Address will normally fail to 
             establish a wireless link. However, rare circumstances 
             may establish a partial wireless link and detect this 
             situation. NB: A non-zero value on start-up, or a change 
             of value during operation, may generate an SNMP trap 
             and/or SMTP email alert"  
      ::= 9

   installArmStateTrap TRAP-TYPE
      ENTERPRISE ptpTraps
      VARIABLES { installArmState }
      DESCRIPTION
             "Indicates if the unit is being installed. NB: a value 
             other than 'disarmed' on startup, or a change of state 
             during operation may generate an SNMP trap and/or SMTP 
             email alert"  
      ::= 10

   unitOutOfCalibrationTrap TRAP-TYPE
      ENTERPRISE ptpTraps
      VARIABLES { unitOutOfCalibration }
      DESCRIPTION
             "The unit is out of calibration"  
      ::= 11

   incompatibleRegionCodesTrap TRAP-TYPE
      ENTERPRISE ptpTraps
      VARIABLES { incompatibleRegionCodes }
      DESCRIPTION
             "The master and slave units have incompatible region 
             codes. NB: Both units must have compatible licence keys"  
      ::= 14

   noWirelessChannelAvailableTrap TRAP-TYPE
      ENTERPRISE ptpTraps
      VARIABLES { noWirelessChannelAvailable }
      DESCRIPTION
             "Spectrum Management was unable to locate a suitable 
             wireless channel to operate on"  
      ::= 15

   wirelessLinkDisabledWarningTrap TRAP-TYPE
      ENTERPRISE ptpTraps
      VARIABLES { wirelessLinkDisabledWarning }
      DESCRIPTION
             "The SNMP ifAdminStatus of the wireless interface has 
             disabled wireless traffic"  
      ::= 16

   dataPortDisabledWarningTrap TRAP-TYPE
      ENTERPRISE ptpTraps
      VARIABLES { dataPortDisabledWarning }
      DESCRIPTION
             "The SNMP ifAdminStatus of the Ethernet interface has 
             disabled Ethernet traffic"  
      ::= 17

   dataPortConfigurationMismatchTrap TRAP-TYPE
      ENTERPRISE ptpTraps
      VARIABLES { dataPortConfigurationMismatch }
      DESCRIPTION
             "The detection of Ethernet fragments (runt packets) when 
             the link is in full duplex is an indication of an 
             auto-negotiation or forced configuration mismatch"  
      ::= 19

   incompatibleMasterAndSlaveTrap TRAP-TYPE
      ENTERPRISE ptpTraps
      VARIABLES { incompatibleMasterAndSlave }
      DESCRIPTION
             "A non-zero value indicates that the master and slave 
             ends of a link are different hardware products, or have 
             different software versions. NB: It is very unusual to 
             detect this, because incompatible units will normally 
             fail to establish a wireless link. However, some 
             combinations may establish a partial wireless link and 
             detect this situation. NB: A non-zero value may generate 
             an SNMP trap and/or SMTP email alert"  
      ::= 20

   sNTPSyncTrap TRAP-TYPE
      ENTERPRISE ptpTraps
      VARIABLES { sNTPSync }
      DESCRIPTION
             "If SNTP Sync fails then check the server settings in the 
             Remote Management page, or disable SNTP. NB: a change of 
             state may generate an SNMP trap and/or SMTP email alert"  
      ::= 21

   tDDSynchronizationAlarmTrap TRAP-TYPE
      ENTERPRISE ptpTraps
      VARIABLES { tDDSynchronizationAlarm }
      DESCRIPTION
             "Not Synchronized indicates failure of the external 
             timing system for a period greater than the holdover 
             timer. TDD frame timing will have drifted, and this link 
             may cause interference with other links in a synchronized 
             network. Timing System Failure is an early warning, 
             indicating that 80% of the holdover period has expired."  
      ::= 22

   linkModeOptimizationMismatchTrap TRAP-TYPE
      ENTERPRISE ptpTraps
      VARIABLES { linkModeOptimizationMismatch }
      DESCRIPTION
             "The remote node of this link has been configured with a 
             different link mode optimization"  
      ::= 25

   capacityLicenseMismatchTrap TRAP-TYPE
      ENTERPRISE ptpTraps
      VARIABLES { capacityLicenseMismatch }
      DESCRIPTION
             "The local and remote units have different licensed 
             capacity and/or the full capacity trial has been 
             activated at only one unit. The wireless link is 
             operating at the capacity of the lowest capacity unit"  
      ::= 27

   syslogStateTrap TRAP-TYPE
      ENTERPRISE ptpTraps
      VARIABLES { syslogState }
      DESCRIPTION
             "The syslog service has been enabled or disabled"  
      ::= 30

   syslogLocalNearlyFullTrap TRAP-TYPE
      ENTERPRISE ptpTraps
      DESCRIPTION "The syslog local log is nearly full (90%)"
      ::= 31

   syslogLocalWrappedTrap TRAP-TYPE
      ENTERPRISE ptpTraps
      DESCRIPTION "The syslog local log has wrapped"
      ::= 32

   syslogClientTrap TRAP-TYPE
      ENTERPRISE ptpTraps
      VARIABLES { syslogClient }
      DESCRIPTION
             "Enable or disable the syslog client"  
      ::= 33

   END
