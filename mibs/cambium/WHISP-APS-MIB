--
--      whisp-aps-mib.mib
--      GENERATED FROM ui_db.xml
--
--      *******************************************************************************************************
--      Copyright 2005 - 2015 (c), Cambium Networks
--      Cambium Networks Confidential Proprietary
--      *******************************************************************************************************
--
--      Canopy Access Point and Backhaul Timing Master specific MIB definitions.
--
--     ********************************************************************************************************

WHISP-APS-MIB   DEFINITIONS ::= BEGIN
IMPORTS
		MODULE-IDENTITY, OBJECT-TYPE, Counter32, Counter64, Gauge32, IpAddress, NOTIFICATION-TYPE, TimeTicks, Unsigned32
				FROM SNMPv2-SMI
		DisplayString, PhysAddress, MacAddress
				FROM SNMPv2-TC
		OBJECT-GROUP
				FROM SNMPv2-CONF
		WhispLUID, WhispMACAddress, EventString
				FROM WHISP-TCV2-MIB
		whispModules, whispBox, whispAps
				FROM WHISP-GLOBAL-REG-MIB
		whispBoxEsn, whispBoxRFPhysicalRadioEntry
				FROM WHISP-BOX-MIBV2-MIB
				;

whispApsMibModule  MODULE-IDENTITY
	LAST-UPDATED	"200304150000Z"
	ORGANIZATION	"Cambium Networks"
	CONTACT-INFO
		"Cambium Networks Support
        email: support@cambiumnetworks.com"
	DESCRIPTION
		"This module contains MIB definitions for APs."
	::= {whispModules 12}

-- -------------------------------------------------------------------------
-- Top Level Registrations

whispApsConfig		OBJECT IDENTIFIER ::= {whispAps 1}
whispApsLink		OBJECT IDENTIFIER ::= {whispAps 2}
whispApsLinkTestConfig		OBJECT IDENTIFIER ::= {whispApsLink 1}
whispApsLinkTestResult		OBJECT IDENTIFIER ::= {whispApsLink 2}
whispApsGPS		OBJECT IDENTIFIER ::= {whispAps 3}
whispApsEvent		OBJECT IDENTIFIER ::= {whispAps 5}
whispApsRegEvent		OBJECT IDENTIFIER ::= {whispApsEvent 1}
whispGPSEvent		OBJECT IDENTIFIER ::= {whispApsEvent 2}
whispApsDfsEvent		OBJECT IDENTIFIER ::= {whispApsEvent 3}
whispApRegulatoryEvent		OBJECT IDENTIFIER ::= {whispApsEvent 4}
whispApRFOverloadEvent		OBJECT IDENTIFIER ::= {whispApsEvent 5}
whispApsMumimoTrialEvent		OBJECT IDENTIFIER ::= {whispApsEvent 6}
whispApLqiEvent		OBJECT IDENTIFIER ::= {whispApsEvent 7}
whispApsCbrsEvent		OBJECT IDENTIFIER ::= {whispApsEvent 8}
whispApsGroups		OBJECT IDENTIFIER ::= {whispAps 6}
whispApsFrUtlStats		OBJECT IDENTIFIER ::= {whispAps 12}
whispApsFrUtlStatsIntervalLow		OBJECT IDENTIFIER ::= {whispApsFrUtlStats 1}
whispApsFrUtlStatsIntervalMedium		OBJECT IDENTIFIER ::= {whispApsFrUtlStats 2}
whispApsFrUtlStatsIntervalHigh		OBJECT IDENTIFIER ::= {whispApsFrUtlStats 3}
whispApsStatus		OBJECT IDENTIFIER ::= {whispAps 7}
whispApsDHCPv6RelayStats		OBJECT IDENTIFIER ::= {whispApsStatus 49}
whispApsDNS		OBJECT IDENTIFIER ::= {whispAps 9}
whispApsControls		OBJECT IDENTIFIER ::= {whispAps 11}
whispApsLQI		OBJECT IDENTIFIER ::= {whispAps 13}
whispApsCbrs		OBJECT IDENTIFIER ::= {whispAps 14}
whispApsCbrsConfig		OBJECT IDENTIFIER ::= {whispApsCbrs 1}
whispApsCbrsApStatus		OBJECT IDENTIFIER ::= {whispApsCbrs 2}
whispApsRFConfig		OBJECT IDENTIFIER ::= {whispAps 10}
whispApsRFStatus		OBJECT IDENTIFIER ::= {whispAps 15}

-- -------------------------------------------------------------------------


	gpsInput	OBJECT-TYPE
		SYNTAX		INTEGER {
					generateSyncSignal(0),
					syncToReceivedSignalTimingPort(1),
					syncToReceivedSignalPowerPort(2)}
		MAX-ACCESS	read-write
		STATUS		obsolete
		DESCRIPTION		
			"The variable is obsolete.  See gpsInput in whispBoxConfig."
		::={whispApsConfig 1}

	rfFreqCarrier	OBJECT-TYPE
		SYNTAX		INTEGER {
					wired(0)}
		MAX-ACCESS	read-write
		STATUS		deprecated
		DESCRIPTION		
			"The primary transmit frequency.
                            Also see radioFreqCarrier."
		::={whispApsConfig 2}

	apLinkSpeed	OBJECT-TYPE
		SYNTAX		DisplayString
		MAX-ACCESS	read-write
		STATUS		obsolete
		DESCRIPTION		
			"The variable is deprecated."
		::={whispApsConfig 3}

	dwnLnkData	OBJECT-TYPE
		SYNTAX		INTEGER (1..99)
		UNITS		"%"
		MAX-ACCESS	read-write
		STATUS		deprecated
		DESCRIPTION		
			"This attribute is deprecated.  Please see radioDownlinkPercent."
		::={whispApsConfig 4}

	highPriorityUpLnkPct	OBJECT-TYPE
		SYNTAX		INTEGER (0..99)
		UNITS		"%"
		MAX-ACCESS	read-write
		STATUS		obsolete
		DESCRIPTION		
			"Percentage of uplink slots for high priority data."
		::={whispApsConfig 5}

	numUAckSlots	OBJECT-TYPE
		SYNTAX		INTEGER
		MAX-ACCESS	read-write
		STATUS		obsolete
		DESCRIPTION		
			"Total number of upstream ack slots."
		::={whispApsConfig 6}

	uAcksReservHigh	OBJECT-TYPE
		SYNTAX		INTEGER
		MAX-ACCESS	read-write
		STATUS		obsolete
		DESCRIPTION		
			"Total number of upstream high priority ack slots"
		::={whispApsConfig 7}

	numDAckSlots	OBJECT-TYPE
		SYNTAX		INTEGER
		MAX-ACCESS	read-write
		STATUS		obsolete
		DESCRIPTION		
			"Total number of downstream ack slots."
		::={whispApsConfig 8}

	dAcksReservHigh	OBJECT-TYPE
		SYNTAX		INTEGER
		MAX-ACCESS	read-write
		STATUS		obsolete
		DESCRIPTION		
			"Total number of high priority downstream ack slots."
		::={whispApsConfig 9}

	numCtlSlots	OBJECT-TYPE
		SYNTAX		INTEGER
		MAX-ACCESS	read-write
		STATUS		obsolete
		DESCRIPTION		
			"This OID is deprecated, please use numCtlSlotsHW."
		::={whispApsConfig 10}

	numCtlSlotsReserveHigh	OBJECT-TYPE
		SYNTAX		INTEGER
		MAX-ACCESS	read-write
		STATUS		obsolete
		DESCRIPTION		
			"Total number of High priority upstream control (contention) slots."
		::={whispApsConfig 11}

	upLnkDataRate	OBJECT-TYPE
		SYNTAX		INTEGER
		UNITS		"Kilobits/sec"
		MAX-ACCESS	read-write
		STATUS		current
		DESCRIPTION		
			"Sustained uplink bandwidth cap."
		::={whispApsConfig 12}

	upLnkLimit	OBJECT-TYPE
		SYNTAX		INTEGER
		UNITS		"Kilobits/sec"
		MAX-ACCESS	read-write
		STATUS		current
		DESCRIPTION		
			"Burst uplink bandwidth cap."
		::={whispApsConfig 13}

	dwnLnkDataRate	OBJECT-TYPE
		SYNTAX		INTEGER
		UNITS		"Kilobits/sec"
		MAX-ACCESS	read-write
		STATUS		current
		DESCRIPTION		
			"Sustained downlink bandwidth cap."
		::={whispApsConfig 14}

	dwnLnkLimit	OBJECT-TYPE
		SYNTAX		INTEGER
		UNITS		"Kilobits/sec"
		MAX-ACCESS	read-write
		STATUS		current
		DESCRIPTION		
			"Burst downlink bandwidth cap."
		::={whispApsConfig 15}

	sectorID	OBJECT-TYPE
		SYNTAX		INTEGER (0..15)
		MAX-ACCESS	read-write
		STATUS		current
		DESCRIPTION		
			"Advertise sector number for an AP.
                            Not supported on 450 platform."
		::={whispApsConfig 16}

	maxRange	OBJECT-TYPE
		SYNTAX		INTEGER
		MAX-ACCESS	read-write
		STATUS		deprecated
		DESCRIPTION		
			"This attribute is deprecated.  Please see radioMaxRange."
		::={whispApsConfig 17}

	airLinkSecurity	OBJECT-TYPE
		SYNTAX		INTEGER {
					standard(0),
					desEnhanced(1),
					desEnhancedAndAuthentication(2),
					authenticationIfAvailable(3)}
		MAX-ACCESS	read-write
		STATUS		obsolete
		DESCRIPTION		
			"Air Link Security.
            desEnhancedAndAuthentication(2) and authenticationIfAvailable(3)
            are only for APAS."
		::={whispApsConfig 18}

	berMode	OBJECT-TYPE
		SYNTAX		INTEGER {
					berStream(0),
					noBerStream(1)}
		MAX-ACCESS	read-write
		STATUS		obsolete
		DESCRIPTION		
			"AP backgroup BER mode."
		::={whispApsConfig 19}

	asIP1	OBJECT-TYPE
		SYNTAX		IpAddress
		MAX-ACCESS	read-write
		STATUS		obsolete
		DESCRIPTION		
			"Obsoleted. Configure with whispApsDNS.authServer1."
		::={whispApsConfig 20}

	asIP2	OBJECT-TYPE
		SYNTAX		IpAddress
		MAX-ACCESS	read-write
		STATUS		obsolete
		DESCRIPTION		
			"Obsoleted. Configure with whispApsDNS.authServer2."
		::={whispApsConfig 21}

	asIP3	OBJECT-TYPE
		SYNTAX		IpAddress
		MAX-ACCESS	read-write
		STATUS		obsolete
		DESCRIPTION		
			"Obsoleted. Configure with whispApsDNS.authServer3."
		::={whispApsConfig 22}

	lanIpAp	OBJECT-TYPE
		SYNTAX		IpAddress
		MAX-ACCESS	read-write
		STATUS		current
		DESCRIPTION		
			"LAN IP."
		::={whispApsConfig 23}

	lanMaskAp	OBJECT-TYPE
		SYNTAX		IpAddress
		MAX-ACCESS	read-write
		STATUS		current
		DESCRIPTION		
			"LAN subnet mask."
		::={whispApsConfig 24}

	defaultGwAp	OBJECT-TYPE
		SYNTAX		IpAddress
		MAX-ACCESS	read-write
		STATUS		current
		DESCRIPTION		
			"Default gateway"
		::={whispApsConfig 25}

	privateIp	OBJECT-TYPE
		SYNTAX		IpAddress
		MAX-ACCESS	read-write
		STATUS		current
		DESCRIPTION		
			"Private IP."
		::={whispApsConfig 26}

	gpsTrap	OBJECT-TYPE
		SYNTAX		INTEGER {
					gpsTrapDisabled(0),
					gpsTrapEnabled(1)}
		MAX-ACCESS	read-write
		STATUS		current
		DESCRIPTION		
			"Variable to enable/disable GPS sync/out-sync traps."
		::={whispApsConfig 27}

	regTrap	OBJECT-TYPE
		SYNTAX		INTEGER {
					regTrapDisabled(0),
					regTrapEnabled(1)}
		MAX-ACCESS	read-write
		STATUS		current
		DESCRIPTION		
			"Variable to enable/disable registration complete/lost traps."
		::={whispApsConfig 28}

	txSpreading	OBJECT-TYPE
		SYNTAX		INTEGER {
					txSpreadingDisabled(0),
					txSpreadingEnabled(1)}
		MAX-ACCESS	read-write
		STATUS		obsolete
		DESCRIPTION		
			"Variable to enable/disable Transmit Frame Spreading.  This option is for FSK only."
		::={whispApsConfig 29}

	apBeaconInfo	OBJECT-TYPE
		SYNTAX		INTEGER {
					enableApBeaconInfo(0),
					disableApBeaconInfo(1)}
		MAX-ACCESS	read-write
		STATUS		current
		DESCRIPTION		
			"Variable to enable/disable displaying AP beacon info through AP eval."
		::={whispApsConfig 30}

	authMode	OBJECT-TYPE
		SYNTAX		INTEGER {
					authenticationDisabled(0),
					authenticationRequiredBam(1),
					authenticationRequiredAP(3),
					authenticationRequiredAAA(4)}
		MAX-ACCESS	read-write
		STATUS		current
		DESCRIPTION		
			"Variable to enable/disable authentication. The authentication optional mode
            is for APs only. This variable can only be set when authentication feature
            is enabled.  Setting it to 1 will use a BAM server for authentication of SMs.  Setting
            it to 2 will make use of the Authentication Key on the AP for authenticating SMs.  The
            keys must match on SM and AP in order for the SM to be authenticated in this mode."
		::={whispApsConfig 31}

	authKeyAp	OBJECT-TYPE
		SYNTAX		DisplayString
		MAX-ACCESS	read-write
		STATUS		current
		DESCRIPTION		
			"Authentication key 128-bit. It should be up to 32 hex characters long.  Can be used on MultiPoint AP if PSK Authentication mode is selected.
            Otherwise, it is used on Backhauls."
		::={whispApsConfig 32}

	encryptionMode	OBJECT-TYPE
		SYNTAX		INTEGER {
					encryptionDisabled(0),
					encryptionEnabled(1)}
		MAX-ACCESS	read-write
		STATUS		current
		DESCRIPTION		
			"Variable to enable/disable encryption."
		::={whispApsConfig 33}

	ntpServerIp	OBJECT-TYPE
		SYNTAX		IpAddress
		MAX-ACCESS	read-write
		STATUS		obsolete
		DESCRIPTION		
			"Obsoleted.  Configure with whispApsDNS.ntpServer1, whispApsDNS.ntpServer2, and whispApsDNS.ntpServer3."
		::={whispApsConfig 34}

	broadcastRetryCount	OBJECT-TYPE
		SYNTAX		INTEGER
		MAX-ACCESS	read-write
		STATUS		current
		DESCRIPTION		
			"Broadcast Repeat Count : Range 0 -- 2. For APs."
		::={whispApsConfig 35}

	encryptDwBroadcast	OBJECT-TYPE
		SYNTAX		INTEGER {
					disable(0),
					enable(1)}
		MAX-ACCESS	read-write
		STATUS		deprecated
		DESCRIPTION		
			"To enable or disable Encrypted Downlink Broadcast. For FSK APs."
		::={whispApsConfig 36}

	updateAppAddress	OBJECT-TYPE
		SYNTAX		IpAddress
		MAX-ACCESS	read-write
		STATUS		current
		DESCRIPTION		
			"Update Application Address."
		::={whispApsConfig 37}

	dfsConfig	OBJECT-TYPE
		SYNTAX		INTEGER {
					disable(0),
					enable(1)}
		MAX-ACCESS	read-write
		STATUS		obsolete
		DESCRIPTION		
			"To configure proper regions for Dynamic Frequency Shifting. For 5.2/5.4/5.7 GHz radios."
		::={whispApsConfig 38}

	vlanEnable	OBJECT-TYPE
		SYNTAX		INTEGER {
					disable(0),
					enable(1)}
		MAX-ACCESS	read-write
		STATUS		current
		DESCRIPTION		
			"To enable or disable VLAN."
		::={whispApsConfig 39}

	configSource	OBJECT-TYPE
		SYNTAX		INTEGER {
					bam(0),
					sm(1),
					bamsm(2)}
		MAX-ACCESS	read-write
		STATUS		current
		DESCRIPTION		
			"To configure CIR, MIR and VLAN through SM or BAM."
		::={whispApsConfig 40}

	apRateAdapt	OBJECT-TYPE
		SYNTAX		INTEGER {
					onex(0),
					onextwox(1),
					onextwoxthreex(2)}
		MAX-ACCESS	read-write
		STATUS		obsolete
		DESCRIPTION		
			"To enable or disable double rate."
		::={whispApsConfig 41}

	numCtlSlotsHW	OBJECT-TYPE
		SYNTAX		INTEGER
		MAX-ACCESS	read-write
		STATUS		deprecated
		DESCRIPTION		
			"This attribute is deprecated.  Please see radioControlSlots."
		::={whispApsConfig 42}

	displayAPEval	OBJECT-TYPE
		SYNTAX		INTEGER {
					enable(0),
					disable(1)}
		MAX-ACCESS	read-write
		STATUS		current
		DESCRIPTION		
			"If enable, it allows display of AP Eval Data at the SM."
		::={whispApsConfig 43}

	smIsolation	OBJECT-TYPE
		SYNTAX		INTEGER {
					smIsolationDisable(0),
					smIsolationDrop(1),
					smIsolationFwd(2)}
		MAX-ACCESS	read-write
		STATUS		current
		DESCRIPTION		
			"(0) -- Disable SM Isolation.
                            (1) -- Enable SM Isolation by blocking SM destined packets.
                            (2) -- Enable SM Isolation by forwarding SM packets upstream."
		::={whispApsConfig 44}

	ipAccessFilterEnable	OBJECT-TYPE
		SYNTAX		INTEGER {
					disable(0),
					enable(1)}
		MAX-ACCESS	read-write
		STATUS		current
		DESCRIPTION		
			"To enable or disable IP access filtering to Management functions.
            (0) - IP access will be allowed from all addresses.
            (1) - IP access will be controlled using allowedIPAccess1-3 entries."
		::={whispApsConfig 45}

	allowedIPAccess1	OBJECT-TYPE
		SYNTAX		IpAddress
		MAX-ACCESS	read-write
		STATUS		current
		DESCRIPTION		
			"Allow access to AP Management from this IP.
            0 is default setting to allow from all IPs."
		::={whispApsConfig 46}

	allowedIPAccess2	OBJECT-TYPE
		SYNTAX		IpAddress
		MAX-ACCESS	read-write
		STATUS		current
		DESCRIPTION		
			"Allow access to AP Management from this IP.
            0 is default setting to allow from all IPs."
		::={whispApsConfig 47}

	allowedIPAccess3	OBJECT-TYPE
		SYNTAX		IpAddress
		MAX-ACCESS	read-write
		STATUS		current
		DESCRIPTION		
			"Allow access to AP Management from this IP.
            0 is default setting to allow from all IPs."
		::={whispApsConfig 48}

	tslBridging	OBJECT-TYPE
		SYNTAX		INTEGER {
					disable(0),
					enable(1)}
		MAX-ACCESS	read-write
		STATUS		current
		DESCRIPTION		
			"1 = We are performing Translation Bridging 0 = We are not."
		::={whispApsConfig 49}

	untranslatedArp	OBJECT-TYPE
		SYNTAX		INTEGER {
					disable(0),
					enable(1)}
		MAX-ACCESS	read-write
		STATUS		current
		DESCRIPTION		
			"1 = We are sending untranslated ARP response. 0 = We are not."
		::={whispApsConfig 50}

	limitFreqBand900	OBJECT-TYPE
		SYNTAX		INTEGER {
					disable(0),
					enable(1)}
		MAX-ACCESS	read-write
		STATUS		obsolete
		DESCRIPTION		
			"1 = We are limiting the freq band of 900 radios.  0 = We are not.
                       FSK radios only."
		::={whispApsConfig 51}

	txPwrLevel	OBJECT-TYPE
		SYNTAX		INTEGER
		MAX-ACCESS	read-write
		STATUS		obsolete
		DESCRIPTION		
			"Deprecated, use 'transmitterOP' instead."
		::={whispApsConfig 52}

	rfFreqCaralt1	OBJECT-TYPE
		SYNTAX		INTEGER {
					none(0)}
		MAX-ACCESS	read-write
		STATUS		current
		DESCRIPTION		
			"First DFS Alternate RF Frequency. (Only available for DFS radios)  Used
            as a backup frequency when Radar is detected on DFS enabled Radios.
            The frequencies are:

            5.4 radios:(5475,5485,5490 OFDM only),5495,5500,5505,5510,5515,5520,5525,
                   5530,5535,5540,5545,5550,5555,5560,5565,5570,5575,5580,5585,5590,5595,
                   5600,5605,5610,5615,5620,5625,5630,5635,5640,5645,5650,5655,5660,5665,
                   5670,5675,5680,5685,5690,5695,5700,5705,(5710,5715 OFDM Only).

            (5.7 Platform 10 (SAL) radios with non-connectorized antennas do not support DFS)

            5.7 radios:5745,5750,5755,5760,5765,5770,5775,5780,5785,5790,5795,5800,5805.
            5.7 radios with ISM enabled :5735,5740,5745,5750,5755,5760,5765,5770,5775,
                   5780,5785,5790,5795,5800,5805,5810,5815,5820,5825,5830,5835,5840.
            0:  None."
		::={whispApsConfig 53}

	rfFreqCaralt2	OBJECT-TYPE
		SYNTAX		INTEGER {
					none(0)}
		MAX-ACCESS	read-write
		STATUS		current
		DESCRIPTION		
			"Second DFS Alternate RF Frequency. (Only available for DFS radios)  Used
            as a backup frequency when Radar is detected on DFS enabled Radios.
            The frequencies are:

            5.4 radios:(5475,5485,5490 OFDM only),5495,5500,5505,5510,5515,5520,5525,
                   5530,5535,5540,5545,5550,5555,5560,5565,5570,5575,5580,5585,5590,5595,
                   5600,5605,5610,5615,5620,5625,5630,5635,5640,5645,5650,5655,5660,5665,
                   5670,5675,5680,5685,5690,5695,5700,5705,(5710,5715 OFDM Only).

            (5.7 Platform 10 (SAL) radios with non-connectorized antennas do not support DFS)

            5.7 radios:5745,5750,5755,5760,5765,5770,5775,5780,5785,5790,5795,5800,5805.
            5.7 radios with ISM enabled :5735,5740,5745,5750,5755,5760,5765,5770,5775,
                   5780,5785,5790,5795,5800,5805,5810,5815,5820,5825,5830,5835,5840.
            0:  None."
		::={whispApsConfig 54}

	scheduleWhitening	OBJECT-TYPE
		SYNTAX		INTEGER {
					disable(0),
					enable(1)}
		MAX-ACCESS	read-write
		STATUS		deprecated
		DESCRIPTION		
			"1 = Schedule Whitening allowed.  0 = Schedule Whitening not allowed.  This option is for FSK only"
		::={whispApsConfig 55}

	remoteSpectrumAnalysisDuration	OBJECT-TYPE
		SYNTAX		INTEGER (10..1000)
		MAX-ACCESS	read-write
		STATUS		current
		DESCRIPTION		
			"Value in seconds for a remote spectrum analysis on an SM. Range is 10-1000 seconds."
		::={whispApsConfig 56}

-- Perform Remote Spectrum Analysis on an LUID

	remoteSpectrumAnalyzerLUID	OBJECT-TYPE
		SYNTAX		INTEGER (2..239)
		MAX-ACCESS	read-write
		STATUS		current
		DESCRIPTION		
			"Get will always return 0.
                            Set will start Remote Spectrum Analyzer on specified LUID.
                            *Warning* This will cause the SM to disconnect from the AP!
                            You will lose the session for the specified duration!
                            If general error was returned then the LUID does not have an active session, or the
                            SM does not support Remote Spectrum Analysis."
		::={whispApsConfig 57}

-- Forces BHS reregistration every 24 hours

	bhReReg	OBJECT-TYPE
		SYNTAX		INTEGER {
					disabled(0),
					enabled(1)}
		MAX-ACCESS	read-write
		STATUS		current
		DESCRIPTION		
			"Forces BHS reregistration every 24 hours. Enable forces reregistration and Disable does not. 24 Hour Encryption Refresh."
		::={whispApsConfig 58}

	dlnkBcastCIR	OBJECT-TYPE
		SYNTAX		INTEGER
		MAX-ACCESS	read-write
		STATUS		current
		DESCRIPTION		
			"Downlink Broadcast CIR (kbps)"
		::={whispApsConfig 59}

	verifyGPSChecksum	OBJECT-TYPE
		SYNTAX		INTEGER {
					doNotVerifyGPSMessageChecksum(0),
					verifyGPSMessageChecksum(1)}
		MAX-ACCESS	read-write
		STATUS		current
		DESCRIPTION		
			"Enable/Disable verification of GPS message checksums."
		::={whispApsConfig 60}

	apVlanOverride	OBJECT-TYPE
		SYNTAX		INTEGER {
					disable(0),
					enable(1)}
		MAX-ACCESS	read-write
		STATUS		current
		DESCRIPTION		
			"Setting this option will cause an AP to retain its VLAN settings when turning it into an SM.  It will be mostly helpful for
                            running spectrum analysis on the AP.  Since doing that requires the AP to be turned into an SM, enabling this option will
                            allow you to keep the AP's VLAN configuration in place while the AP is running as an SM."
		::={whispApsConfig 61}

	dhcpRelayAgentEnable	OBJECT-TYPE
		SYNTAX		INTEGER {
					disable(0),
					fullRelay(1),
					option82Only(2)}
		MAX-ACCESS	read-write
		STATUS		current
		DESCRIPTION		
			"Enable or Disable MultiPoint AP acting as DHCP Relay Agent for all SMs and Clients underneath it.
            (0) - Relay Agent disabled - SM/CPE devices will perform DHCP normally
            (1) - Relay Agent enabled - AP will intercept DHCP DISCOVER message from SM and CPE, insert Option 82 containing SM's MAC address, and forward request to specified DHCP server."
		::={whispApsConfig 62}

	dhcpRelayAgentSrvrIP	OBJECT-TYPE
		SYNTAX		IpAddress
		MAX-ACCESS	read-write
		STATUS		obsolete
		DESCRIPTION		
			"Obsoleted.  Configure with whispApsDNS.dhcprServer."
		::={whispApsConfig 63}

	colorCodeRescanTimer	OBJECT-TYPE
		SYNTAX		INTEGER (0..43200)
		MAX-ACCESS	read-write
		STATUS		current
		DESCRIPTION		
			"Time in minutes for the subscriber to begin the idle timer.  This timer
                        will begin as soon as a session is started.
                        This only fires if the device is in session with a non-primary color code.
                        A value of zero (0) disables this timer
                        (MultiPoint system Only)"
		::={whispApsConfig 64}

	colorCodeRescanIdleTimer	OBJECT-TYPE
		SYNTAX		INTEGER (0..60)
		MAX-ACCESS	read-write
		STATUS		current
		DESCRIPTION		
			"Time in minutes for the subscriber to check for an idle state.  If an period has pass where no unicast RF traffic has occured (idle),
                        then the subscriber will begin to rescan.
                        This timer will wait until the timer set in colorCodeRescanTimer has expired before beginning.
                        This timer only fires if the device is in session with a non-primary color code.
                        A value of zero (0) mean to rescan without waiting for idle.
                        (MultiPoint system Only)"
		::={whispApsConfig 65}

	authKeyOptionAP	OBJECT-TYPE
		SYNTAX		INTEGER {
					useDefault(0),
					useKeySet(1)}
		MAX-ACCESS	read-write
		STATUS		current
		DESCRIPTION		
			"This option is for Multipoint APs only.  This option will only be used if Authentication Mode is set
            to AP Pre-Shared Key.
            0 - Use default 128-bit key.
            1 - Use set 128-bit key."
		::={whispApsConfig 66}

	asIP4	OBJECT-TYPE
		SYNTAX		IpAddress
		MAX-ACCESS	read-write
		STATUS		obsolete
		DESCRIPTION		
			"Obsoleted. Configure with whispApsDNS.authServer4."
		::={whispApsConfig 67}

	asIP5	OBJECT-TYPE
		SYNTAX		IpAddress
		MAX-ACCESS	read-write
		STATUS		obsolete
		DESCRIPTION		
			"Obsoleted. Configure with whispApsDNS.authServer5."
		::={whispApsConfig 68}

	onlyAllowVer95OrAbove	OBJECT-TYPE
		SYNTAX		INTEGER {
					onlyAllowVer95OrAboveDisabled(0),
					onlyAllowVer95OrAboveEnabled(1)}
		MAX-ACCESS	read-write
		STATUS		obsolete
		DESCRIPTION		
			"Only allow subscribers that are running version 9.5 or above.  Any radio that has a version below 9.5 will not be allowed to register."
		::={whispApsConfig 69}

	apRxDelay	OBJECT-TYPE
		SYNTAX		INTEGER
		MAX-ACCESS	read-write
		STATUS		current
		DESCRIPTION		
			"This is used for engineering debug and needs to be removed or moved to eng MIB before releasing the MIB."
		::={whispApsConfig 70}

	qinqEthType	OBJECT-TYPE
		SYNTAX		INTEGER {
					x88a8(0),
					x8100(1),
					x9100(2),
					x9200(3),
					x9300(4)}
		MAX-ACCESS	read-write
		STATUS		current
		DESCRIPTION		
			"EtherType for QinQ (802.1ad) outer tag (S-Tag). 0x88a8 by default."
		::={whispApsConfig 71}

	sMTxPowerControl	OBJECT-TYPE
		SYNTAX		INTEGER {
					disable(0),
					enable(1)}
		MAX-ACCESS	read-write
		STATUS		current
		DESCRIPTION		
			"Enable/Disable AP control of SM Tx power.
                            Engineering use only."
		::={whispApsConfig 72}

	fskSMRcvTargetLvl	OBJECT-TYPE
		SYNTAX		INTEGER (-80..-40)
		UNITS		"dBm"
		MAX-ACCESS	read-write
		STATUS		obsolete
		DESCRIPTION		
			"Desired SM Receive Level at AP (dBm, Range -40dBm to -80 dBm).
                        FSK only."
		::={whispApsConfig 73}

	authSharedSecret1	OBJECT-TYPE
		SYNTAX		DisplayString
		MAX-ACCESS	read-write
		STATUS		current
		DESCRIPTION		
			"Authentication Server 1 Shared Secret."
		::={whispApsConfig 74}

	authSharedSecret2	OBJECT-TYPE
		SYNTAX		DisplayString
		MAX-ACCESS	read-write
		STATUS		current
		DESCRIPTION		
			"Authentication Server 2 Shared Secret."
		::={whispApsConfig 75}

	authSharedSecret3	OBJECT-TYPE
		SYNTAX		DisplayString
		MAX-ACCESS	read-write
		STATUS		current
		DESCRIPTION		
			"Authentication Server 3 Shared Secret."
		::={whispApsConfig 76}

	whispUsrAuthSharedSecret1	OBJECT-TYPE
		SYNTAX		DisplayString
		MAX-ACCESS	read-write
		STATUS		obsolete
		DESCRIPTION		
			"Obsoleted. Use whispApsConfig.authSharedSecret1."
		::={whispApsConfig 79}

	whispUsrAuthSharedSecret2	OBJECT-TYPE
		SYNTAX		DisplayString
		MAX-ACCESS	read-write
		STATUS		obsolete
		DESCRIPTION		
			"Obsoleted. Use whispApsConfig.authSharedSecret2."
		::={whispApsConfig 80}

	whispUsrAuthSharedSecret3	OBJECT-TYPE
		SYNTAX		DisplayString
		MAX-ACCESS	read-write
		STATUS		obsolete
		DESCRIPTION		
			"Obsoleted. Use whispApsConfig.authSharedSecret3."
		::={whispApsConfig 81}

	whispUsrAcctSvr1	OBJECT-TYPE
		SYNTAX		DisplayString
		MAX-ACCESS	read-write
		STATUS		obsolete
		DESCRIPTION		
			"Obsoleted.  Use whispApsDNS.authServer1."
		::={whispApsConfig 82}

	whispUsrAcctSvr2	OBJECT-TYPE
		SYNTAX		DisplayString
		MAX-ACCESS	read-write
		STATUS		obsolete
		DESCRIPTION		
			"Obsoleted.  Use whispApsDNS.authServer2."
		::={whispApsConfig 83}

	whispUsrAcctSvr3	OBJECT-TYPE
		SYNTAX		DisplayString
		MAX-ACCESS	read-write
		STATUS		obsolete
		DESCRIPTION		
			"Obsoleted.  Use whispApsDNS.authServer3."
		::={whispApsConfig 84}

	whispUsrAuthPhase1	OBJECT-TYPE
		SYNTAX		INTEGER {
					md5(0)}
		MAX-ACCESS	read-write
		STATUS		deprecated
		DESCRIPTION		
			"Select method for User Authentication. This is deprecated.
                            Please use whispUsrAuth."
		::={whispApsConfig 85}

	whispWebUseAuthServer	OBJECT-TYPE
		SYNTAX		INTEGER {
					useRADIUSAccountingSvr(0),
					useRADIUSAuthenticationSvr(1)}
		MAX-ACCESS	read-write
		STATUS		obsolete
		DESCRIPTION		
			"Obsoleted.  Use whispApsDNS.authServer[1-3]."
		::={whispApsConfig 86}

	dropSession	OBJECT-TYPE
		SYNTAX		WhispMACAddress
		MAX-ACCESS	read-write
		STATUS		current
		DESCRIPTION		
			"SM/BHS MAC Address to drop session from the AP/BHM."
		::={whispApsConfig 87}

	uGPSPower	OBJECT-TYPE
		SYNTAX		INTEGER {
					off(0),
					on(1)}
		MAX-ACCESS	read-write
		STATUS		current
		DESCRIPTION		
			"Enable or Disable aux port power to Universal GPS module (UGPS capable APs only, when GPS_output_enable is NOT set)."
		::={whispApsConfig 88}

	timeZone	OBJECT-TYPE
		SYNTAX		INTEGER (0..124)
		MAX-ACCESS	read-write
		STATUS		current
		DESCRIPTION		
			"Set the timezone offset for the radio.  This change takes affect dynamically.
            The available timezones are:
             0 : (UTC) UTC - Coordinated Universal Time
             1 : (UTC) GMT - Greenwich Mean Time
             2 : (UTC) WET - Western European Time
             3 : (UTC-12) BIT - Baker Island Time
             4 : (UTC-11) SST - Samoa Standard Time
             5 : (UTC-10) CKT - Cook Island Time
             6 : (UTC-10) HAST - Hawaii-Aleutian Standard Time
             7 : (UTC-10) HST - Hawaii Standard Time
             8 : (UTC-10) TAHT - Tahiti Time
             9 : (UTC-09:30) MIT - Marquesas Islands Time
             10 : (UTC-09) AKST - Alaska Standard Time
             11 : (UTC-09) GIT - Gambier Island Time
             12 : (UTC-09) HADT - Hawaii-Aleutian Daylight Time
             13 : (UTC-08) AKDT - Alaska Daylight Time
             14 : (UTC-08) CIST - Clipperton Island Standard Time
             15 : (UTC-08) PST - Pacific Standard Time (North America)
             16 : (UTC-07) MST - Mountain Standard Time (North America)
             17 : (UTC-07) PDT - Pacific Daylight Time (North America)
             18 : (UTC-06) CST - Central Standard Time (North America)
             19 : (UTC-06) EAST - Easter Island Standard Time
             20 : (UTC-06) GALT - Galapagos Time
             21 : (UTC-06) MDT - Mountain Daylight Time (North America)
             22 : (UTC-05) CDT - Central Daylight Time (North America)
             23 : (UTC-05) COT - Colombia Time
             24 : (UTC-05) ECT - Ecuador Time
             25 : (UTC-05) EST - Eastern Standard Time (North America)
             26 : (UTC-04:30) VET - Venezuelan Standard Time
             27 : (UTC-04) AST - Atlantic Standard Time
             28 : (UTC-04) BOT - Bolivia Time
             29 : (UTC-04) CLT - Chile Standard Time
             30 : (UTC-04) COST - Colombia Summer Time
             31 : (UTC-04) ECT - Eastern Caribbean Time (does not recognise DST)
             32 : (UTC-04) EDT - Eastern Daylight Time (North America)
             33 : (UTC-04) FKT - Falkland Islands Time
             34 : (UTC-04) GYT - Guyana Time
             35 : (UTC-03:30) NST - Newfoundland Standard Time
             36 : (UTC-03:30) NT - Newfoundland Time
             37 : (UTC-03) ADT - Atlantic Daylight Time
             38 : (UTC-03) ART - Argentina Time
             39 : (UTC-03) BRT - Brasilia Time
             40 : (UTC-03) CLST - Chile Summer Time
             41 : (UTC-03) FKST - Falkland Islands Summer Time
             42 : (UTC-03) GFT - French Guiana Time
             43 : (UTC-03) UYT - Uruguay Standard Time
             44 : (UTC-02:30) NDT - Newfoundland Daylight Time
             45 : (UTC-02) GST - South Georgia and the South Sandwich Islands
             46 : (UTC-02) UYST - Uruguay Summer Time
             47 : (UTC-01) AZOST - Azores Standard Time
             48 : (UTC-01) CVT - Cape Verde Time
             49 : (UTC+01) BST - British Summer Time (British Standard Time from Feb 1968 to Oct 1971)
             50 : (UTC+01) CET - Central European Time
             51 : (UTC+01) DFT - AIX specific equivalent of Central European Time
             52 : (UTC+01) IST - Irish Summer Time
             53 : (UTC+01) WAT - West Africa Time
             54 : (UTC+01) WEDT - Western European Daylight Time
             55 : (UTC+01) WEST - Western European Summer Time
             56 : (UTC+02) CAT - Central Africa Time
             57 : (UTC+02) CEDT - Central European Daylight Time
             58 : (UTC+02) CEST - Central European Summer Time
             59 : (UTC+02) EET - Eastern European Time
             60 : (UTC+02) IST - Israel Standard Time
             61 : (UTC+02) SAST - South African Standard Time
             62 : (UTC+03) AST - Arab Standard Time (Kuwait, Riyadh)
             63 : (UTC+03) AST - Arabic Standard Time (Baghdad)
             64 : (UTC+03) EAT - East Africa Time
             65 : (UTC+03) EEDT - Eastern European Daylight Time
             66 : (UTC+03) EEST - Eastern European Summer Time
             67 : (UTC+03) MSK - Moscow Standard Time
             68 : (UTC+03:30) IRST - Iran Standard Time
             69 : (UTC+04) AMT - Armenia Time
             70 : (UTC+04) AST - Arabian Standard Time (Abu Dhabi, Muscat)
             71 : (UTC+04) AZT - Azerbaijan Time
             72 : (UTC+04) GET - Georgia Standard Time
             73 : (UTC+04) MSD - Moscow Summer Time
             74 : (UTC+04) MUT - Mauritius Time
             75 : (UTC+04) RET - Reunion Time
             76 : (UTC+04) SAMT - Samara Time
             77 : (UTC+04) SCT - Seychelles Time
             78 : (UTC+04:30) AFT - Afghanistan Time
             79 : (UTC+05) AMST - Armenia Summer Time
             80 : (UTC+05) HMT - Heard and McDonald Islands Time
             81 : (UTC+05) PKT - Pakistan Standard Time
             82 : (UTC+05) YEKT - Yekaterinburg Time
             83 : (UTC+05:30) IST - Indian Standard Time
             84 : (UTC+05:30) SLT - Sri Lanka Time
             85 : (UTC+05:45) NPT - Nepal Time
             86 : (UTC+06) BIOT - British Indian Ocean Time
             87 : (UTC+06) BST - Bangladesh Standard Time
             88 : (UTC+06) BTT - Bhutan Time
             89 : (UTC+06) OMST - Omsk Time
             90 : (UTC+06:30) CCT - Cocos Islands Time
             91 : (UTC+06:30) MST - Myanmar Standard Time
             92 : (UTC+07) CXT - Christmas Island Time
             93 : (UTC+07) ICT - Indochina Time
             94 : (UTC+07) KRAT - Krasnoyarsk Time
             95 : (UTC+07) THA - Thailand Standard Time
             96 : (UTC+08) ACT - ASEAN Common Time
             97 : (UTC+08) AWST - Australian Western Standard Time
             98 : (UTC+08) BDT - Brunei Time
             99 : (UTC+08) CST - China Standard Time
             100 : (UTC+08) HKT - Hong Kong Time
             101 : (UTC+08) IRKT - Irkutsk Time
             102 : (UTC+08) MST - Malaysian Standard Time
             103 : (UTC+08) PST - Philippine Standard Time
             104 : (UTC+08) SST - Singapore Standard Time
             105 : (UTC+09) AWDT - Australian Western Daylight Time
             106 : (UTC+09) JST - Japan Standard Time
             107 : (UTC+09) KST - Korea Standard Time
             108 : (UTC+09) YAKT - Yakutsk Time
             109 : (UTC+09:30) ACST - Australian Central Standard Time
             110 : (UTC+10) AEST - Australian Eastern Standard Time
             111 : (UTC+10) ChST - Chamorro Standard Time
             112 : (UTC+10) VLAT - Vladivostok Time
             113 : (UTC+10:30) ACDT - Australian Central Daylight Time
             114 : (UTC+10:30) LHST - Lord Howe Standard Time
             115 : (UTC+11) AEDT - Australian Eastern Daylight Time
             116 : (UTC+11) MAGT - Magadan Time
             117 : (UTC+11) SBT - Solomon Islands Time
             118 : (UTC+11:30) NFT - Norfolk Time[1]
             119 : (UTC+12) FJT - Fiji Time
             120 : (UTC+12) GILT - Gilbert Island Time
             121 : (UTC+12) PETT - Kamchatka Time
             122 : (UTC+12:45) CHAST - Chatham Standard Time
             123 : (UTC+13) PHOT - Phoenix Island Time
             124 : (UTC+14) LINT - Line Islands Time"
		::={whispApsConfig 89}

	ofdmSMRcvTargetLvl	OBJECT-TYPE
		SYNTAX		INTEGER (-80..-40)
		UNITS		"dBm"
		MAX-ACCESS	read-write
		STATUS		current
		DESCRIPTION		
			"Desired SM Receive Level at AP (dBm, Range -40dBm to -80 dBm). As of release 12.1, on MIMO systems this is a combined power level value."
		::={whispApsConfig 90}

	radiusPort	OBJECT-TYPE
		SYNTAX		INTEGER
		MAX-ACCESS	read-write
		STATUS		current
		DESCRIPTION		
			"Port used to connect to the RADIUS server.  Default is 1812."
		::={whispApsConfig 91}

	radiusAcctPort	OBJECT-TYPE
		SYNTAX		INTEGER
		MAX-ACCESS	read-write
		STATUS		current
		DESCRIPTION		
			"Port used to for RADIUS Accounting.  Default is 1813."
		::={whispApsConfig 92}

	lastSesStatsReset	OBJECT-TYPE
		SYNTAX		DisplayString
		MAX-ACCESS	read-only
		STATUS		current
		DESCRIPTION		
			"Displays the timestamp of last reset of session stats or None otherwise."
		::={whispApsConfig 93}

	resetSesStats	OBJECT-TYPE
		SYNTAX		INTEGER {
					noReset(0),
					reset(1)}
		MAX-ACCESS	read-write
		STATUS		current
		DESCRIPTION		
			"Resets the session stats if true."
		::={whispApsConfig 94}

	rfOLTrap	OBJECT-TYPE
		SYNTAX		INTEGER {
					enable(1),
					disable(0)}
		MAX-ACCESS	read-write
		STATUS		current
		DESCRIPTION		
			"Enable/Disable SNMP Trap for when RF Overload exceeds configured Threshold level."
		::={whispApsConfig 95}

	rfOLThreshold	OBJECT-TYPE
		SYNTAX		INTEGER (1..100)
		UNITS		"%"
		MAX-ACCESS	read-write
		STATUS		current
		DESCRIPTION		
			"Percent of packet overload in the RF Downlink where SNMP is generated and sent to Network Manager."
		::={whispApsConfig 96}

	rfOLEnable	OBJECT-TYPE
		SYNTAX		INTEGER {
					enable(1),
					disable(0)}
		MAX-ACCESS	read-write
		STATUS		current
		DESCRIPTION		
			"Enable/Disable Throughput RF Overload Monitoring monitoring."
		::={whispApsConfig 97}

	actionListFilename	OBJECT-TYPE
		SYNTAX		DisplayString
		MAX-ACCESS	read-write
		STATUS		current
		DESCRIPTION		
			"Name of the file that contains the Action List for Auto update commands from CNUT"
		::={whispApsConfig 98}

	enableAutoupdate	OBJECT-TYPE
		SYNTAX		INTEGER {
					disable(0),
					enable(1)}
		MAX-ACCESS	read-write
		STATUS		current
		DESCRIPTION		
			"Enables/Disables auto-update of the SM's under an AP"
		::={whispApsConfig 99}

	accountingSmReAuthInterval	OBJECT-TYPE
		SYNTAX		INTEGER
		MAX-ACCESS	read-write
		STATUS		current
		DESCRIPTION		
			"Select Interval for Reauthentication of SM"
		::={whispApsConfig 100}

	syslogDomainNameAppend	OBJECT-TYPE
		SYNTAX		INTEGER {
					disableDomain(0),
					appendDomain(1)}
		MAX-ACCESS	read-write
		STATUS		deprecated
		DESCRIPTION		
			"This attribute is deprecated. Use syslogDomainNameAppend in whispBoxAttributesGroup"
		::={whispApsConfig 101}

	syslogServerAddr	OBJECT-TYPE
		SYNTAX		DisplayString
		MAX-ACCESS	read-write
		STATUS		deprecated
		DESCRIPTION		
			"This attribute is deprecated. Use syslogServerAddr in whispBoxAttributesGroup"
		::={whispApsConfig 102}

	syslogServerPort	OBJECT-TYPE
		SYNTAX		INTEGER
		MAX-ACCESS	read-write
		STATUS		deprecated
		DESCRIPTION		
			"This attribute is deprecated. Use syslogServerPort in whispBoxAttributesGroup"
		::={whispApsConfig 103}

	syslogXmitAP	OBJECT-TYPE
		SYNTAX		INTEGER {
					disable(0),
					enable(1)}
		MAX-ACCESS	read-write
		STATUS		current
		DESCRIPTION		
			"Enables/Disables transmission of Syslogs from AP/BHM"
		::={whispApsConfig 104}

	syslogXmitSMs	OBJECT-TYPE
		SYNTAX		INTEGER {
					disable(0),
					enable(1)}
		MAX-ACCESS	read-write
		STATUS		current
		DESCRIPTION		
			"Enables/Disables transmission of Syslogs from connected SMs/BHS. This can be over-ridden by the setting on individual SMs/ the BHS."
		::={whispApsConfig 105}

	accountingInterimUpdateInterval	OBJECT-TYPE
		SYNTAX		INTEGER
		MAX-ACCESS	read-write
		STATUS		current
		DESCRIPTION		
			"Select Interval for Interim Updates"
		::={whispApsConfig 106}

	gpsOutputEn	OBJECT-TYPE
		SYNTAX		INTEGER {
					off(0),
					on(1)}
		MAX-ACCESS	read-write
		STATUS		deprecated
		DESCRIPTION		
			"Controls sync config for AUX port.
                            On 450b SM/BHS and all AP/BHM's except for 450b BHM, there are two options: 0 disabled and 1 output.  
                            On 450b disabled allows alignment tone to output to the AUX port and on all AP/BHM's except for 450b 
                            BHM disabled allows sync input from AUX port.  On both output allows the sync output to the AUX port.
                            
                            On 450b BHM, there are three options: 0 disable, 1 output, and 2 input. Disabled allows alignment tone 
                            output to the AUX port, output allows sync output to the AUX port, and input allows sync input from AUX port.
                            
                            Deprecated in 16.1 - Use corresponding OID in whipsBoxConfig MIB."
		::={whispApsConfig 107}

	removeIdleSMs	OBJECT-TYPE
		SYNTAX		INTEGER {
					stopped(0),
					start(1)}
		MAX-ACCESS	read-write
		STATUS		current
		DESCRIPTION		
			"Setting this to a value 1 will remove all SMs which are in Idle state from AP's Session list."
		::={whispApsConfig 108}

	lastTimeIdleSMsRemoved	OBJECT-TYPE
		SYNTAX		DisplayString
		MAX-ACCESS	read-only
		STATUS		current
		DESCRIPTION		
			"Displays the timestamp of last removal of Idle SMs from AP's Session list"
		::={whispApsConfig 109}

	userAuthSharedSecret1	OBJECT-TYPE
		SYNTAX		DisplayString
		MAX-ACCESS	read-write
		STATUS		current
		DESCRIPTION		
			"User Authentication Server 1 Shared Secret."
		::={whispApsConfig 110}

	userAuthSharedSecret2	OBJECT-TYPE
		SYNTAX		DisplayString
		MAX-ACCESS	read-write
		STATUS		current
		DESCRIPTION		
			"User Authentication Server 2 Shared Secret."
		::={whispApsConfig 111}

	userAuthSharedSecret3	OBJECT-TYPE
		SYNTAX		DisplayString
		MAX-ACCESS	read-write
		STATUS		current
		DESCRIPTION		
			"User Authentication Server 3 Shared Secret."
		::={whispApsConfig 112}

	trapDelayAfterBootup	OBJECT-TYPE
		SYNTAX		INTEGER (0..120)
		UNITS		"seconds"
		MAX-ACCESS	read-write
		STATUS		current
		DESCRIPTION		
			"Delays sending of SNMP traps after radio boots up for this many number of seconds."
		::={whispApsConfig 113}

	sessionActions	OBJECT-TYPE
		SYNTAX		INTEGER {
					dropAllSessions(0),
					dropAllSessionsRemovePrimary(1)}
		MAX-ACCESS	read-write
		STATUS		current
		DESCRIPTION		
			"0: Drop all the sessions from AP.
                            1: Remove last known primary AP from all SMs/BHS which are in Registered state and also drop sessions."
		::={whispApsConfig 114}

	configAction	OBJECT-TYPE
		SYNTAX		INTEGER {
					instant(0),
					delayed(1),
					apply(2)}
		MAX-ACCESS	read-write
		STATUS		current
		DESCRIPTION		
			"Applicable after 16.1 onwards, AP/BHM now no longer required reboot when frequency and channel bandwidth settings are change
                        and radio start transmitting on new frequency.
                        Using this OID you can control configuring new value and when the setting should be applied.
                        0 - Instant, Radio will start transmitting on new configuration.(default)
                        1 - Delayed, Radio will save the new configuration but will wait to transmit.
                        2 - Apply changes, Radio will start transmitting on new configuration."
		::={whispApsConfig 116}

	radioMode	OBJECT-TYPE
		SYNTAX		INTEGER {
					mimoOnly(2)}
		MAX-ACCESS	read-write
		STATUS		obsolete
		DESCRIPTION		
			"This OID is obsolete."
		::={whispApsConfig 206}

	rfTelnetAccess	OBJECT-TYPE
		SYNTAX		INTEGER {
					disable(0),
					enable(1)}
		MAX-ACCESS	read-write
		STATUS		current
		DESCRIPTION		
			"Allows/prohibits uplink Telnet access (SM->AP)."
		::={whispApsConfig 207}

	upLnkMaxBurstDataRate	OBJECT-TYPE
		SYNTAX		INTEGER
		UNITS		"Kilobits/sec"
		MAX-ACCESS	read-write
		STATUS		current
		DESCRIPTION		
			"Maximum burst uplink rate."
		::={whispApsConfig 208}

	dwnLnkMaxBurstDataRate	OBJECT-TYPE
		SYNTAX		INTEGER
		UNITS		"Kilobits/sec"
		MAX-ACCESS	read-write
		STATUS		current
		DESCRIPTION		
			"Maximum burst downlink rate."
		::={whispApsConfig 209}

	rfPPPoEPADIForwarding	OBJECT-TYPE
		SYNTAX		INTEGER {
					disable(0),
					enable(1)}
		MAX-ACCESS	read-write
		STATUS		current
		DESCRIPTION		
			"Enables/disables forwarding of PPPoE PADI packets from AP to SM."
		::={whispApsConfig 210}

	allowedIPAccessNMLength1	OBJECT-TYPE
		SYNTAX		INTEGER (1..32)
		MAX-ACCESS	read-write
		STATUS		current
		DESCRIPTION		
			"Length of the network mask to apply to the AllowedIPAddress when assessing if access is allowed"
		::={whispApsConfig 211}

	allowedIPAccessNMLength2	OBJECT-TYPE
		SYNTAX		INTEGER (1..32)
		MAX-ACCESS	read-write
		STATUS		current
		DESCRIPTION		
			"Length of the network mask to apply to the AllowedIPAddress when assessing if access is allowed"
		::={whispApsConfig 212}

	allowedIPAccessNMLength3	OBJECT-TYPE
		SYNTAX		INTEGER (1..32)
		MAX-ACCESS	read-write
		STATUS		current
		DESCRIPTION		
			"Length of the network mask to apply to the AllowedIPAddress when assessing if access is allowed"
		::={whispApsConfig 213}

	bridgeFloodUnknownsEnable	OBJECT-TYPE
		SYNTAX		INTEGER {
					disable(0),
					enable(1)}
		MAX-ACCESS	read-write
		STATUS		current
		DESCRIPTION		
			"Forward unicast packets with an unknown address to all SMs. This can significantly reduce downlink throughput.
                            (0) - Drop unknown unicast packets.
                            (1) - Forward unknown unicast packets to all SMs."
		::={whispApsConfig 214}

	berModSelect	OBJECT-TYPE
		SYNTAX		INTEGER {
					qpsk(0),
					qam-8(4),
					qam-16(1),
					qam-32(5),
					qam-64(2),
					qam-128(6),
					qam-256(3)}
		MAX-ACCESS	read-write
		STATUS		current
		DESCRIPTION		
			"The BER modulation configured at the AP. 0 for QPSK, 1 for 16-QAM, 2 for 64-QAM, 3 for 256-QAM, 4 for 8-QAM, 5 for 32-QAM, 6 for 128-QAM.
                             Engineering use only."
		::={whispApsConfig 215}

	remoteSpectrumAnalyzerScanBandwidth	OBJECT-TYPE
		SYNTAX		INTEGER {
					bandwidth5MHz(0),
					bandwidth10MHz(1),
					bandwidth20MHz(2),
					bandwidth7MHz(3),
					bandwidth15MHz(4),
					bandwidth30MHz(5),
					bandwidth40MHz(6)}
		MAX-ACCESS	read-write
		STATUS		current
		DESCRIPTION		
			"Scanning Bandwidth used for the Remote Spectrum Analyzer. As of 22.0, this also changes the AP's channel bandwidth for a Spectrum Analysis in all other platforms except 450m."
		::={whispApsConfig 216}

	multicastVCDataRate	OBJECT-TYPE
		SYNTAX		INTEGER {
					disable(0),
					rate2XmimoB(5),
					rate3XmimoB(6),
					rate4XmimoB(7),
					rate5XmimoB(2),
					rate6XmimoB(8),
					rate7XmimoB(3),
					rate8XmimoB(9),
					rate1XmimoA(4),
					rate2XmimoA(10),
					rate3XmimoA(11),
					rate4XmimoA(12)}
		MAX-ACCESS	read-write
		STATUS		current
		DESCRIPTION		
			"Enables and selects the data rate of the Multicast VC.
                            If disabled, multicast messages are sent using the broadcast VC.
                            This VC does not automatically rate adapt.
                            Note: SMs that cannot receive at the selected rate will receive no multicast messages.
                            For PMP AP only."
		::={whispApsConfig 217}

	dlnkMcastCIR	OBJECT-TYPE
		SYNTAX		INTEGER
		MAX-ACCESS	read-write
		STATUS		current
		DESCRIPTION		
			"Downlink Multicast CIR (kbps).
                                Can only be set if Multicast VC is enabled.
                                For PMP AP only."
		::={whispApsConfig 218}

	multicastRetryCount	OBJECT-TYPE
		SYNTAX		INTEGER
		MAX-ACCESS	read-write
		STATUS		current
		DESCRIPTION		
			"Multicast Repeat Count : Range 0 - 2.
                            Can only be set if Multicast VC is enabled.
                            For PMP AP only."
		::={whispApsConfig 219}

	apConfigAdjacentChanSupport	OBJECT-TYPE
		SYNTAX		INTEGER {
					disable(0),
					enable(1)}
		MAX-ACCESS	read-write
		STATUS		current
		DESCRIPTION		
			"Used to enable or disable adjacent channel support.
                        This could be needed when there is no guard band between co-located APs.
                        Only available for APs in 3 GHz, 4.9 GHz and all 5 GHz frequency bands. 
                        For 3 GHz, this caps SMs to max transmit power of 23 dBm.
                        When disabled, allows 3 GHz SMs to max out transmit power at 25 dBm.
                        For 4.9-5.9 GHz, this caps 450b SMs to max transmit power of 25 dBm.
                        When disabled, allows 4.9-5.9 GHz 450b SMs to max out transmit power at 27 dBm."
		::={whispApsConfig 220}

	pmp430InteropMode	OBJECT-TYPE
		SYNTAX		INTEGER {
					mimoa(0),
					siso(1)}
		MAX-ACCESS	read-only
		STATUS		obsolete
		DESCRIPTION		
			"When the AP talks to a PMP 430 it can do so in either MIMO-A or SISO mode.
                            0 = MIMO-A
                            1 = SISO
                            Only applies to PMP 450 AP at 5 GHz.
                            By default in 13.2 the AP talks in MIMO-A to PMP 430 SISO SMs.
                            Setting this to a 1 will enable SISO mode to PMP 430 SISO SMs, as it was in 13.1.3 and before.

                            As of 16.1, PMP 430 SMs are no longer supported on the 450 platform.
                            On that release and forward, this OID is read-only and returns MIMO-A."
		::={whispApsConfig 221}

	framePeriod	OBJECT-TYPE
		SYNTAX		INTEGER {
					twoPointFiveMs(0),
					fiveMs(1)}
		MAX-ACCESS	read-write
		STATUS		current
		DESCRIPTION		
			"Changes frame period to 2.5 ms or 5ms.
                            Note: If set to 5 ms, only SM/BHS from 13.3 and onward will be able to register.
                            Only on PMP and PTP 450.
                            Not available in all regions."
		::={whispApsConfig 223}

	enableRadiusDynAuth	OBJECT-TYPE
		SYNTAX		INTEGER {
					disableDynAuth(0),
					enableDynAuth(1)}
		MAX-ACCESS	read-write
		STATUS		current
		DESCRIPTION		
			"This option can be used to enable Radius Dynamic Authorization Extensions.Both CoA, which change the SM config parameters from the Radius server while an SM is already in session and Disconnect Message are supported. 
            This option will only be used if Authentication mode is set to Radius AAA.
            0 - Disable Radius Dynamic Authorization Extension.
            1 - Enable Radius Dynamic Authorization Extension."
		::={whispApsConfig 224}

	pmp430SMRegistration	OBJECT-TYPE
		SYNTAX		INTEGER {
					deny(0),
					allow(1)}
		MAX-ACCESS	read-only
		STATUS		deprecated
		DESCRIPTION		
			"Option to allow/disallow PMP 430 SMs to register to this AP.
                            When disabled PMP 430 SMs registrations will be rejected.

                            As of 16.1, PMP 430 SMs are no longer supported on the 450 platform.
                            On that release and forward, this OID is read-only and returns deny."
		::={whispApsConfig 225}

	disableAuthForICCSM	OBJECT-TYPE
		SYNTAX		INTEGER {
					disabled(0),
					enabled(1)}
		MAX-ACCESS	read-write
		STATUS		current
		DESCRIPTION		
			"Bypass Authentication for ICC SMs"
		::={whispApsConfig 226}

	enableEuSecurityCheck	OBJECT-TYPE
		SYNTAX		INTEGER {
					disabled(0),
					enabled(1)}
		MAX-ACCESS	read-write
		STATUS		current
		DESCRIPTION		
			"Enable/Disable EU Security compliance check"
		::={whispApsConfig 227}

	onlyAllowPMP450iSMRegistration	OBJECT-TYPE
		SYNTAX		INTEGER {
					only450i(0),
					all(1)}
		MAX-ACCESS	read-write
		STATUS		current
		DESCRIPTION		
			"Option to limit SM registration to only allow PMP 450i and newer devices or allow all devices (450 and newer) to register.
                            Setting this to only 450i or newer will force an Auth Fail registration failure when a PMP 450 SM device tries to register.
                            This option only applies to PMP 450i or newer AP devices."
		::={whispApsConfig 228}

	pmp450430LegacyMode	OBJECT-TYPE
		SYNTAX		INTEGER {
					disabled(0),
					enabled(1)}
		MAX-ACCESS	read-only
		STATUS		deprecated
		DESCRIPTION		
			"Option to put the PMP 450b/450i/450m into a Legacy mode for communicating with PMP 450 SMs running SW older than 13.3 and PMP 430 SMs running SW older than 13.4.1.
                            Enabling this option will have an impact on sector throughput performance so should only be enabled to allow upgrading of the mixed sector.
                            450m will operate in SU-MIMO Mode.

                            As of 16.1, PMP 430 SMs are no longer supported on the 450 platform.
                            On that release and forward, this OID is read-only and returns disabled."
		::={whispApsConfig 229}

	pagerRejectFilterSelect	OBJECT-TYPE
		SYNTAX		INTEGER {
					enable(1),
					disable(0)}
		MAX-ACCESS	read-write
		STATUS		current
		DESCRIPTION		
			"Enable or disable the Pager filter which can filter out Pager signals interfering in the 900 MHz band.
                            NOTE: Frequencies 920 MHz and above will not work when enabled.
                            Only applicable to 900 MHz devices."
		::={whispApsConfig 230}

	freeRunGPSSyncBypass	OBJECT-TYPE
		SYNTAX		INTEGER {
					disabled(0),
					enabled(1)}
		MAX-ACCESS	read-write
		STATUS		current
		DESCRIPTION		
			"Enable to allow Free Run to begin immediately after radio bootup.  Normally, Free Run is only allowed
                        after GPS sync has been established at least once, then lost."
		::={whispApsConfig 231}

	useAPManagementVIDForICCSM	OBJECT-TYPE
		SYNTAX		INTEGER {
					disable(0),
					enable(1)}
		MAX-ACCESS	read-write
		STATUS		current
		DESCRIPTION		
			"When enabled, SM connected via ICC uses APs MVID instead of its own."
		::={whispApsConfig 232}

	frameAlignmentLegacyMode	OBJECT-TYPE
		SYNTAX		INTEGER {
					off(0),
					mode1(1),
					mode2(2)}
		MAX-ACCESS	read-write
		STATUS		deprecated
		DESCRIPTION		
			"Option to adjust the frame alignment for compatibility with different GPS sync sources and software versions.
                            Please see user guide for more information.
                            Not applicable to 3 GHz radios running with 5ms frame, nor PMP 450m.
                            As of 22.1 this OID is deprecated and only supports alignment with software release 16.X and later."
		::={whispApsConfig 233}

	noRebootFreqChange	OBJECT-TYPE
		SYNTAX		INTEGER {
					default(0),
					noreboot(1)}
		MAX-ACCESS	read-write
		STATUS		current
		DESCRIPTION		
			"Enable/Disable option to change frequency without rebooting.
                            Engineering use only."
		::={whispApsConfig 234}

	mumimoTrialMode	OBJECT-TYPE
		SYNTAX		INTEGER {
					enable(1),
					disable(0)}
		MAX-ACCESS	read-write
		STATUS		current
		DESCRIPTION		
			"Enable MU-MIMO Trial, Trial Mode units will decrement until units are exhausted or Trial Mode is disabled.
                            Disable MU-MIMO Trial, radio is still functional with SU-MIMO operation. Trial Mode units will not decrement.                   
                            450m only."
		::={whispApsConfig 236}

	weightedWindowInterval	OBJECT-TYPE
		SYNTAX		INTEGER (1..127)
		UNITS		"TDD Frames"
		MAX-ACCESS	read-write
		STATUS		current
		DESCRIPTION		
			"Weighted Window Interval for SM Prioritization and Weighted Fair Queueing.
                            Indicates the number of TDD frames over which the SM Prioritization, WFQ, and Rate Plan will be managed.
                            Engineering only."
		::={whispApsConfig 237}

	smPrioritization	OBJECT-TYPE
		SYNTAX		INTEGER {
					disabled(0),
					enabled(1)}
		MAX-ACCESS	read-write
		STATUS		current
		DESCRIPTION		
			"SM Prioritization Enable/Disable.
                            Currently not supported on PMP 450m."
		::={whispApsConfig 238}

	smPrioritizationAllocationLow	OBJECT-TYPE
		SYNTAX		INTEGER (1..100)
		UNITS		"%"
		MAX-ACCESS	read-write
		STATUS		current
		DESCRIPTION		
			"SM Prioritization Low Group allocation.
                            Indicates the percentage of the scheduling window allocated for the SM Prioritization Low Group."
		::={whispApsConfig 239}

	smPrioritizationAllocationHigh	OBJECT-TYPE
		SYNTAX		INTEGER (0..99)
		UNITS		"%"
		MAX-ACCESS	read-only
		STATUS		current
		DESCRIPTION		
			"SM Prioritization High Group allocation.
                            Indicates the percentage of the scheduling window allocated for the SM Prioritization High Group.
                            This is read-only because it is derived from the SM Prioritization Low Group Rate."
		::={whispApsConfig 240}

	wfq	OBJECT-TYPE
		SYNTAX		INTEGER {
					disabled(0),
					enabled(1)}
		MAX-ACCESS	read-write
		STATUS		current
		DESCRIPTION		
			"Weighted Fair Queuing Enable/Disable.
                            Currently not supported on PMP 450m."
		::={whispApsConfig 241}

	wfqAllocationLowSMPrioritization	OBJECT-TYPE
		SYNTAX		DisplayString
		MAX-ACCESS	read-write
		STATUS		current
		DESCRIPTION		
			"Weighted Fair Queuing Allocation for SM Prioritization Low Group.
                            Indicates the percentage of the scheduling window allocated for the various QoS Levels for the SM Prioritization Low Group.
                            Please enter the 5 allocations, commma separated, which correspond to the following Data Channels:
                            (Broadcast/Multicast, Low Priority, Medium Priority, High Priority, Ultra High Priority).
                            The sum of of the values must add up to 100.
                            If more than 5 values are entered, only the first 5 will be considered, the rest will be discarded.
                            It is valid to enter fewer than 5 values, in this case the values entered will be concatentated with the unchanged values,
                            but the sum must still add up to 100."
		::={whispApsConfig 242}

	wfqAllocationHighSMPrioritization	OBJECT-TYPE
		SYNTAX		DisplayString
		MAX-ACCESS	read-write
		STATUS		current
		DESCRIPTION		
			"Weighted Fair Queuing Allocation for High SM Prioritization.
                            Indicates the percentage of the scheduling window allocated for the various Data Channels for the SM Prioritization High Group.
                            Please enter the 4 allocations, commma separated, which correspond to the following QoS Levels:
                            (Low Priority, Medium Priority, High Priority, Ultra High Priority).
                            The sum of of the values must add up to 100.
                            If more than 4 values are entered, only the first 4 will be considered, the rest will be discarded.
                            It is valid to enter fewer than 4 values, in this case the values entered will be concatentated with the unchanged values,
                            but the sum must still add up to 100."
		::={whispApsConfig 243}

	authKey256Ap	OBJECT-TYPE
		SYNTAX		DisplayString
		MAX-ACCESS	read-write
		STATUS		current
		DESCRIPTION		
			"Authentication key 256-bit. It should be up to 64 hex characters long.  Can be used on MultiPoint AP if PSK Authentication mode is selected.
            Otherwise, it is used on Backhauls. If the AP and SM are both capable of AES-256 they will use this."
		::={whispApsConfig 244}

	authKey256OptionAP	OBJECT-TYPE
		SYNTAX		INTEGER {
					useDefault(0),
					useKeySet(1)}
		MAX-ACCESS	read-write
		STATUS		current
		DESCRIPTION		
			"This option is for Multipoint APs only.  This option will only be used if Authentication Mode is set
            to AP Pre-Shared Key.
            0 - Use default 256-bit key.
            1 - Use set 256-bit key."
		::={whispApsConfig 245}

	localNTPServer	OBJECT-TYPE
		SYNTAX		INTEGER {
					disablentp(0),
					enabletntp(1)}
		MAX-ACCESS	read-write
		STATUS		current
		DESCRIPTION		
			"This OID determines if NTP server is enabled or not.
                          0: Disable NTP server
                          1: Enable NTP server"
		::={whispApsConfig 246}

	prioritizeMgmtData	OBJECT-TYPE
		SYNTAX		INTEGER {
					low(0),
					high(1)}
		MAX-ACCESS	read-write
		STATUS		current
		DESCRIPTION		
			"0 - Management data will use low priority VC.
                           1 - If high priority VC is configured will use that, otherwise will use low priority VC"
		::={whispApsConfig 247}

	smLimit	OBJECT-TYPE
		SYNTAX		INTEGER (1..238)
		MAX-ACCESS	read-write
		STATUS		current
		DESCRIPTION		
			"SM Registration Limit. This represents the maximum number of subscribers that can register to this AP."
		::={whispApsConfig 248}

	oneXEnable	OBJECT-TYPE
		SYNTAX		INTEGER {
					disable(0),
					enable(1)}
		MAX-ACCESS	read-write
		STATUS		current
		DESCRIPTION		
			"enable(1) or disable(0) 802.1X Authentication."
		::={whispApsConfig 249}

	oneXSharedSecret	OBJECT-TYPE
		SYNTAX		DisplayString
		MAX-ACCESS	read-write
		STATUS		current
		DESCRIPTION		
			"802.1X Authentication Server Shared Secret."
		::={whispApsConfig 250}

	lteFrameConfigurationOption	OBJECT-TYPE
		SYNTAX		INTEGER {
					disable(0),
					config0(1),
					config1(2),
					config2(3)}
		MAX-ACCESS	read-write
		STATUS		current
		DESCRIPTION		
			"Used to determine if Co-location with LTE is being used and calculate the frame delay needed so PMP and LTE frames can align."
		::={whispApsConfig 252}

	apScheduler	OBJECT-TYPE
		SYNTAX		INTEGER {
					legacy(0),
					proportional(1),
					airtimeFairness(2)}
		MAX-ACCESS	read-write
		STATUS		current
		DESCRIPTION		
			"Scheduler selection legacy or proportional or airtime fairness.
                                     Airtime Fairness scheduler is same as Proportion scheduler with fixed configuration
                                     parameters for all SMs. Proportional scheduler will be enabled for proportional and 
                                     airtime fairness configuration."
		::={whispApsConfig 253}

	defaultDownlinkPlan	OBJECT-TYPE
		SYNTAX		INTEGER
		MAX-ACCESS	read-write
		STATUS		current
		DESCRIPTION		
			"Default downlink plan in Kbps."
		::={whispApsConfig 254}

	defaultUplinkPlan	OBJECT-TYPE
		SYNTAX		INTEGER
		MAX-ACCESS	read-write
		STATUS		current
		DESCRIPTION		
			"Default uplink plan in Kbps"
		::={whispApsConfig 255}

	dhcpRelayOpt82CircuitID	OBJECT-TYPE
		SYNTAX		DisplayString
		MAX-ACCESS	read-write
		STATUS		current
		DESCRIPTION		
			"Circuit ID for DHCP Relay Option 82 data.  Supports following wildcards:
                               $apmac$  - AP MAC address in ascii format, no delimiters
                               $apmacbi$ - AP MAC address in hex format (6 bytes)
                               $smmac$  - SM MAC address in ascii format, no delimiters
                               $smmacbi$ - SM MAC address in hex format (6 bytes)
                               $apsn$   - AP Site Name (may be truncated to 32 chars)
                               $smsn$   - SM Site Name (may be truncated to 32 chars)
                               $smvid$  - SM Port VID in ascii format, leading 0 included, 4 chars long
                               $smvidbi$ - SM Port VID in hex format (2 bytes)
                               $smluid$ - SM LUID
                             
                            Note that overall expanded Option 82 data is limited to 255 bytes."
		::={whispApsConfig 257}

	dhcpRelayOpt82RemoteID	OBJECT-TYPE
		SYNTAX		DisplayString
		MAX-ACCESS	read-write
		STATUS		current
		DESCRIPTION		
			"Remote ID for DHCP Relay Option 82 data.  Supports following wildcards:
                               $apmac$  - AP MAC address in ascii format, no delimiters
                               $apmacbi$ - AP MAC address in hex format (6 bytes)
                               $smmac$  - SM MAC address in ascii format, no delimiters
                               $smmacbi$ - SM MAC address in hex format (6 bytes)
                               $apsn$   - AP Site Name (may be truncated to 32 chars)
                               $smsn$   - SM Site Name (may be truncated to 32 chars)
                               $smvid$  - SM Port VID in ascii format, leading 0 included, 4 chars long
                               $smvidbi$ - SM Port VID in hex format (2 bytes)
                               $smluid$ - SM LUID
                             
                            Note that overall expanded Option 82 data is limited to 255 bytes."
		::={whispApsConfig 258}

	dhcpRelayOpt82VendorSpecificID	OBJECT-TYPE
		SYNTAX		DisplayString
		MAX-ACCESS	read-write
		STATUS		current
		DESCRIPTION		
			"Vendor Specific ID for DHCP Relay Option 82 data.  Supports following wildcards:
                               $apmac$  - AP MAC address in ascii format, no delimiters
                               $apmacbi$ - AP MAC address in hex format (6 bytes)
                               $smmac$  - SM MAC address in ascii format, no delimiters
                               $smmacbi$ - SM MAC address in hex format (6 bytes)
                               $apsn$   - AP Site Name (may be truncated to 32 chars)
                               $smsn$   - SM Site Name (may be truncated to 32 chars)
                               $smvid$  - SM Port VID in ascii format, leading 0 included, 4 chars long
                               $smvidbi$ - SM Port VID in hex format (2 bytes)
                               $smluid$ - SM LUID
                             
                            Note that overall expanded Option 82 data is limited to 255 bytes."
		::={whispApsConfig 259}

	autoContention	OBJECT-TYPE
		SYNTAX		INTEGER {
					disabled(0),
					enabled(1)}
		MAX-ACCESS	read-write
		STATUS		current
		DESCRIPTION		
			"Enable Auto Contention.
                            Currently not supported on PMP 450m."
		::={whispApsConfig 260}

	lqiMetric	OBJECT-TYPE
		SYNTAX		INTEGER {
					rate(0),
					evm(1)}
		MAX-ACCESS	read-write
		STATUS		current
		DESCRIPTION		
			"Metric used for LQI"
		::={whispApsConfig 261}

	lqiTrapsEnable	OBJECT-TYPE
		SYNTAX		INTEGER {
					disabled(0),
					enabled(1)}
		MAX-ACCESS	read-write
		STATUS		current
		DESCRIPTION		
			"Enable or Disable LQI Traps."
		::={whispApsConfig 262}

	lqiRaiseTrapThreshold	OBJECT-TYPE
		SYNTAX		INTEGER (1..99)
		MAX-ACCESS	read-write
		STATUS		current
		DESCRIPTION		
			"Minimum tolerable decreasing LQI level. Trap will be raised when delta from reference LQI falls below this level."
		::={whispApsConfig 263}

	lqiClearTrapThreshold	OBJECT-TYPE
		SYNTAX		INTEGER (1..99)
		MAX-ACCESS	read-write
		STATUS		current
		DESCRIPTION		
			"Minimum tolerable increasing LQI level. Trap will be cleared when delta from reference LQI raises above this level."
		::={whispApsConfig 264}

	lqiTrapsObservePeriod	OBJECT-TYPE
		SYNTAX		INTEGER (1..15)
		MAX-ACCESS	read-write
		STATUS		current
		DESCRIPTION		
			"Minimum observation period in minutes before traps are raised or cleared."
		::={whispApsConfig 265}

	otarInterval	OBJECT-TYPE
		SYNTAX		INTEGER (0..1440)
		UNITS		"minutes"
		MAX-ACCESS	read-write
		STATUS		current
		DESCRIPTION		
			"Over The Air Rekey Interval : 60 -- 1440 Minutes, 0 for disabling the feature.
                        
                        Available only if feature key is applied."
		::={whispApsConfig 266}

	systemTimeSet	OBJECT-TYPE
		SYNTAX		INTEGER {
					allowGpsSetSystemTime(0),
					noGpsSetSystemTime(1)}
		MAX-ACCESS	read-write
		STATUS		current
		DESCRIPTION		
			"The radio's System Time can be set via NTP, GPS, cnMaestro or manually.
                            This OID controls what sources allow the radio's System Time to be set.
                            
                            0 = Allow GPS to set System Time (default)
                            1 = Do not allow GPS to set System Time. 
                            This can be helpful for certain GPS chips that occasionally give incorrect date and/or time.
                            
                            When running CBRS, this OID is read-only to not allow GPS to set the time and will need to be set via NTP."
		::={whispApsConfig 267}

	bhsTxPowerControl	OBJECT-TYPE
		SYNTAX		INTEGER {
					disable(0),
					enable(1)}
		MAX-ACCESS	read-write
		STATUS		current
		DESCRIPTION		
			"Disable/Enable on BHM to control BHS Tx power remotely."
		::={whispApsConfig 268}

	autoUpdateFileServer	OBJECT-TYPE
		SYNTAX		INTEGER {
					enable(1),
					disable(0)}
		MAX-ACCESS	read-write
		STATUS		obsolete
		DESCRIPTION		
			"Added in 16.2.1 to allow 450 APs to host 450i and 450b images for AutoUpdate.
                        Obsolete in 20.0 whereas this is no longer possible.
                        As a work-around, use CNUT as a File Server, or use cnMaestro to upgrade."
		::={whispApsConfig 269}

	paHighbandSwitchoverFrequency	OBJECT-TYPE
		SYNTAX		INTEGER (3302500..4197500)
		MAX-ACCESS	read-write
		STATUS		current
		DESCRIPTION		
			"Power Amplifier high band switch over frequency point.
                            450m only
                            Engineering use only"
		::={whispApsConfig 270}

	rfHighbandSwitchoverFrequency	OBJECT-TYPE
		SYNTAX		INTEGER (3302500..4197500)
		MAX-ACCESS	read-write
		STATUS		current
		DESCRIPTION		
			"RF high band switch over frequency point.
                            450m only
                            Engineering use only"
		::={whispApsConfig 271}

	reconnectReportEnable	OBJECT-TYPE
		SYNTAX		INTEGER {
					disable(0),
					enable(1)}
		MAX-ACCESS	read-write
		STATUS		current
		DESCRIPTION		
			"Enable(1)/Disable(0) SM reconnection failure report after channel change or EIRP change.
                            PMP only."
		::={whispApsConfig 272}

	failureReportingThreshold	OBJECT-TYPE
		SYNTAX		INTEGER (0..100)
		MAX-ACCESS	read-write
		STATUS		current
		DESCRIPTION		
			"Failure reporting threshold percentage. 
                            If the percentage of number of SMs which failed to reconnect after EIRP/channel change exceeds this value, failure will be reported (default is 10%).
                            PMP only."
		::={whispApsConfig 273}

	reconnectReportDuration	OBJECT-TYPE
		SYNTAX		INTEGER (1..30)
		MAX-ACCESS	read-write
		STATUS		current
		DESCRIPTION		
			"Stop reporting reconnection failure after configured duration, default is 7 days.
                            PMP only."
		::={whispApsConfig 274}

	bhsRcvTargetLvl	OBJECT-TYPE
		SYNTAX		INTEGER
		MAX-ACCESS	read-write
		STATUS		current
		DESCRIPTION		
			"Desired receive power level at BHM in dBm. bhsTxPowerControl must be enabled on the BHM for this level to be targetted."
		::={whispApsConfig 275}

	speedTestServer1	OBJECT-TYPE
		SYNTAX		DisplayString
		MAX-ACCESS	read-write
		STATUS		current
		DESCRIPTION		
			"Set the speed test server IPv4 IP. The traffic to this server gets elevated to high prioritization. 
                            This is designed to help get improved results for a speed test server while other traffic is on the sector.
                            Setting 0.0.0.0 disables this feature."
		::={whispApsConfig 276}

	otherFrameConfigurationOption	OBJECT-TYPE
		SYNTAX		INTEGER {
					disable(0),
					lteFrameConfig0(1),
					lteFrameConfig1(2),
					lteFrameConfig2(3),
					fiveGNRFrameConfig1(4),
					fiveGNRFrameConfig2(5)}
		MAX-ACCESS	read-write
		STATUS		current
		DESCRIPTION		
			"Used to determine if Co-location with LTE or 5G-NR is being used and calculate the frame delay needed so PMP and LTE or 5G frames can align. Available on 3 GHz PMP AP radios only and reboot required."
		::={whispApsConfig 277}

	lteSFrameConfiguration	OBJECT-TYPE
		SYNTAX		INTEGER {
					s0(0),
					s1(1),
					s2(2),
					s3(3),
					s4(4),
					s5(5),
					s6(6),
					s7(7),
					s8(8),
					s9(9)}
		MAX-ACCESS	read-write
		STATUS		current
		DESCRIPTION		
			"The Special Frame type used on the LTE device to be co-located with. Applicable only if otherFrameConfigurationOption is set to one of the LTE options."
		::={whispApsConfig 278}

	lteCyclicPrefix	OBJECT-TYPE
		SYNTAX		INTEGER {
					normal(0),
					extended(1)}
		MAX-ACCESS	read-write
		STATUS		current
		DESCRIPTION		
			"The downlink and uplink cyclic prefix used on the LTE device to be co-located with. Applicable only if otherFrameConfigurationOption is set to one of the LTE options."
		::={whispApsConfig 279}

	guardSymbols5GNR	OBJECT-TYPE
		SYNTAX		INTEGER {
					normal(4),
					extended(6)}
		MAX-ACCESS	read-write
		STATUS		current
		DESCRIPTION		
			"The guard symbols on the 5G-NR device to be co-located with. Applicable only if otherFrameConfigurationOption is set to 5G-NR option."
		::={whispApsConfig 280}

	interferenceCancellationTrialMode	OBJECT-TYPE
		SYNTAX		INTEGER {
					enable(1),
					disable(0)}
		MAX-ACCESS	read-write
		STATUS		current
		DESCRIPTION		
			"Enable Interference Cancellation Trial, Trial Mode units will decrement until units are exhausted or Trial Mode is disabled.
                            Disable Interference Cancellation Trial, radio is still functional with UL MU-MIMO operation. Trial Mode units will not decrement.                   
                            450m only."
		::={whispApsConfig 281}

	interferenceCancellation	OBJECT-TYPE
		SYNTAX		INTEGER {
					disabled(0),
					enabled(1)}
		MAX-ACCESS	read-write
		STATUS		current
		DESCRIPTION		
			"Note that if Interference Cancellation is enabled then UL MU-MIMO operation is disabled.                
                            450m only."
		::={whispApsConfig 282}

	domainProxyTimeSynch	OBJECT-TYPE
		SYNTAX		INTEGER {
					disable(0),
					enable(1)}
		MAX-ACCESS	read-write
		STATUS		current
		DESCRIPTION		
			"Enables device to automatically use the Domain Proxy time in CBRS mode if the local time gets out of sync."
		::={whispApsConfig 283}

	radiusVendorID	OBJECT-TYPE
		SYNTAX		INTEGER {
					legacy(0),
					cambium(1)}
		MAX-ACCESS	read-write
		STATUS		current
		DESCRIPTION		
			"(0) - Supports Legacy Vendor Id (161).
            				(1) - Supports Cambium Vendor ID (17713)."
		::={whispApsConfig 284}

	limit450bSMMaxTxPowerEnable	OBJECT-TYPE
		SYNTAX		INTEGER {
					disable(0),
					enable(1)}
		MAX-ACCESS	read-write
		STATUS		current
		DESCRIPTION		
			"Enable/Disable AP control of 450b SM Max Tx power."
		::={whispApsConfig 285}

	limit450bSMMaxTxPowerValue	OBJECT-TYPE
		SYNTAX		INTEGER
		MAX-ACCESS	read-write
		STATUS		current
		DESCRIPTION		
			"Value of AP Controlled 450b SM Max Tx Power."
		::={whispApsConfig 286}

	whispRegStatus	OBJECT-TYPE
		SYNTAX		DisplayString
		MAX-ACCESS	read-only
		STATUS		obsolete
		DESCRIPTION		
			"This shows the registration status of a link.[This variable is deprecated, please refer whispBoxLink OIDs]"
		::={whispApsLink 4}

-- Link test configuration

	linkTestLUID	OBJECT-TYPE
		SYNTAX		INTEGER
		MAX-ACCESS	read-write
		STATUS		deprecated
		DESCRIPTION		
			"LUID selection for Link Test. Valid range: 2-255. [This variable is deprecated, please refer whispBoxLink OIDs]"
		::={whispApsLinkTestConfig 1}

	linkTestDuration	OBJECT-TYPE
		SYNTAX		INTEGER
		MAX-ACCESS	read-write
		STATUS		deprecated
		DESCRIPTION		
			"Duration for the Link Test. Valid range: 2-10 seconds. [This variable is deprecated, please refer whispBoxLink OIDs]"
		::={whispApsLinkTestConfig 2}

-- Link test action

	linkTestAction	OBJECT-TYPE
		SYNTAX		INTEGER {
					stopped(0),
					start(1)}
		MAX-ACCESS	read-write
		STATUS		deprecated
		DESCRIPTION		
			"Setting value 1 will initiate link test. Note that trying to set 0 will not stop the test.
            In fact it will return an error message. The value of 0 just indicates the idle state
            meaning no test is running or the current test is done.
            That's why the word stopped is used and not the action verb stop.
            [This variable is deprecated, please refer whispBoxLink OIDs]"
		::={whispApsLinkTestConfig 3}

	linkTestPktLength	OBJECT-TYPE
		SYNTAX		INTEGER
		MAX-ACCESS	read-write
		STATUS		deprecated
		DESCRIPTION		
			"Packet length for Link Test. Valid range: 64-1714 bytes. [This variable is deprecated, please refer whispBoxLink OIDs]"
		::={whispApsLinkTestConfig 4}

	linkTestMode	OBJECT-TYPE
		SYNTAX		INTEGER {
					linktestwithmultipleVCs(4),
					linktestwithoutbridging(0),
					linktestwithbridging(1),
					linktestwithbridgingandmir(2),
					extrapolatedlinktest(3)}
		MAX-ACCESS	read-write
		STATUS		deprecated
		DESCRIPTION		
			"Link Test Mode
                            0 = Link Test without Bridging
                            1 = Link Test with Bridging
                            2 = Link Test with Bridging and MIR
                            3 = Extrapolated Link Test (send only a few packets measuring their quality and extrapolate out the throughput)
                            This is an estimation of the throughput based upon the modulation, efficiency, and data slots available.
                            It intended to provide a basic link test test without impacting service for the sector.
                            Extrapolated Link Test is not available for FSK radios.
                            4 = Link Test with Multiple LUIDs (traffic sent to all registered VCs, or specified VCs) - 450m only
                            [This Variable is deprecated. Please refer whispBoxLink OIDs]"
		::={whispApsLinkTestConfig 5}

	linkTestSNRCalculation	OBJECT-TYPE
		SYNTAX		INTEGER {
					enable(1),
					disable(0)}
		MAX-ACCESS	read-write
		STATUS		deprecated
		DESCRIPTION		
			"Enable or disable Signal to Noise Ratio (SNR) calculations during a Link Test.
                            Enabling(1) will calulate SNR on all receiving packets.
                            Due to load on CPU, will slightly degrade packet per second capabilities.
                            Only applicable to GenII OFDM products and up.
                            [This Variable is deprecated. Please refer whispBoxLink OIDs]"
		::={whispApsLinkTestConfig 6}

	linkTestWithDualPath	OBJECT-TYPE
		SYNTAX		INTEGER {
					lowpriorityvconly(0),
					highandlowpriorityvcs(1)}
		MAX-ACCESS	read-write
		STATUS		deprecated
		DESCRIPTION		
			"Link Test with:
                            0 = Low Priority Data Channel only
                            1 = High and Low Priority Data Channels
                            [This variable is deprecated. Please refer whispBoxLink OIDs]"
		::={whispApsLinkTestConfig 7}

-- Link test configuration

	linkTestNumPkt	OBJECT-TYPE
		SYNTAX		INTEGER
		MAX-ACCESS	read-write
		STATUS		deprecated
		DESCRIPTION		
			"Number of packets to send. Valid range: 0-512 where 0 will
            flood the link for the duration of the test.
            [This variable is deprecated. Please refer whispBoxLink OIDs]"
		::={whispApsLinkTestConfig 8}

	linkTestForceModulation	OBJECT-TYPE
		SYNTAX		INTEGER {
					normalRateAdapt(0),
					forceMaxModulation(1)}
		MAX-ACCESS	read-write
		STATUS		deprecated
		DESCRIPTION		
			"Engineering use only.
                            Link Test with:
                            0 = Normal Rate Adapt algorithm
                            1 = Force to max modultion - No Rate Adapt Algorithm
                            [This variable is deprecated. Please refer whispBoxLink OIDs]"
		::={whispApsLinkTestConfig 9}

	linkTestDirection	OBJECT-TYPE
		SYNTAX		INTEGER {
					bidirectional(0),
					uplinkonly(1),
					downlinkonly(2)}
		MAX-ACCESS	read-write
		STATUS		deprecated
		DESCRIPTION		
			"Link Test Direction - Engineering Use Only
                            0 = default (will do bidirectional)
                            1 = Uplink Only
                            2 = Downlink Only
                            3 = Bi-Directional (same as 0, setting to 3 will result in setting it to 0)
                            [This variable is deprecated. Please refer whispBoxLink OIDs]"
		::={whispApsLinkTestConfig 10}

-- Link test results

	testLUID	OBJECT-TYPE
		SYNTAX		INTEGER
		MAX-ACCESS	read-only
		STATUS		deprecated
		DESCRIPTION		
			"LUID number of selected unit. [This variable is deprecated, please refer whispBoxLink OIDs]"
		::={whispApsLinkTestResult 1}

	linkTestStatus	OBJECT-TYPE
		SYNTAX		DisplayString
		MAX-ACCESS	read-only
		STATUS		deprecated
		DESCRIPTION		
			"Status for Link Test.[This variable is deprecated, please refer whispBoxLink OIDs]"
		::={whispApsLinkTestResult 2}

	linkTestError	OBJECT-TYPE
		SYNTAX		DisplayString
		MAX-ACCESS	read-only
		STATUS		deprecated
		DESCRIPTION		
			"Error status of Link Test:
            (1) Failed to recieve handshake from remote device
            (2) No session with selected LUID. Please try again after session established.
            (3) Received a bad transaction ID.  Please try again.
            (4) We werent able to send the test request to the remote device.
            (5) We didnt receive any results from the remote device.
            [This variable is deprecated, please refer whispBoxLink OIDs]"
		::={whispApsLinkTestResult 3}

	testDuration	OBJECT-TYPE
		SYNTAX		INTEGER
		MAX-ACCESS	read-only
		STATUS		deprecated
		DESCRIPTION		
			"Duration of link test.[This variable is deprecated, please refer whispBoxLink OIDs]"
		::={whispApsLinkTestResult 4}

	downLinkRate	OBJECT-TYPE
		SYNTAX		INTEGER
		UNITS		"bps"
		MAX-ACCESS	read-only
		STATUS		deprecated
		DESCRIPTION		
			"Downlink Rate
                            This result includes RF retransmissions. For more accurate result see downLinkRateBox.
                            [This variable is deprecated, please refer whispBoxLink OIDs]"
		::={whispApsLinkTestResult 5}

	upLinkRate	OBJECT-TYPE
		SYNTAX		INTEGER
		UNITS		"bps"
		MAX-ACCESS	read-only
		STATUS		deprecated
		DESCRIPTION		
			"Uplink Rate.
                            This result includes RF retransmissions. For more accurate result see upLinkRateBox.
                            [This variable is deprecated, please refer whispBoxLink OIDs]"
		::={whispApsLinkTestResult 6}

	downLinkEff	OBJECT-TYPE
		SYNTAX		INTEGER
		UNITS		"%"
		MAX-ACCESS	read-only
		STATUS		deprecated
		DESCRIPTION		
			"Downlink Efficiency."
		::={whispApsLinkTestResult 7}

	maxDwnLinkIndex	OBJECT-TYPE
		SYNTAX		INTEGER
		MAX-ACCESS	read-only
		STATUS		deprecated
		DESCRIPTION		
			"For link test results, the maximum possible downlink efficiency percentage (always 100%).[This variable is deprecated, please refer whispBoxLink OIDs]"
		::={whispApsLinkTestResult 8}

	actDwnLinkIndex	OBJECT-TYPE
		SYNTAX		INTEGER
		MAX-ACCESS	read-only
		STATUS		deprecated
		DESCRIPTION		
			"Actual downlink index.[This variable is deprecated, please refer whispBoxLink OIDs]"
		::={whispApsLinkTestResult 9}

	expDwnFragCount	OBJECT-TYPE
		SYNTAX		Gauge32
		MAX-ACCESS	read-only
		STATUS		deprecated
		DESCRIPTION		
			"Expected Fragment Count.[This variable is deprecated, please refer whispBoxLink OIDs]"
		::={whispApsLinkTestResult 10}

	actDwnFragCount	OBJECT-TYPE
		SYNTAX		Gauge32
		MAX-ACCESS	read-only
		STATUS		deprecated
		DESCRIPTION		
			"Actual Fragment Count.[This variable is deprecated, please refer whispBoxLink OIDs]"
		::={whispApsLinkTestResult 11}

	upLinkEff	OBJECT-TYPE
		SYNTAX		INTEGER
		UNITS		"%"
		MAX-ACCESS	read-only
		STATUS		deprecated
		DESCRIPTION		
			"Uplink efficiency.[This variable is deprecated, please refer whispBoxLink OIDs]"
		::={whispApsLinkTestResult 12}

	expUpFragCount	OBJECT-TYPE
		SYNTAX		Gauge32
		MAX-ACCESS	read-only
		STATUS		deprecated
		DESCRIPTION		
			"Uplink expected Fragment Count.[This variable is deprecated, please refer whispBoxLink OIDs]"
		::={whispApsLinkTestResult 13}

	actUpFragCount	OBJECT-TYPE
		SYNTAX		Gauge32
		MAX-ACCESS	read-only
		STATUS		deprecated
		DESCRIPTION		
			"Actual uplink Fragment Count.[This variable is deprecated, please refer whispBoxLink OIDs]"
		::={whispApsLinkTestResult 14}

	maxUpLinkIndex	OBJECT-TYPE
		SYNTAX		INTEGER
		MAX-ACCESS	read-only
		STATUS		deprecated
		DESCRIPTION		
			"For link test results, the maximum possible uplink efficiency percentage (always 100%).[This variable is deprecated, please refer whispBoxLink OIDs]"
		::={whispApsLinkTestResult 15}

	actUpLinkIndex	OBJECT-TYPE
		SYNTAX		INTEGER
		MAX-ACCESS	read-only
		STATUS		deprecated
		DESCRIPTION		
			"Actual Uplink index.[This variable is deprecated, please refer whispBoxLink OIDs]"
		::={whispApsLinkTestResult 16}

	fragments1xDwnLinkVertical	OBJECT-TYPE
		SYNTAX		INTEGER
		MAX-ACCESS	read-only
		STATUS		deprecated
		DESCRIPTION		
			"Number of fragments received on downlink at 1X (QPSK).
                            For Gen II OFDM and forward.
                            For MIMO this is the vertical path.
                            [This variable is deprecated, please refer whispBoxLink OIDs]"
		::={whispApsLinkTestResult 17}

	fragments2xDwnLinkVertical	OBJECT-TYPE
		SYNTAX		INTEGER
		MAX-ACCESS	read-only
		STATUS		deprecated
		DESCRIPTION		
			"Number of fragments received on downlink at 2X (16-QAM).
                            For Gen II OFDM and forward.
                            For MIMO this is the vertical path.
                            [This variable is deprecated, please refer whispBoxLink OIDs]"
		::={whispApsLinkTestResult 18}

	fragments3xDwnLinkVertical	OBJECT-TYPE
		SYNTAX		INTEGER
		MAX-ACCESS	read-only
		STATUS		deprecated
		DESCRIPTION		
			"Number of fragments received on downlink at 3X (64-QAM).
                            For Gen II OFDM and forward.
                            For MIMO this is the vertical path.
                            [This variable is deprecated, please refer whispBoxLink OIDs]"
		::={whispApsLinkTestResult 19}

	fragments4xDwnLinkVertical	OBJECT-TYPE
		SYNTAX		INTEGER
		MAX-ACCESS	read-only
		STATUS		deprecated
		DESCRIPTION		
			"Number of fragments received on downlink at 4X (256-QAM).
                            For Gen II OFDM and forward.
                            For MIMO this is the vertical path.
                            [This variable is deprecated, please refer whispBoxLink OIDs]"
		::={whispApsLinkTestResult 20}

	fragments1xUpLinkVertical	OBJECT-TYPE
		SYNTAX		INTEGER
		MAX-ACCESS	read-only
		STATUS		deprecated
		DESCRIPTION		
			"Number of fragments received on uplink at 1X (QPSK).
                            For Gen II OFDM and forward.
                            For MIMO this is the vertical path.
                            [This variable is deprecated, please refer whispBoxLink OIDs]"
		::={whispApsLinkTestResult 21}

	fragments2xUpLinkVertical	OBJECT-TYPE
		SYNTAX		INTEGER
		MAX-ACCESS	read-only
		STATUS		deprecated
		DESCRIPTION		
			"Number of fragments received on uplink at 2X (16-QAM).
                            For Gen II OFDM and forward.
                            For MIMO this is the vertical path.
                            [This variable is deprecated, please refer whispBoxLink OIDs]"
		::={whispApsLinkTestResult 22}

	fragments3xUpLinkVertical	OBJECT-TYPE
		SYNTAX		INTEGER
		MAX-ACCESS	read-only
		STATUS		deprecated
		DESCRIPTION		
			"Number of fragments received on uplink at 3X (64-QAM).
                            For Gen II OFDM and forward.
                            For MIMO this is the vertical path.
                            [This variable is deprecated, please refer whispBoxLink OIDs]"
		::={whispApsLinkTestResult 23}

	fragments4xUpLinkVertical	OBJECT-TYPE
		SYNTAX		INTEGER
		MAX-ACCESS	read-only
		STATUS		deprecated
		DESCRIPTION		
			"Number of fragments received on uplink at 4X (256-QAM).
                            For Gen II OFDM and forward.
                            For MIMO this is the vertical path.
                            [This variable is deprecated, please refer whispBoxLink OIDs]"
		::={whispApsLinkTestResult 24}

	bitErrorsCorrected1xDwnLinkVertical	OBJECT-TYPE
		SYNTAX		DisplayString
		MAX-ACCESS	read-only
		STATUS		deprecated
		DESCRIPTION		
			"Number of bit errors corrected on average per fragment on downlink at 1X (QPSK).
                            For Gen II OFDM and forward.
                            For MIMO this is the vertical path.
                            [This variable is deprecated, please refer whispBoxLink OIDs]"
		::={whispApsLinkTestResult 25}

	bitErrorsCorrected2xDwnLinkVertical	OBJECT-TYPE
		SYNTAX		DisplayString
		MAX-ACCESS	read-only
		STATUS		deprecated
		DESCRIPTION		
			"Number of bit errors corrected on average per fragment on downlink at 2X (16-QAM).
                            For Gen II OFDM and forward.
                            For MIMO this is the vertical path.
                            [This variable is deprecated, please refer whispBoxLink OIDs]"
		::={whispApsLinkTestResult 26}

	bitErrorsCorrected3xDwnLinkVertical	OBJECT-TYPE
		SYNTAX		DisplayString
		MAX-ACCESS	read-only
		STATUS		deprecated
		DESCRIPTION		
			"Number of bit errors corrected on average per fragment on downlink at 3X (64-QAM).
                            For Gen II OFDM and forward.
                            For MIMO this is the vertical path.
                            [This variable is deprecated, please refer whispBoxLink OIDs]"
		::={whispApsLinkTestResult 27}

	bitErrorsCorrected4xDwnLinkVertical	OBJECT-TYPE
		SYNTAX		DisplayString
		MAX-ACCESS	read-only
		STATUS		deprecated
		DESCRIPTION		
			"Number of bit errors corrected on average per fragment on downlink at 4X (256-QAM).
                            For Gen II OFDM and forward.
                            For MIMO this is the vertical path.
                            [This variable is deprecated, please refer whispBoxLink OIDs]"
		::={whispApsLinkTestResult 28}

	bitErrorsCorrected1xUpLinkVertical	OBJECT-TYPE
		SYNTAX		DisplayString
		MAX-ACCESS	read-only
		STATUS		deprecated
		DESCRIPTION		
			"Number of bit errors corrected on average per fragment on uplink at 1X (QPSK).
                            For Gen II OFDM and forward.
                            For MIMO this is the vertical path.
                            [This variable is deprecated, please refer whispBoxLink OIDs]"
		::={whispApsLinkTestResult 29}

	bitErrorsCorrected2xUpLinkVertical	OBJECT-TYPE
		SYNTAX		DisplayString
		MAX-ACCESS	read-only
		STATUS		deprecated
		DESCRIPTION		
			"Number of bit errors corrected on average per fragment on uplink at 2X (16-QAM).
                            For Gen II OFDM and forward.
                            For MIMO this is the vertical path.
                            [This variable is deprecated, please refer whispBoxLink OIDs]"
		::={whispApsLinkTestResult 30}

	bitErrorsCorrected3xUpLinkVertical	OBJECT-TYPE
		SYNTAX		DisplayString
		MAX-ACCESS	read-only
		STATUS		deprecated
		DESCRIPTION		
			"Number of bit errors corrected on average per fragment on uplink at 3X (64-QAM).
                            For Gen II OFDM and forward.
                            For MIMO this is the vertical path.
                            [This variable is deprecated, please refer whispBoxLink OIDs]"
		::={whispApsLinkTestResult 31}

	bitErrorsCorrected4xUpLinkVertical	OBJECT-TYPE
		SYNTAX		DisplayString
		MAX-ACCESS	read-only
		STATUS		deprecated
		DESCRIPTION		
			"Number of bit errors corrected on average per fragment on uplink at 4X (256-QAM).
                            For Gen II OFDM and forward.
                            For MIMO this is the vertical path.
                            [This variable is deprecated, please refer whispBoxLink OIDs]"
		::={whispApsLinkTestResult 32}

	signalToNoiseRatioDownLinkVertical	OBJECT-TYPE
		SYNTAX		INTEGER
		MAX-ACCESS	read-only
		STATUS		deprecated
		DESCRIPTION		
			"Estimated Signal to Noise Ratio in dB for the downlink.
                            For Gen II OFDM and forward.
                            For MIMO this is the vertical path.
                            [This variable is deprecated, please refer whispBoxLink OIDs]"
		::={whispApsLinkTestResult 33}

	signalToNoiseRatioUpLinkVertical	OBJECT-TYPE
		SYNTAX		INTEGER
		MAX-ACCESS	read-only
		STATUS		deprecated
		DESCRIPTION		
			"Estimated Signal to Noise Ratio in dB for the uplink.
                            For Gen II OFDM and forward.
                            For MIMO this is the vertical path.
                            [This variable is deprecated, please refer whispBoxLink OIDs]"
		::={whispApsLinkTestResult 34}

	fragments1xDwnLinkHorizontal	OBJECT-TYPE
		SYNTAX		INTEGER
		MAX-ACCESS	read-only
		STATUS		deprecated
		DESCRIPTION		
			"Number of fragments received on downlink at 1X (QPSK).
                            For MIMO only.
                            For MIMO this is the horizontal path.
                            Fragments received in MIMO-A will only be counted on vertical.
                            [This variable is deprecated, please refer whispBoxLink OIDs]"
		::={whispApsLinkTestResult 35}

	fragments2xDwnLinkHorizontal	OBJECT-TYPE
		SYNTAX		INTEGER
		MAX-ACCESS	read-only
		STATUS		deprecated
		DESCRIPTION		
			"Number of fragments received on downlink at 2X (16-QAM).
                            For MIMO only.
                            For MIMO this is the horizontal path.
                            Fragments received in MIMO-A will only be counted on vertical.
                            [This variable is deprecated, please refer whispBoxLink OIDs]"
		::={whispApsLinkTestResult 36}

	fragments3xDwnLinkHorizontal	OBJECT-TYPE
		SYNTAX		INTEGER
		MAX-ACCESS	read-only
		STATUS		deprecated
		DESCRIPTION		
			"Number of fragments received on downlink at 3X (64-QAM).
                            For MIMO only.
                            For MIMO this is the horizontal path.
                            Fragments received in MIMO-A will only be counted on vertical.
                            [This variable is deprecated, please refer whispBoxLink OIDs]"
		::={whispApsLinkTestResult 37}

	fragments4xDwnLinkHorizontal	OBJECT-TYPE
		SYNTAX		INTEGER
		MAX-ACCESS	read-only
		STATUS		deprecated
		DESCRIPTION		
			"Number of fragments received on downlink at 4X (256-QAM).
                            For MIMO only.
                            For MIMO this is the horizontal path.
                            Fragments received in MIMO-A will only be counted on vertical.
                            [This variable is deprecated, please refer whispBoxLink OIDs]"
		::={whispApsLinkTestResult 38}

	fragments1xUpLinkHorizontal	OBJECT-TYPE
		SYNTAX		INTEGER
		MAX-ACCESS	read-only
		STATUS		deprecated
		DESCRIPTION		
			"Number of fragments received on uplink at 1X (QPSK).
                            For MIMO only.
                            For MIMO this is the horizontal path.
                            Fragments received in MIMO-A will only be counted on vertical.
                            [This variable is deprecated, please refer whispBoxLink OIDs]"
		::={whispApsLinkTestResult 39}

	fragments2xUpLinkHorizontal	OBJECT-TYPE
		SYNTAX		INTEGER
		MAX-ACCESS	read-only
		STATUS		deprecated
		DESCRIPTION		
			"Number of fragments received on uplink at 2X (16-QAM).
                            For MIMO only.
                            For MIMO this is the horizontal path.
                            Fragments received in MIMO-A will only be counted on vertical.
                            [This variable is deprecated, please refer whispBoxLink OIDs]"
		::={whispApsLinkTestResult 40}

	fragments3xUpLinkHorizontal	OBJECT-TYPE
		SYNTAX		INTEGER
		MAX-ACCESS	read-only
		STATUS		deprecated
		DESCRIPTION		
			"Number of fragments received on uplink at 3X (64-QAM).
                            For MIMO only.
                            For MIMO this is the horizontal path.
                            Fragments received in MIMO-A will only be counted on vertical.
                            [This variable is deprecated, please refer whispBoxLink OIDs]"
		::={whispApsLinkTestResult 41}

	fragments4xUpLinkHorizontal	OBJECT-TYPE
		SYNTAX		INTEGER
		MAX-ACCESS	read-only
		STATUS		deprecated
		DESCRIPTION		
			"Number of fragments received on uplink at 4X (256-QAM).
                            For MIMO only.
                            For MIMO this is the horizontal path.
                            Fragments received in MIMO-A will only be counted on vertical.
                            [This variable is deprecated, please refer whispBoxLink OIDs]"
		::={whispApsLinkTestResult 42}

	bitErrorsCorrected1xDwnLinkHorizontal	OBJECT-TYPE
		SYNTAX		DisplayString
		MAX-ACCESS	read-only
		STATUS		deprecated
		DESCRIPTION		
			"Number of bit errors corrected on average per fragment on downlink at 1X (QPSK).
                            For MIMO and forward.
                            For MIMO this is the horizontal path.
                            Fragments received in MIMO-A will only be counted on vertical.
                            [This variable is deprecated, please refer whispBoxLink OIDs]"
		::={whispApsLinkTestResult 43}

	bitErrorsCorrected2xDwnLinkHorizontal	OBJECT-TYPE
		SYNTAX		DisplayString
		MAX-ACCESS	read-only
		STATUS		deprecated
		DESCRIPTION		
			"Number of bit errors corrected on average per fragment on downlink at 2X (16-QAM).
                            For MIMO and forward.
                            For MIMO this is the horizontal path.
                            Fragments received in MIMO-A will only be counted on vertical.
                            [This variable is deprecated, please refer whispBoxLink OIDs]"
		::={whispApsLinkTestResult 44}

	bitErrorsCorrected3xDwnLinkHorizontal	OBJECT-TYPE
		SYNTAX		DisplayString
		MAX-ACCESS	read-only
		STATUS		deprecated
		DESCRIPTION		
			"Number of bit errors corrected on average per fragment on downlink at 3X (64-QAM).
                            For MIMO and forward.
                            For MIMO this is the horizontal path.
                            Fragments received in MIMO-A will only be counted on vertical.
                            [This variable is deprecated, please refer whispBoxLink OIDs]"
		::={whispApsLinkTestResult 45}

	bitErrorsCorrected4xDwnLinkHorizontal	OBJECT-TYPE
		SYNTAX		DisplayString
		MAX-ACCESS	read-only
		STATUS		deprecated
		DESCRIPTION		
			"Number of bit errors corrected on average per fragment on downlink at 4X (256-QAM).
                            For MIMO and forward.
                            For MIMO this is the horizontal path.
                            Fragments received in MIMO-A will only be counted on vertical.
                            [This variable is deprecated, please refer whispBoxLink OIDs]"
		::={whispApsLinkTestResult 46}

	bitErrorsCorrected1xUpLinkHorizontal	OBJECT-TYPE
		SYNTAX		DisplayString
		MAX-ACCESS	read-only
		STATUS		deprecated
		DESCRIPTION		
			"Number of bit errors corrected on average per fragment on uplink at 1X (QPSK).
                            For MIMO and forward.
                            For MIMO this is the horizontal path.
                            Fragments received in MIMO-A will only be counted on vertical.
                            [This variable is deprecated, please refer whispBoxLink OIDs]"
		::={whispApsLinkTestResult 47}

	bitErrorsCorrected2xUpLinkHorizontal	OBJECT-TYPE
		SYNTAX		DisplayString
		MAX-ACCESS	read-only
		STATUS		deprecated
		DESCRIPTION		
			"Number of bit errors corrected on average per fragment on uplink at 2X (16-QAM).
                            For MIMO and forward.
                            For MIMO this is the horizontal path.
                            Fragments received in MIMO-A will only be counted on vertical.
                            [This variable is deprecated, please refer whispBoxLink OIDs]"
		::={whispApsLinkTestResult 48}

	bitErrorsCorrected3xUpLinkHorizontal	OBJECT-TYPE
		SYNTAX		DisplayString
		MAX-ACCESS	read-only
		STATUS		deprecated
		DESCRIPTION		
			"Engineering use only.
                            Number of bit errors corrected on average per fragment on uplink at 3X (64-QAM).
                            For MIMO and forward.
                            For MIMO this is the horizontal path.
                            Fragments received in MIMO-A will only be counted on vertical.
                            [This variable is deprecated, please refer whispBoxLink OIDs]"
		::={whispApsLinkTestResult 49}

	bitErrorsCorrected4xUpLinkHorizontal	OBJECT-TYPE
		SYNTAX		DisplayString
		MAX-ACCESS	read-only
		STATUS		deprecated
		DESCRIPTION		
			"Number of bit errors corrected on average per fragment on uplink at 4X (256-QAM).
                            For MIMO and forward.
                            For MIMO this is the horizontal path.
                            Fragments received in MIMO-A will only be counted on vertical.
                            [This variable is deprecated, please refer whispBoxLink OIDs]"
		::={whispApsLinkTestResult 50}

	signalToNoiseRatioDownLinkHorizontal	OBJECT-TYPE
		SYNTAX		INTEGER
		MAX-ACCESS	read-only
		STATUS		deprecated
		DESCRIPTION		
			"Estimated Signal to Noise Ratio in dB for the downlink.
                            For MIMO and forward.
                            For MIMO this is the horizontal path.
                            If operating in MIMO-A this will return 0.
                            [This variable is deprecated, please refer whispBoxLink OIDs]"
		::={whispApsLinkTestResult 51}

	signalToNoiseRatioUpLinkHorizontal	OBJECT-TYPE
		SYNTAX		INTEGER
		MAX-ACCESS	read-only
		STATUS		deprecated
		DESCRIPTION		
			"Estimated Signal to Noise Ratio in dB for the uplink.
                            For Gen II OFDM and forward.
                            For MIMO this is the horizontal path.
                            If operating in MIMO-A this will return 0.
                            [This variable is deprecated, please refer whispBoxLink OIDs]"
		::={whispApsLinkTestResult 52}

	downLinkRateExtrapolated	OBJECT-TYPE
		SYNTAX		INTEGER
		UNITS		"bps"
		MAX-ACCESS	read-only
		STATUS		deprecated
		DESCRIPTION		
			"Extrapolated Downlink Rate from an extrapolated link test.
                            Extrapolated Link Test sends only a few packets over the link and extrapolates this out to what would happen on a full link test.
                            This is an estimation of the throughput based upon the modulation, efficiency, and data slots available.
                            It intended to provide a basic link test test without impacting service for the sector.
                            [This variable is deprecated, please refer whispBoxLink OIDs]"
		::={whispApsLinkTestResult 53}

	upLinkRateExtrapolated	OBJECT-TYPE
		SYNTAX		INTEGER
		UNITS		"bps"
		MAX-ACCESS	read-only
		STATUS		deprecated
		DESCRIPTION		
			"Extrapolated Uplink Rate from an extrapolated link test.
                            Extrapolated Link Test sends only a few packets over the link and extrapolates this out to what would happen on a full link test.
                            This is an estimation of the throughput based upon the modulation, efficiency, and data slots available.
                            It intended to provide a basic link test test without impacting service for the sector.
                            [This variable is deprecated, please refer whispBoxLink OIDs]"
		::={whispApsLinkTestResult 54}

	whispGPSStats	OBJECT-TYPE
		SYNTAX		INTEGER {
					gpsSynchronized(1),
					gpsLostSync(2),
					generatingSync(3)}
		MAX-ACCESS	read-only
		STATUS		current
		DESCRIPTION		
			"This shows whether the AP is synchrinized
                        to the GPS timer."
		::={whispApsGPS 1}

	gpsSyncSource	OBJECT-TYPE
		SYNTAX		DisplayString
		MAX-ACCESS	read-only
		STATUS		current
		DESCRIPTION		
			"Source of GPS Sync Pulse."
		::={whispApsGPS 2}

	gpsSyncStatus	OBJECT-TYPE
		SYNTAX		DisplayString
		MAX-ACCESS	read-only
		STATUS		current
		DESCRIPTION		
			"Current Live value of Sync Status."
		::={whispApsGPS 3}

	gpsTrackingMode	OBJECT-TYPE
		SYNTAX		DisplayString
		MAX-ACCESS	read-only
		STATUS		current
		DESCRIPTION		
			"GPS tracking mode."
		::={whispApsGPS 4}

	gpsTime	OBJECT-TYPE
		SYNTAX		DisplayString
		MAX-ACCESS	read-only
		STATUS		current
		DESCRIPTION		
			"GPS time."
		::={whispApsGPS 5}

	gpsDate	OBJECT-TYPE
		SYNTAX		DisplayString
		MAX-ACCESS	read-only
		STATUS		current
		DESCRIPTION		
			"GPS date."
		::={whispApsGPS 6}

	gpsSatellitesTracked	OBJECT-TYPE
		SYNTAX		DisplayString
		MAX-ACCESS	read-only
		STATUS		current
		DESCRIPTION		
			"Returns Current number of satellites GPS is tracking in string format. Use gpsSatellitesTrackedInt to get the value in integer"
		::={whispApsGPS 7}

	gpsSatellitesVisible	OBJECT-TYPE
		SYNTAX		DisplayString
		MAX-ACCESS	read-only
		STATUS		current
		DESCRIPTION		
			"Return Number of satellites GPS is seeing in string format. Use gpsSatellitesVisibleInt to get value in integer"
		::={whispApsGPS 8}

	gpsHeight	OBJECT-TYPE
		SYNTAX		DisplayString
		MAX-ACCESS	read-only
		STATUS		current
		DESCRIPTION		
			"GPS height."
		::={whispApsGPS 9}

	gpsAntennaConnection	OBJECT-TYPE
		SYNTAX		DisplayString
		MAX-ACCESS	read-only
		STATUS		current
		DESCRIPTION		
			"Antenna Connection status."
		::={whispApsGPS 10}

	gpsLatitude	OBJECT-TYPE
		SYNTAX		DisplayString
		MAX-ACCESS	read-only
		STATUS		current
		DESCRIPTION		
			"GPS Latitude."
		::={whispApsGPS 11}

	gpsLongitude	OBJECT-TYPE
		SYNTAX		DisplayString
		MAX-ACCESS	read-only
		STATUS		current
		DESCRIPTION		
			"GPS Longitude."
		::={whispApsGPS 12}

	gpsInvalidMsg	OBJECT-TYPE
		SYNTAX		DisplayString
		MAX-ACCESS	read-only
		STATUS		current
		DESCRIPTION		
			"Number of invalid messages."
		::={whispApsGPS 13}

	gpsRestartCount	OBJECT-TYPE
		SYNTAX		INTEGER
		MAX-ACCESS	read-only
		STATUS		current
		DESCRIPTION		
			"Number of GPS unit restarts."
		::={whispApsGPS 14}

	gpsReInitCount	OBJECT-TYPE
		SYNTAX		INTEGER
		MAX-ACCESS	read-only
		STATUS		current
		DESCRIPTION		
			"GPS ReInit counts.  The number of times we have done a complete re-initialization of the GPS device."
		::={whispApsGPS 15}

	gpsReceiverInfo	OBJECT-TYPE
		SYNTAX		DisplayString
		MAX-ACCESS	read-only
		STATUS		current
		DESCRIPTION		
			"A textual string contains information on GPS receiver."
		::={whispApsGPS 16}

	gpsFreeRun	OBJECT-TYPE
		SYNTAX		INTEGER {
					disable(0),
					enable(1)}
		MAX-ACCESS	read-write
		STATUS		current
		DESCRIPTION		
			"This variable is deprecated.
                              Setting this value to false will set AutoSync.
                              Setting this value to true will set AutoSync plus Free Run."
		::={whispApsGPS 17}

	autoSyncStatus	OBJECT-TYPE
		SYNTAX		INTEGER {
					noSync(0),
					onBoardGPSSync(1),
					timingPortUGPSSync(2),
					onBoardGPSAndTimingPortUGPSSync(3),
					powrPortSync(4),
					onBoardGPSAndPowrPortSync(5),
					timingPortUGPSAndPowrPortSync(6),
					onBoardGPSAndTimingPortUGPSAndPowrPortSync(7),
					cambiumSync(8),
					onBoardGPSandCambiumSyncOverPowerMainPort(9),
					timingPortUGPSSyncAndCambiumSync(10),
					onBoardGPSandTimingPortUGPSSyncAndCambiumSync(11)}
		MAX-ACCESS	read-only
		STATUS		current
		DESCRIPTION		
			"Current Live value of Sync Status.
                        Following values represent what sources have sync.
                        (0) No Sync
                        (1) On-board GPS Sync
                        (2) Timing Port (UGPS/cnPulse) Sync
                        (3) On-board GPS and Timing Port (UGPS/cnPulse) Sync
                        (4) Canopy Sync Over Power Port
                        (5) On-board GPS and Canopy Sync Over Power
                        (6) Timing Port (UGPS/cnPulse) and Canopy Sync Over Power
                        (7) On-board GPS, Timing Port (UGPS/cnPulse) and Canopy Sync Over Power
                        (8) Cambium Sync Over Power/Main Port
                        (9) On-board GPS and Cambium Sync Over Power/Main Port
                        (10) Timing Port (UGPS/cnPulse) and Cambium Sync Over Power/Main Port
                        (11) On-board GPS and Timing Port (UGPS/cnPulse) and Cambium Sync Over Power/Main Port
                        
                        When the radio is set to Generate Sync it will always return 0."
		::={whispApsGPS 18}

	gpsSatellitesTrackedInt	OBJECT-TYPE
		SYNTAX		INTEGER
		MAX-ACCESS	read-only
		STATUS		current
		DESCRIPTION		
			"Current number of satellites GPS is tracking in integer format."
		::={whispApsGPS 19}

	gpsSatellitesVisibleInt	OBJECT-TYPE
		SYNTAX		INTEGER
		MAX-ACCESS	read-only
		STATUS		current
		DESCRIPTION		
			"Number of satellites the GPS sees in integer format"
		::={whispApsGPS 20}

	ppsLossCountStatus	OBJECT-TYPE
		SYNTAX		INTEGER
		MAX-ACCESS	read-only
		STATUS		current
		DESCRIPTION		
			"Current value of PPS_LOST_CNT. Engineering use only."
		::={whispApsGPS 21}

	clearPPSLossCount	OBJECT-TYPE
		SYNTAX		INTEGER
		MAX-ACCESS	read-write
		STATUS		current
		DESCRIPTION		
			"Write-Only OID, clear current value of PPS_LOST_CNT.  Engineering use only."
		::={whispApsGPS 22}

	ppsLossPercent	OBJECT-TYPE
		SYNTAX		DisplayString
		MAX-ACCESS	read-only
		STATUS		deprecated
		DESCRIPTION		
			"Deprecated -Average Sync PPS received over largest measurement interval (15 minutes currently)
                        See syncMetricsTable instead."
		::={whispApsGPS 23}

	syncMetricsTable OBJECT-TYPE
		SYNTAX		SEQUENCE OF SyncMetricsTableEntry
		MAX-ACCESS	not-accessible
		STATUS		current
		DESCRIPTION
			"Sync Pulse Metrics"
		::= {whispApsGPS 24}

	syncMetricsTableEntry OBJECT-TYPE
		SYNTAX		SyncMetricsTableEntry
		MAX-ACCESS	not-accessible
		STATUS		current
		DESCRIPTION
			"Sync Pulse Metrics"
		INDEX		{syncMetricsTableInterval}
		::= {syncMetricsTable 1}

		SyncMetricsTableEntry ::= SEQUENCE{
			syncMetricsTableInterval		INTEGER,
			syncMetricsTablePulseReceivedPct		INTEGER,
			syncMetricsTableSatSNRAvg		INTEGER,
			syncMetricsTableSatVisibleAvg		INTEGER,
			syncMetricsTableSatTrackedAvg	INTEGER
			}

	syncMetricsTableInterval	OBJECT-TYPE
		SYNTAX		INTEGER (0..2)
		MAX-ACCESS	read-only
		STATUS		current
		DESCRIPTION		
			"Sync Metrics measurement interval.
                            0: 1 minute
                            1: 5 minutes
                            2: 15 minutes"
		::={syncMetricsTableEntry 1}

	syncMetricsTablePulseReceivedPct	OBJECT-TYPE
		SYNTAX		INTEGER
		MAX-ACCESS	read-only
		STATUS		current
		DESCRIPTION		
			"Percentage of sync pulses received successfully during the measurement interval.
                            This value is scaled up by 100 (i.e. 9769 is equivalent to 97.69%)"
		::={syncMetricsTableEntry 2}

	syncMetricsTableSatSNRAvg	OBJECT-TYPE
		SYNTAX		INTEGER
		MAX-ACCESS	read-only
		STATUS		current
		DESCRIPTION		
			"Average Satellite Signal-to-noise Ratio during the measurement interval.
                            0 may indicate no valid source of GPS data is available (from internal or timing port GPS source).
                            This value is scaled up by 100 (i.e. 2735 is equivalent to 27.35)"
		::={syncMetricsTableEntry 3}

	syncMetricsTableSatVisibleAvg	OBJECT-TYPE
		SYNTAX		INTEGER
		MAX-ACCESS	read-only
		STATUS		current
		DESCRIPTION		
			"Average Visible Satellite count during the measurement interval.
                            0 may indicate no valid source of GPS data is available (from internal or timing port GPS source).
                            This value is scaled up by 100 (i.e. 2146 is equivalent to 21.46)"
		::={syncMetricsTableEntry 4}

	syncMetricsTableSatTrackedAvg	OBJECT-TYPE
		SYNTAX		INTEGER
		MAX-ACCESS	read-only
		STATUS		current
		DESCRIPTION		
			"Average Tracked Satellite count during the measurement interval.
                            0 may indicate no valid source of GPS data is available (from internal or timing port GPS source).
                            This value is scaled up by 100 (i.e. 1420 is equivalent to 14.20)"
		::={syncMetricsTableEntry 5}

-- Registration Events

	whispRegComplete	NOTIFICATION-TYPE
		OBJECTS {
					linkLUID,
					linkPhysAddress}
		STATUS		current
		DESCRIPTION		
			"Signals registration complete."
		::={whispApsRegEvent 1}

	whispRegLost	NOTIFICATION-TYPE
		OBJECTS {
					linkLUID,
					linkPhysAddress,
					smSessionTmr,
					lastPowerLevel,
					signalToNoiseRatioVertical,
					signalToNoiseRatioHorizontal,
					adaptRate,
					lqiLowDownlinkQualityIndex,
					lqiLowUplinkQualityIndex}
		STATUS		current
		DESCRIPTION		
			"Signals registration lost."
		::={whispApsRegEvent 2}

	whispRegFailure	NOTIFICATION-TYPE
		OBJECTS {
					regFailESN,
					regFailSeqNum,
					regFailReasonText}
		STATUS		current
		DESCRIPTION		
			"Signals a registration failure has occured."
		::={whispApsRegEvent 3}

	whispDefKeyUsed	NOTIFICATION-TYPE
		OBJECTS {
					linkLUID,
					linkPhysAddress}
		STATUS		current
		DESCRIPTION		
			"Signals Default Key used for encryptiont."
		::={whispApsRegEvent 4}

-- GPS Events

	whispGPSInSync	NOTIFICATION-TYPE
		OBJECTS {
					whispGPSStats,
					whispBoxEsn}
		STATUS		current
		DESCRIPTION		
			"Signals a transition from not-synchronized to synchronized."
		::={whispGPSEvent 1}

	whispGPSOutSync	NOTIFICATION-TYPE
		OBJECTS {
					gpsStatus,
					whispBoxEsn}
		STATUS		current
		DESCRIPTION		
			"Signals a transition from synchronized to not-synchronized."
		::={whispGPSEvent 2}

-- DFS events

	whispRadarDetected	NOTIFICATION-TYPE
		OBJECTS {
					dfsStatus,
					whispBoxEsn}
		STATUS		current
		DESCRIPTION		
			"Radar detected transmit stopped."
		::={whispApsDfsEvent 1}

	whispRadarEnd	NOTIFICATION-TYPE
		OBJECTS {
					dfsStatus,
					whispBoxEsn}
		STATUS		current
		DESCRIPTION		
			"Radar ended back to normal transmit."
		::={whispApsDfsEvent 2}

-- Regulatory Failure due to Invalid Channel set for the region.

	regulatoryApCheckInvalidChanFailed	NOTIFICATION-TYPE
		OBJECTS {
					regulatoryStatus,
					whispBoxEsn}
		STATUS		current
		DESCRIPTION		
			"Regulatory Check failed for the unit due to a invalid channel for the configured region.
                            regulatoryStatus - Text description for the failure.
                            physAddress - the MAC address of the unit."
		::={whispApRegulatoryEvent 1}

-- Regulatory Failure due to no region set

	regulatoryCheckFailedNoRegionAp	NOTIFICATION-TYPE
		OBJECTS {
					whispBoxEsn}
		STATUS		current
		DESCRIPTION		
			"Regulatory Check failed because a valid region has not be configured.
                            physAddress - the MAC address of the unit."
		::={whispApRegulatoryEvent 2}

-- Regulatory Failure due to Invalid Channel Bandwidth set for the region.

	regulatoryApCheckInvalidChBwFailed	NOTIFICATION-TYPE
		OBJECTS {
					regulatoryStatus,
					whispBoxEsn}
		STATUS		current
		DESCRIPTION		
			"Regulatory Check failed due to an invalid channel bandwidth for the configured region.
                            regulatoryStatus - Text description for the failure.
                            physAddress - the MAC address of the unit."
		::={whispApRegulatoryEvent 3}

-- RF link overload detection in the Downlink Direction.

	rfLinkOverloadCondition	NOTIFICATION-TYPE
		OBJECTS {
					rfOutDiscardRate,
					whispBoxEsn}
		STATUS		current
		DESCRIPTION		
			"AP has exceeded the preset discard percentage in the RF Downlink Direction.
                            rfOutDiscardRate - Current discard Rate.
                            physAddress - the MAC address of the unit."
		::={whispApRFOverloadEvent 1}

-- MU-MIMO Trial Event Notification.

	mumimoTrialEvent	NOTIFICATION-TYPE
		OBJECTS {
					mumimoTrialPercentageRemaining,
					whispBoxEsn}
		STATUS		current
		DESCRIPTION		
			"MU-MIMO Trial Event Notification.
                            Value indicates percentage of trial licenses remaining."
		::={whispApsMumimoTrialEvent 1}

-- LQI Events

	whispDownlinkLqiBelowThreshold	NOTIFICATION-TYPE
		OBJECTS {
					linkLUID,
					linkPhysAddress,
					lqiLowDownlinkQualityIndex,
					lqiLowDownlinkActualAverageEVM,
					lqiLowDownlinkExpectedEVM,
					lqiLowBeaconPercent,
					lqiLowBeaconQualityIndex}
		STATUS		current
		DESCRIPTION		
			"Signals Downlink Link Quality Indicator falling below raise trap threshold"
		::={whispApLqiEvent 1}

	whispDownlinkLqiRestored	NOTIFICATION-TYPE
		OBJECTS {
					linkLUID,
					linkPhysAddress,
					lqiLowDownlinkQualityIndex,
					lqiLowDownlinkActualAverageEVM,
					lqiLowDownlinkExpectedEVM,
					lqiLowBeaconPercent,
					lqiLowBeaconQualityIndex}
		STATUS		current
		DESCRIPTION		
			"Signals Downlink Link Quality Indicator going back above or equal to the clear trap threshold"
		::={whispApLqiEvent 2}

-- LQI Events

	whispUplinkLqiBelowThreshold	NOTIFICATION-TYPE
		OBJECTS {
					linkLUID,
					linkPhysAddress,
					lqiLowUplinkQualityIndex,
					lqiLowUplinkActualAverageEVM,
					lqiLowUplinkExpectedEVM}
		STATUS		current
		DESCRIPTION		
			"Signals Uplink Link Quality Indicator falling below raise trap threshold."
		::={whispApLqiEvent 3}

	whispUplinkLqiRestored	NOTIFICATION-TYPE
		OBJECTS {
					linkLUID,
					linkPhysAddress,
					lqiLowUplinkQualityIndex,
					lqiLowUplinkActualAverageEVM,
					lqiLowUplinkExpectedEVM}
		STATUS		current
		DESCRIPTION		
			"Signals Uplink Link Quality Indicator going back above or equal to the clear trap threshold."
		::={whispApLqiEvent 4}

-- CBRS events

	cbrsTxEnable	NOTIFICATION-TYPE
		OBJECTS {
					cbsdStatus,
					linkPhysAddress,
					linkLUID}
		STATUS		current
		DESCRIPTION		
			"CBRS Transmission Enable Notification"
		::={whispApsCbrsEvent 1}

	cbrsTxDisable	NOTIFICATION-TYPE
		OBJECTS {
					cbsdStatus,
					linkPhysAddress,
					linkLUID}
		STATUS		current
		DESCRIPTION		
			"CBRS Transmission Disable Notification"
		::={whispApsCbrsEvent 2}

	whispLinkTestGroup	OBJECT-GROUP
			OBJECTS {
					linkTestLUID,
					linkTestDuration,
					linkTestAction,
					linkTestPktLength,
					testLUID,
					linkTestStatus,
					linkTestError,
					testDuration,
					downLinkRate,
					upLinkRate,
					downLinkRateExtrapolated,
					upLinkRateExtrapolated,
					downLinkEff,
					maxDwnLinkIndex,
					actDwnLinkIndex,
					expDwnFragCount,
					actDwnFragCount,
					upLinkEff,
					expUpFragCount,
					actUpFragCount,
					maxUpLinkIndex,
					actUpLinkIndex,
					fragments1xDwnLinkVertical,
					fragments2xDwnLinkVertical,
					fragments3xDwnLinkVertical,
					fragments4xDwnLinkVertical,
					fragments1xUpLinkVertical,
					fragments2xUpLinkVertical,
					fragments3xUpLinkVertical,
					fragments4xUpLinkVertical,
					fragments1xDwnLinkHorizontal,
					fragments2xDwnLinkHorizontal,
					fragments3xDwnLinkHorizontal,
					fragments4xDwnLinkHorizontal,
					fragments1xUpLinkHorizontal,
					fragments2xUpLinkHorizontal,
					fragments3xUpLinkHorizontal,
					fragments4xUpLinkHorizontal,
					bitErrorsCorrected1xDwnLinkVertical,
					bitErrorsCorrected2xDwnLinkVertical,
					bitErrorsCorrected3xDwnLinkVertical,
					bitErrorsCorrected4xDwnLinkVertical,
					bitErrorsCorrected1xUpLinkVertical,
					bitErrorsCorrected2xUpLinkVertical,
					bitErrorsCorrected3xUpLinkVertical,
					bitErrorsCorrected4xUpLinkVertical,
					signalToNoiseRatioDownLinkVertical,
					signalToNoiseRatioUpLinkVertical,
					bitErrorsCorrected1xDwnLinkHorizontal,
					bitErrorsCorrected2xDwnLinkHorizontal,
					bitErrorsCorrected3xDwnLinkHorizontal,
					bitErrorsCorrected4xDwnLinkHorizontal,
					bitErrorsCorrected1xUpLinkHorizontal,
					bitErrorsCorrected2xUpLinkHorizontal,
					bitErrorsCorrected3xUpLinkHorizontal,
					bitErrorsCorrected4xUpLinkHorizontal,
					signalToNoiseRatioDownLinkHorizontal,
					signalToNoiseRatioUpLinkHorizontal,
					linkTestSNRCalculation,
					linkTestWithDualPath,
					linkTestForceModulation,
					linkTestMode,
					linkTestNumPkt,
					linkTestDirection}
		STATUS		current
		DESCRIPTION
			"WHiSP APs link test group."
		::= {whispApsGroups 1}

	whispApsConfigGroup	OBJECT-GROUP
			OBJECTS {
					gpsInput,
					rfFreqCarrier,
					dwnLnkData,
					highPriorityUpLnkPct,
					numUAckSlots,
					uAcksReservHigh,
					numDAckSlots,
					dAcksReservHigh,
					numCtlSlots,
					numCtlSlotsReserveHigh,
					upLnkMaxBurstDataRate,
					upLnkDataRate,
					upLnkLimit,
					dwnLnkMaxBurstDataRate,
					dwnLnkDataRate,
					dwnLnkLimit,
					sectorID,
					maxRange,
					asIP1,
					asIP2,
					asIP3,
					asIP4,
					asIP5,
					lanIpAp,
					lanMaskAp,
					defaultGwAp,
					privateIp,
					gpsTrap,
					regTrap,
					txSpreading,
					apBeaconInfo,
					authMode,
					authKeyAp,
					authKey256Ap,
					authKeyOptionAP,
					authKey256OptionAP,
					enableRadiusDynAuth,
					disableAuthForICCSM,
					enableEuSecurityCheck,
					encryptionMode,
					ntpServerIp,
					multicastVCDataRate,
					multicastRetryCount,
					encryptDwBroadcast,
					updateAppAddress,
					dfsConfig,
					vlanEnable,
					configSource,
					apRateAdapt,
					numCtlSlotsHW,
					displayAPEval,
					smIsolation,
					bridgeFloodUnknownsEnable,
					ipAccessFilterEnable,
					allowedIPAccess1,
					allowedIPAccess2,
					allowedIPAccess3,
					allowedIPAccessNMLength1,
					allowedIPAccessNMLength2,
					allowedIPAccessNMLength3,
					rfTelnetAccess,
					rfPPPoEPADIForwarding,
					tslBridging,
					untranslatedArp,
					limitFreqBand900,
					txPwrLevel,
					rfFreqCaralt1,
					rfFreqCaralt2,
					scheduleWhitening,
					remoteSpectrumAnalysisDuration,
					remoteSpectrumAnalyzerLUID,
					bhReReg,
					otarInterval,
					dlnkBcastCIR,
					dlnkMcastCIR,
					verifyGPSChecksum,
					mumimoTrialMode,
					interferenceCancellationTrialMode,
					qinqEthType,
					useAPManagementVIDForICCSM,
					configAction,
					radiusVendorID,
					pmp450430LegacyMode,
					onlyAllowPMP450iSMRegistration,
					frameAlignmentLegacyMode,
					pmp430SMRegistration,
					colorCodeRescanTimer,
					colorCodeRescanIdleTimer,
					domainProxyTimeSynch,
					cbrsEnable,
					cbrsMultiGrantEnable,
					cbrsRebootRadio,
					cbrsChannelHunt,
					cbrsChannelChange,
					cbrsChannelChangeThreshold,
					cbrsOriginalChannelRestoreTime,
					cbsdCoexPrependUserId,
					cbsdUserID,
					cbsdCoexSectorId,
					cbsdCoexSpectrumReuseId,
					apCbsdSelectRelinquishment,
					apCbsdSelectDeregistration,
					performRelinquishDeregister,
					fskSMRcvTargetLvl,
					berModSelect,
					lastSesStatsReset,
					resetSesStats,
					syslogDomainNameAppend,
					syslogServerAddr,
					syslogServerPort,
					syslogXmitAP,
					syslogXmitSMs,
					oneXEnable,
					oneXSharedSecret,
					freeRunGPSSyncBypass,
					uGPSPower,
					gpsOutputEn,
					weightedWindowInterval,
					smPrioritization,
					smPrioritizationAllocationLow,
					smPrioritizationAllocationHigh,
					wfq,
					wfqAllocationLowSMPrioritization,
					wfqAllocationHighSMPrioritization,
					prioritizeMgmtData,
					radioMode,
					paHighbandSwitchoverFrequency,
					rfHighbandSwitchoverFrequency,
					autoContention,
					interferenceCancellation,
					noRebootFreqChange,
					trapDelayAfterBootup,
					pagerRejectFilterSelect,
					authSharedSecret1,
					authSharedSecret2,
					authSharedSecret3,
					radiusPort,
					radiusAcctPort,
					localNTPServer,
					rfOLEnable,
					rfOLTrap,
					rfOLThreshold,
					framePeriod,
					remoteSpectrumAnalyzerScanBandwidth,
					bhsRcvTargetLvl,
					speedTestServer1,
					apConfigAdjacentChanSupport,
					ofdmSMRcvTargetLvl,
					sMTxPowerControl,
					bhsTxPowerControl,
					limit450bSMMaxTxPowerEnable,
					limit450bSMMaxTxPowerValue,
					pmp430InteropMode,
					apRxDelay,
					apVlanOverride,
					dhcpRelayAgentEnable,
					dhcpRelayAgentSrvrIP,
					dhcpRelayOpt82CircuitID,
					dhcpRelayOpt82RemoteID,
					dhcpRelayOpt82VendorSpecificID,
					reconnectReportEnable,
					failureReportingThreshold,
					reconnectReportDuration,
					onlyAllowVer95OrAbove,
					whispWebUseAuthServer,
					whispUsrAuthSharedSecret1,
					whispUsrAuthSharedSecret2,
					whispUsrAuthSharedSecret3,
					whispUsrAcctSvr1,
					whispUsrAcctSvr2,
					whispUsrAcctSvr3,
					whispUsrAuthPhase1,
					accountingInterimUpdateInterval,
					accountingSmReAuthInterval,
					dropSession,
					removeIdleSMs,
					lastTimeIdleSMsRemoved,
					sessionActions,
					lqiMetric,
					userAuthSharedSecret1,
					userAuthSharedSecret2,
					userAuthSharedSecret3,
					timeZone,
					systemTimeSet,
					actionListFilename,
					enableAutoupdate,
					autoUpdateFileServer,
					lqiTrapsEnable,
					lqiRaiseTrapThreshold,
					lqiClearTrapThreshold,
					lqiTrapsObservePeriod,
					apScheduler,
					defaultDownlinkPlan,
					defaultUplinkPlan}
		STATUS		current
		DESCRIPTION
			"WHiSP APs configuration group."
		::= {whispApsGroups 2}

	whispApsLinkTableGroup	OBJECT-GROUP
			OBJECTS {
					linkLUID,
					linkDescr,
					linkPhysAddress,
					linkManagementIP,
					linkFragmentsReceived1XVertical,
					linkFragmentsReceived2XVertical,
					linkFragmentsReceived3XVertical,
					linkFragmentsReceived4XVertical,
					signalToNoiseRatioVertical,
					linkFragmentsReceived1XHorizontal,
					linkFragmentsReceived2XHorizontal,
					linkFragmentsReceived3XHorizontal,
					linkFragmentsReceived4XHorizontal,
					signalToNoiseRatioHorizontal,
					linkSignalStrengthRatio,
					linkRadioDbmHorizontal,
					linkRadioDbmVertical,
					maxSMTxPwr,
					productType,
					linkAdaptRateLowPri,
					linkAdaptRateHighPri,
					avgPowerLevelInt,
					mimoPowerLevelVertical,
					mimoPowerLevelHorizontal,
					autoUpdateStatus,
					linkMtu,
					linkSpeed,
					linkOperStatus,
					linkInOctets,
					linkInOctets64,
					linkInUcastPkts,
					linkInUcastPkts64,
					linkInNUcastPkts,
					linkInNUcastPkts64,
					linkInDiscards,
					linkInDiscards64,
					linkInError,
					linkInError64,
					linkInUnknownProtos,
					linkOutOctets,
					linkOutOctets64,
					linkOutUcastPkts,
					linkOutUcastPkts64,
					linkOutNUcastPkts,
					linkOutNUcastPkts64,
					linkOutDiscards,
					linkOutDiscards64,
					linkOutError,
					linkOutError64,
					linkOutQLen,
					linkSessState,
					linkESN,
					linkRSSI,
					linkAveJitter,
					linkLastJitter,
					linkAirDelay,
					linkRegCount,
					linkReRegCount,
					linkTimeOut,
					linkLastRSSI,
					sessionCount,
					softwareVersion,
					linkSwVersion,
					linkSpatialFrequency,
					soundingState,
					downlinkSoundingState,
					uplinkSoundingState,
					downlinkMumimoRateAdapt,
					uplinkMumimoRateAdapt,
					softwareBootVersion,
					fpgaVersion,
					linkSiteName,
					avgPowerLevel,
					lastPowerLevel,
					sesDownLinkRate,
					sesDownLinkLimit,
					sesUpLinkRate,
					sesUpLinkLimit,
					adaptRate,
					modRateDL,
					sesLoUpCIR,
					sesLoDownCIR,
					sesMedUpCIR,
					sesMedDownCIR,
					sesHiUpCIR,
					sesHiDownCIR,
					sesUHiUpCIR,
					sesUHiDownCIR,
					linkPlatformVer,
					smSessionTmr,
					smSessionSeqNumMismatch,
					dataVCNum,
					hiPriQEn,
					dataVCNumHiQ,
					linkInOctetsHiQ,
					linkInOctetsHiQ64,
					linkInUcastPktsHiQ,
					linkInUcastPktsHiQ64,
					linkInNUcastPktsHiQ,
					linkInNUcastPktsHiQ64,
					linkInDiscardsHiQ,
					linkInDiscardsHiQ64,
					linkInErrorHiQ,
					linkInErrorHiQ64,
					linkInUnknownProtosHiQ,
					linkOutOctetsHiQ,
					linkOutOctetsHiQ64,
					linkOutUcastPktsHiQ,
					linkOutUcastPktsHiQ64,
					linkOutNUcastPktsHiQ,
					linkOutNUcastPktsHiQ64,
					linkOutDiscardsHiQ,
					linkOutDiscardsHiQ64,
					linkOutErrorHiQ,
					linkOutErrorHiQ64,
					retransmittedFragmentsCount,
					mediumPriQEn,
					dataVCNumMediumQ,
					linkInOctetsMediumQ,
					linkInUcastPktsMediumQ,
					linkInNUcastPktsMediumQ,
					linkInDiscardsMediumQ,
					linkInErrorMediumQ,
					linkInUnknownProtosMediumQ,
					linkOutOctetsMediumQ,
					linkOutUcastPktsMediumQ,
					linkOutNUcastPktsMediumQ,
					linkOutDiscardsMediumQ,
					linkOutErrorMediumQ,
					ultraHighPriQEn,
					dataVCNumUltraHighQ,
					linkInOctetsUltraHighQ,
					linkInUcastPktsUltraHighQ,
					linkInNUcastPktsUltraHighQ,
					linkInDiscardsUltraHighQ,
					linkInErrorUltraHighQ,
					linkInUnknownProtosUltraHighQ,
					linkOutOctetsUltraHighQ,
					linkOutUcastPktsUltraHighQ,
					linkOutNUcastPktsUltraHighQ,
					linkOutDiscardsUltraHighQ,
					linkOutErrorUltraHighQ,
					vcQOverflow,
					vcQOverflowHiQ,
					vcQOverflowMediumQ,
					vcQOverflowUltraHighQ,
					p7p8HiPriQEn,
					p7p8HiPriQ,
					linkAirDelayns,
					linkQualityAPData,
					fastRateAdaptActive,
					bestEvmDownlinkPathA,
					bestEvmDownlinkPathB,
					bestEvmUplinkPathA,
					bestEvmUplinkPathB,
					worstEvmDownlinkPathA,
					worstEvmDownlinkPathB,
					worstEvmUplinkPathA,
					worstEvmUplinkPathB,
					linkColorCodePriority,
					averageEvmDownlinkPathA,
					averageEvmDownlinkPathB,
					combinedEvmDownlink,
					averageEvmUplinkPathA,
					averageEvmUplinkPathB,
					combinedEvmUplink,
					linkVcDepth,
					radiusReplyMsg,
					radiusFramedIPAddress,
					radiusFramedIPNetmask,
					radiusDefaultGateway}
		STATUS		current
		DESCRIPTION
			"WHiSP APs Link Table group."
		::= {whispApsGroups 3}

	whispApsNotifGroup	NOTIFICATION-GROUP
			NOTIFICATIONS {
					whispRegComplete,
					whispRegLost,
					whispRegFailure,
					whispDefKeyUsed,
					whispGPSInSync,
					whispGPSOutSync,
					whispRadarDetected,
					whispRadarEnd,
					regulatoryApCheckInvalidChanFailed,
					regulatoryCheckFailedNoRegionAp,
					regulatoryApCheckInvalidChBwFailed,
					rfLinkOverloadCondition,
					whispDownlinkLqiBelowThreshold,
					whispDownlinkLqiRestored,
					whispUplinkLqiBelowThreshold,
					whispUplinkLqiRestored,
					mumimoTrialEvent,
					cbrsTxEnable,
					cbrsTxDisable}
		STATUS		current
		DESCRIPTION
			"WHiSP APs notification group."
		::= {whispApsGroups 4}

	whispApsFailedRegTableGroup	OBJECT-GROUP
			OBJECTS {
					regGrantReason,
					regFailESN,
					regFailTime,
					regFailSeqNum,
					regFailReasonText}
		STATUS		current
		DESCRIPTION
			"WHiSP APs Failed Registration Table group."
		::= {whispApsGroups 5}

	whispApsFrUtlStatsIntervalLowGroup	OBJECT-GROUP
			OBJECTS {
					frUtlLowTotalDownlinkUtilization,
					frUtlLowTotalUplinkUtilization,
					frUtlLowTotalDownlinkSlots,
					frUtlLowDownlinkLowPrioSlots,
					frUtlLowDownlinkHiPrioSlots,
					frUtlLowDownlinkBcastSlots,
					frUtlLowDownlinkAckSlots,
					frUtlLowDownlinkCntlMsgSlots,
					frUtlLowTotalUplinkSlots,
					frUtlLowUplinkLowPrioSlots,
					frUtlLowUplinkHiPrioSlots,
					frUtlLowUplinkAckSlots,
					frUtlLowMaxDownlinkSlots,
					frUtlLowMaxUplinkSlots,
					frUtlLowEthInDiscards,
					frUtlLowEthOutDiscards,
					frUtlLowRFInDiscards,
					frUtlLowRFOutDiscards,
					frUtlLowIntervalBwReqPercentage,
					frUtlLowIntervalBwReqRx,
					frUtlLowIntervalBwReqMissed,
					frUtlLowContentionSlots,
					frUtlLowAvgDownlinkSlots,
					frUtlLowAvgUplinkSlots,
					frUtlLowAvgContentionSlots,
					frUtlLowAvgReservedContentionSlots,
					frUtlLowAvgEffectiveContentionSlots,
					frUtlLowMaxContentionSlots,
					frUtlLowDownlinkAckUtilization,
					frUtlLowUplinkAckUtilization,
					frUtlLowDownlinkMumimoAckUtilization,
					frUtlLowUplinkMumimoAckUtilization,
					frUtlLowDownlinkBcastMcastUtilization,
					frUtlLowMumimoDownlinkSectorUtilization,
					frUtlLowMumimoUplinkSectorUtilization,
					frUtlLowMumimoDownlinkMumimoUtilization,
					frUtlLowMumimoUplinkMumimoUtilization,
					frUtlLowMumimoDownlinkSumimoUtilization,
					frUtlLowMumimoUplinkSumimoUtilization,
					frUtlLowMumimoDownlinkMultiplexingGain,
					frUtlLowMumimoUplinkMultiplexingGain,
					frUtlLowDownlinkAvgGroupSizeCombined,
					frUtlLowUplinkAvgGroupSizeCombined,
					frUtlLowMumimoDownlinkAvgGroupSize,
					frUtlLowMumimoUplinkAvgGroupSize,
					frUtlLowDownlinkMediumPrioSlots,
					frUtlLowDownlinkUltraHighPrioSlots,
					frUtlLowDownlinkAAAMsgSlots,
					frUtlLowDownlink1xModSlots,
					frUtlLowDownlink2xModSlots,
					frUtlLowDownlink3xModSlots,
					frUtlLowDownlink4xModSlots,
					frUtlLowDownlink5xModSlots,
					frUtlLowDownlink6xModSlots,
					frUtlLowDownlink7xModSlots,
					frUtlLowDownlink8xModSlots,
					frUtlLowDLSpecEffExtrap,
					frUtlLowDLSpecEffMax,
					frUtlLowDLAvgFragsPerSlot,
					frUtlLowUplinkMediumPrioSlots,
					frUtlLowUplinkUltraHighPrioSlots,
					frUtlLowUplinkAAAMsgSlots,
					frUtlLowUplink1xModSlots,
					frUtlLowUplink2xModSlots,
					frUtlLowUplink3xModSlots,
					frUtlLowUplink4xModSlots,
					frUtlLowUplink5xModSlots,
					frUtlLowUplink6xModSlots,
					frUtlLowUplink7xModSlots,
					frUtlLowUplink8xModSlots,
					frUtlLowULSpecEffExtrap,
					frUtlLowULSpecEffMax,
					frUtlLowULAvgFragsPerSlot,
					frUtlLowULMissedAcksSuMimo,
					frUtlLowULMissedAcksMuMimo,
					frUtlLowUplinkAvgSchedCycles,
					frUtlLowDownlinkAvgSchedCycles}
		STATUS		current
		DESCRIPTION
			"WHiSP APs Frame Utilization Statistics group for interval of 1 minute. Only supported for PMP and PTP 450 AP and Backhauls."
		::= {whispApsGroups 7}

	whispApsFrUtlStatsIntervalMediumGroup	OBJECT-GROUP
			OBJECTS {
					frUtlMedTotalDownlinkUtilization,
					frUtlMedTotalUplinkUtilization,
					frUtlMedTotalDownlinkSlots,
					frUtlMedDownlinkLowPrioSlots,
					frUtlMedDownlinkHiPrioSlots,
					frUtlMedDownlinkBcastSlots,
					frUtlMedDownlinkAckSlots,
					frUtlMedDownlinkCntlMsgSlots,
					frUtlMedTotalUplinkSlots,
					frUtlMedUplinkLowPrioSlots,
					frUtlMedUplinkHiPrioSlots,
					frUtlMedUplinkAckSlots,
					frUtlMedMaxDownlinkSlots,
					frUtlMedMaxUplinkSlots,
					frUtlMedEthInDiscards,
					frUtlMedEthOutDiscards,
					frUtlMedRFInDiscards,
					frUtlMedRFOutDiscards,
					frUtlMediumIntervalBwReqPercentage,
					frUtlMediumIntervalBwReqRx,
					frUtlMediumIntervalBwReqMissed,
					frUtlMediumContentionSlots,
					frUtlMediumAvgDownlinkSlots,
					frUtlMediumAvgUplinkSlots,
					frUtlMediumAvgContentionSlots,
					frUtlMediumAvgReservedContentionSlots,
					frUtlMediumAvgEffectiveContentionSlots,
					frUtlMediumMaxContentionSlots,
					frUtlMedDownlinkAckUtilization,
					frUtlMedUplinkAckUtilization,
					frUtlMedDownlinkMumimoAckUtilization,
					frUtlMedUplinkMumimoAckUtilization,
					frUtlMedDownlinkBcastMcastUtilization,
					frUtlMedMumimoDownlinkSectorUtilization,
					frUtlMedMumimoUplinkSectorUtilization,
					frUtlMedMumimoDownlinkMumimoUtilization,
					frUtlMedMumimoUplinkMumimoUtilization,
					frUtlMedMumimoDownlinkSumimoUtilization,
					frUtlMedMumimoUplinkSumimoUtilization,
					frUtlMedMumimoDownlinkMultiplexingGain,
					frUtlMedMumimoUplinkMultiplexingGain,
					frUtlMedDownlinkAvgGroupSizeCombined,
					frUtlMedUplinkAvgGroupSizeCombined,
					frUtlMedMumimoDownlinkAvgGroupSize,
					frUtlMedMumimoUplinkAvgGroupSize,
					frUtlMediumULMissedAcksSuMimo,
					frUtlMediumULMissedAcksMuMimo,
					frUtlMedDownlinkMediumPrioSlots,
					frUtlMedDownlinkUltraHighPrioSlots,
					frUtlMedDownlinkAAAMsgSlots,
					frUtlMedDownlink1xModSlots,
					frUtlMedDownlink2xModSlots,
					frUtlMedDownlink3xModSlots,
					frUtlMedDownlink4xModSlots,
					frUtlMedDownlink5xModSlots,
					frUtlMedDownlink6xModSlots,
					frUtlMedDownlink7xModSlots,
					frUtlMedDownlink8xModSlots,
					frUtlMediumDLSpecEffExtrap,
					frUtlMediumDLSpecEffMax,
					frUtlMediumDLAvgFragsPerSlot,
					frUtlMedUplinkMediumPrioSlots,
					frUtlMedUplinkUltraHighPrioSlots,
					frUtlMedUplinkAAAMsgSlots,
					frUtlMedUplink1xModSlots,
					frUtlMedUplink2xModSlots,
					frUtlMedUplink3xModSlots,
					frUtlMedUplink4xModSlots,
					frUtlMedUplink5xModSlots,
					frUtlMedUplink6xModSlots,
					frUtlMedUplink7xModSlots,
					frUtlMedUplink8xModSlots,
					frUtlMediumULSpecEffExtrap,
					frUtlMediumULSpecEffMax,
					frUtlMediumULAvgFragsPerSlot,
					frUtlMedUplinkAvgSchedCycles,
					frUtlMedDownlinkAvgSchedCycles}
		STATUS		current
		DESCRIPTION
			"WHiSP APs Frame Utilization Statistics group for interval of 5 minutes. Only supported for PMP and PTP 450 AP and Backhauls."
		::= {whispApsGroups 8}

	whispApsFrUtlStatsIntervalHighGroup	OBJECT-GROUP
			OBJECTS {
					frUtlHighTotalDownlinkUtilization,
					frUtlHighTotalUplinkUtilization,
					frUtlHighTotalDownlinkSlots,
					frUtlHighDownlinkLowPrioSlots,
					frUtlHighDownlinkHiPrioSlots,
					frUtlHighDownlinkBcastSlots,
					frUtlHighDownlinkAckSlots,
					frUtlHighDownlinkCntlMsgSlots,
					frUtlHighTotalUplinkSlots,
					frUtlHighUplinkLowPrioSlots,
					frUtlHighUplinkHiPrioSlots,
					frUtlHighUplinkAckSlots,
					frUtlHighMaxDownlinkSlots,
					frUtlHighMaxUplinkSlots,
					frUtlHighEthInDiscards,
					frUtlHighEthOutDiscards,
					frUtlHighRFInDiscards,
					frUtlHighRFOutDiscards,
					frUtlHighIntervalBwReqPercentage,
					frUtlHighIntervalBwReqRx,
					frUtlHighIntervalBwReqMissed,
					frUtlHighContentionSlots,
					frUtlHighAvgDownlinkSlots,
					frUtlHighAvgUplinkSlots,
					frUtlHighAvgContentionSlots,
					frUtlHighAvgReservedContentionSlots,
					frUtlHighAvgEffectiveContentionSlots,
					frUtlHighMaxContentionSlots,
					frUtlHighDownlinkAckUtilization,
					frUtlHighUplinkAckUtilization,
					frUtlHighDownlinkMumimoAckUtilization,
					frUtlHighUplinkMumimoAckUtilization,
					frUtlHighDownlinkBcastMcastUtilization,
					frUtlHighMumimoDownlinkSectorUtilization,
					frUtlHighMumimoUplinkSectorUtilization,
					frUtlHighMumimoDownlinkMumimoUtilization,
					frUtlHighMumimoUplinkMumimoUtilization,
					frUtlHighMumimoDownlinkSumimoUtilization,
					frUtlHighMumimoUplinkSumimoUtilization,
					frUtlHighMumimoDownlinkMultiplexingGain,
					frUtlHighMumimoUplinkMultiplexingGain,
					frUtlHighDownlinkAvgGroupSizeCombined,
					frUtlHighUplinkAvgGroupSizeCombined,
					frUtlHighMumimoDownlinkAvgGroupSize,
					frUtlHighMumimoiUplinkAvgGroupSize,
					frUtlHighULMissedAcksSuMimo,
					frUtlHighULMissedAcksMuMimo,
					frUtlHighDownlinkMediumPrioSlots,
					frUtlHighDownlinkUltraHighPrioSlots,
					frUtlHighDownlinkAAAMsgSlots,
					frUtlHighDownlink1xModSlots,
					frUtlHighDownlink2xModSlots,
					frUtlHighDownlink3xModSlots,
					frUtlHighDownlink4xModSlots,
					frUtlHighDownlink5xModSlots,
					frUtlHighDownlink6xModSlots,
					frUtlHighDownlink7xModSlots,
					frUtlHighDownlink8xModSlots,
					frUtlHighDLSpecEffExtrap,
					frUtlHighDLSpecEffMax,
					frUtlHighDLAvgFragsPerSlot,
					frUtlHighUplinkMediumPrioSlots,
					frUtlHighUplinkUltraHighPrioSlots,
					frUtlHighUplinkAAAMsgSlots,
					frUtlHighUplink1xModSlots,
					frUtlHighUplink2xModSlots,
					frUtlHighUplink3xModSlots,
					frUtlHighUplink4xModSlots,
					frUtlHighUplink5xModSlots,
					frUtlHighUplink6xModSlots,
					frUtlHighUplink7xModSlots,
					frUtlHighUplink8xModSlots,
					frUtlHighULSpecEffExtrap,
					frUtlHighULSpecEffMax,
					frUtlHighULAvgFragsPerSlot,
					frUtlHighUplinkAvgSchedCycles,
					frUtlHighDownlinkAvgSchedCycles}
		STATUS		current
		DESCRIPTION
			"WHiSP APs Frame Utilization Statistics group for interval of 15 minutes. Only supported for PMP and PTP 450 AP and Backhauls."
		::= {whispApsGroups 9}

	whispApsDHCPv6RelayGroup	OBJECT-GROUP
			OBJECTS {
					reqRecvd,
					reqRelayed,
					reqDiscards,
					respRecvd,
					respRelayed,
					respDiscards,
					pktTooBig}
		STATUS		current
		DESCRIPTION
			"WHiSP APs DHCPv6 Relay Statistics group."
		::= {whispApsGroups 10}

	frUtlLowTotalDownlinkUtilization	OBJECT-TYPE
		SYNTAX		INTEGER
		MAX-ACCESS	read-only
		STATUS		current
		DESCRIPTION		
			"Percentage of total downlink utilization in the last 1 minute. Only supported for PMP and PTP 450 AP and Backhauls."
		::={whispApsFrUtlStatsIntervalLow 1}

	frUtlLowTotalUplinkUtilization	OBJECT-TYPE
		SYNTAX		INTEGER
		MAX-ACCESS	read-only
		STATUS		current
		DESCRIPTION		
			"Percentage of total uplink utilization in the last 1 minute. Only supported for PMP 450 AP platform."
		::={whispApsFrUtlStatsIntervalLow 2}

	frUtlLowTotalDownlinkSlots	OBJECT-TYPE
		SYNTAX		INTEGER
		MAX-ACCESS	read-only
		STATUS		current
		DESCRIPTION		
			"Total downlink data slots in the last 1 minute. Only supported for PMP and PTP 450 AP and Backhauls."
		::={whispApsFrUtlStatsIntervalLow 3}

	frUtlLowDownlinkLowPrioSlots	OBJECT-TYPE
		SYNTAX		INTEGER
		MAX-ACCESS	read-only
		STATUS		current
		DESCRIPTION		
			"Number of data slots used for downlink low priority traffic in the last 1 minute. Only supported for PMP and PTP 450 AP and Backhauls."
		::={whispApsFrUtlStatsIntervalLow 4}

	frUtlLowDownlinkHiPrioSlots	OBJECT-TYPE
		SYNTAX		INTEGER
		MAX-ACCESS	read-only
		STATUS		current
		DESCRIPTION		
			"Number of data slots used for downlink high priority traffic in the last 1 minute. Only supported for PMP and PTP 450 AP and Backhauls."
		::={whispApsFrUtlStatsIntervalLow 5}

	frUtlLowDownlinkBcastSlots	OBJECT-TYPE
		SYNTAX		INTEGER
		MAX-ACCESS	read-only
		STATUS		current
		DESCRIPTION		
			"Number of data slots used for downlink broadcast and multicast traffic in the last 1 minute. Only supported for PMP and PTP 450 AP and Backhauls."
		::={whispApsFrUtlStatsIntervalLow 6}

	frUtlLowDownlinkAckSlots	OBJECT-TYPE
		SYNTAX		INTEGER
		MAX-ACCESS	read-only
		STATUS		current
		DESCRIPTION		
			"Number of data slots used for Downlink Canopy MAC Acknowledgements in the last 1 minute. Only supported for PMP and PTP 450 AP and Backhauls."
		::={whispApsFrUtlStatsIntervalLow 7}

	frUtlLowDownlinkCntlMsgSlots	OBJECT-TYPE
		SYNTAX		INTEGER
		MAX-ACCESS	read-only
		STATUS		current
		DESCRIPTION		
			"Number of data slots used for downlink registration and control messages in the last 1 minute. Only supported for PMP and PTP 450 AP and Backhauls."
		::={whispApsFrUtlStatsIntervalLow 8}

	frUtlLowTotalUplinkSlots	OBJECT-TYPE
		SYNTAX		INTEGER
		MAX-ACCESS	read-only
		STATUS		current
		DESCRIPTION		
			"Total uplink data slots in the last 1 minute. Only supported for PMP 450 AP platform."
		::={whispApsFrUtlStatsIntervalLow 9}

	frUtlLowUplinkLowPrioSlots	OBJECT-TYPE
		SYNTAX		INTEGER
		MAX-ACCESS	read-only
		STATUS		current
		DESCRIPTION		
			"Number of data slots used for uplink low priority traffic in the last 1 minute. Only supported for PMP 450 AP platform."
		::={whispApsFrUtlStatsIntervalLow 10}

	frUtlLowUplinkHiPrioSlots	OBJECT-TYPE
		SYNTAX		INTEGER
		MAX-ACCESS	read-only
		STATUS		current
		DESCRIPTION		
			"Number of data slots used for uplink high priority traffic in the last 1 minute. Only supported for PMP 450 AP platform."
		::={whispApsFrUtlStatsIntervalLow 11}

	frUtlLowUplinkAckSlots	OBJECT-TYPE
		SYNTAX		INTEGER
		MAX-ACCESS	read-only
		STATUS		current
		DESCRIPTION		
			"Number of data slots used for Uplink Canopy MAC Acknowledgements in the last 1 minute. Only supported for PMP 450 AP platform."
		::={whispApsFrUtlStatsIntervalLow 12}

	frUtlLowMaxDownlinkSlots	OBJECT-TYPE
		SYNTAX		INTEGER
		MAX-ACCESS	read-only
		STATUS		current
		DESCRIPTION		
			"Maximum possible downlink data slots for a minute. 
                        This is calculated as ((Downlink slots in a frame) * (Number of frames in a second) * 60). 
                        Downlink slots in a frame depends on the frame configuration. 
                        Number of frames in a second depends on the configured frame period of 5 ms (200 frames) or 2.5 ms (400 frames). 
                        Only supported for PMP and PTP 450 AP and Backhauls."
		::={whispApsFrUtlStatsIntervalLow 13}

	frUtlLowMaxUplinkSlots	OBJECT-TYPE
		SYNTAX		INTEGER
		MAX-ACCESS	read-only
		STATUS		current
		DESCRIPTION		
			"Maximum possible uplink data slots for a minute. 
                        This is calculated as ((Uplink slots in a frame) * (Number of frames in a second) * 60). 
                        Uplink slots in a frame depends on the frame configuration. 
                        Number of frames in a second depends on the configured frame period of 5 ms (200 frames) or 2.5 ms (400 frames).  
                        Only supported for PMP 450 AP platform."
		::={whispApsFrUtlStatsIntervalLow 14}

	frUtlLowEthInDiscards	OBJECT-TYPE
		SYNTAX		INTEGER
		MAX-ACCESS	read-only
		STATUS		current
		DESCRIPTION		
			"Number of incoming Ethernet packets discarded in the last 1 minute. Only supported for PMP and PTP 450 AP and Backhauls."
		::={whispApsFrUtlStatsIntervalLow 15}

	frUtlLowEthOutDiscards	OBJECT-TYPE
		SYNTAX		INTEGER
		MAX-ACCESS	read-only
		STATUS		current
		DESCRIPTION		
			"Number of outgoing Ethernet packets discarded in the last 1 minute. Only supported for PMP and PTP 450 AP and Backhauls."
		::={whispApsFrUtlStatsIntervalLow 16}

	frUtlLowRFInDiscards	OBJECT-TYPE
		SYNTAX		INTEGER
		MAX-ACCESS	read-only
		STATUS		current
		DESCRIPTION		
			"Number of incoming radio packets discarded in the last 1 minute. Only supported for PMP and PTP 450 AP and Backhauls."
		::={whispApsFrUtlStatsIntervalLow 17}

	frUtlLowRFOutDiscards	OBJECT-TYPE
		SYNTAX		INTEGER
		MAX-ACCESS	read-only
		STATUS		current
		DESCRIPTION		
			"Number of outgoing radio packets discarded in the last 1 minute. Only supported for PMP and PTP 450 AP and Backhauls."
		::={whispApsFrUtlStatsIntervalLow 18}

	frUtlLowIntervalBwReqPercentage	OBJECT-TYPE
		SYNTAX		INTEGER
		MAX-ACCESS	read-only
		STATUS		current
		DESCRIPTION		
			"Percentage of bandwidth request received in the last 1 minute.
                            Only supported for PMP 450 platform.
                            PMP 430 SMs will not be included in this statistic."
		::={whispApsFrUtlStatsIntervalLow 19}

	frUtlLowIntervalBwReqRx	OBJECT-TYPE
		SYNTAX		INTEGER
		MAX-ACCESS	read-only
		STATUS		current
		DESCRIPTION		
			"Number of bandwidth request received in the last 1 minute.
                            Only supported for PMP 450 platform.
                            PMP 430 SMs will not be included in this statistic."
		::={whispApsFrUtlStatsIntervalLow 20}

	frUtlLowIntervalBwReqMissed	OBJECT-TYPE
		SYNTAX		INTEGER
		MAX-ACCESS	read-only
		STATUS		current
		DESCRIPTION		
			"Number of bandwidth request missed in the last 1 minute.
                            Only supported for PMP 450 platform.
                            PMP 430 SMs will not be included in this statistic."
		::={whispApsFrUtlStatsIntervalLow 21}

	frUtlLowContentionSlots	OBJECT-TYPE
		SYNTAX		INTEGER
		MAX-ACCESS	read-only
		STATUS		current
		DESCRIPTION		
			"Number of scheduled contention slots available in the last 1 minute. 
                            Only supported for PMP 450 AP platform."
		::={whispApsFrUtlStatsIntervalLow 22}

	frUtlLowAvgDownlinkSlots	OBJECT-TYPE
		SYNTAX		INTEGER
		MAX-ACCESS	read-only
		STATUS		current
		DESCRIPTION		
			"Average downlink data slots per frame in the last 1 minute. Only supported for PMP and PTP 450 AP and Backhauls."
		::={whispApsFrUtlStatsIntervalLow 23}

	frUtlLowAvgUplinkSlots	OBJECT-TYPE
		SYNTAX		INTEGER
		MAX-ACCESS	read-only
		STATUS		current
		DESCRIPTION		
			"Average uplink data slots per frame in the last 1 minute. Only supported for PMP 450 AP platform."
		::={whispApsFrUtlStatsIntervalLow 24}

	frUtlLowAvgContentionSlots	OBJECT-TYPE
		SYNTAX		INTEGER
		MAX-ACCESS	read-only
		STATUS		current
		DESCRIPTION		
			"Average contention slots per frame in the last 1 minute. 
                            Only supported for PMP 450 AP platform."
		::={whispApsFrUtlStatsIntervalLow 25}

	frUtlLowMaxContentionSlots	OBJECT-TYPE
		SYNTAX		INTEGER
		MAX-ACCESS	read-only
		STATUS		current
		DESCRIPTION		
			"Maximum possible contention slots for 1 minute. 
                        This is calculated as (((Uplink slots in a frame) + (Contention slots in a frame)) * (Number of frames in a second) * 60(seconds)). 
                        Uplink slots and contention slots in a frame depend on the frame configuration. 
                        Number of frames in a second depends on the configured frame period of 5 ms (200 frames) or 2.5 ms (400 frames). 
                        Only supported for PMP 450 AP platform."
		::={whispApsFrUtlStatsIntervalLow 26}

	frUtlLowDownlinkAckUtilization	OBJECT-TYPE
		SYNTAX		INTEGER
		MAX-ACCESS	read-only
		STATUS		current
		DESCRIPTION		
			"Percentage of downlink Canopy MAC Acknowledgment utilization in the last 1 minute.
                            Presented in Statistics -> Frame Utilization -> Sector Utilization -> ACK."
		::={whispApsFrUtlStatsIntervalLow 27}

	frUtlLowDownlinkBcastMcastUtilization	OBJECT-TYPE
		SYNTAX		INTEGER
		MAX-ACCESS	read-only
		STATUS		current
		DESCRIPTION		
			"Percentage of downlink Broadcast/Multicast utilization in the last 1 minute.
                            Presented in Statistics -> Frame Utilization -> Sector Utilization -> Broadcast and Multicast."
		::={whispApsFrUtlStatsIntervalLow 28}

	frUtlLowMumimoDownlinkSectorUtilization	OBJECT-TYPE
		SYNTAX		INTEGER
		MAX-ACCESS	read-only
		STATUS		current
		DESCRIPTION		
			"Percentage of MU-MIMO downlink Sector utilization in the last 1 minute. 
                            Presented in Statistics -> Frame Utilization -> Sector Utilization -> Total Utilization.
                            MU-MIMO only."
		::={whispApsFrUtlStatsIntervalLow 29}

	frUtlLowMumimoDownlinkMumimoUtilization	OBJECT-TYPE
		SYNTAX		INTEGER
		MAX-ACCESS	read-only
		STATUS		current
		DESCRIPTION		
			"Percentage of MU-MIMO downlink utilization in the last 1 minute.
                            Presented in Statistics -> Frame Utilization -> Sector Utilization -> MU-MIMO.
                            MU-MIMO only."
		::={whispApsFrUtlStatsIntervalLow 30}

	frUtlLowMumimoDownlinkSumimoUtilization	OBJECT-TYPE
		SYNTAX		INTEGER
		MAX-ACCESS	read-only
		STATUS		current
		DESCRIPTION		
			"Percentage of SU-MIMO downlink utilization in the last 1 minute.
                            Presented in Statistics -> Frame Utilization -> Sector Utilization -> SU-MIMO.
                            MU-MIMO only."
		::={whispApsFrUtlStatsIntervalLow 31}

	frUtlLowMumimoDownlinkMultiplexingGain	OBJECT-TYPE
		SYNTAX		INTEGER (0..700)
		MAX-ACCESS	read-only
		STATUS		current
		DESCRIPTION		
			"MU-MIMO Multiplexing Gain in the last 1 minute. This compares the SU and MU usage for data and ACK allocations.
                            This value is scaled up by 100 (ie. 269 = 2.69).
                            MU-MIMO only."
		::={whispApsFrUtlStatsIntervalLow 32}

	frUtlLowMumimoDownlinkAvgGroupSize	OBJECT-TYPE
		SYNTAX		INTEGER (0..700)
		MAX-ACCESS	read-only
		STATUS		current
		DESCRIPTION		
			"Average MU-MIMO Group Size for data allocations in the last 1 minute.
                            This value is scaled up by 100 (ie. 269 = 2.69).
                            MU-MIMO only."
		::={whispApsFrUtlStatsIntervalLow 33}

	frUtlLowDownlinkMediumPrioSlots	OBJECT-TYPE
		SYNTAX		INTEGER
		MAX-ACCESS	read-only
		STATUS		current
		DESCRIPTION		
			"Number of data slots used for downlink medium priority traffic in the last 1 minute. Only supported for PMP and PTP 450 AP and Backhauls."
		::={whispApsFrUtlStatsIntervalLow 34}

	frUtlLowDownlinkUltraHighPrioSlots	OBJECT-TYPE
		SYNTAX		INTEGER
		MAX-ACCESS	read-only
		STATUS		current
		DESCRIPTION		
			"Number of data slots used for downlink ultra high priority traffic in the last 1 minute. Only supported for PMP and PTP 450 AP and Backhauls."
		::={whispApsFrUtlStatsIntervalLow 35}

	frUtlLowDownlinkAAAMsgSlots	OBJECT-TYPE
		SYNTAX		INTEGER
		MAX-ACCESS	read-only
		STATUS		current
		DESCRIPTION		
			"Number of data slots used for downlink Authentication and Configuration messages in the last 1 minute. Only supported for PMP and PTP 450 AP and Backhauls."
		::={whispApsFrUtlStatsIntervalLow 36}

	frUtlLowUplinkMediumPrioSlots	OBJECT-TYPE
		SYNTAX		INTEGER
		MAX-ACCESS	read-only
		STATUS		current
		DESCRIPTION		
			"Number of data slots used for uplink medium priority traffic in the last 1 minute. Only supported for PMP 450 AP platform."
		::={whispApsFrUtlStatsIntervalLow 37}

	frUtlLowUplinkUltraHighPrioSlots	OBJECT-TYPE
		SYNTAX		INTEGER
		MAX-ACCESS	read-only
		STATUS		current
		DESCRIPTION		
			"Number of data slots used for uplink ultra high priority traffic in the last 1 minute. Only supported for PMP 450 AP platform."
		::={whispApsFrUtlStatsIntervalLow 38}

	frUtlLowUplinkAAAMsgSlots	OBJECT-TYPE
		SYNTAX		INTEGER
		MAX-ACCESS	read-only
		STATUS		current
		DESCRIPTION		
			"Number of data slots used for uplink Authentication and Configuration messages in the last 1 minute. Only supported for PMP 450 AP platform."
		::={whispApsFrUtlStatsIntervalLow 39}

	frUtlLowMumimoUplinkSectorUtilization	OBJECT-TYPE
		SYNTAX		INTEGER
		MAX-ACCESS	read-only
		STATUS		current
		DESCRIPTION		
			"Percentage of MU-MIMO uplink Sector utilization in the last 1 minute.
                            Presented in Statistics -> Frame Utilization -> Sector Utilization -> Total Utilization.
                            MU-MIMO only."
		::={whispApsFrUtlStatsIntervalLow 40}

	frUtlLowMumimoUplinkMumimoUtilization	OBJECT-TYPE
		SYNTAX		INTEGER
		MAX-ACCESS	read-only
		STATUS		current
		DESCRIPTION		
			"Percentage of MU-MIMO uplink utilization in the last 1 minute.
                            Presented in Statistics -> Frame Utilization -> Sector Utilization -> MU-MIMO.
                            MU-MIMO only."
		::={whispApsFrUtlStatsIntervalLow 41}

	frUtlLowMumimoUplinkSumimoUtilization	OBJECT-TYPE
		SYNTAX		INTEGER
		MAX-ACCESS	read-only
		STATUS		current
		DESCRIPTION		
			"Percentage of SU-MIMO uplink utilization in the last 1 minute.
                            Presented in Statistics -> Frame Utilization -> Sector Utilization -> SU-MIMO.
                            MU-MIMO only."
		::={whispApsFrUtlStatsIntervalLow 42}

	frUtlLowMumimoUplinkMultiplexingGain	OBJECT-TYPE
		SYNTAX		INTEGER (0..700)
		MAX-ACCESS	read-only
		STATUS		current
		DESCRIPTION		
			"MU-MIMO Multiplexing Gain in the last 1 minute. This compares the SU and MU usage for data and ACK allocations.
                            This value is scaled up by 100 (ie. 269 = 2.69).
                            MU-MIMO only."
		::={whispApsFrUtlStatsIntervalLow 43}

	frUtlLowDownlinkAvgGroupSizeCombined	OBJECT-TYPE
		SYNTAX		INTEGER (0..700)
		MAX-ACCESS	read-only
		STATUS		current
		DESCRIPTION		
			"Average MU-MIMO Group Size for data and ACK allocations in the last 1 minute.
                           This value is scaled up by 100 (ie. 269 = 2.69).
                           MU-MIMO only."
		::={whispApsFrUtlStatsIntervalLow 44}

	frUtlLowUplinkAvgGroupSizeCombined	OBJECT-TYPE
		SYNTAX		INTEGER (0..700)
		MAX-ACCESS	read-only
		STATUS		current
		DESCRIPTION		
			"Average MU-MIMO Group Size for data and ACK allocations in the last 1 minute.
                            This value is scaled up by 100 (ie. 269 = 2.69).
                            MU-MIMO only."
		::={whispApsFrUtlStatsIntervalLow 45}

	frUtlLowMumimoUplinkAvgGroupSize	OBJECT-TYPE
		SYNTAX		INTEGER (0..700)
		MAX-ACCESS	read-only
		STATUS		current
		DESCRIPTION		
			"Average MU-MIMO Group Size for data allocations in the last 1 minute.
                            This value is scaled up by 100 (ie. 269 = 2.69).
                            MU-MIMO only."
		::={whispApsFrUtlStatsIntervalLow 46}

	frUtlLowUplinkAckUtilization	OBJECT-TYPE
		SYNTAX		INTEGER
		MAX-ACCESS	read-only
		STATUS		current
		DESCRIPTION		
			"Percentage of uplink Canopy MAC Acknowledgment utilization in the last 1 minute.
                            Presented in Statistics -> Frame Utilization -> Sector Utilization -> ACK."
		::={whispApsFrUtlStatsIntervalLow 47}

	frUtlLowDownlinkMumimoAckUtilization	OBJECT-TYPE
		SYNTAX		INTEGER
		MAX-ACCESS	read-only
		STATUS		current
		DESCRIPTION		
			"Percentage of downlink Canopy MAC Mumimo Acknowledgment utilization in the last 1 minute.
                            Presented in Statistics -> Frame Utilization -> Sector Utilization -> MU-MIMO ACK."
		::={whispApsFrUtlStatsIntervalLow 48}

	frUtlLowUplinkMumimoAckUtilization	OBJECT-TYPE
		SYNTAX		INTEGER
		MAX-ACCESS	read-only
		STATUS		current
		DESCRIPTION		
			"Percentage of uplink Canopy MAC Mumimo Acknowledgment utilization in the last 1 minute.
                            Presented in Statistics -> Frame Utilization -> Sector Utilization -> MU-MIMO ACK."
		::={whispApsFrUtlStatsIntervalLow 49}

	frUtlLowUplinkAvgSchedCycles	OBJECT-TYPE
		SYNTAX		INTEGER
		MAX-ACCESS	read-only
		STATUS		current
		DESCRIPTION		
			"Engineering use only.
                            Average number of uplink scheduling window in the last 1 minute.
                            An average scheduling window size of
                            a. 1  TDD cycle is  expected if there is no traffic.
                            b. 10 TDD cycles is expected on a heavily loaded system."
		::={whispApsFrUtlStatsIntervalLow 50}

	frUtlLowDownlinkAvgSchedCycles	OBJECT-TYPE
		SYNTAX		INTEGER
		MAX-ACCESS	read-only
		STATUS		current
		DESCRIPTION		
			"Engineering use only.
                            Average number of downlink scheduling window in the last 1 minute.
                            An average scheduling window size of
                            a. 1  TDD cycle is  expected if there is no traffic.
                            b. 10 TDD cycles is expected on a heavily loaded system."
		::={whispApsFrUtlStatsIntervalLow 51}

	frUtlLowAvgReservedContentionSlots	OBJECT-TYPE
		SYNTAX		INTEGER
		MAX-ACCESS	read-only
		STATUS		current
		DESCRIPTION		
			"Average Reserved contention slots per frame in the last 1 minute. 
                            PMP Only."
		::={whispApsFrUtlStatsIntervalLow 52}

	frUtlLowAvgEffectiveContentionSlots	OBJECT-TYPE
		SYNTAX		INTEGER
		MAX-ACCESS	read-only
		STATUS		current
		DESCRIPTION		
			"Average Effective contention slots in the last 1 minute. 
                            Only supported for PMP 450 AP platform.
                            Engineering use only."
		::={whispApsFrUtlStatsIntervalLow 53}

	frUtlLowDownlink1xModSlots	OBJECT-TYPE
		SYNTAX		INTEGER
		MAX-ACCESS	read-only
		STATUS		current
		DESCRIPTION		
			"Number of data slots used for downlink 1x modulation traffic in the last 1 minute. Only applies to PMP AP and Backhauls.
                                     Not currently supported on 450m"
		::={whispApsFrUtlStatsIntervalLow 54}

	frUtlLowDownlink2xModSlots	OBJECT-TYPE
		SYNTAX		INTEGER
		MAX-ACCESS	read-only
		STATUS		current
		DESCRIPTION		
			"Number of data slots used for downlink 2x modulation traffic in the last 1 minute. Only applies to PMP AP and Backhauls.
                                     Not currently supported on 450m"
		::={whispApsFrUtlStatsIntervalLow 55}

	frUtlLowDownlink3xModSlots	OBJECT-TYPE
		SYNTAX		INTEGER
		MAX-ACCESS	read-only
		STATUS		current
		DESCRIPTION		
			"Number of data slots used for downlink 3x modulation traffic in the last 1 minute. Only applies to PMP AP and Backhauls.
                                     Not currently supported on 450m"
		::={whispApsFrUtlStatsIntervalLow 56}

	frUtlLowDownlink4xModSlots	OBJECT-TYPE
		SYNTAX		INTEGER
		MAX-ACCESS	read-only
		STATUS		current
		DESCRIPTION		
			"Number of data slots used for downlink 4x modulation traffic in the last 1 minute. Only applies to PMP AP and Backhauls.
                                     Not currently supported on 450m"
		::={whispApsFrUtlStatsIntervalLow 57}

	frUtlLowDownlink5xModSlots	OBJECT-TYPE
		SYNTAX		INTEGER
		MAX-ACCESS	read-only
		STATUS		current
		DESCRIPTION		
			"Number of data slots used for downlink 5x modulation traffic in the last 1 minute. Only applies to PMP AP and Backhauls.
                                     Not currently supported on 450m"
		::={whispApsFrUtlStatsIntervalLow 58}

	frUtlLowDownlink6xModSlots	OBJECT-TYPE
		SYNTAX		INTEGER
		MAX-ACCESS	read-only
		STATUS		current
		DESCRIPTION		
			"Number of data slots used for downlink 6x modulation traffic in the last 1 minute. Only applies to PMP AP and Backhauls.
                                     Not currently supported on 450m"
		::={whispApsFrUtlStatsIntervalLow 59}

	frUtlLowDownlink7xModSlots	OBJECT-TYPE
		SYNTAX		INTEGER
		MAX-ACCESS	read-only
		STATUS		current
		DESCRIPTION		
			"Number of data slots used for downlink 7x modulation traffic in the last 1 minute. Only applies to PMP AP and Backhauls.
                                     Not currently supported on 450m"
		::={whispApsFrUtlStatsIntervalLow 60}

	frUtlLowDownlink8xModSlots	OBJECT-TYPE
		SYNTAX		INTEGER
		MAX-ACCESS	read-only
		STATUS		current
		DESCRIPTION		
			"Number of data slots used for downlink 8x modulation traffic in the last 1 minute. Only applies to PMP AP and Backhauls.
                                     Not currently supported on 450m"
		::={whispApsFrUtlStatsIntervalLow 61}

	frUtlLowUplink1xModSlots	OBJECT-TYPE
		SYNTAX		INTEGER
		MAX-ACCESS	read-only
		STATUS		current
		DESCRIPTION		
			"Number of data slots used for uplink 1x modulation traffic in the last 1 minute. Only applies to PMP AP and Backhauls.
                                     Not currently supported on 450m"
		::={whispApsFrUtlStatsIntervalLow 62}

	frUtlLowUplink2xModSlots	OBJECT-TYPE
		SYNTAX		INTEGER
		MAX-ACCESS	read-only
		STATUS		current
		DESCRIPTION		
			"Number of data slots used for uplink 2x modulation traffic in the last 1 minute. Only applies to PMP AP and Backhauls.
                                     Not currently supported on 450m"
		::={whispApsFrUtlStatsIntervalLow 63}

	frUtlLowUplink3xModSlots	OBJECT-TYPE
		SYNTAX		INTEGER
		MAX-ACCESS	read-only
		STATUS		current
		DESCRIPTION		
			"Number of data slots used for uplink 3x modulation traffic in the last 1 minute. Only applies to PMP AP and Backhauls.
                                     Not currently supported on 450m"
		::={whispApsFrUtlStatsIntervalLow 64}

	frUtlLowUplink4xModSlots	OBJECT-TYPE
		SYNTAX		INTEGER
		MAX-ACCESS	read-only
		STATUS		current
		DESCRIPTION		
			"Number of data slots used for uplink 4x modulation traffic in the last 1 minute. Only applies to PMP AP and Backhauls.
                                     Not currently supported on 450m"
		::={whispApsFrUtlStatsIntervalLow 65}

	frUtlLowUplink5xModSlots	OBJECT-TYPE
		SYNTAX		INTEGER
		MAX-ACCESS	read-only
		STATUS		current
		DESCRIPTION		
			"Number of data slots used for uplink 5x modulation traffic in the last 1 minute. Only applies to PMP AP and Backhauls.
                                     Not currently supported on 450m"
		::={whispApsFrUtlStatsIntervalLow 66}

	frUtlLowUplink6xModSlots	OBJECT-TYPE
		SYNTAX		INTEGER
		MAX-ACCESS	read-only
		STATUS		current
		DESCRIPTION		
			"Number of data slots used for uplink 6x modulation traffic in the last 1 minute. Only applies to PMP AP and Backhauls.
                                     Not currently supported on 450m"
		::={whispApsFrUtlStatsIntervalLow 67}

	frUtlLowUplink7xModSlots	OBJECT-TYPE
		SYNTAX		INTEGER
		MAX-ACCESS	read-only
		STATUS		current
		DESCRIPTION		
			"Number of data slots used for uplink 7x modulation traffic in the last 1 minute. Only applies to PMP AP and Backhauls.
                                     Not currently supported on 450m"
		::={whispApsFrUtlStatsIntervalLow 68}

	frUtlLowUplink8xModSlots	OBJECT-TYPE
		SYNTAX		INTEGER
		MAX-ACCESS	read-only
		STATUS		current
		DESCRIPTION		
			"Number of data slots used for uplink 8x modulation traffic in the last 1 minute. Only applies to PMP AP and Backhauls.
                                     Not currently supported on 450m"
		::={whispApsFrUtlStatsIntervalLow 69}

	frUtlLowDLSpecEffExtrap	OBJECT-TYPE
		SYNTAX		INTEGER
		MAX-ACCESS	read-only
		STATUS		current
		DESCRIPTION		
			"Extrapolated downlink Spectral Efficiency in the last 1 minute (Multiplied by 1000). Measured in units of user data bits per second per hertz.
                                     Divide by 1000 for actual number.
                                     Not currently supported on 450m"
		::={whispApsFrUtlStatsIntervalLow 70}

	frUtlLowDLSpecEffMax	OBJECT-TYPE
		SYNTAX		INTEGER
		MAX-ACCESS	read-only
		STATUS		current
		DESCRIPTION		
			"Maximum possible downlink Spectral Efficiency in the last 1 minute (Multiplied by 1000). Measured in units of user data bits per second per hertz.
                                     Divide by 1000 for actual number.
                                     Not currently supported on 450m"
		::={whispApsFrUtlStatsIntervalLow 71}

	frUtlLowULSpecEffExtrap	OBJECT-TYPE
		SYNTAX		INTEGER
		MAX-ACCESS	read-only
		STATUS		current
		DESCRIPTION		
			"Extrapolated uplink Spectral Efficiency in the last 1 minute (Multiplied by 1000). Measured in units of user data bits per second per hertz.
                                     Divide by 1000 for actual number.
                                     Not currently supported on 450m"
		::={whispApsFrUtlStatsIntervalLow 72}

	frUtlLowULSpecEffMax	OBJECT-TYPE
		SYNTAX		INTEGER
		MAX-ACCESS	read-only
		STATUS		current
		DESCRIPTION		
			"Maximum possible uplink Spectral Efficiency in the last 1 minute (Multiplied by 1000). Measured in units of user data bits per second per hertz.
                                     Divide by 1000 for actual number.
                                     Not currently supported on 450m"
		::={whispApsFrUtlStatsIntervalLow 73}

	frUtlLowDLAvgFragsPerSlot	OBJECT-TYPE
		SYNTAX		INTEGER
		MAX-ACCESS	read-only
		STATUS		current
		DESCRIPTION		
			"Average number of fragments per slot in the last 1 minute (Multiplied by 100).
                                     Divide by 100 for actual number.
                                     Not currently supported on 450m"
		::={whispApsFrUtlStatsIntervalLow 74}

	frUtlLowULAvgFragsPerSlot	OBJECT-TYPE
		SYNTAX		INTEGER
		MAX-ACCESS	read-only
		STATUS		current
		DESCRIPTION		
			"Average number of fragments per slot in the last 1 minute (Multiplied by 100).
                                     Divide by 100 for actual number.
                                     Not currently supported on 450m"
		::={whispApsFrUtlStatsIntervalLow 75}

	frUtlLowULMissedAcksSuMimo	OBJECT-TYPE
		SYNTAX		INTEGER
		MAX-ACCESS	read-only
		STATUS		current
		DESCRIPTION		
			"Number of missed Uplink MAC Acknowledgements in the last 1 minute.
                            PMP only.
                            For 450m, this is the SU-MIMO ACKs."
		::={whispApsFrUtlStatsIntervalLow 76}

	frUtlLowULMissedAcksMuMimo	OBJECT-TYPE
		SYNTAX		INTEGER
		MAX-ACCESS	read-only
		STATUS		current
		DESCRIPTION		
			"Number of missed Uplink MU-MIMO MAC Acknowledgements in the last 1 minute.
                            PMP only.
                            MU-MIMO platforms only."
		::={whispApsFrUtlStatsIntervalLow 77}

	frUtlMedTotalDownlinkUtilization	OBJECT-TYPE
		SYNTAX		INTEGER
		MAX-ACCESS	read-only
		STATUS		current
		DESCRIPTION		
			"Percentage of total downlink utilization in the last 5 minutes. Only supported for PMP and PTP 450 AP and Backhauls."
		::={whispApsFrUtlStatsIntervalMedium 1}

	frUtlMedTotalUplinkUtilization	OBJECT-TYPE
		SYNTAX		INTEGER
		MAX-ACCESS	read-only
		STATUS		current
		DESCRIPTION		
			"Percentage of total uplink utilization in the last 5 minutes. Only supported for PMP 450 AP platform."
		::={whispApsFrUtlStatsIntervalMedium 2}

	frUtlMedTotalDownlinkSlots	OBJECT-TYPE
		SYNTAX		INTEGER
		MAX-ACCESS	read-only
		STATUS		current
		DESCRIPTION		
			"Total downlink data slots in the last 5 minutes. Only supported for PMP and PTP 450 AP and Backhauls."
		::={whispApsFrUtlStatsIntervalMedium 3}

	frUtlMedDownlinkLowPrioSlots	OBJECT-TYPE
		SYNTAX		INTEGER
		MAX-ACCESS	read-only
		STATUS		current
		DESCRIPTION		
			"Number of data slots used for downlink low priority traffic in the last 5 minutes. Only supported for PMP and PTP 450 AP and Backhauls."
		::={whispApsFrUtlStatsIntervalMedium 4}

	frUtlMedDownlinkHiPrioSlots	OBJECT-TYPE
		SYNTAX		INTEGER
		MAX-ACCESS	read-only
		STATUS		current
		DESCRIPTION		
			"Number of data slots used for downlink high priority traffic in the last 5 minutes. Only supported for PMP and PTP 450 AP and Backhauls."
		::={whispApsFrUtlStatsIntervalMedium 5}

	frUtlMedDownlinkBcastSlots	OBJECT-TYPE
		SYNTAX		INTEGER
		MAX-ACCESS	read-only
		STATUS		current
		DESCRIPTION		
			"Number of data slots used for downlink broadcast and multicast traffic in the last 5 minutes. Only supported for PMP and PTP 450 AP and Backhauls."
		::={whispApsFrUtlStatsIntervalMedium 6}

	frUtlMedDownlinkAckSlots	OBJECT-TYPE
		SYNTAX		INTEGER
		MAX-ACCESS	read-only
		STATUS		current
		DESCRIPTION		
			"Number of data slots used for Downlink Canopy MAC Acknowledgements in the last 5 minutes. Only supported for PMP and PTP 450 AP and Backhauls."
		::={whispApsFrUtlStatsIntervalMedium 7}

	frUtlMedDownlinkCntlMsgSlots	OBJECT-TYPE
		SYNTAX		INTEGER
		MAX-ACCESS	read-only
		STATUS		current
		DESCRIPTION		
			"Number of data slots used for downlink registration and control messages in the last 5 minutes. Only supported for PMP and PTP 450 AP and Backhauls."
		::={whispApsFrUtlStatsIntervalMedium 8}

	frUtlMedTotalUplinkSlots	OBJECT-TYPE
		SYNTAX		INTEGER
		MAX-ACCESS	read-only
		STATUS		current
		DESCRIPTION		
			"Total uplink data slots in the last 5 minutes. Only supported for PMP 450 AP platform."
		::={whispApsFrUtlStatsIntervalMedium 9}

	frUtlMedUplinkLowPrioSlots	OBJECT-TYPE
		SYNTAX		INTEGER
		MAX-ACCESS	read-only
		STATUS		current
		DESCRIPTION		
			"Number of data slots used for uplink low priority traffic in the last 5 minutes. Only supported for PMP 450 AP platform."
		::={whispApsFrUtlStatsIntervalMedium 10}

	frUtlMedUplinkHiPrioSlots	OBJECT-TYPE
		SYNTAX		INTEGER
		MAX-ACCESS	read-only
		STATUS		current
		DESCRIPTION		
			"Number of data slots used for uplink high priority traffic in the last 5 minutes. Only supported for PMP 450 AP platform."
		::={whispApsFrUtlStatsIntervalMedium 11}

	frUtlMedUplinkAckSlots	OBJECT-TYPE
		SYNTAX		INTEGER
		MAX-ACCESS	read-only
		STATUS		current
		DESCRIPTION		
			"Number of data slots used for Uplink Canopy MAC Acknowledgements in the last 5 minutes. Only supported for PMP 450 AP platform."
		::={whispApsFrUtlStatsIntervalMedium 12}

	frUtlMedMaxDownlinkSlots	OBJECT-TYPE
		SYNTAX		INTEGER
		MAX-ACCESS	read-only
		STATUS		current
		DESCRIPTION		
			"Maximum possible downlink data slots for 5 minutes. 
                        This is calculated as ((Downlink slots in a frame) * (Number of frames in a second) * 5 * 60 (seconds)). 
                        Downlink slots in a frame depends on the frame configuration. 
                        Number of frames in a second depends on the configured frame period of 5 ms (200 frames) or 2.5 ms (400 frames). 
                        Only supported for PMP and PTP 450 AP and Backhauls."
		::={whispApsFrUtlStatsIntervalMedium 13}

	frUtlMedMaxUplinkSlots	OBJECT-TYPE
		SYNTAX		INTEGER
		MAX-ACCESS	read-only
		STATUS		current
		DESCRIPTION		
			"Maximum possible uplink data slots for 5 minutes. 
                        This is calculated as ((Uplink slots in a frame) * (Number of frames in a second) * 5 * 60(seconds)). 
                        Uplink slots in a frame depends on the frame configuration. 
                        Number of frames in a second depends on the configured frame period of 5 ms (200 frames) or 2.5 ms (400 frames). 
                        Only supported for PMP 450 AP platform."
		::={whispApsFrUtlStatsIntervalMedium 14}

	frUtlMedEthInDiscards	OBJECT-TYPE
		SYNTAX		INTEGER
		MAX-ACCESS	read-only
		STATUS		current
		DESCRIPTION		
			"Number of incoming Ethernet packets discarded in the last 5 minutes. Only supported for PMP and PTP 450 AP and Backhauls."
		::={whispApsFrUtlStatsIntervalMedium 15}

	frUtlMedEthOutDiscards	OBJECT-TYPE
		SYNTAX		INTEGER
		MAX-ACCESS	read-only
		STATUS		current
		DESCRIPTION		
			"Number of outgoing Ethernet packets discarded in the last 5 minutes. Only supported for PMP and PTP 450 AP and Backhauls."
		::={whispApsFrUtlStatsIntervalMedium 16}

	frUtlMedRFInDiscards	OBJECT-TYPE
		SYNTAX		INTEGER
		MAX-ACCESS	read-only
		STATUS		current
		DESCRIPTION		
			"Number of incoming radio packets discarded in the last 5 minutes. Only supported for PMP and PTP 450 AP and Backhauls."
		::={whispApsFrUtlStatsIntervalMedium 17}

	frUtlMedRFOutDiscards	OBJECT-TYPE
		SYNTAX		INTEGER
		MAX-ACCESS	read-only
		STATUS		current
		DESCRIPTION		
			"Number of outgoing radio packets discarded in the last 5 minutes. Only supported for PMP and PTP 450 AP and Backhauls."
		::={whispApsFrUtlStatsIntervalMedium 18}

	frUtlMediumIntervalBwReqPercentage	OBJECT-TYPE
		SYNTAX		INTEGER
		MAX-ACCESS	read-only
		STATUS		current
		DESCRIPTION		
			"Percentage of bandwidth request received in the last 5 minutes.
                            Only supported for PMP 450 platform.
                            PMP 430 SMs will not be included in this statistic."
		::={whispApsFrUtlStatsIntervalMedium 19}

	frUtlMediumIntervalBwReqRx	OBJECT-TYPE
		SYNTAX		INTEGER
		MAX-ACCESS	read-only
		STATUS		current
		DESCRIPTION		
			"Number of bandwidth request received in the last 5 minutes.
                            Only supported for PMP 450 platform.
                            PMP 430 SMs will not be included in this statistic."
		::={whispApsFrUtlStatsIntervalMedium 20}

	frUtlMediumIntervalBwReqMissed	OBJECT-TYPE
		SYNTAX		INTEGER
		MAX-ACCESS	read-only
		STATUS		current
		DESCRIPTION		
			"Number of bandwidth request missed in the last 5 minutes.
                            Only supported for PMP 450 platform.
                            PMP 430 SMs will not be included in this statistic."
		::={whispApsFrUtlStatsIntervalMedium 21}

	frUtlMediumContentionSlots	OBJECT-TYPE
		SYNTAX		INTEGER
		MAX-ACCESS	read-only
		STATUS		current
		DESCRIPTION		
			"Number of scheduled contention slots available in the last 5 minutes. 
                            Only supported for PMP 450 AP platform."
		::={whispApsFrUtlStatsIntervalMedium 22}

	frUtlMediumAvgDownlinkSlots	OBJECT-TYPE
		SYNTAX		INTEGER
		MAX-ACCESS	read-only
		STATUS		current
		DESCRIPTION		
			"Average downlink data slots per frame in the last 5 minutes. Only supported for PMP and PTP 450 AP and Backhauls."
		::={whispApsFrUtlStatsIntervalMedium 23}

	frUtlMediumAvgUplinkSlots	OBJECT-TYPE
		SYNTAX		INTEGER
		MAX-ACCESS	read-only
		STATUS		current
		DESCRIPTION		
			"Average uplink data slots per frame in the last 5 minutes. Only supported for PMP 450 AP platform."
		::={whispApsFrUtlStatsIntervalMedium 24}

	frUtlMediumAvgContentionSlots	OBJECT-TYPE
		SYNTAX		INTEGER
		MAX-ACCESS	read-only
		STATUS		current
		DESCRIPTION		
			"Average contention slots per frame in the last 5 minutes. 
                            Only supported for PMP 450 AP platform."
		::={whispApsFrUtlStatsIntervalMedium 25}

	frUtlMediumMaxContentionSlots	OBJECT-TYPE
		SYNTAX		INTEGER
		MAX-ACCESS	read-only
		STATUS		current
		DESCRIPTION		
			"Maximum possible contention slots for 5 minutes. 
                        This is calculated as (((Uplink slots in a frame) + (Contention slots in a frame)) * (Number of frames in a second) * 5 * 60(seconds)). 
                        Uplink slots and contention slots in a frame depend on the frame configuration. 
                        Number of frames in a second depends on the configured frame period of 5 ms (200 frames) or 2.5 ms (400 frames). 
                        Only supported for PMP 450 AP platform."
		::={whispApsFrUtlStatsIntervalMedium 26}

	frUtlMedDownlinkAckUtilization	OBJECT-TYPE
		SYNTAX		INTEGER
		MAX-ACCESS	read-only
		STATUS		current
		DESCRIPTION		
			"Percentage of downlink Canopy MAC Acknowledgment utilization in the last 5 minutes.
                            Presented in Statistics -> Frame Utilization -> Sector Utilization -> ACK."
		::={whispApsFrUtlStatsIntervalMedium 27}

	frUtlMedDownlinkBcastMcastUtilization	OBJECT-TYPE
		SYNTAX		INTEGER
		MAX-ACCESS	read-only
		STATUS		current
		DESCRIPTION		
			"Percentage of downlink Broadcast/Multicast utilization in the last 5 minutes.
                            Presented in Statistics -> Frame Utilization -> Sector Utilization -> Broadcast and Multicast."
		::={whispApsFrUtlStatsIntervalMedium 28}

	frUtlMedMumimoDownlinkSectorUtilization	OBJECT-TYPE
		SYNTAX		INTEGER
		MAX-ACCESS	read-only
		STATUS		current
		DESCRIPTION		
			"Percentage of MU-MIMO downlink Sector utilization in the last 5 minutes.
                            Presented in Statistics -> Frame Utilization -> Sector Utilization -> Total Utilization.
                            MU-MIMO only."
		::={whispApsFrUtlStatsIntervalMedium 29}

	frUtlMedMumimoDownlinkMumimoUtilization	OBJECT-TYPE
		SYNTAX		INTEGER
		MAX-ACCESS	read-only
		STATUS		current
		DESCRIPTION		
			"Percentage of MU-MIMO downlink utilization in the last 5 minutes.
                            Presented in Statistics -> Frame Utilization -> Sector Utilization -> MU-MIMO.
                            MU-MIMO only."
		::={whispApsFrUtlStatsIntervalMedium 30}

	frUtlMedMumimoDownlinkSumimoUtilization	OBJECT-TYPE
		SYNTAX		INTEGER
		MAX-ACCESS	read-only
		STATUS		current
		DESCRIPTION		
			"Percentage of SU-MIMO downlink utilization in the last 5 minutes.
                            Presented in Statistics -> Frame Utilization -> Sector Utilization -> SU-MIMO.
                            MU-MIMO only."
		::={whispApsFrUtlStatsIntervalMedium 31}

	frUtlMedMumimoDownlinkMultiplexingGain	OBJECT-TYPE
		SYNTAX		INTEGER (0..700)
		MAX-ACCESS	read-only
		STATUS		current
		DESCRIPTION		
			"MU-MIMO Multiplexing Gain in the last 5 minutes. This compares the SU and MU usage for data and ACK allocations.
                            This value is scaled up by 100 (ie. 269 = 2.69).
                            MU-MIMO only."
		::={whispApsFrUtlStatsIntervalMedium 32}

	frUtlMedMumimoDownlinkAvgGroupSize	OBJECT-TYPE
		SYNTAX		INTEGER (0..700)
		MAX-ACCESS	read-only
		STATUS		current
		DESCRIPTION		
			"Average MU-MIMO Group Size for data allocations in the last 5 minutes.
                            This value is scaled up by 100 (ie. 269 = 2.69).
                            MU-MIMO only."
		::={whispApsFrUtlStatsIntervalMedium 33}

	frUtlMedDownlinkMediumPrioSlots	OBJECT-TYPE
		SYNTAX		INTEGER
		MAX-ACCESS	read-only
		STATUS		current
		DESCRIPTION		
			"Number of data slots used for downlink medium priority traffic in the last 5 minutes. Only supported for PMP and PTP 450 AP and Backhauls."
		::={whispApsFrUtlStatsIntervalMedium 34}

	frUtlMedDownlinkUltraHighPrioSlots	OBJECT-TYPE
		SYNTAX		INTEGER
		MAX-ACCESS	read-only
		STATUS		current
		DESCRIPTION		
			"Number of data slots used for downlink ultra high priority traffic in the last 5 minutes. Only supported for PMP and PTP 450 AP and Backhauls."
		::={whispApsFrUtlStatsIntervalMedium 35}

	frUtlMedDownlinkAAAMsgSlots	OBJECT-TYPE
		SYNTAX		INTEGER
		MAX-ACCESS	read-only
		STATUS		current
		DESCRIPTION		
			"Number of data slots used for downlink Authentication and Configuration messages in the last 5 minutes. Only supported for PMP and PTP 450 AP and Backhauls."
		::={whispApsFrUtlStatsIntervalMedium 36}

	frUtlMedUplinkMediumPrioSlots	OBJECT-TYPE
		SYNTAX		INTEGER
		MAX-ACCESS	read-only
		STATUS		current
		DESCRIPTION		
			"Number of data slots used for uplink medium priority traffic in the last 5 minutes. Only supported for PMP 450 AP platform."
		::={whispApsFrUtlStatsIntervalMedium 37}

	frUtlMedUplinkUltraHighPrioSlots	OBJECT-TYPE
		SYNTAX		INTEGER
		MAX-ACCESS	read-only
		STATUS		current
		DESCRIPTION		
			"Number of data slots used for uplink ultra high priority traffic in the last 5 minutes. Only supported for PMP 450 AP platform."
		::={whispApsFrUtlStatsIntervalMedium 38}

	frUtlMedUplinkAAAMsgSlots	OBJECT-TYPE
		SYNTAX		INTEGER
		MAX-ACCESS	read-only
		STATUS		current
		DESCRIPTION		
			"Number of data slots used for uplink Authentication and Configuration messages in the last 5 minutes. Only supported for PMP 450 AP platform."
		::={whispApsFrUtlStatsIntervalMedium 39}

	frUtlMedMumimoUplinkSectorUtilization	OBJECT-TYPE
		SYNTAX		INTEGER
		MAX-ACCESS	read-only
		STATUS		current
		DESCRIPTION		
			"Percentage of MU-MIMO uplink Sector utilization in the last 5 minutes.
                            Presented in Statistics -> Frame Utilization -> Sector Utilization -> Total Utilization.
                            MU-MIMO only."
		::={whispApsFrUtlStatsIntervalMedium 40}

	frUtlMedMumimoUplinkMumimoUtilization	OBJECT-TYPE
		SYNTAX		INTEGER
		MAX-ACCESS	read-only
		STATUS		current
		DESCRIPTION		
			"Percentage of MU-MIMO Uplink utilization in the last 5 minutes.
                            Presented in Statistics -> Frame Utilization -> Sector Utilization -> MU-MIMO.
                            MU-MIMO only."
		::={whispApsFrUtlStatsIntervalMedium 41}

	frUtlMedMumimoUplinkSumimoUtilization	OBJECT-TYPE
		SYNTAX		INTEGER
		MAX-ACCESS	read-only
		STATUS		current
		DESCRIPTION		
			"Percentage of SU-MIMO uplink utilization in the last 5 minutes.
                            Presented in Statistics -> Frame Utilization -> Sector Utilization -> SU-MIMO.
                            MU-MIMO only."
		::={whispApsFrUtlStatsIntervalMedium 42}

	frUtlMedMumimoUplinkMultiplexingGain	OBJECT-TYPE
		SYNTAX		INTEGER (0..700)
		MAX-ACCESS	read-only
		STATUS		current
		DESCRIPTION		
			"MU-MIMO Multiplexing Gain in the last 5 minutes. This compares the SU and MU usage for data and ACK allocations.
                            This value is scaled up by 100 (ie. 269 = 2.69).
                            MU-MIMO only."
		::={whispApsFrUtlStatsIntervalMedium 43}

	frUtlMedDownlinkAvgGroupSizeCombined	OBJECT-TYPE
		SYNTAX		INTEGER (0..700)
		MAX-ACCESS	read-only
		STATUS		current
		DESCRIPTION		
			"Average MU-MIMO Group Size for data and ACK allocations in the last 5 minutes.
                            This value is scaled up by 100 (ie. 269 = 2.69).
                            MU-MIMO only."
		::={whispApsFrUtlStatsIntervalMedium 44}

	frUtlMedUplinkAvgGroupSizeCombined	OBJECT-TYPE
		SYNTAX		INTEGER (0..700)
		MAX-ACCESS	read-only
		STATUS		current
		DESCRIPTION		
			"Average MU-MIMO Group Size for data and ACK allocations in the last 5 minutes.
                            This value is scaled up by 100 (ie. 269 = 2.69).
                            MU-MIMO only."
		::={whispApsFrUtlStatsIntervalMedium 45}

	frUtlMedMumimoUplinkAvgGroupSize	OBJECT-TYPE
		SYNTAX		INTEGER (0..700)
		MAX-ACCESS	read-only
		STATUS		current
		DESCRIPTION		
			"Average MU-MIMO Group Size for data allocations in the last 5 minutes.
                            This value is scaled up by 100 (ie. 269 = 2.69).
                            MU-MIMO only."
		::={whispApsFrUtlStatsIntervalMedium 46}

	frUtlMedUplinkAckUtilization	OBJECT-TYPE
		SYNTAX		INTEGER
		MAX-ACCESS	read-only
		STATUS		current
		DESCRIPTION		
			"Percentage of uplink Canopy MAC Acknowledgment utilization in the last 5 minutes.
                            Presented in Statistics -> Frame Utilization -> Sector Utilization -> ACK."
		::={whispApsFrUtlStatsIntervalMedium 47}

	frUtlMedDownlinkMumimoAckUtilization	OBJECT-TYPE
		SYNTAX		INTEGER
		MAX-ACCESS	read-only
		STATUS		current
		DESCRIPTION		
			"Percentage of downlink Canopy MAC Mumimo Acknowledgment utilization in the last 5 minutes.
                            Presented in Statistics -> Frame Utilization -> Sector Utilization -> MU-MIMO ACK."
		::={whispApsFrUtlStatsIntervalMedium 48}

	frUtlMedUplinkMumimoAckUtilization	OBJECT-TYPE
		SYNTAX		INTEGER
		MAX-ACCESS	read-only
		STATUS		current
		DESCRIPTION		
			"Percentage of uplink Canopy MAC Mumimo Acknowledgment utilization in the last 5 minutes.
                            Presented in Statistics -> Frame Utilization -> Sector Utilization -> MU-MIMO ACK."
		::={whispApsFrUtlStatsIntervalMedium 49}

	frUtlMedUplinkAvgSchedCycles	OBJECT-TYPE
		SYNTAX		INTEGER
		MAX-ACCESS	read-only
		STATUS		current
		DESCRIPTION		
			"Engineering use only.
                            Average number of uplink scheduling window cycles in the last 5 minutes.
                            An average scheduling window size of
                            a. 1  TDD cycle is  expected if there is no traffic.
                            b. 10 TDD cycles is expected on a heavily loaded system."
		::={whispApsFrUtlStatsIntervalMedium 50}

	frUtlMedDownlinkAvgSchedCycles	OBJECT-TYPE
		SYNTAX		INTEGER
		MAX-ACCESS	read-only
		STATUS		current
		DESCRIPTION		
			"Engineering use only.
                            Average nunmber of downlink scheduling window cycles in the last 5 minutes
                            An average scheduling window size of
                            a. 1  TDD cycle is  expected if there is no traffic.
                            b. 10 TDD cycles is expected on a heavily loaded system."
		::={whispApsFrUtlStatsIntervalMedium 51}

	frUtlMediumAvgReservedContentionSlots	OBJECT-TYPE
		SYNTAX		INTEGER
		MAX-ACCESS	read-only
		STATUS		current
		DESCRIPTION		
			"Average Reserved contention slots per frame in the last 5 minutes. 
                            Only supported for PMP 450 AP platform."
		::={whispApsFrUtlStatsIntervalMedium 52}

	frUtlMediumAvgEffectiveContentionSlots	OBJECT-TYPE
		SYNTAX		INTEGER
		MAX-ACCESS	read-only
		STATUS		current
		DESCRIPTION		
			"Average Effective contention slots in the last 5 minutes. 
                            Only supported for PMP 450 AP platform.
                            Engineering use only."
		::={whispApsFrUtlStatsIntervalMedium 53}

	frUtlMedDownlink1xModSlots	OBJECT-TYPE
		SYNTAX		INTEGER
		MAX-ACCESS	read-only
		STATUS		current
		DESCRIPTION		
			"Number of data slots used for downlink 1x modulation traffic in the last 5 minutes. Only applies to PMP AP and Backhauls.
                                     Not currently supported on 450m"
		::={whispApsFrUtlStatsIntervalMedium 54}

	frUtlMedDownlink2xModSlots	OBJECT-TYPE
		SYNTAX		INTEGER
		MAX-ACCESS	read-only
		STATUS		current
		DESCRIPTION		
			"Number of data slots used for downlink 2x modulation traffic in the last 5 minutes. Only applies to PMP AP and Backhauls.
                                     Not currently supported on 450m"
		::={whispApsFrUtlStatsIntervalMedium 55}

	frUtlMedDownlink3xModSlots	OBJECT-TYPE
		SYNTAX		INTEGER
		MAX-ACCESS	read-only
		STATUS		current
		DESCRIPTION		
			"Number of data slots used for downlink 3x modulation traffic in the last 5 minutes. Only applies to PMP AP and Backhauls.
                                     Not currently supported on 450m"
		::={whispApsFrUtlStatsIntervalMedium 56}

	frUtlMedDownlink4xModSlots	OBJECT-TYPE
		SYNTAX		INTEGER
		MAX-ACCESS	read-only
		STATUS		current
		DESCRIPTION		
			"Number of data slots used for downlink 4x modulation traffic in the last 5 minutes. Only applies to PMP AP and Backhauls.
                                     Not currently supported on 450m"
		::={whispApsFrUtlStatsIntervalMedium 57}

	frUtlMedDownlink5xModSlots	OBJECT-TYPE
		SYNTAX		INTEGER
		MAX-ACCESS	read-only
		STATUS		current
		DESCRIPTION		
			"Number of data slots used for downlink 5x modulation traffic in the last 5 minutes. Only applies to PMP AP and Backhauls.
                                     Not currently supported on 450m"
		::={whispApsFrUtlStatsIntervalMedium 58}

	frUtlMedDownlink6xModSlots	OBJECT-TYPE
		SYNTAX		INTEGER
		MAX-ACCESS	read-only
		STATUS		current
		DESCRIPTION		
			"Number of data slots used for downlink 6x modulation traffic in the last 5 minutes. Only applies to PMP AP and Backhauls.
                                     Not currently supported on 450m"
		::={whispApsFrUtlStatsIntervalMedium 59}

	frUtlMedDownlink7xModSlots	OBJECT-TYPE
		SYNTAX		INTEGER
		MAX-ACCESS	read-only
		STATUS		current
		DESCRIPTION		
			"Number of data slots used for downlink 7x modulation traffic in the last 5 minutes. Only applies to PMP AP and Backhauls.
                                     Not currently supported on 450m"
		::={whispApsFrUtlStatsIntervalMedium 60}

	frUtlMedDownlink8xModSlots	OBJECT-TYPE
		SYNTAX		INTEGER
		MAX-ACCESS	read-only
		STATUS		current
		DESCRIPTION		
			"Number of data slots used for downlink 8x modulation traffic in the last 5 minutes. Only applies to PMP AP and Backhauls.
                                     Not currently supported on 450m"
		::={whispApsFrUtlStatsIntervalMedium 61}

	frUtlMedUplink1xModSlots	OBJECT-TYPE
		SYNTAX		INTEGER
		MAX-ACCESS	read-only
		STATUS		current
		DESCRIPTION		
			"Number of data slots used for uplink 1x modulation traffic in the last 5 minutes. Only supported for PMP 450 AP platform."
		::={whispApsFrUtlStatsIntervalMedium 62}

	frUtlMedUplink2xModSlots	OBJECT-TYPE
		SYNTAX		INTEGER
		MAX-ACCESS	read-only
		STATUS		current
		DESCRIPTION		
			"Number of data slots used for uplink 2x modulation traffic in the last 5 minutes. Only supported for PMP 450 AP platform."
		::={whispApsFrUtlStatsIntervalMedium 63}

	frUtlMedUplink3xModSlots	OBJECT-TYPE
		SYNTAX		INTEGER
		MAX-ACCESS	read-only
		STATUS		current
		DESCRIPTION		
			"Number of data slots used for uplink 3x modulation traffic in the last 5 minutes. Only supported for PMP 450 AP platform."
		::={whispApsFrUtlStatsIntervalMedium 64}

	frUtlMedUplink4xModSlots	OBJECT-TYPE
		SYNTAX		INTEGER
		MAX-ACCESS	read-only
		STATUS		current
		DESCRIPTION		
			"Number of data slots used for uplink 4x modulation traffic in the last 5 minutes. Only supported for PMP 450 AP platform."
		::={whispApsFrUtlStatsIntervalMedium 65}

	frUtlMedUplink5xModSlots	OBJECT-TYPE
		SYNTAX		INTEGER
		MAX-ACCESS	read-only
		STATUS		current
		DESCRIPTION		
			"Number of data slots used for uplink 5x modulation traffic in the last 5 minutes. Only supported for PMP 450 AP platform."
		::={whispApsFrUtlStatsIntervalMedium 66}

	frUtlMedUplink6xModSlots	OBJECT-TYPE
		SYNTAX		INTEGER
		MAX-ACCESS	read-only
		STATUS		current
		DESCRIPTION		
			"Number of data slots used for uplink 6x modulation traffic in the last 5 minutes. Only supported for PMP 450 AP platform."
		::={whispApsFrUtlStatsIntervalMedium 67}

	frUtlMedUplink7xModSlots	OBJECT-TYPE
		SYNTAX		INTEGER
		MAX-ACCESS	read-only
		STATUS		current
		DESCRIPTION		
			"Number of data slots used for uplink 7x modulation traffic in the last 5 minutes. Only supported for PMP 450 AP platform."
		::={whispApsFrUtlStatsIntervalMedium 68}

	frUtlMedUplink8xModSlots	OBJECT-TYPE
		SYNTAX		INTEGER
		MAX-ACCESS	read-only
		STATUS		current
		DESCRIPTION		
			"Number of data slots used for uplink 8x modulation traffic in the last 5 minutes. Only supported for PMP 450 AP platform."
		::={whispApsFrUtlStatsIntervalMedium 69}

	frUtlMediumDLSpecEffExtrap	OBJECT-TYPE
		SYNTAX		INTEGER
		MAX-ACCESS	read-only
		STATUS		current
		DESCRIPTION		
			"Extrapolated downlink Spectral Efficiency in the last 5 minute (Multiplied by 1000). Measured in units of user data bits per second per hertz.
                                     Divide by 1000 for actual number.
                                     Not currently supported on 450m"
		::={whispApsFrUtlStatsIntervalMedium 70}

	frUtlMediumDLSpecEffMax	OBJECT-TYPE
		SYNTAX		INTEGER
		MAX-ACCESS	read-only
		STATUS		current
		DESCRIPTION		
			"Maximum possible downlink Spectral Efficiency in the last 5 minute (Multiplied by 1000). Measured in units of user data bits per second per hertz.
                                     Divide by 1000 for actual number.
                                     Not currently supported on 450m"
		::={whispApsFrUtlStatsIntervalMedium 71}

	frUtlMediumULSpecEffExtrap	OBJECT-TYPE
		SYNTAX		INTEGER
		MAX-ACCESS	read-only
		STATUS		current
		DESCRIPTION		
			"Extrapolated uplink Spectral Efficiency in the last 5 minute (Multiplied by 1000). Measured in units of user data bits per second per hertz.
                                     Divide by 1000 for actual number.
                                     Not currently supported on 450m"
		::={whispApsFrUtlStatsIntervalMedium 72}

	frUtlMediumULSpecEffMax	OBJECT-TYPE
		SYNTAX		INTEGER
		MAX-ACCESS	read-only
		STATUS		current
		DESCRIPTION		
			"Maximum possible uplink Spectral Efficiency in the last 5 minute (Multiplied by 1000). Measured in units of user data bits per second per hertz.
                                     Divide by 1000 for actual number.
                                     Not currently supported on 450m"
		::={whispApsFrUtlStatsIntervalMedium 73}

	frUtlMediumDLAvgFragsPerSlot	OBJECT-TYPE
		SYNTAX		INTEGER
		MAX-ACCESS	read-only
		STATUS		current
		DESCRIPTION		
			"Average number of fragments per slot in the last 5 minute (Multiplied by 100).
                                     Divide by 100 for actual number.
                                     Not currently supported on 450m"
		::={whispApsFrUtlStatsIntervalMedium 74}

	frUtlMediumULAvgFragsPerSlot	OBJECT-TYPE
		SYNTAX		INTEGER
		MAX-ACCESS	read-only
		STATUS		current
		DESCRIPTION		
			"Average number of fragments per slot in the last 5 minute (Multiplied by 100).
                                     Divide by 100 for actual number.
                                     Not currently supported on 450m"
		::={whispApsFrUtlStatsIntervalMedium 75}

	frUtlMediumULMissedAcksSuMimo	OBJECT-TYPE
		SYNTAX		INTEGER
		MAX-ACCESS	read-only
		STATUS		current
		DESCRIPTION		
			"Number of missed Uplink MAC Acknowledgements in the last 5 minutes.
                            PMP only.
                            For 450m, this is the SU-MIMO ACKs."
		::={whispApsFrUtlStatsIntervalMedium 76}

	frUtlMediumULMissedAcksMuMimo	OBJECT-TYPE
		SYNTAX		INTEGER
		MAX-ACCESS	read-only
		STATUS		current
		DESCRIPTION		
			"Number of missed Uplink MU-MIMO MAC Acknowledgements in the last 5 minutes.
                            PMP only.
                            MU-MIMO platforms only."
		::={whispApsFrUtlStatsIntervalMedium 77}

	frUtlHighTotalDownlinkUtilization	OBJECT-TYPE
		SYNTAX		INTEGER
		MAX-ACCESS	read-only
		STATUS		current
		DESCRIPTION		
			"Percentage of total downlink utilization in the last 15 minutes. Only supported for PMP and PTP 450 AP and Backhauls."
		::={whispApsFrUtlStatsIntervalHigh 1}

	frUtlHighTotalUplinkUtilization	OBJECT-TYPE
		SYNTAX		INTEGER
		MAX-ACCESS	read-only
		STATUS		current
		DESCRIPTION		
			"Percentage of total uplink utilization in the last 15 minutes. Only supported for PMP 450 AP platform."
		::={whispApsFrUtlStatsIntervalHigh 2}

	frUtlHighTotalDownlinkSlots	OBJECT-TYPE
		SYNTAX		INTEGER
		MAX-ACCESS	read-only
		STATUS		current
		DESCRIPTION		
			"Total downlink data slots in the last 15 minutes. Only supported for PMP and PTP 450 AP and Backhauls."
		::={whispApsFrUtlStatsIntervalHigh 3}

	frUtlHighDownlinkLowPrioSlots	OBJECT-TYPE
		SYNTAX		INTEGER
		MAX-ACCESS	read-only
		STATUS		current
		DESCRIPTION		
			"Number of data slots used for downlink low priority traffic in the last 15 minutes. Only supported for PMP and PTP 450 AP and Backhauls."
		::={whispApsFrUtlStatsIntervalHigh 4}

	frUtlHighDownlinkHiPrioSlots	OBJECT-TYPE
		SYNTAX		INTEGER
		MAX-ACCESS	read-only
		STATUS		current
		DESCRIPTION		
			"Number of data slots used for downlink high priority traffic in the last 15 minutes. Only supported for PMP and PTP 450 AP and Backhauls."
		::={whispApsFrUtlStatsIntervalHigh 5}

	frUtlHighDownlinkBcastSlots	OBJECT-TYPE
		SYNTAX		INTEGER
		MAX-ACCESS	read-only
		STATUS		current
		DESCRIPTION		
			"Number of data slots used for downlink broadcast and multicast traffic in the last 15 minutes. Only supported for PMP and PTP 450 AP and Backhauls."
		::={whispApsFrUtlStatsIntervalHigh 6}

	frUtlHighDownlinkAckSlots	OBJECT-TYPE
		SYNTAX		INTEGER
		MAX-ACCESS	read-only
		STATUS		current
		DESCRIPTION		
			"Number of data slots used for Downlink Canopy MAC Acknowledgements in the last 15 minutes. Only supported for PMP and PTP 450 AP and Backhauls."
		::={whispApsFrUtlStatsIntervalHigh 7}

	frUtlHighDownlinkCntlMsgSlots	OBJECT-TYPE
		SYNTAX		INTEGER
		MAX-ACCESS	read-only
		STATUS		current
		DESCRIPTION		
			"Number of data slots used for downlink registration and control messages in the last 15 minutes. Only supported for PMP and PTP 450 AP and Backhauls."
		::={whispApsFrUtlStatsIntervalHigh 8}

	frUtlHighTotalUplinkSlots	OBJECT-TYPE
		SYNTAX		INTEGER
		MAX-ACCESS	read-only
		STATUS		current
		DESCRIPTION		
			"Total uplink data slots in the last 15 minutes. Only supported for PMP 450 AP platform."
		::={whispApsFrUtlStatsIntervalHigh 9}

	frUtlHighUplinkLowPrioSlots	OBJECT-TYPE
		SYNTAX		INTEGER
		MAX-ACCESS	read-only
		STATUS		current
		DESCRIPTION		
			"Number of data slots used for uplink low priority traffic in the last 15 minutes. Only supported for PMP 450 AP platform."
		::={whispApsFrUtlStatsIntervalHigh 10}

	frUtlHighUplinkHiPrioSlots	OBJECT-TYPE
		SYNTAX		INTEGER
		MAX-ACCESS	read-only
		STATUS		current
		DESCRIPTION		
			"Number of data slots used for uplink high priority traffic in the last 15 minutes. Only supported for PMP 450 AP platform."
		::={whispApsFrUtlStatsIntervalHigh 11}

	frUtlHighUplinkAckSlots	OBJECT-TYPE
		SYNTAX		INTEGER
		MAX-ACCESS	read-only
		STATUS		current
		DESCRIPTION		
			"Number of data slots used for Uplink Canopy MAC Acknowledgements in the last 15 minutes. Only supported for PMP 450 AP platform."
		::={whispApsFrUtlStatsIntervalHigh 12}

	frUtlHighMaxDownlinkSlots	OBJECT-TYPE
		SYNTAX		INTEGER
		MAX-ACCESS	read-only
		STATUS		current
		DESCRIPTION		
			"Maximum possible downlink data slots for 15 minutes. 
                        This is calculated as ((Downlink slots in a frame) * (Number of frames in a second) * 15 * 60(seconds)). 
                        Downlink slots in a frame depends on the frame configuration. 
                        Number of frames in a second depends on the configured frame period of 5 ms (200 frames) or 2.5 ms (400 frames). 
                        Only supported for PMP and PTP 450 AP and Backhauls."
		::={whispApsFrUtlStatsIntervalHigh 13}

	frUtlHighMaxUplinkSlots	OBJECT-TYPE
		SYNTAX		INTEGER
		MAX-ACCESS	read-only
		STATUS		current
		DESCRIPTION		
			"Maximum possible uplink data slots for 15 minutes. 
                        This is calculated as ((Uplink slots in a frame) * (Number of frames in a second) * 15 * 60(seconds)). 
                        Uplink slots in a frame depends on the frame configuration. 
                        Number of frames in a second depends on the configured frame period of 5 ms (200 frames) or 2.5 ms (400 frames). 
                        Only supported for PMP 450 AP platform."
		::={whispApsFrUtlStatsIntervalHigh 14}

	frUtlHighEthInDiscards	OBJECT-TYPE
		SYNTAX		INTEGER
		MAX-ACCESS	read-only
		STATUS		current
		DESCRIPTION		
			"Number of incoming Ethernet packets discarded in the last 15 minutes. Only supported for PMP and PTP 450 AP and Backhauls."
		::={whispApsFrUtlStatsIntervalHigh 15}

	frUtlHighEthOutDiscards	OBJECT-TYPE
		SYNTAX		INTEGER
		MAX-ACCESS	read-only
		STATUS		current
		DESCRIPTION		
			"Number of outgoing Ethernet packets discarded in the last 15 minutes. Only supported for PMP and PTP 450 AP and Backhauls."
		::={whispApsFrUtlStatsIntervalHigh 16}

	frUtlHighRFInDiscards	OBJECT-TYPE
		SYNTAX		INTEGER
		MAX-ACCESS	read-only
		STATUS		current
		DESCRIPTION		
			"Number of incoming radio packets discarded in the last 15 minutes. Only supported for PMP and PTP 450 AP and Backhauls."
		::={whispApsFrUtlStatsIntervalHigh 17}

	frUtlHighRFOutDiscards	OBJECT-TYPE
		SYNTAX		INTEGER
		MAX-ACCESS	read-only
		STATUS		current
		DESCRIPTION		
			"Number of outgoing radio packets discarded in the last 15 minutes. Only supported for PMP and PTP 450 AP and Backhauls."
		::={whispApsFrUtlStatsIntervalHigh 18}

	frUtlHighIntervalBwReqPercentage	OBJECT-TYPE
		SYNTAX		INTEGER
		MAX-ACCESS	read-only
		STATUS		current
		DESCRIPTION		
			"Percentage of bandwidth request received in the last 15 minutes.
                            Only supported for PMP 450 platform.
                            PMP 430 SMs will not be included in this statistic."
		::={whispApsFrUtlStatsIntervalHigh 19}

	frUtlHighIntervalBwReqRx	OBJECT-TYPE
		SYNTAX		INTEGER
		MAX-ACCESS	read-only
		STATUS		current
		DESCRIPTION		
			"Number of bandwidth request received in the last 15 minutes.
                            Only supported for PMP 450 platform.
                            PMP 430 SMs will not be included in this statistic."
		::={whispApsFrUtlStatsIntervalHigh 20}

	frUtlHighIntervalBwReqMissed	OBJECT-TYPE
		SYNTAX		INTEGER
		MAX-ACCESS	read-only
		STATUS		current
		DESCRIPTION		
			"Number of bandwidth request missed in the last 15 minutes.
                            Only supported for PMP 450 platform.
                            PMP 430 SMs will not be included in this statistic."
		::={whispApsFrUtlStatsIntervalHigh 21}

	frUtlHighContentionSlots	OBJECT-TYPE
		SYNTAX		INTEGER
		MAX-ACCESS	read-only
		STATUS		current
		DESCRIPTION		
			"Number of scheduled contention slots available in the last 15 minutes. 
                            Only supported for PMP 450 AP platform."
		::={whispApsFrUtlStatsIntervalHigh 22}

	frUtlHighAvgDownlinkSlots	OBJECT-TYPE
		SYNTAX		INTEGER
		MAX-ACCESS	read-only
		STATUS		current
		DESCRIPTION		
			"Average downlink data slots per frame in the last 15 minutes. Only supported for PMP and PTP 450 AP and Backhauls."
		::={whispApsFrUtlStatsIntervalHigh 23}

	frUtlHighAvgUplinkSlots	OBJECT-TYPE
		SYNTAX		INTEGER
		MAX-ACCESS	read-only
		STATUS		current
		DESCRIPTION		
			"Average uplink data slots per frame in the last 15 minutes. Only supported for PMP 450 AP platform."
		::={whispApsFrUtlStatsIntervalHigh 24}

	frUtlHighAvgContentionSlots	OBJECT-TYPE
		SYNTAX		INTEGER
		MAX-ACCESS	read-only
		STATUS		current
		DESCRIPTION		
			"Average contention slots per frame in the last 15 minutes. 
                            Only supported for PMP 450 AP platform."
		::={whispApsFrUtlStatsIntervalHigh 25}

	frUtlHighMaxContentionSlots	OBJECT-TYPE
		SYNTAX		INTEGER
		MAX-ACCESS	read-only
		STATUS		current
		DESCRIPTION		
			"Maximum possible contention slots for 15 minutes. 
                        This is calculated as (((Uplink slots in a frame) + (Contention slots in a frame)) * (Number of frames in a second) * 15 * 60(seconds)). 
                        Uplink slots and contention slots in a frame depend on the frame configuration. 
                        Number of frames in a second depends on the configured frame period of 5 ms (200 frames) or 2.5 ms (400 frames). 
                        Only supported for PMP 450 AP platform."
		::={whispApsFrUtlStatsIntervalHigh 26}

	frUtlHighDownlinkAckUtilization	OBJECT-TYPE
		SYNTAX		INTEGER
		MAX-ACCESS	read-only
		STATUS		current
		DESCRIPTION		
			"Percentage of downlink Canopy MAC Acknowledgment utilization in the last 15 minutes.
                            Presented in Statistics -> Frame Utilization -> Sector Utilization -> ACK.
                            MU-MIMO only."
		::={whispApsFrUtlStatsIntervalHigh 27}

	frUtlHighDownlinkBcastMcastUtilization	OBJECT-TYPE
		SYNTAX		INTEGER
		MAX-ACCESS	read-only
		STATUS		current
		DESCRIPTION		
			"Percentage of downlink Broadcast/Multicast utilization in the last 15 minutes.
                            Presented in Statistics -> Frame Utilization -> Sector Utilization -> Broadcast and Multicast."
		::={whispApsFrUtlStatsIntervalHigh 28}

	frUtlHighMumimoDownlinkSectorUtilization	OBJECT-TYPE
		SYNTAX		INTEGER
		MAX-ACCESS	read-only
		STATUS		current
		DESCRIPTION		
			"Percentage of MU-MIMO downlink Sector utilization in the last 15 minutes.
                            Presented in Statistics -> Frame Utilization -> Sector Utilization -> Total Utilization.
                            MU-MIMO only."
		::={whispApsFrUtlStatsIntervalHigh 29}

	frUtlHighMumimoDownlinkMumimoUtilization	OBJECT-TYPE
		SYNTAX		INTEGER
		MAX-ACCESS	read-only
		STATUS		current
		DESCRIPTION		
			"Percentage of MU-MIMO downlink utilization in the last 15 minutes.
                            Presented in Statistics -> Frame Utilization -> Sector Utilization -> MU-MIMO.
                            MU-MIMO only."
		::={whispApsFrUtlStatsIntervalHigh 30}

	frUtlHighMumimoDownlinkSumimoUtilization	OBJECT-TYPE
		SYNTAX		INTEGER
		MAX-ACCESS	read-only
		STATUS		current
		DESCRIPTION		
			"Percentage of SU-MIMO downlink utilization in the last 15 minutes.
                            Presented in Statistics -> Frame Utilization -> Sector Utilization -> SU-MIMO.
                            MU-MIMO only."
		::={whispApsFrUtlStatsIntervalHigh 31}

	frUtlHighMumimoDownlinkMultiplexingGain	OBJECT-TYPE
		SYNTAX		INTEGER (0..700)
		MAX-ACCESS	read-only
		STATUS		current
		DESCRIPTION		
			"MU-MIMO Multiplexing Gain in the last 15 minutes. This compares the SU and MU usage for data and ACK allocations.
                            This value is scaled up by 100 (ie. 269 = 2.69).
                            MU-MIMO only."
		::={whispApsFrUtlStatsIntervalHigh 32}

	frUtlHighMumimoDownlinkAvgGroupSize	OBJECT-TYPE
		SYNTAX		INTEGER (0..700)
		MAX-ACCESS	read-only
		STATUS		current
		DESCRIPTION		
			"Average MU-MIMO Group Size for data allocations in the last 15 minutes.
                            This value is scaled up by 100 (ie. 269 = 2.69).
                            MU-MIMO only."
		::={whispApsFrUtlStatsIntervalHigh 33}

	frUtlHighDownlinkMediumPrioSlots	OBJECT-TYPE
		SYNTAX		INTEGER
		MAX-ACCESS	read-only
		STATUS		current
		DESCRIPTION		
			"Number of data slots used for downlink medium priority traffic in the last 15 minutes. Only supported for PMP and PTP 450 AP and Backhauls."
		::={whispApsFrUtlStatsIntervalHigh 34}

	frUtlHighDownlinkUltraHighPrioSlots	OBJECT-TYPE
		SYNTAX		INTEGER
		MAX-ACCESS	read-only
		STATUS		current
		DESCRIPTION		
			"Number of data slots used for downlink ultra high priority traffic in the last 15 minutes. Only supported for PMP and PTP 450 AP and Backhauls."
		::={whispApsFrUtlStatsIntervalHigh 35}

	frUtlHighDownlinkAAAMsgSlots	OBJECT-TYPE
		SYNTAX		INTEGER
		MAX-ACCESS	read-only
		STATUS		current
		DESCRIPTION		
			"Number of data slots used for downlink Authentication and Configuration messages in the last 15 minutes. Only supported for PMP and PTP 450 AP and Backhauls."
		::={whispApsFrUtlStatsIntervalHigh 36}

	frUtlHighUplinkMediumPrioSlots	OBJECT-TYPE
		SYNTAX		INTEGER
		MAX-ACCESS	read-only
		STATUS		current
		DESCRIPTION		
			"Number of data slots used for uplink medium priority traffic in the last 15 minutes. Only supported for PMP 450 AP platform."
		::={whispApsFrUtlStatsIntervalHigh 37}

	frUtlHighUplinkUltraHighPrioSlots	OBJECT-TYPE
		SYNTAX		INTEGER
		MAX-ACCESS	read-only
		STATUS		current
		DESCRIPTION		
			"Number of data slots used for uplink ultra high priority traffic in the last 15 minutes. Only supported for PMP 450 AP platform."
		::={whispApsFrUtlStatsIntervalHigh 38}

	frUtlHighUplinkAAAMsgSlots	OBJECT-TYPE
		SYNTAX		INTEGER
		MAX-ACCESS	read-only
		STATUS		current
		DESCRIPTION		
			"Number of data slots used for uplink Authentication and Configuration messages in the last 15 minutes. Only supported for PMP 450 AP platform."
		::={whispApsFrUtlStatsIntervalHigh 39}

	frUtlHighMumimoUplinkSectorUtilization	OBJECT-TYPE
		SYNTAX		INTEGER
		MAX-ACCESS	read-only
		STATUS		current
		DESCRIPTION		
			"Percentage of MU-MIMO Uplink Sector utilization in the last 15 minutes.
                            Presented in Statistics -> Frame Utilization -> Sector Utilization -> Total Utilization.
                            MU-MIMO only."
		::={whispApsFrUtlStatsIntervalHigh 40}

	frUtlHighMumimoUplinkMumimoUtilization	OBJECT-TYPE
		SYNTAX		INTEGER
		MAX-ACCESS	read-only
		STATUS		current
		DESCRIPTION		
			"Percentage of MU-MIMO uplink utilization in the last 15 minutes.
                            Presented in Statistics -> Frame Utilization -> Sector Utilization -> MU-MIMO.
                            MU-MIMO only."
		::={whispApsFrUtlStatsIntervalHigh 41}

	frUtlHighMumimoUplinkSumimoUtilization	OBJECT-TYPE
		SYNTAX		INTEGER
		MAX-ACCESS	read-only
		STATUS		current
		DESCRIPTION		
			"Percentage of SU-MIMO uplink utilization in the last 15 minutes.
                            Presented in Statistics -> Frame Utilization -> Sector Utilization -> SU-MIMO.
                            MU-MIMO only."
		::={whispApsFrUtlStatsIntervalHigh 42}

	frUtlHighMumimoUplinkMultiplexingGain	OBJECT-TYPE
		SYNTAX		INTEGER (0..700)
		MAX-ACCESS	read-only
		STATUS		current
		DESCRIPTION		
			"MU-MIMO  Multiplexing Gain in the last 15 minutes. This compares the SU and MU usage for data and ACK allocations.
                            This value is scaled up by 100 (ie. 269 = 2.69).
                            MU-MIMO only."
		::={whispApsFrUtlStatsIntervalHigh 43}

	frUtlHighDownlinkAvgGroupSizeCombined	OBJECT-TYPE
		SYNTAX		INTEGER (0..700)
		MAX-ACCESS	read-only
		STATUS		current
		DESCRIPTION		
			"Average MU-MIMO Group Size for data and ACK allocations in the last 15 minutes.
                            This value is scaled up by 100 (ie. 269 = 2.69).
                            MU-MIMO only."
		::={whispApsFrUtlStatsIntervalHigh 44}

	frUtlHighUplinkAvgGroupSizeCombined	OBJECT-TYPE
		SYNTAX		INTEGER (0..700)
		MAX-ACCESS	read-only
		STATUS		current
		DESCRIPTION		
			"Average MU-MIMO Group Size for data and ACK allocations in the last 15 minutes.
                            This value is scaled up by 100 (ie. 269 = 2.69).
                            MU-MIMO only."
		::={whispApsFrUtlStatsIntervalHigh 45}

	frUtlHighMumimoiUplinkAvgGroupSize	OBJECT-TYPE
		SYNTAX		INTEGER (0..700)
		MAX-ACCESS	read-only
		STATUS		current
		DESCRIPTION		
			"Average MU-MIMO Group Size for data allocations in the last 15 minutes.
                            This value is scaled up by 100 (ie. 269 = 2.69).
                            MU-MIMO only."
		::={whispApsFrUtlStatsIntervalHigh 46}

	frUtlHighUplinkAckUtilization	OBJECT-TYPE
		SYNTAX		INTEGER
		MAX-ACCESS	read-only
		STATUS		current
		DESCRIPTION		
			"Percentage of uplink Canopy MAC Acknowledgment utilization in the last 15 minutes.
                            Presented in Statistics -> Frame Utilization -> Sector Utilization -> ACK.
                            MU-MIMO only."
		::={whispApsFrUtlStatsIntervalHigh 47}

	frUtlHighDownlinkMumimoAckUtilization	OBJECT-TYPE
		SYNTAX		INTEGER
		MAX-ACCESS	read-only
		STATUS		current
		DESCRIPTION		
			"Percentage of downlink Canopy MAC Mumimo Acknowledgment utilization in the last 15 minutes.
                            Presented in Statistics -> Frame Utilization -> Sector Utilization -> MU-MIMO ACK."
		::={whispApsFrUtlStatsIntervalHigh 48}

	frUtlHighUplinkMumimoAckUtilization	OBJECT-TYPE
		SYNTAX		INTEGER
		MAX-ACCESS	read-only
		STATUS		current
		DESCRIPTION		
			"Percentage of uplink Canopy MAC Mumimo Acknowledgment utilization in the last 15 minutes.
                            Presented in Statistics -> Frame Utilization -> Sector Utilization -> MU-MIMO ACK."
		::={whispApsFrUtlStatsIntervalHigh 49}

	frUtlHighUplinkAvgSchedCycles	OBJECT-TYPE
		SYNTAX		INTEGER
		MAX-ACCESS	read-only
		STATUS		current
		DESCRIPTION		
			"Engineering use only.
                            Average number of uplink scheduling window cycles in the last 15 minutes.
                            An average scheduling window size of
                            a. 1  TDD cycle is  expected if there is no traffic.
                            b. 10 TDD cycles is expected on a heavily loaded system."
		::={whispApsFrUtlStatsIntervalHigh 50}

	frUtlHighDownlinkAvgSchedCycles	OBJECT-TYPE
		SYNTAX		INTEGER
		MAX-ACCESS	read-only
		STATUS		current
		DESCRIPTION		
			"Engineering use only.
                            Average number of  downlink scheduling window cycles in the last 15 minutes
                            An average scheduling window size of
                            a. 1  TDD cycle is  expected if there is no traffic.
                            b. 10 TDD cycles is expected on a heavily loaded system."
		::={whispApsFrUtlStatsIntervalHigh 51}

	frUtlHighAvgReservedContentionSlots	OBJECT-TYPE
		SYNTAX		INTEGER
		MAX-ACCESS	read-only
		STATUS		current
		DESCRIPTION		
			"Average Reserved contention slots per frame in the last 15 minutes. 
                            Only supported for PMP 450 AP platform."
		::={whispApsFrUtlStatsIntervalHigh 52}

	frUtlHighAvgEffectiveContentionSlots	OBJECT-TYPE
		SYNTAX		INTEGER
		MAX-ACCESS	read-only
		STATUS		current
		DESCRIPTION		
			"Average Effective contention slots in the last 15 minutes. 
                            Only supported for PMP 450 AP platform.
                            Engineering use only."
		::={whispApsFrUtlStatsIntervalHigh 53}

	frUtlHighDownlink1xModSlots	OBJECT-TYPE
		SYNTAX		INTEGER
		MAX-ACCESS	read-only
		STATUS		current
		DESCRIPTION		
			"Number of data slots used for downlink 1x modulation traffic in the last 15 minutes. Only applies to PMP AP and Backhauls.
                                     Not currently supported on 450m"
		::={whispApsFrUtlStatsIntervalHigh 54}

	frUtlHighDownlink2xModSlots	OBJECT-TYPE
		SYNTAX		INTEGER
		MAX-ACCESS	read-only
		STATUS		current
		DESCRIPTION		
			"Number of data slots used for downlink 2x modulation traffic in the last 15 minutes. Only applies to PMP AP and Backhauls.
                                     Not currently supported on 450m"
		::={whispApsFrUtlStatsIntervalHigh 55}

	frUtlHighDownlink3xModSlots	OBJECT-TYPE
		SYNTAX		INTEGER
		MAX-ACCESS	read-only
		STATUS		current
		DESCRIPTION		
			"Number of data slots used for downlink 3x modulation traffic in the last 15 minutes. Only applies to PMP AP and Backhauls.
                                     Not currently supported on 450m"
		::={whispApsFrUtlStatsIntervalHigh 56}

	frUtlHighDownlink4xModSlots	OBJECT-TYPE
		SYNTAX		INTEGER
		MAX-ACCESS	read-only
		STATUS		current
		DESCRIPTION		
			"Number of data slots used for downlink 4x modulation traffic in the last 15 minutes. Only applies to PMP AP and Backhauls.
                                     Not currently supported on 450m"
		::={whispApsFrUtlStatsIntervalHigh 57}

	frUtlHighDownlink5xModSlots	OBJECT-TYPE
		SYNTAX		INTEGER
		MAX-ACCESS	read-only
		STATUS		current
		DESCRIPTION		
			"Number of data slots used for downlink 5x modulation traffic in the last 15 minutes. Only applies to PMP AP and Backhauls.
                                     Not currently supported on 450m"
		::={whispApsFrUtlStatsIntervalHigh 58}

	frUtlHighDownlink6xModSlots	OBJECT-TYPE
		SYNTAX		INTEGER
		MAX-ACCESS	read-only
		STATUS		current
		DESCRIPTION		
			"Number of data slots used for downlink 6x modulation traffic in the last 15 minutes. Only applies to PMP AP and Backhauls.
                                     Not currently supported on 450m"
		::={whispApsFrUtlStatsIntervalHigh 59}

	frUtlHighDownlink7xModSlots	OBJECT-TYPE
		SYNTAX		INTEGER
		MAX-ACCESS	read-only
		STATUS		current
		DESCRIPTION		
			"Number of data slots used for downlink 7x modulation traffic in the last 15 minutes. Only applies to PMP AP and Backhauls.
                                     Not currently supported on 450m"
		::={whispApsFrUtlStatsIntervalHigh 60}

	frUtlHighDownlink8xModSlots	OBJECT-TYPE
		SYNTAX		INTEGER
		MAX-ACCESS	read-only
		STATUS		current
		DESCRIPTION		
			"Number of data slots used for downlink 8x modulation traffic in the last 15 minutes. Only applies to PMP AP and Backhauls.
                                     Not currently supported on 450m"
		::={whispApsFrUtlStatsIntervalHigh 61}

	frUtlHighUplink1xModSlots	OBJECT-TYPE
		SYNTAX		INTEGER
		MAX-ACCESS	read-only
		STATUS		current
		DESCRIPTION		
			"Number of data slots used for uplink 1x modulation traffic in the last 15 minutes. Only supported for PMP 450 AP platform."
		::={whispApsFrUtlStatsIntervalHigh 62}

	frUtlHighUplink2xModSlots	OBJECT-TYPE
		SYNTAX		INTEGER
		MAX-ACCESS	read-only
		STATUS		current
		DESCRIPTION		
			"Number of data slots used for uplink 2x modulation traffic in the last 15 minutes. Only supported for PMP 450 AP platform."
		::={whispApsFrUtlStatsIntervalHigh 63}

	frUtlHighUplink3xModSlots	OBJECT-TYPE
		SYNTAX		INTEGER
		MAX-ACCESS	read-only
		STATUS		current
		DESCRIPTION		
			"Number of data slots used for uplink 3x modulation traffic in the last 15 minutes. Only supported for PMP 450 AP platform."
		::={whispApsFrUtlStatsIntervalHigh 64}

	frUtlHighUplink4xModSlots	OBJECT-TYPE
		SYNTAX		INTEGER
		MAX-ACCESS	read-only
		STATUS		current
		DESCRIPTION		
			"Number of data slots used for uplink 4x modulation traffic in the last 15 minutes. Only supported for PMP 450 AP platform."
		::={whispApsFrUtlStatsIntervalHigh 65}

	frUtlHighUplink5xModSlots	OBJECT-TYPE
		SYNTAX		INTEGER
		MAX-ACCESS	read-only
		STATUS		current
		DESCRIPTION		
			"Number of data slots used for uplink 5x modulation traffic in the last 15 minutes. Only supported for PMP 450 AP platform."
		::={whispApsFrUtlStatsIntervalHigh 66}

	frUtlHighUplink6xModSlots	OBJECT-TYPE
		SYNTAX		INTEGER
		MAX-ACCESS	read-only
		STATUS		current
		DESCRIPTION		
			"Number of data slots used for uplink 6x modulation traffic in the last 15 minutes. Only supported for PMP 450 AP platform."
		::={whispApsFrUtlStatsIntervalHigh 67}

	frUtlHighUplink7xModSlots	OBJECT-TYPE
		SYNTAX		INTEGER
		MAX-ACCESS	read-only
		STATUS		current
		DESCRIPTION		
			"Number of data slots used for uplink 7x modulation traffic in the last 15 minutes. Only supported for PMP 450 AP platform."
		::={whispApsFrUtlStatsIntervalHigh 68}

	frUtlHighUplink8xModSlots	OBJECT-TYPE
		SYNTAX		INTEGER
		MAX-ACCESS	read-only
		STATUS		current
		DESCRIPTION		
			"Number of data slots used for uplink 8x modulation traffic in the last 15 minutes. Only supported for PMP 450 AP platform."
		::={whispApsFrUtlStatsIntervalHigh 69}

	frUtlHighDLSpecEffExtrap	OBJECT-TYPE
		SYNTAX		INTEGER
		MAX-ACCESS	read-only
		STATUS		current
		DESCRIPTION		
			"Extrapolated downlink Spectral Efficiency in the last 15 minute (Multiplied by 1000). Measured in units of user data bits per second per hertz.
                                     Divide by 1000 for actual number.
                                     Not currently supported on 450m"
		::={whispApsFrUtlStatsIntervalHigh 70}

	frUtlHighDLSpecEffMax	OBJECT-TYPE
		SYNTAX		INTEGER
		MAX-ACCESS	read-only
		STATUS		current
		DESCRIPTION		
			"Maximum possible downlink Spectral Efficiency in the last 15 minute (Multiplied by 1000). Measured in units of user data bits per second per hertz.
                                     Divide by 1000 for actual number.
                                     Not currently supported on 450m"
		::={whispApsFrUtlStatsIntervalHigh 71}

	frUtlHighULSpecEffExtrap	OBJECT-TYPE
		SYNTAX		INTEGER
		MAX-ACCESS	read-only
		STATUS		current
		DESCRIPTION		
			"Extrapolated uplink Spectral Efficiency in the last 15 minute (Multiplied by 1000). Measured in units of user data bits per second per hertz.
                                     Divide by 1000 for actual number.
                                     Not currently supported on 450m"
		::={whispApsFrUtlStatsIntervalHigh 72}

	frUtlHighULSpecEffMax	OBJECT-TYPE
		SYNTAX		INTEGER
		MAX-ACCESS	read-only
		STATUS		current
		DESCRIPTION		
			"Maximum possible uplink Spectral Efficiency in the last 15 minute (Multiplied by 1000). Measured in units of user data bits per second per hertz.
                                     Divide by 1000 for actual number.
                                     Not currently supported on 450m"
		::={whispApsFrUtlStatsIntervalHigh 73}

	frUtlHighDLAvgFragsPerSlot	OBJECT-TYPE
		SYNTAX		INTEGER
		MAX-ACCESS	read-only
		STATUS		current
		DESCRIPTION		
			"Average number of fragments per slot in the last 15 minute (Multiplied by 100).
                                     Divide by 100 for actual number.
                                     Not currently supported on 450m"
		::={whispApsFrUtlStatsIntervalHigh 74}

	frUtlHighULAvgFragsPerSlot	OBJECT-TYPE
		SYNTAX		INTEGER
		MAX-ACCESS	read-only
		STATUS		current
		DESCRIPTION		
			"Average number of fragments per slot in the last 15 minute (Multiplied by 100).
                                     Divide by 100 for actual number.
                                     Not currently supported on 450m"
		::={whispApsFrUtlStatsIntervalHigh 75}

	frUtlHighULMissedAcksSuMimo	OBJECT-TYPE
		SYNTAX		INTEGER
		MAX-ACCESS	read-only
		STATUS		current
		DESCRIPTION		
			"Number of missed Uplink MAC Acknowledgements in the last 15 minutes.
                            PMP only.
                            For 450m, this is the SU-MIMO ACKs."
		::={whispApsFrUtlStatsIntervalHigh 76}

	frUtlHighULMissedAcksMuMimo	OBJECT-TYPE
		SYNTAX		INTEGER
		MAX-ACCESS	read-only
		STATUS		current
		DESCRIPTION		
			"Number of missed Uplink MU-MIMO MAC Acknowledgements in the last 15 minutes.
                            PMP only.
                            MU-MIMO platforms only."
		::={whispApsFrUtlStatsIntervalHigh 77}

	whispApsFrUtlStatsMumimoSpatialTable OBJECT-TYPE
		SYNTAX		SEQUENCE OF WhispApsFrUtlStatsMumimoSpatialEntry
		MAX-ACCESS	not-accessible
		STATUS		current
		DESCRIPTION
			"MU-MIMO Spatial Utilization Metrics."
		::= {whispApsFrUtlStats 4}

	whispApsFrUtlStatsMumimoSpatialEntry OBJECT-TYPE
		SYNTAX		WhispApsFrUtlStatsMumimoSpatialEntry
		MAX-ACCESS	not-accessible
		STATUS		current
		DESCRIPTION
			"MU-MIMO Spatial Utilization Metrics."
		INDEX		{frUtlMumimoDownlinkUtilizationSfBin}
		::= {whispApsFrUtlStatsMumimoSpatialTable 1}

		WhispApsFrUtlStatsMumimoSpatialEntry ::= SEQUENCE{
			frUtlMumimoDownlinkUtilizationSfBin		INTEGER,
			frUtlMumimoDownlinkUtilizationSfRange		DisplayString,
			frUtlMumimoDownlinkUtilizationAzimuth		DisplayString,
			frUtlMumimoDownlinkUtilizationVcRange		DisplayString,
			frUtlMumimoDownlinkUtilizationLUIDRange		DisplayString,
			frUtlMumimoDownlinkInstantaneousUtilization		INTEGER,
			frUtlLowTotalMumimoDownlinkUtilization		INTEGER,
			frUtlMedTotalMumimoDownlinkUtilization		INTEGER,
			frUtlHighTotalMumimoDownlinkUtilization		INTEGER,
			frUtlLowMaxMumimoDownlinkUtilization		INTEGER,
			frUtlMedMaxMumimoDownlinkUtilization		INTEGER,
			frUtlHighMaxMumimoDownlinkUtilization		INTEGER,
			frUtlLowMinMumimoDownlinkUtilization		INTEGER,
			frUtlMedMinMumimoDownlinkUtilization		INTEGER,
			frUtlHighMinMumimoDownlinkUtilization	INTEGER
			}

	frUtlMumimoDownlinkUtilizationSfBin	OBJECT-TYPE
		SYNTAX		INTEGER (0..32)
		MAX-ACCESS	read-only
		STATUS		current
		DESCRIPTION		
			"Spatial Frequency Bin.
                            MU-MIMO only."
		::={whispApsFrUtlStatsMumimoSpatialEntry 1}

	frUtlMumimoDownlinkUtilizationSfRange	OBJECT-TYPE
		SYNTAX		DisplayString
		MAX-ACCESS	read-only
		STATUS		current
		DESCRIPTION		
			"Spatial Frequency Range.
                            MU-MIMO only."
		::={whispApsFrUtlStatsMumimoSpatialEntry 2}

	frUtlMumimoDownlinkUtilizationAzimuth	OBJECT-TYPE
		SYNTAX		DisplayString
		MAX-ACCESS	read-only
		STATUS		current
		DESCRIPTION		
			"Azimuth Ranges per Spatial Frequency bin.
                            MU-MIMO only."
		::={whispApsFrUtlStatsMumimoSpatialEntry 3}

	frUtlMumimoDownlinkUtilizationVcRange	OBJECT-TYPE
		SYNTAX		DisplayString
		MAX-ACCESS	read-only
		STATUS		current
		DESCRIPTION		
			"VCs in Spatial Frequency Range.
                            MU-MIMO only."
		::={whispApsFrUtlStatsMumimoSpatialEntry 4}

	frUtlMumimoDownlinkInstantaneousUtilization	OBJECT-TYPE
		SYNTAX		INTEGER
		MAX-ACCESS	read-only
		STATUS		current
		DESCRIPTION		
			"Instantanous MU-MIMO downlink utilization. This updates every 500ms.
                            MU-MIMO only."
		::={whispApsFrUtlStatsMumimoSpatialEntry 5}

	frUtlLowTotalMumimoDownlinkUtilization	OBJECT-TYPE
		SYNTAX		INTEGER
		MAX-ACCESS	read-only
		STATUS		current
		DESCRIPTION		
			"Percentage of total MU-MIMO downlink utilization in the last 1 minute.
                            MU-MIMO only."
		::={whispApsFrUtlStatsMumimoSpatialEntry 6}

	frUtlMedTotalMumimoDownlinkUtilization	OBJECT-TYPE
		SYNTAX		INTEGER
		MAX-ACCESS	read-only
		STATUS		current
		DESCRIPTION		
			"Percentage of total MU-MIMO downlink utilization in the last 5 minutes.
                            MU-MIMO only."
		::={whispApsFrUtlStatsMumimoSpatialEntry 7}

	frUtlHighTotalMumimoDownlinkUtilization	OBJECT-TYPE
		SYNTAX		INTEGER
		MAX-ACCESS	read-only
		STATUS		current
		DESCRIPTION		
			"Percentage of total MU-MIMO downlink utilization in the last 15 minutes.
                            MU-MIMO only."
		::={whispApsFrUtlStatsMumimoSpatialEntry 8}

	frUtlLowMaxMumimoDownlinkUtilization	OBJECT-TYPE
		SYNTAX		INTEGER
		MAX-ACCESS	read-only
		STATUS		current
		DESCRIPTION		
			"Maximum MU-MIMO downlink utilization in the last 1 minute.
                            MU-MIMO only."
		::={whispApsFrUtlStatsMumimoSpatialEntry 9}

	frUtlMedMaxMumimoDownlinkUtilization	OBJECT-TYPE
		SYNTAX		INTEGER
		MAX-ACCESS	read-only
		STATUS		current
		DESCRIPTION		
			"Maximum MU-MIMO downlink utilization in the last 5 minutes.
                            MU-MIMO only."
		::={whispApsFrUtlStatsMumimoSpatialEntry 10}

	frUtlHighMaxMumimoDownlinkUtilization	OBJECT-TYPE
		SYNTAX		INTEGER
		MAX-ACCESS	read-only
		STATUS		current
		DESCRIPTION		
			"Maximum MU-MIMO downlink utilization in the last 15 minutes.
                            MU-MIMO only."
		::={whispApsFrUtlStatsMumimoSpatialEntry 11}

	frUtlLowMinMumimoDownlinkUtilization	OBJECT-TYPE
		SYNTAX		INTEGER
		MAX-ACCESS	read-only
		STATUS		current
		DESCRIPTION		
			"Minimum MU-MIMO downlink utilization in the last 1 minute.
                            MU-MIMO only."
		::={whispApsFrUtlStatsMumimoSpatialEntry 12}

	frUtlMedMinMumimoDownlinkUtilization	OBJECT-TYPE
		SYNTAX		INTEGER
		MAX-ACCESS	read-only
		STATUS		current
		DESCRIPTION		
			"Minimum MU-MIMO downlink utilization in the last 5 minutes.
                            MU-MIMO only."
		::={whispApsFrUtlStatsMumimoSpatialEntry 13}

	frUtlHighMinMumimoDownlinkUtilization	OBJECT-TYPE
		SYNTAX		INTEGER
		MAX-ACCESS	read-only
		STATUS		current
		DESCRIPTION		
			"Minimum MU-MIMO downlink utilization in the last 15 minutes.
                            MU-MIMO only."
		::={whispApsFrUtlStatsMumimoSpatialEntry 14}

	frUtlMumimoDownlinkUtilizationLUIDRange	OBJECT-TYPE
		SYNTAX		DisplayString
		MAX-ACCESS	read-only
		STATUS		current
		DESCRIPTION		
			"LUIDs in Spatial Frequency Range.
                            MU-MIMO only."
		::={whispApsFrUtlStatsMumimoSpatialEntry 15}

	whispApsFrUtlStatsMumimoDistributionTable OBJECT-TYPE
		SYNTAX		SEQUENCE OF WhispApsFrUtlStatsMumimoDistributionEntry
		MAX-ACCESS	not-accessible
		STATUS		current
		DESCRIPTION
			"MU-MIMO Distribution Metrics."
		::= {whispApsFrUtlStats 5}

	whispApsFrUtlStatsMumimoDistributionEntry OBJECT-TYPE
		SYNTAX		WhispApsFrUtlStatsMumimoDistributionEntry
		MAX-ACCESS	not-accessible
		STATUS		current
		DESCRIPTION
			"MU-MIMO Distribution Metrics."
		INDEX		{frUtlMumimoDownlinkDistributionIndex}
		::= {whispApsFrUtlStatsMumimoDistributionTable 1}

		WhispApsFrUtlStatsMumimoDistributionEntry ::= SEQUENCE{
			frUtlMumimoDownlinkDistributionIndex		INTEGER,
			frUtlMumimoDownlinkDistributionGroup		DisplayString,
			frUtlMumimoDownlinkDistributionVc		DisplayString,
			frUtlMumimoDownlinkDistributionLUID		DisplayString,
			frUtlMumimoDownlinkDistributionMedianSlotCount	INTEGER
			}

	frUtlMumimoDownlinkDistributionIndex	OBJECT-TYPE
		SYNTAX		INTEGER (0..9)
		MAX-ACCESS	read-only
		STATUS		current
		DESCRIPTION		
			"MU-MIMO downlink Distribution Table Index.
                            MU-MIMO only."
		::={whispApsFrUtlStatsMumimoDistributionEntry 1}

	frUtlMumimoDownlinkDistributionGroup	OBJECT-TYPE
		SYNTAX		DisplayString
		MAX-ACCESS	read-only
		STATUS		current
		DESCRIPTION		
			"MU-MIMO downlink Distribution Group.
                            MU-MIMO only."
		::={whispApsFrUtlStatsMumimoDistributionEntry 2}

	frUtlMumimoDownlinkDistributionVc	OBJECT-TYPE
		SYNTAX		DisplayString
		MAX-ACCESS	read-only
		STATUS		current
		DESCRIPTION		
			"MU-MIMO downlink VC Distribution.
                            MU-MIMO only."
		::={whispApsFrUtlStatsMumimoDistributionEntry 3}

	frUtlMumimoDownlinkDistributionMedianSlotCount	OBJECT-TYPE
		SYNTAX		INTEGER
		MAX-ACCESS	read-only
		STATUS		current
		DESCRIPTION		
			"MU-MIMO downlink Median Slot Count Distribution.
                            MU-MIMO only."
		::={whispApsFrUtlStatsMumimoDistributionEntry 4}

	frUtlMumimoDownlinkDistributionLUID	OBJECT-TYPE
		SYNTAX		DisplayString
		MAX-ACCESS	read-only
		STATUS		current
		DESCRIPTION		
			"MU-MIMO downlink LUID Distribution.
                            MU-MIMO only."
		::={whispApsFrUtlStatsMumimoDistributionEntry 5}

-- Access Point status page

	regCount	OBJECT-TYPE
		SYNTAX		Unsigned32
		MAX-ACCESS	read-only
		STATUS		current
		DESCRIPTION		
			"Number of registered SMs."
		::={whispApsStatus 1}

	gpsStatus	OBJECT-TYPE
		SYNTAX		DisplayString
		MAX-ACCESS	read-only
		STATUS		current
		DESCRIPTION		
			"GPS status."
		::={whispApsStatus 2}

	radioSlicingAp	OBJECT-TYPE
		SYNTAX		INTEGER
		MAX-ACCESS	read-only
		STATUS		obsolete
		DESCRIPTION		
			"The variable is deprecated."
		::={whispApsStatus 3}

	radioTxGainAp	OBJECT-TYPE
		SYNTAX		INTEGER
		MAX-ACCESS	read-only
		STATUS		current
		DESCRIPTION		
			"Radio transmit gain setting."
		::={whispApsStatus 4}

	dataSlotDwn	OBJECT-TYPE
		SYNTAX		INTEGER
		MAX-ACCESS	read-only
		STATUS		current
		DESCRIPTION		
			"Number of data slot down."
		::={whispApsStatus 5}

	dataSlotUp	OBJECT-TYPE
		SYNTAX		INTEGER
		MAX-ACCESS	read-only
		STATUS		current
		DESCRIPTION		
			"Number of data slot up."
		::={whispApsStatus 6}

	dataSlotUpHi	OBJECT-TYPE
		SYNTAX		Unsigned32
		MAX-ACCESS	read-only
		STATUS		obsolete
		DESCRIPTION		
			"Number of high priority data slot up."
		::={whispApsStatus 7}

	upLnkAckSlot	OBJECT-TYPE
		SYNTAX		Unsigned32
		MAX-ACCESS	read-only
		STATUS		obsolete
		DESCRIPTION		
			"Uplink ack slots."
		::={whispApsStatus 8}

	upLnkAckSlotHi	OBJECT-TYPE
		SYNTAX		Unsigned32
		MAX-ACCESS	read-only
		STATUS		obsolete
		DESCRIPTION		
			"Hige priority uplink ack slots."
		::={whispApsStatus 9}

	dwnLnkAckSlot	OBJECT-TYPE
		SYNTAX		Unsigned32
		MAX-ACCESS	read-only
		STATUS		obsolete
		DESCRIPTION		
			"Downlink ack slots."
		::={whispApsStatus 10}

	dwnLnkAckSlotHi	OBJECT-TYPE
		SYNTAX		Unsigned32
		MAX-ACCESS	read-only
		STATUS		obsolete
		DESCRIPTION		
			"Hige priority downlink ack slots."
		::={whispApsStatus 11}

	numCtrSlot	OBJECT-TYPE
		SYNTAX		Unsigned32
		MAX-ACCESS	read-only
		STATUS		obsolete
		DESCRIPTION		
			"Number of contention slots."
		::={whispApsStatus 12}

	numCtrSlotHi	OBJECT-TYPE
		SYNTAX		Unsigned32
		MAX-ACCESS	read-only
		STATUS		obsolete
		DESCRIPTION		
			"High priority control slot."
		::={whispApsStatus 13}

	dfsStatus	OBJECT-TYPE
		SYNTAX		DisplayString
		MAX-ACCESS	read-only
		STATUS		current
		DESCRIPTION		
			"Dynamic frequency shifting status."
		::={whispApsStatus 14}

	dfsStatusPrimary	OBJECT-TYPE
		SYNTAX		DisplayString
		MAX-ACCESS	read-only
		STATUS		current
		DESCRIPTION		
			"Dynamic frequency shifting status for Primary Channel."
		::={whispApsStatus 15}

	dfsStatusAlt1	OBJECT-TYPE
		SYNTAX		DisplayString
		MAX-ACCESS	read-only
		STATUS		current
		DESCRIPTION		
			"Dynamic frequency shifting status for Alternate Channel 1"
		::={whispApsStatus 16}

	dfsStatusAlt2	OBJECT-TYPE
		SYNTAX		DisplayString
		MAX-ACCESS	read-only
		STATUS		current
		DESCRIPTION		
			"Dynamic frequency shifting status for Alternate Channel 2"
		::={whispApsStatus 17}

	maxRegSMCount	OBJECT-TYPE
		SYNTAX		INTEGER
		MAX-ACCESS	read-only
		STATUS		current
		DESCRIPTION		
			"Maximum number of unique Subscriber Modules registered with this AP at once"
		::={whispApsStatus 18}

	systemTime	OBJECT-TYPE
		SYNTAX		DisplayString
		MAX-ACCESS	read-only
		STATUS		current
		DESCRIPTION		
			"Displays the system time of the unit"
		::={whispApsStatus 19}

	lastNTPTime	OBJECT-TYPE
		SYNTAX		DisplayString
		MAX-ACCESS	read-only
		STATUS		current
		DESCRIPTION		
			"Displays the last NTP time acquired by the AP"
		::={whispApsStatus 20}

	regulatoryStatus	OBJECT-TYPE
		SYNTAX		DisplayString
		MAX-ACCESS	read-only
		STATUS		current
		DESCRIPTION		
			"The current status of the regulatory check on the AP."
		::={whispApsStatus 21}

	dhcpRlyAgntStat-reqRecvd	OBJECT-TYPE
		SYNTAX		Counter32
		MAX-ACCESS	read-only
		STATUS		current
		DESCRIPTION		
			"Number of DHCP Requests received by the DHCP Relay."
		::={whispApsStatus 22}

	dhcpRlyAgntStat-reqRelayed	OBJECT-TYPE
		SYNTAX		Counter32
		MAX-ACCESS	read-only
		STATUS		current
		DESCRIPTION		
			"Number of DHCP Requests relayed by the DHCP Relay."
		::={whispApsStatus 23}

	dhcpRlyAgntStat-reqDiscards	OBJECT-TYPE
		SYNTAX		Counter32
		MAX-ACCESS	read-only
		STATUS		current
		DESCRIPTION		
			"Number of DHCP Requests discarded by the DHCP Relay."
		::={whispApsStatus 24}

	dhcpRlyAgntStat-respRecvd	OBJECT-TYPE
		SYNTAX		Counter32
		MAX-ACCESS	read-only
		STATUS		current
		DESCRIPTION		
			"Number of DHCP Replies received by the DHCP Relay."
		::={whispApsStatus 25}

	dhcpRlyAgntStat-respRelayed	OBJECT-TYPE
		SYNTAX		Counter32
		MAX-ACCESS	read-only
		STATUS		current
		DESCRIPTION		
			"Number of DHCP Replies relayed by the DHCP Relay."
		::={whispApsStatus 26}

	dhcpRlyAgntStat-respDiscards	OBJECT-TYPE
		SYNTAX		Counter32
		MAX-ACCESS	read-only
		STATUS		current
		DESCRIPTION		
			"Number of DHCP Replies discarded by the DHCP Relay."
		::={whispApsStatus 27}

	dhcpRlyAgntStat-untrustedDiscards	OBJECT-TYPE
		SYNTAX		Counter32
		MAX-ACCESS	read-only
		STATUS		current
		DESCRIPTION		
			"Number of untrusted messages discarded by the DHCP Relay."
		::={whispApsStatus 28}

	dhcpRlyAgntStat-maxHopDiscards	OBJECT-TYPE
		SYNTAX		Counter32
		MAX-ACCESS	read-only
		STATUS		current
		DESCRIPTION		
			"Number of messages discarded by the DHCP Relay due to exceeded max hop."
		::={whispApsStatus 29}

	dhcpRlyAgntStat-pktTooBig	OBJECT-TYPE
		SYNTAX		Counter32
		MAX-ACCESS	read-only
		STATUS		current
		DESCRIPTION		
			"Number of messages forwarded without relay information by the DHCP Relay due to relay information exceeding max message size."
		::={whispApsStatus 30}

	dhcpRlyAgntStat-invalidGiaddrDiscards	OBJECT-TYPE
		SYNTAX		Counter32
		MAX-ACCESS	read-only
		STATUS		current
		DESCRIPTION		
			"Number of messages discarded by the DHCP Relay due to invalid giaddr in packet."
		::={whispApsStatus 31}

	regFailureCount	OBJECT-TYPE
		SYNTAX		Counter32
		MAX-ACCESS	read-only
		STATUS		current
		DESCRIPTION		
			"The Total number or Registration Grant Failures."
		::={whispApsStatus 32}

	ntpLogSNMP	OBJECT-TYPE
		SYNTAX		EventString
		MAX-ACCESS	read-only
		STATUS		current
		DESCRIPTION		
			"NTP Log"
		::={whispApsStatus 33}

	uGPSPowerStatus	OBJECT-TYPE
		SYNTAX		DisplayString
		MAX-ACCESS	read-only
		STATUS		current
		DESCRIPTION		
			"Current Aux Port Power to UGPS Status (UGPS capable APs only)."
		::={whispApsStatus 34}

	rfOutDiscardRate	OBJECT-TYPE
		SYNTAX		INTEGER (0..100)
		MAX-ACCESS	read-only
		STATUS		current
		DESCRIPTION		
			"Percentage of OutDiscards on the RF link (RF Overload %) in the last minute."
		::={whispApsStatus 35}

	autoUpdateGlobalStatus	OBJECT-TYPE
		SYNTAX		INTEGER
		MAX-ACCESS	read-only
		STATUS		current
		DESCRIPTION		
			"Status of the Auto-Update Command"
		::={whispApsStatus 36}

	currentRadioFreqCarrier	OBJECT-TYPE
		SYNTAX		INTEGER
		MAX-ACCESS	read-only
		STATUS		current
		DESCRIPTION		
			"Returns the current operating frequency of the AP in units of kHz."
		::={whispApsStatus 37}

	mumimoMode	OBJECT-TYPE
		SYNTAX		DisplayString
		MAX-ACCESS	read-only
		STATUS		current
		DESCRIPTION		
			"Returns the current operating mode of MU-MIMO.
                          PMP 450m only."
		::={whispApsStatus 38}

-- Access Point status page

	vcCount	OBJECT-TYPE
		SYNTAX		Unsigned32
		MAX-ACCESS	read-only
		STATUS		deprecated
		DESCRIPTION		
			"Number of VCs allocated across all registered SMs.
                            This OID is deprecated. Please use dataChannelCount instead."
		::={whispApsStatus 39}

	mumimoTrialPercentageRemaining	OBJECT-TYPE
		SYNTAX		INTEGER (0..100)
		MAX-ACCESS	read-only
		STATUS		current
		DESCRIPTION		
			"Percentage of remaining MU-MIMO Trial Licenses"
		::={whispApsStatus 40}

	smPrioritizationCountLow	OBJECT-TYPE
		SYNTAX		INTEGER (0..239)
		MAX-ACCESS	read-only
		STATUS		current
		DESCRIPTION		
			"SM Prioritization Low Group count.
                            Indicates the number of SMs that belong to the SM Prioritization Low Group."
		::={whispApsStatus 41}

	smPrioritizationCountHigh	OBJECT-TYPE
		SYNTAX		INTEGER (0..239)
		MAX-ACCESS	read-only
		STATUS		current
		DESCRIPTION		
			"SM Prioritization High Group count.
                            Indicates the number of SMs that belong to the SM Prioritization High Group."
		::={whispApsStatus 42}

	lowPriorityDataChannelCount	OBJECT-TYPE
		SYNTAX		INTEGER (0..238)
		MAX-ACCESS	read-only
		STATUS		current
		DESCRIPTION		
			"Low Priority Data Channel count.
                            Indicates the number of Data Channels configured at Low Priority QoS level."
		::={whispApsStatus 43}

	mediumPriorityDataChannelCount	OBJECT-TYPE
		SYNTAX		INTEGER (0..238)
		MAX-ACCESS	read-only
		STATUS		current
		DESCRIPTION		
			"Medium Priority Data Channel count.
                            Indicates the number of Data Channels configured at Medium Priority QoS level."
		::={whispApsStatus 44}

	highPriorityDataChannelCount	OBJECT-TYPE
		SYNTAX		INTEGER (0..238)
		MAX-ACCESS	read-only
		STATUS		current
		DESCRIPTION		
			"High Priority Data Channel count.
                            Indicates the number of Data Channels configured at High Priority QoS level."
		::={whispApsStatus 45}

	ultraHighPriorityDataChannelCount	OBJECT-TYPE
		SYNTAX		INTEGER (0..238)
		MAX-ACCESS	read-only
		STATUS		current
		DESCRIPTION		
			"Ultra High Priority Data Channel count.
                            Indicates the number of Data Channels configured at Ultra High Priority QoS level."
		::={whispApsStatus 46}

-- Access Point status page

	dataChannelCount	OBJECT-TYPE
		SYNTAX		Unsigned32
		MAX-ACCESS	read-only
		STATUS		current
		DESCRIPTION		
			"Number of Data Channels allocated across all registered SMs."
		::={whispApsStatus 47}

	aes256FeatureKeyStatus	OBJECT-TYPE
		SYNTAX		DisplayString
		MAX-ACCESS	read-only
		STATUS		current
		DESCRIPTION		
			"Returns the status of the AES-256 Encryption feature Key."
		::={whispApsStatus 48}

	totalActiveSmCount	OBJECT-TYPE
		SYNTAX		Counter32
		MAX-ACCESS	read-only
		STATUS		current
		DESCRIPTION		
			"Returns the total number of SMs before last channel/EIRP change.
                            PMP Only."
		::={whispApsStatus 50}

	failedSmCountStatus	OBJECT-TYPE
		SYNTAX		Counter32
		MAX-ACCESS	read-only
		STATUS		current
		DESCRIPTION		
			"Returns the number of SMs not reconnected after last channel/EIRP change.
                            PMP Only."
		::={whispApsStatus 51}

	failedSmPercent	OBJECT-TYPE
		SYNTAX		DisplayString
		MAX-ACCESS	read-only
		STATUS		current
		DESCRIPTION		
			"Returns the percentage of SMs that did not reconnect after last channel/EIRP change.
                            PMP Only."
		::={whispApsStatus 52}

	activeIdleSmCount	OBJECT-TYPE
		SYNTAX		Counter32
		MAX-ACCESS	read-only
		STATUS		current
		DESCRIPTION		
			"Returns the number of idle SMs which are considered active.
                            This count is included while computing total SM count.
                            PMP Only."
		::={whispApsStatus 53}

	dhcpRlyAgntStat-invalidPacketDiscards	OBJECT-TYPE
		SYNTAX		Counter32
		MAX-ACCESS	read-only
		STATUS		current
		DESCRIPTION		
			"Number of messages discarded by the DHCP Relay due to invalid or corrupted packet."
		::={whispApsStatus 54}

	interferenceCancellationMode	OBJECT-TYPE
		SYNTAX		DisplayString
		MAX-ACCESS	read-only
		STATUS		current
		DESCRIPTION		
			"Returns the current operating mode of Interference Cancellation.
                          PMP 450m only."
		::={whispApsStatus 55}

	interferenceCancellationTrialPercentageRemaining	OBJECT-TYPE
		SYNTAX		INTEGER (0..100)
		MAX-ACCESS	read-only
		STATUS		current
		DESCRIPTION		
			"Percentage of remaining Interference Cancellation Trial Licenses"
		::={whispApsStatus 56}

	reqRecvd	OBJECT-TYPE
		SYNTAX		Counter32
		MAX-ACCESS	read-only
		STATUS		current
		DESCRIPTION		
			"Number of DHCPv6 Requests received by the DHCPv6 Relay."
		::={whispApsDHCPv6RelayStats 1}

	reqRelayed	OBJECT-TYPE
		SYNTAX		Counter32
		MAX-ACCESS	read-only
		STATUS		current
		DESCRIPTION		
			"Number of DHCPv6 Requests relayed by the DHCP Relay."
		::={whispApsDHCPv6RelayStats 2}

	reqDiscards	OBJECT-TYPE
		SYNTAX		Counter32
		MAX-ACCESS	read-only
		STATUS		current
		DESCRIPTION		
			"Number of DHCPv6 Requests discarded by the DHCPv6 Relay."
		::={whispApsDHCPv6RelayStats 3}

	respRecvd	OBJECT-TYPE
		SYNTAX		Counter32
		MAX-ACCESS	read-only
		STATUS		current
		DESCRIPTION		
			"Number of DHCPv6 Replies received by the DHCPv6 Relay."
		::={whispApsDHCPv6RelayStats 4}

	respRelayed	OBJECT-TYPE
		SYNTAX		Counter32
		MAX-ACCESS	read-only
		STATUS		current
		DESCRIPTION		
			"Number of DHCPv6 Replies relayed by the DHCPv6 Relay."
		::={whispApsDHCPv6RelayStats 5}

	respDiscards	OBJECT-TYPE
		SYNTAX		Counter32
		MAX-ACCESS	read-only
		STATUS		current
		DESCRIPTION		
			"Number of DHCPv6 Replies discarded by the DHCPv6 Relay."
		::={whispApsDHCPv6RelayStats 6}

	pktTooBig	OBJECT-TYPE
		SYNTAX		Counter32
		MAX-ACCESS	read-only
		STATUS		current
		DESCRIPTION		
			"Number of messages forwarded without relay information by the DHCPv6 Relay due to relay information exceeding max message size."
		::={whispApsDHCPv6RelayStats 7}

	ntpDomainNameAppend	OBJECT-TYPE
		SYNTAX		INTEGER {
					disableDomain(0),
					appendDomain(1)}
		MAX-ACCESS	read-write
		STATUS		current
		DESCRIPTION		
			"Select whether to append the configured management domain name to
            the configured trap names.  For example, if dnsMgmtDomainName is
            set to 'example.com', ntpServer is set to 'ntp', and ntpDomainNameAppend
            is set to appendDomain, the ntpServer name used would be 'ntp.example.com'."
		::={whispApsDNS 1}

	ntpServer1	OBJECT-TYPE
		SYNTAX		DisplayString
		MAX-ACCESS	read-write
		STATUS		current
		DESCRIPTION		
			"NTP Server 1 Address.
            Format is either an IP address or DNS name."
		::={whispApsDNS 2}

	ntpServer2	OBJECT-TYPE
		SYNTAX		DisplayString
		MAX-ACCESS	read-write
		STATUS		current
		DESCRIPTION		
			"NTP Server 2 Address.
            Format is either an IP address or DNS name."
		::={whispApsDNS 3}

	ntpServer3	OBJECT-TYPE
		SYNTAX		DisplayString
		MAX-ACCESS	read-write
		STATUS		current
		DESCRIPTION		
			"NTP Server 3 Address.
            Format is either an IP address or DNS name."
		::={whispApsDNS 4}

	dhcprDomainNameAppend	OBJECT-TYPE
		SYNTAX		INTEGER {
					disableDomain(0),
					appendDomain(1)}
		MAX-ACCESS	read-write
		STATUS		current
		DESCRIPTION		
			"Select whether to append the configured management domain name to
            the configured trap names.  For example, if dnsMgmtDomainName is
            set to 'example.com', dhcprServer is set to 'dhcpr', and dhcprDomainNameAppend
            is set to appendDomain, the dhcprServer name used would be 'dhcpr.example.com'."
		::={whispApsDNS 5}

	dhcprServer	OBJECT-TYPE
		SYNTAX		DisplayString
		MAX-ACCESS	read-write
		STATUS		current
		DESCRIPTION		
			"DHCP Server IP which will be used for forwarding DHCP messages
            by the DHCP Relay Agent in the MultiPoint AP.
              - Format is either an IP address or DNS name.
              - Default is 255.255.255.255 (broadcast)."
		::={whispApsDNS 6}

	authDomainNameAppend	OBJECT-TYPE
		SYNTAX		INTEGER {
					disableDNSDomain(0),
					enableDNSDomain(1)}
		MAX-ACCESS	read-write
		STATUS		current
		DESCRIPTION		
			"Select whether to append the configured management domain name to
            the configured authServer names.  For example, if dnsMgmtDomainName is
            set to 'example.com', authServer1 is set to 'auth1', and authDomainNameAppend
            is set to appendDomain, the authServer1 name used would be 'auth1.example.com'."
		::={whispApsDNS 7}

	authServer1	OBJECT-TYPE
		SYNTAX		DisplayString
		MAX-ACCESS	read-write
		STATUS		current
		DESCRIPTION		
			"Authentication Server 1.
            Format is either an IP address or DNS name."
		::={whispApsDNS 8}

	authServer2	OBJECT-TYPE
		SYNTAX		DisplayString
		MAX-ACCESS	read-write
		STATUS		current
		DESCRIPTION		
			"Authentication Server 2.
            Format is either an IP address or DNS name."
		::={whispApsDNS 9}

	authServer3	OBJECT-TYPE
		SYNTAX		DisplayString
		MAX-ACCESS	read-write
		STATUS		current
		DESCRIPTION		
			"Authentication Server 3.
            Format is either an IP address or DNS name."
		::={whispApsDNS 10}

	authServer4	OBJECT-TYPE
		SYNTAX		DisplayString
		MAX-ACCESS	read-write
		STATUS		current
		DESCRIPTION		
			"Authentication Server 4.
            Format is either an IP address or DNS name."
		::={whispApsDNS 11}

	authServer5	OBJECT-TYPE
		SYNTAX		DisplayString
		MAX-ACCESS	read-write
		STATUS		current
		DESCRIPTION		
			"Authentication Server 5.
            Format is either an IP address or DNS name."
		::={whispApsDNS 12}

	acctDomainNameAppend	OBJECT-TYPE
		SYNTAX		INTEGER {
					disableDomain(0),
					appendDomain(1)}
		MAX-ACCESS	read-write
		STATUS		obsolete
		DESCRIPTION		
			"Obsoleted.  Use whispApsDNS.authDomainNameAppend."
		::={whispApsDNS 13}

	userAuthServer1	OBJECT-TYPE
		SYNTAX		DisplayString
		MAX-ACCESS	read-write
		STATUS		current
		DESCRIPTION		
			"User Authentication Server 1.
            Format is either an IP address or DNS name."
		::={whispApsDNS 14}

	userAuthServer2	OBJECT-TYPE
		SYNTAX		DisplayString
		MAX-ACCESS	read-write
		STATUS		current
		DESCRIPTION		
			"User Authentication Server 2.
            Format is either an IP address or DNS name."
		::={whispApsDNS 15}

	userAuthServer3	OBJECT-TYPE
		SYNTAX		DisplayString
		MAX-ACCESS	read-write
		STATUS		current
		DESCRIPTION		
			"User Authentication Server 3.
            Format is either an IP address or DNS name."
		::={whispApsDNS 16}

	userAuthDomainNameAppend	OBJECT-TYPE
		SYNTAX		INTEGER {
					disableDNSDomain(0),
					enableDNSDomain(1)}
		MAX-ACCESS	read-write
		STATUS		current
		DESCRIPTION		
			"Select whether to append the configured management domain name to
            the configured user authentication server names.  For example, if dnsMgmtDomainName is
            set to 'example.com', authServer1 is set to 'auth1', and userAuthDomainNameAppend
            is set to enableDNSDomain, the authServer1 name used would be 'auth1.example.com'."
		::={whispApsDNS 17}

	oneXDomainNameAppend	OBJECT-TYPE
		SYNTAX		INTEGER {
					disableDNSDomain(0),
					enableDNSDomain(1)}
		MAX-ACCESS	read-write
		STATUS		current
		DESCRIPTION		
			"Select whether to append the configured management domain name to
            the configured 802.1X Authentication server names.  For example, if dnsMgmtDomainName is
            set to 'example.com', oneXServer is set to 'auth', and authDomainNameAppend
            is set to appendDomain, the authServer1 name used would be 'auth.example.com'."
		::={whispApsDNS 18}

	oneXServer	OBJECT-TYPE
		SYNTAX		DisplayString
		MAX-ACCESS	read-write
		STATUS		current
		DESCRIPTION		
			"802.1X Authentication Server Address."
		::={whispApsDNS 19}

	ntpEnable	OBJECT-TYPE
		SYNTAX		INTEGER {
					disable(0),
					enable(1)}
		MAX-ACCESS	read-write
		STATUS		current
		DESCRIPTION		
			"Enable NTP."
		::={whispApsDNS 20}

	clearLinkTableStats	OBJECT-TYPE
		SYNTAX		INTEGER
		MAX-ACCESS	read-write
		STATUS		current
		DESCRIPTION		
			"Setting this to a nonzero value will clear the link table stats."
		::={whispApsControls 1}

	setSectorReferenceEVM	OBJECT-TYPE
		SYNTAX		INTEGER {
					alwaysOverride(0),
					setEVMifNotAlreadySet(1)}
		MAX-ACCESS	read-write
		STATUS		current
		DESCRIPTION		
			"1 = Set Reference EVM only if it is not already set
                        0 = Always override
                        Valid only on PMP devices"
		::={whispApsControls 2}

	whispApsLQILowInterval OBJECT-TYPE
		SYNTAX		SEQUENCE OF WhispApsLQILowIntervalEntry
		MAX-ACCESS	not-accessible
		STATUS		current
		DESCRIPTION
			"Link Quality Indicator one minute interval table."
		::= {whispApsLQI 1}

	whispApsLQILowIntervalEntry OBJECT-TYPE
		SYNTAX		WhispApsLQILowIntervalEntry
		MAX-ACCESS	not-accessible
		STATUS		current
		DESCRIPTION
			"Link Quality Indicator for one minute Interval entry."
		INDEX		{lqiLowLinkLUID}
		::= {whispApsLQILowInterval 1}

		WhispApsLQILowIntervalEntry ::= SEQUENCE{
			lqiLowLinkLUID		INTEGER,
			lqiLowLQI		INTEGER,
			lqiLowDownlinkQualityIndex		INTEGER,
			lqiLowDownlinkAverageActualRate		INTEGER,
			lqiLowDownlinkExpectedRate		INTEGER,
			lqiLowUplinkQualityIndex		INTEGER,
			lqiLowUplinkAverageActualRate		INTEGER,
			lqiLowUplinkExpectedRate		INTEGER,
			lqiLowBeaconQualityIndex		INTEGER,
			lqiLowBeaconPercent		INTEGER,
			lqiLowReRegQualityIndex		INTEGER,
			lqiLowReRegCount		INTEGER,
			lqiLowLinkESN		PhysAddress,
			lqiLowDownlinkActualAverageEVM		INTEGER,
			lqiLowDownlinkExpectedEVM		INTEGER,
			lqiLowUplinkActualAverageEVM		INTEGER,
			lqiLowUplinkExpectedEVM	INTEGER
			}

	lqiLowLinkLUID	OBJECT-TYPE
		SYNTAX		INTEGER (2..239)
		MAX-ACCESS	read-only
		STATUS		current
		DESCRIPTION		
			"Logical User Identfication (LUID) number"
		::={whispApsLQILowIntervalEntry 1}

	lqiLowLQI	OBJECT-TYPE
		SYNTAX		INTEGER (0..100)
		MAX-ACCESS	read-only
		STATUS		current
		DESCRIPTION		
			"Link Quality Indicator for one minute interval. 
                            Ranges from 0 to 100 where 100 is the best.
                            It's calculated based on receive power, modulation rate, reregistrations and beacon/map percentage."
		::={whispApsLQILowIntervalEntry 2}

	lqiLowDownlinkQualityIndex	OBJECT-TYPE
		SYNTAX		INTEGER (0..100)
		MAX-ACCESS	read-only
		STATUS		current
		DESCRIPTION		
			"Downlink Quality Index for one minute interval in percentage. 100% is best quality"
		::={whispApsLQILowIntervalEntry 3}

	lqiLowDownlinkAverageActualRate	OBJECT-TYPE
		SYNTAX		INTEGER (0..80)
		MAX-ACCESS	read-only
		STATUS		current
		DESCRIPTION		
			"Downlink Actual average transmit modulation rate in tenths for one minute interval. eg: 73 is 7.3X"
		::={whispApsLQILowIntervalEntry 4}

	lqiLowDownlinkExpectedRate	OBJECT-TYPE
		SYNTAX		INTEGER (0..80)
		MAX-ACCESS	read-only
		STATUS		current
		DESCRIPTION		
			"Downlink Expected Rate in tenths for one minute interval. eg: 80 is 8X
                            This is based upon the uplink receive power and does not take into account interference."
		::={whispApsLQILowIntervalEntry 5}

	lqiLowUplinkQualityIndex	OBJECT-TYPE
		SYNTAX		INTEGER (0..100)
		MAX-ACCESS	read-only
		STATUS		current
		DESCRIPTION		
			"Uplink Quality Index for one minute interval in percentage. 100% is best quality"
		::={whispApsLQILowIntervalEntry 6}

	lqiLowUplinkAverageActualRate	OBJECT-TYPE
		SYNTAX		INTEGER (0..80)
		MAX-ACCESS	read-only
		STATUS		current
		DESCRIPTION		
			"Uplink Actual average transmit modulation rate in tenths for one minute interval. eg: 73 is 7.3X"
		::={whispApsLQILowIntervalEntry 7}

	lqiLowUplinkExpectedRate	OBJECT-TYPE
		SYNTAX		INTEGER (0..80)
		MAX-ACCESS	read-only
		STATUS		current
		DESCRIPTION		
			"Uplink Expected Rate in tenths for one minute interval. eg: 80 is 8X
                            This is based upon the uplink receive power and does not take into account interference."
		::={whispApsLQILowIntervalEntry 8}

	lqiLowBeaconQualityIndex	OBJECT-TYPE
		SYNTAX		INTEGER (0..100)
		MAX-ACCESS	read-only
		STATUS		current
		DESCRIPTION		
			"Beacon Quality Index for one minute interval in percentage. 100% is best quality
                            For PMP this also includes the Scheduling Uplink Map."
		::={whispApsLQILowIntervalEntry 9}

	lqiLowBeaconPercent	OBJECT-TYPE
		SYNTAX		INTEGER (0..100)
		MAX-ACCESS	read-only
		STATUS		current
		DESCRIPTION		
			"Received beacon percentage for one minute interval
                            For PMP this also includes the Scheduling Uplink Map."
		::={whispApsLQILowIntervalEntry 10}

	lqiLowReRegQualityIndex	OBJECT-TYPE
		SYNTAX		INTEGER (0..100)
		MAX-ACCESS	read-only
		STATUS		current
		DESCRIPTION		
			"Reregistration Quality Index for one minute interval in percentage. 100% is best quality"
		::={whispApsLQILowIntervalEntry 11}

	lqiLowReRegCount	OBJECT-TYPE
		SYNTAX		INTEGER (0..100)
		MAX-ACCESS	read-only
		STATUS		current
		DESCRIPTION		
			"Reregistration count for one minute interval"
		::={whispApsLQILowIntervalEntry 12}

	lqiLowLinkESN	OBJECT-TYPE
		SYNTAX		PhysAddress
		MAX-ACCESS	read-only
		STATUS		current
		DESCRIPTION		
			"The link's Electronic Serial Number, which is the device's Ethernet MAC address."
		::={whispApsLQILowIntervalEntry 13}

	lqiLowDownlinkActualAverageEVM	OBJECT-TYPE
		SYNTAX		INTEGER
		MAX-ACCESS	read-only
		STATUS		current
		DESCRIPTION		
			"Downlink Actual average EVM in tenths for one minute interval. eg: -315 is -31.5 dB"
		::={whispApsLQILowIntervalEntry 14}

	lqiLowDownlinkExpectedEVM	OBJECT-TYPE
		SYNTAX		INTEGER
		MAX-ACCESS	read-only
		STATUS		current
		DESCRIPTION		
			"Downlink Expected EVM in tenths eg: -315 is -31.5 dB"
		::={whispApsLQILowIntervalEntry 15}

	lqiLowUplinkActualAverageEVM	OBJECT-TYPE
		SYNTAX		INTEGER
		MAX-ACCESS	read-only
		STATUS		current
		DESCRIPTION		
			"Uplink Actual average EVM in tenths for one minute interval. eg: -315 is -31.5 dB"
		::={whispApsLQILowIntervalEntry 16}

	lqiLowUplinkExpectedEVM	OBJECT-TYPE
		SYNTAX		INTEGER
		MAX-ACCESS	read-only
		STATUS		current
		DESCRIPTION		
			"Uplink Expected EVM in tenths eg: -315 is -31.5 dB"
		::={whispApsLQILowIntervalEntry 17}

	whispApsLQIMidInterval OBJECT-TYPE
		SYNTAX		SEQUENCE OF WhispApsLQIMidIntervalEntry
		MAX-ACCESS	not-accessible
		STATUS		current
		DESCRIPTION
			"Link Quality Indicator five minutes interval table."
		::= {whispApsLQI 2}

	whispApsLQIMidIntervalEntry OBJECT-TYPE
		SYNTAX		WhispApsLQIMidIntervalEntry
		MAX-ACCESS	not-accessible
		STATUS		current
		DESCRIPTION
			"Link Quality Indicator for five minutes interval entry."
		INDEX		{lqiMidLinkLUID}
		::= {whispApsLQIMidInterval 1}

		WhispApsLQIMidIntervalEntry ::= SEQUENCE{
			lqiMidLinkLUID		INTEGER,
			lqiMidLQI		INTEGER,
			lqiMidDownlinkQualityIndex		INTEGER,
			lqiMidDownlinkAverageActualRate		INTEGER,
			lqiMidDownlinkExpectedRate		INTEGER,
			lqiMidUplinkQualityIndex		INTEGER,
			lqiMidUplinkAverageActualRate		INTEGER,
			lqiMidUplinkExpectedRate		INTEGER,
			lqiMidBeaconQualityIndex		INTEGER,
			lqiMidBeaconPercent		INTEGER,
			lqiMidReRegQualityIndex		INTEGER,
			lqiMidReRegCount		INTEGER,
			lqiMidLinkESN		PhysAddress,
			lqiMidDownlinkActualAverageEVM		INTEGER,
			lqiMidDownlinkExpectedEVM		INTEGER,
			lqiMidUplinkActualAverageEVM		INTEGER,
			lqiMidUplinkExpectedEVM	INTEGER
			}

	lqiMidLinkLUID	OBJECT-TYPE
		SYNTAX		INTEGER (2..239)
		MAX-ACCESS	read-only
		STATUS		current
		DESCRIPTION		
			"Logical User Identfication (LUID) number"
		::={whispApsLQIMidIntervalEntry 1}

	lqiMidLQI	OBJECT-TYPE
		SYNTAX		INTEGER (0..100)
		MAX-ACCESS	read-only
		STATUS		current
		DESCRIPTION		
			"Link Quality Indicator for five minutes interval. 
                            Ranges from 0 to 100 where 100 is the best.
                            It's calculated based on receive power, modulation rate, reregistrations and beacon/map percentage."
		::={whispApsLQIMidIntervalEntry 2}

	lqiMidDownlinkQualityIndex	OBJECT-TYPE
		SYNTAX		INTEGER (0..100)
		MAX-ACCESS	read-only
		STATUS		current
		DESCRIPTION		
			"Downlink Quality Index for five minute interval in percentage. 100% is best quality"
		::={whispApsLQIMidIntervalEntry 3}

	lqiMidDownlinkAverageActualRate	OBJECT-TYPE
		SYNTAX		INTEGER (0..80)
		MAX-ACCESS	read-only
		STATUS		current
		DESCRIPTION		
			"Downlink Actual average transmit modulation rate in tenths for five minute interval. eg: 73 is 7.3X"
		::={whispApsLQIMidIntervalEntry 4}

	lqiMidDownlinkExpectedRate	OBJECT-TYPE
		SYNTAX		INTEGER (0..80)
		MAX-ACCESS	read-only
		STATUS		current
		DESCRIPTION		
			"Downlink Expected Rate in tenths for five minute interval. eg: 80 is 8X"
		::={whispApsLQIMidIntervalEntry 5}

	lqiMidUplinkQualityIndex	OBJECT-TYPE
		SYNTAX		INTEGER (0..100)
		MAX-ACCESS	read-only
		STATUS		current
		DESCRIPTION		
			"Uplink Quality Index for five minute interval in percentage. 100% is best quality"
		::={whispApsLQIMidIntervalEntry 6}

	lqiMidUplinkAverageActualRate	OBJECT-TYPE
		SYNTAX		INTEGER (0..80)
		MAX-ACCESS	read-only
		STATUS		current
		DESCRIPTION		
			"Uplink Actual average transmit modulation rate in tenths for five minute interval. eg: 73 is 7.3X"
		::={whispApsLQIMidIntervalEntry 7}

	lqiMidUplinkExpectedRate	OBJECT-TYPE
		SYNTAX		INTEGER (0..80)
		MAX-ACCESS	read-only
		STATUS		current
		DESCRIPTION		
			"Uplink Expected Rate in tenths for five minute interval. eg: 80 is 8X
                            This is based upon the uplink receive power and does not take into account interference."
		::={whispApsLQIMidIntervalEntry 8}

	lqiMidBeaconPercent	OBJECT-TYPE
		SYNTAX		INTEGER (0..100)
		MAX-ACCESS	read-only
		STATUS		current
		DESCRIPTION		
			"Received beacon percent for five minute interval"
		::={whispApsLQIMidIntervalEntry 9}

	lqiMidBeaconQualityIndex	OBJECT-TYPE
		SYNTAX		INTEGER (0..100)
		MAX-ACCESS	read-only
		STATUS		current
		DESCRIPTION		
			"Beacon Quality Index for five minute interval in percentage. 100% is best quality
                            For PMP this also includes the Scheduling Uplink Map."
		::={whispApsLQIMidIntervalEntry 10}

	lqiMidReRegCount	OBJECT-TYPE
		SYNTAX		INTEGER (0..100)
		MAX-ACCESS	read-only
		STATUS		current
		DESCRIPTION		
			"Reregistration count for five minute interval"
		::={whispApsLQIMidIntervalEntry 11}

	lqiMidReRegQualityIndex	OBJECT-TYPE
		SYNTAX		INTEGER (0..100)
		MAX-ACCESS	read-only
		STATUS		current
		DESCRIPTION		
			"Reregistration Quality Index for five minute interval in percentage. 100% is best quality"
		::={whispApsLQIMidIntervalEntry 12}

	lqiMidLinkESN	OBJECT-TYPE
		SYNTAX		PhysAddress
		MAX-ACCESS	read-only
		STATUS		current
		DESCRIPTION		
			"The link's Electronic Serial Number, which is the device's Ethernet MAC address."
		::={whispApsLQIMidIntervalEntry 13}

	lqiMidDownlinkActualAverageEVM	OBJECT-TYPE
		SYNTAX		INTEGER
		MAX-ACCESS	read-only
		STATUS		current
		DESCRIPTION		
			"Downlink Actual average EVM in tenths for five minutes interval. eg: -315 is -31.5 dB"
		::={whispApsLQIMidIntervalEntry 14}

	lqiMidDownlinkExpectedEVM	OBJECT-TYPE
		SYNTAX		INTEGER
		MAX-ACCESS	read-only
		STATUS		current
		DESCRIPTION		
			"Downlink Expected EVM in tenths eg: -315 is -31.5 dB"
		::={whispApsLQIMidIntervalEntry 15}

	lqiMidUplinkActualAverageEVM	OBJECT-TYPE
		SYNTAX		INTEGER
		MAX-ACCESS	read-only
		STATUS		current
		DESCRIPTION		
			"Uplink Actual average EVM in tenths for five minutes interval. eg: -315 is -31.5 dB"
		::={whispApsLQIMidIntervalEntry 16}

	lqiMidUplinkExpectedEVM	OBJECT-TYPE
		SYNTAX		INTEGER
		MAX-ACCESS	read-only
		STATUS		current
		DESCRIPTION		
			"Uplink Expected EVM in tenths eg: -315 is -31.5 dB"
		::={whispApsLQIMidIntervalEntry 17}

	whispApsLQIHighInterval OBJECT-TYPE
		SYNTAX		SEQUENCE OF WhispApsLQIHighIntervalEntry
		MAX-ACCESS	not-accessible
		STATUS		current
		DESCRIPTION
			"Link Quality Indicator fifteen minutes interval table."
		::= {whispApsLQI 3}

	whispApsLQIHighIntervalEntry OBJECT-TYPE
		SYNTAX		WhispApsLQIHighIntervalEntry
		MAX-ACCESS	not-accessible
		STATUS		current
		DESCRIPTION
			"Link Quality Indicator for fifteen minutes interval entry."
		INDEX		{lqiHighLinkLUID}
		::= {whispApsLQIHighInterval 1}

		WhispApsLQIHighIntervalEntry ::= SEQUENCE{
			lqiHighLinkLUID		INTEGER,
			lqiHighLQI		INTEGER,
			lqiHighDownlinkQualityIndex		INTEGER,
			lqiHighDownlinkAverageActualRate		INTEGER,
			lqiHighDownlinkExpectedRate		INTEGER,
			lqiHighUplinkQualityIndex		INTEGER,
			lqiHighUplinkAverageActualRate		INTEGER,
			lqiHighUplinkExpectedRate		INTEGER,
			lqiHighBeaconQualityIndex		INTEGER,
			lqiHighBeaconPercent		INTEGER,
			lqiHighReRegQualityIndex		INTEGER,
			lqiHighReRegCount		INTEGER,
			lqiHighLinkESN		PhysAddress,
			lqiHighDownlinkActualAverageEVM		INTEGER,
			lqiHighDownlinkExpectedEVM		INTEGER,
			lqiHighUplinkActualAverageEVM		INTEGER,
			lqiHighUplinkExpectedEVM	INTEGER
			}

	lqiHighLinkLUID	OBJECT-TYPE
		SYNTAX		INTEGER (2..239)
		MAX-ACCESS	read-only
		STATUS		current
		DESCRIPTION		
			"Logical User Identfication (LUID) number"
		::={whispApsLQIHighIntervalEntry 1}

	lqiHighLQI	OBJECT-TYPE
		SYNTAX		INTEGER (0..100)
		MAX-ACCESS	read-only
		STATUS		current
		DESCRIPTION		
			"Link Quality Indicator for fifteen minutes interval. 
                            Ranges from 0 to 100 where 100 is the best.
                            It's calculated based on receive power, modulation rate, reregistrations and beacon/map percentage."
		::={whispApsLQIHighIntervalEntry 2}

	lqiHighDownlinkQualityIndex	OBJECT-TYPE
		SYNTAX		INTEGER (0..100)
		MAX-ACCESS	read-only
		STATUS		current
		DESCRIPTION		
			"Downlink Quality Index for fifteen minute interval in percentage. 100% is best quality"
		::={whispApsLQIHighIntervalEntry 3}

	lqiHighDownlinkAverageActualRate	OBJECT-TYPE
		SYNTAX		INTEGER (0..80)
		MAX-ACCESS	read-only
		STATUS		current
		DESCRIPTION		
			"Downlink Actual average transmit modulation rate in tenths for fifteen minute interval. eg: 73 is 7.3X"
		::={whispApsLQIHighIntervalEntry 4}

	lqiHighDownlinkExpectedRate	OBJECT-TYPE
		SYNTAX		INTEGER (0..80)
		MAX-ACCESS	read-only
		STATUS		current
		DESCRIPTION		
			"Downlink Expected Rate in tenths for fifteen minute interval. eg: 80 is 8X
                            This is based upon the uplink receive power and does not take into account interference."
		::={whispApsLQIHighIntervalEntry 5}

	lqiHighUplinkQualityIndex	OBJECT-TYPE
		SYNTAX		INTEGER (0..100)
		MAX-ACCESS	read-only
		STATUS		current
		DESCRIPTION		
			"Uplink Quality Index for fifteen minute interval in percentage. 100% is best quality"
		::={whispApsLQIHighIntervalEntry 6}

	lqiHighUplinkAverageActualRate	OBJECT-TYPE
		SYNTAX		INTEGER (0..80)
		MAX-ACCESS	read-only
		STATUS		current
		DESCRIPTION		
			"Uplink Actual average transmit modulation rate in tenths for fifteen minute interval. eg: 73 is 7.3X"
		::={whispApsLQIHighIntervalEntry 7}

	lqiHighUplinkExpectedRate	OBJECT-TYPE
		SYNTAX		INTEGER (0..80)
		MAX-ACCESS	read-only
		STATUS		current
		DESCRIPTION		
			"Uplink Expected Rate in tenths for fifteen minute interval. eg: 80 is 8X
                            This is based upon the uplink receive power and does not take into account interference."
		::={whispApsLQIHighIntervalEntry 8}

	lqiHighBeaconQualityIndex	OBJECT-TYPE
		SYNTAX		INTEGER (0..100)
		MAX-ACCESS	read-only
		STATUS		current
		DESCRIPTION		
			"Beacon Quality Index for fifteen minute interval in percentage. 100% is best quality
                            For PMP this also includes the Scheduling Uplink Map."
		::={whispApsLQIHighIntervalEntry 9}

	lqiHighBeaconPercent	OBJECT-TYPE
		SYNTAX		INTEGER (0..100)
		MAX-ACCESS	read-only
		STATUS		current
		DESCRIPTION		
			"Received beacon percent for fifteen minute interval
                            For PMP this also includes the Scheduling Uplink Map."
		::={whispApsLQIHighIntervalEntry 10}

	lqiHighReRegQualityIndex	OBJECT-TYPE
		SYNTAX		INTEGER (0..100)
		MAX-ACCESS	read-only
		STATUS		current
		DESCRIPTION		
			"Reregistration Quality Index for fifteen minute interval in percentage. 100% is best quality"
		::={whispApsLQIHighIntervalEntry 11}

	lqiHighReRegCount	OBJECT-TYPE
		SYNTAX		INTEGER (0..100)
		MAX-ACCESS	read-only
		STATUS		current
		DESCRIPTION		
			"Reregistration count for fifteen minute interval"
		::={whispApsLQIHighIntervalEntry 12}

	lqiHighLinkESN	OBJECT-TYPE
		SYNTAX		PhysAddress
		MAX-ACCESS	read-only
		STATUS		current
		DESCRIPTION		
			"The link's Electronic Serial Number, which is the device's Ethernet MAC address."
		::={whispApsLQIHighIntervalEntry 13}

	lqiHighDownlinkActualAverageEVM	OBJECT-TYPE
		SYNTAX		INTEGER
		MAX-ACCESS	read-only
		STATUS		current
		DESCRIPTION		
			"Downlink Actual average EVM in tenths for fifteen minute interval. eg: -315 is -31.5 dB"
		::={whispApsLQIHighIntervalEntry 14}

	lqiHighDownlinkExpectedEVM	OBJECT-TYPE
		SYNTAX		INTEGER
		MAX-ACCESS	read-only
		STATUS		current
		DESCRIPTION		
			"Downlink Expected EVM in tenths eg: -315 is -31.5 dB"
		::={whispApsLQIHighIntervalEntry 15}

	lqiHighUplinkActualAverageEVM	OBJECT-TYPE
		SYNTAX		INTEGER
		MAX-ACCESS	read-only
		STATUS		current
		DESCRIPTION		
			"Uplink Actual average EVM in tenths for fifteen minute interval. eg: -315 is -31.5 dB"
		::={whispApsLQIHighIntervalEntry 16}

	lqiHighUplinkExpectedEVM	OBJECT-TYPE
		SYNTAX		INTEGER
		MAX-ACCESS	read-only
		STATUS		current
		DESCRIPTION		
			"Uplink Expected EVM in tenths eg: -315 is -31.5 dB"
		::={whispApsLQIHighIntervalEntry 17}

	cbrsEnable	OBJECT-TYPE
		SYNTAX		INTEGER {
					disable(0),
					enable(1)}
		MAX-ACCESS	read-write
		STATUS		current
		DESCRIPTION		
			"Enables Citizens Broadband Radio Service (CBRS) for FCC 3 GHz shared spectrum."
		::={whispApsCbrsConfig 1}

	cbsdUserID	OBJECT-TYPE
		SYNTAX		DisplayString
		MAX-ACCESS	read-only
		STATUS		current
		DESCRIPTION		
			"User ID for registering the Citizens Broadband Radio Service Device (CBSD) with Spectrum Access System (SAS). This will be used for registering AP and all associated SMs. This value will be always set by cnMaestro so it is a read only data."
		::={whispApsCbrsConfig 2}

	apCbsdSelectRelinquishment	OBJECT-TYPE
		SYNTAX		INTEGER {
					disable(0),
					enable(1)}
		MAX-ACCESS	read-write
		STATUS		current
		DESCRIPTION		
			"Enable to add AP CBSD for spectrum relinquishment and disable to remove it from the selection"
		::={whispApsCbrsConfig 4}

	apCbsdSelectDeregistration	OBJECT-TYPE
		SYNTAX		INTEGER {
					disable(0),
					enable(1)}
		MAX-ACCESS	read-write
		STATUS		current
		DESCRIPTION		
			"Enable to add AP CBSD for deregistration and disable to remove it from the selection"
		::={whispApsCbrsConfig 5}

	performRelinquishDeregister	OBJECT-TYPE
		SYNTAX		INTEGER {
					performRelinquishDeregister(1)}
		MAX-ACCESS	read-write
		STATUS		current
		DESCRIPTION		
			"Relinquish or Deregister CBSDs selected in the table"
		::={whispApsCbrsConfig 6}

	cbsdCoexSectorId	OBJECT-TYPE
		SYNTAX		DisplayString
		MAX-ACCESS	read-write
		STATUS		current
		DESCRIPTION		
			"Unique ID for identifying CBSDs in the sector. 
                            This can not be empty and is defaulted to the AP's MAC address.
                            Unintended Coexistence Sector ID conflicts can cause other CBSDs share overlapping spectrum and cause interference.
                            Do not change this unless really required."
		::={whispApsCbrsConfig 7}

	cbsdCoexSpectrumReuseId	OBJECT-TYPE
		SYNTAX		DisplayString
		MAX-ACCESS	read-write
		STATUS		current
		DESCRIPTION		
			"Sectors in which APs intend to use the same frequency, should configure the same coexistence spectrum reuse ID.
                            Spectrum Access System (SAS) will allow the sectors to use the same frequency if this matches.
                            This can be left empty if there are no nearby sectors sharing the same frequency.
                            Spectrum reuse ID should be unique for the required group of sectors. Unintended spectrum reuse ID conflicts can cause unknown CBSDs share overlapping spectrum and cause interference."
		::={whispApsCbrsConfig 8}

	cbrsMultiGrantEnable	OBJECT-TYPE
		SYNTAX		INTEGER {
					disable(0),
					enable(1)}
		MAX-ACCESS	read-write
		STATUS		obsolete
		DESCRIPTION		
			"Enables fetching multiple grants for wide channels. This option is obsolete from 21.0."
		::={whispApsCbrsConfig 9}

	cbrsRebootRadio	OBJECT-TYPE
		SYNTAX		INTEGER {
					disable(0),
					enable(1)}
		MAX-ACCESS	read-write
		STATUS		current
		DESCRIPTION		
			"Reboot the radio if required for applying channel bandwidth changes based on CBRS channel availibility. Applicable for 450m radios only."
		::={whispApsCbrsConfig 10}

	cbrsChannelHunt	OBJECT-TYPE
		SYNTAX		INTEGER {
					disable(0),
					enable(1)}
		MAX-ACCESS	read-write
		STATUS		current
		DESCRIPTION		
			"Enable search of available channels when no grants are available on the transmitting frequency or a multi grant channel gets suspended or terminated. 
                            This will also automatically select channels, acquire grant and transmit on the granted channels."
		::={whispApsCbrsConfig 11}

	cbsdCoexPrependUserId	OBJECT-TYPE
		SYNTAX		INTEGER {
					disable(0),
					enable(1)}
		MAX-ACCESS	read-write
		STATUS		current
		DESCRIPTION		
			"Enable inclusion of User ID within the Sector ID and Spectrum Reuse ID parameters to make the Coexistence parameters unique within the SAS."
		::={whispApsCbrsConfig 12}

	cbrsChannelChange	OBJECT-TYPE
		SYNTAX		INTEGER {
					disable(0),
					enable(1)}
		MAX-ACCESS	read-write
		STATUS		current
		DESCRIPTION		
			"Enables AP channel change to maintain connectivity to all the SMs, if one or more SMs in a sector are affected by a suspension or a termination.
                            In case of PTP, this option enables BHM channel change to maintain connectivity to the BHS, if only BHS is affected by a suspension or termination and not the BHM."
		::={whispApsCbrsConfig 13}

	cbrsChannelChangeThreshold	OBJECT-TYPE
		SYNTAX		INTEGER (1..99)
		MAX-ACCESS	read-write
		STATUS		current
		DESCRIPTION		
			"Percentage of affected SMs in order to change channel. 
                            A value of 20% indicates that if minimum 20% of SMs are affected by suspension/termination, 
                            then AP channel can be changed to maintain connectivity to all or most of the SMs.
                            Default is 10%."
		::={whispApsCbrsConfig 14}

	cbrsOriginalChannelRestoreTime	OBJECT-TYPE
		SYNTAX		INTEGER
		MAX-ACCESS	read-write
		STATUS		current
		DESCRIPTION		
			"After channel change due to suspension, AP can restore the original channel only after the configured time in minutes.
                            Default is 15 minutes."
		::={whispApsCbrsConfig 15}

	apCbsdStatus	OBJECT-TYPE
		SYNTAX		DisplayString
		MAX-ACCESS	read-only
		STATUS		current
		DESCRIPTION		
			"Current state of the Citizens Broadband Radio Service (CBRS) device."
		::={whispApsCbrsApStatus 1}

	apCbsdStateDuration	OBJECT-TYPE
		SYNTAX		DisplayString
		MAX-ACCESS	read-only
		STATUS		current
		DESCRIPTION		
			"Time elapsed in the current state on the AP."
		::={whispApsCbrsApStatus 2}

	apCbsdLastHeartbeatTime	OBJECT-TYPE
		SYNTAX		DisplayString
		MAX-ACCESS	read-only
		STATUS		current
		DESCRIPTION		
			"Expiry time of the ongoing CBRS request on the AP."
		::={whispApsCbrsApStatus 3}

	apCbsdHeartbeatDuration	OBJECT-TYPE
		SYNTAX		Unsigned32
		UNITS		"seconds"
		MAX-ACCESS	read-only
		STATUS		current
		DESCRIPTION		
			"Heartbeat Interval returned by the Spectrum Access System (SAS) for the AP."
		::={whispApsCbrsApStatus 4}

	apCbsdGrantExpiry	OBJECT-TYPE
		SYNTAX		DisplayString
		MAX-ACCESS	read-only
		STATUS		current
		DESCRIPTION		
			"Expiry time of the grant acquired from the Spectrum Access System (SAS) for the AP."
		::={whispApsCbrsApStatus 5}

	apCbsdTxExpiry	OBJECT-TYPE
		SYNTAX		DisplayString
		MAX-ACCESS	read-only
		STATUS		current
		DESCRIPTION		
			"Transmit expiry time specified by the Spectrum Access System (SAS) for the AP."
		::={whispApsCbrsApStatus 6}

	apCbsdChannelType	OBJECT-TYPE
		SYNTAX		DisplayString
		MAX-ACCESS	read-only
		STATUS		current
		DESCRIPTION		
			"Type of channel allocation done by the Spectrum Access System (SAS) for the AP."
		::={whispApsCbrsApStatus 7}

	apCbsdEirpRequested	OBJECT-TYPE
		SYNTAX		INTEGER
		UNITS		"dBm"
		MAX-ACCESS	read-only
		STATUS		current
		DESCRIPTION		
			"EIRP requested by the AP."
		::={whispApsCbrsApStatus 8}

	apCbsdEirpGranted	OBJECT-TYPE
		SYNTAX		INTEGER
		UNITS		"dBm"
		MAX-ACCESS	read-only
		STATUS		current
		DESCRIPTION		
			"EIRP granted by the Spectrum Access System (SAS) for the AP."
		::={whispApsCbrsApStatus 9}

	apCbsdHeartbeatTotal	OBJECT-TYPE
		SYNTAX		Counter32
		MAX-ACCESS	read-only
		STATUS		current
		DESCRIPTION		
			"Total number of heartbeat requests sent by the AP CBSD to SAS."
		::={whispApsCbrsApStatus 10}

	apCbsdHeartbeatMissed	OBJECT-TYPE
		SYNTAX		Counter32
		MAX-ACCESS	read-only
		STATUS		current
		DESCRIPTION		
			"Number of heartbeat requests which didn't receive a response from the SAS."
		::={whispApsCbrsApStatus 11}

	apCbsdHeartbeatFailed	OBJECT-TYPE
		SYNTAX		Counter32
		MAX-ACCESS	read-only
		STATUS		current
		DESCRIPTION		
			"Number of heartbeat requests which received a failure response for the AP CBSD from the SAS."
		::={whispApsCbrsApStatus 12}

	apCbsdHeartbeatFailedSuspend	OBJECT-TYPE
		SYNTAX		Counter32
		MAX-ACCESS	read-only
		STATUS		current
		DESCRIPTION		
			"Number of heartbeat requests which received a grant suspend for the AP CBSD from the SAS."
		::={whispApsCbrsApStatus 13}

	apCbsdHeartbeatFailedTerminate	OBJECT-TYPE
		SYNTAX		Counter32
		MAX-ACCESS	read-only
		STATUS		current
		DESCRIPTION		
			"Number of heartbeat requests which received a grant terminate response for the AP CBSD from the SAS."
		::={whispApsCbrsApStatus 14}

	apCbsdHeartbeatFailedUnsync	OBJECT-TYPE
		SYNTAX		Counter32
		MAX-ACCESS	read-only
		STATUS		current
		DESCRIPTION		
			"Number of heartbeat requests which received a grant out-of-sync failure response for the AP CBSD from the SAS."
		::={whispApsCbrsApStatus 15}

	apCbsdId	OBJECT-TYPE
		SYNTAX		DisplayString
		MAX-ACCESS	read-only
		STATUS		current
		DESCRIPTION		
			"Unique identifier assigned by the Spectrum Access System (SAS) for AP Citizens Broadband Radio Service Device(CBSD)."
		::={whispApsCbrsApStatus 16}

	apCbsdSasEirpRequested	OBJECT-TYPE
		SYNTAX		DisplayString
		UNITS		"dBm"
		MAX-ACCESS	read-only
		STATUS		current
		DESCRIPTION		
			"EIRP requested by the AP in decimal."
		::={whispApsCbrsApStatus 17}

	apCbsdSasEirpGranted	OBJECT-TYPE
		SYNTAX		DisplayString
		UNITS		"dBm"
		MAX-ACCESS	read-only
		STATUS		current
		DESCRIPTION		
			"EIRP granted by the Spectrum Access System (SAS) for the AP in decimal."
		::={whispApsCbrsApStatus 18}

	apCbsdNumGrants	OBJECT-TYPE
		SYNTAX		INTEGER
		MAX-ACCESS	read-only
		STATUS		current
		DESCRIPTION		
			"Number of valid grants in CBSD"
		::={whispApsCbrsApStatus 19}

	apCbsdMultiGrantMode	OBJECT-TYPE
		SYNTAX		INTEGER {
					false(0),
					true(1)}
		MAX-ACCESS	read-only
		STATUS		current
		DESCRIPTION		
			"Specifies if the radio is running in multi grant mode."
		::={whispApsCbrsApStatus 20}

	bwReductionImpactedSmThreshold	OBJECT-TYPE
		SYNTAX		Counter32
		MAX-ACCESS	read-only
		STATUS		current
		DESCRIPTION		
			"Channel change will be triggered to connect maximum number of SMs when suspended/terminated SM count exceeds/matches this percentage.
                            PMP Only."
		::={whispApsCbrsApStatus 21}

	apCbsdEirpInUse	OBJECT-TYPE
		SYNTAX		INTEGER
		UNITS		"dBm"
		MAX-ACCESS	read-only
		STATUS		current
		DESCRIPTION		
			"EIRP in use by the AP CBSD."
		::={whispApsCbrsApStatus 22}

	apCbsdSasEirpInUse	OBJECT-TYPE
		SYNTAX		DisplayString
		UNITS		"dBm"
		MAX-ACCESS	read-only
		STATUS		current
		DESCRIPTION		
			"EIRP in use by the AP CBSD in decimal."
		::={whispApsCbrsApStatus 23}

	whispApsCbrsStatus OBJECT-TYPE
		SYNTAX		SEQUENCE OF WhispApsCbrsStatusEntry
		MAX-ACCESS	not-accessible
		STATUS		current
		DESCRIPTION
			"Table indicating status of Citizens Broadband Radio Service (CBRS) devices."
		::= {whispApsCbrs 3}

	whispApsCbrsStatusEntry OBJECT-TYPE
		SYNTAX		WhispApsCbrsStatusEntry
		MAX-ACCESS	not-accessible
		STATUS		current
		DESCRIPTION
			"Citizens Broadband Radio Service (CBRS) device status entry."
		INDEX		{cbsdLuid}
		::= {whispApsCbrsStatus 1}

		WhispApsCbrsStatusEntry ::= SEQUENCE{
			cbsdLuid		INTEGER,
			cbsdStatus		DisplayString,
			cbsdStateDuration		DisplayString,
			cbsdLastHeartbeatTime		DisplayString,
			cbsdHeartbeatInterval		INTEGER,
			cbsdGrantExpiry		DisplayString,
			cbsdTxExpiry		DisplayString,
			cbsdChannelType		DisplayString,
			cbsdEirpRequested		INTEGER,
			cbsdEirpGranted		INTEGER,
			cbsdNumGrants		INTEGER,
			cbsdSasEirpRequested		DisplayString,
			cbsdSasEirpGranted		DisplayString,
			cbsdHeartbeatTotal		Counter32,
			cbsdHeartbeatMissed		Counter32,
			cbsdHeartbeatFailed		Counter32,
			cbsdHeartbeatSkipped		Counter32,
			cbsdHeartbeatRelativeBulk		Counter32,
			cbsdHeartbeatStandalone		Counter32,
			cbsdHeartbeatFailedSuspend		Counter32,
			cbsdHeartbeatFailedTerminate		Counter32,
			cbsdHeartbeatFailedUnsync		Counter32,
			cbsdId		DisplayString,
			cbsdMacAddress		DisplayString,
			cbsdMultiGrantMode		INTEGER,
			cbsdEirpInUse		INTEGER,
			cbsdSasEirpInUse	DisplayString
			}

	cbsdLuid	OBJECT-TYPE
		SYNTAX		INTEGER (2..239)
		MAX-ACCESS	read-only
		STATUS		current
		DESCRIPTION		
			"Logical User Identification (LUID) number for the Citizens Broadband Radio Service (CBRS) device."
		::={whispApsCbrsStatusEntry 1}

	cbsdStatus	OBJECT-TYPE
		SYNTAX		DisplayString
		MAX-ACCESS	read-only
		STATUS		current
		DESCRIPTION		
			"Current state of the Citizens Broadband Radio Service (CBRS) device."
		::={whispApsCbrsStatusEntry 2}

	cbsdStateDuration	OBJECT-TYPE
		SYNTAX		DisplayString
		MAX-ACCESS	read-only
		STATUS		current
		DESCRIPTION		
			"Time elapsed in the current state."
		::={whispApsCbrsStatusEntry 3}

	cbsdLastHeartbeatTime	OBJECT-TYPE
		SYNTAX		DisplayString
		MAX-ACCESS	read-only
		STATUS		current
		DESCRIPTION		
			"Expiry time of the ongoing CBRS request."
		::={whispApsCbrsStatusEntry 4}

	cbsdHeartbeatInterval	OBJECT-TYPE
		SYNTAX		INTEGER
		UNITS		"seconds"
		MAX-ACCESS	read-only
		STATUS		current
		DESCRIPTION		
			"Heartbeat Interval returned by the Spectrum Access System (SAS)."
		::={whispApsCbrsStatusEntry 5}

	cbsdGrantExpiry	OBJECT-TYPE
		SYNTAX		DisplayString
		MAX-ACCESS	read-only
		STATUS		current
		DESCRIPTION		
			"Expiry time of the grant acquired from the Spectrum Access System (SAS)."
		::={whispApsCbrsStatusEntry 6}

	cbsdTxExpiry	OBJECT-TYPE
		SYNTAX		DisplayString
		MAX-ACCESS	read-only
		STATUS		current
		DESCRIPTION		
			"Transmit expiry time specified by the Spectrum Access System (SAS)."
		::={whispApsCbrsStatusEntry 7}

	cbsdChannelType	OBJECT-TYPE
		SYNTAX		DisplayString
		MAX-ACCESS	read-only
		STATUS		current
		DESCRIPTION		
			"Type of channel allocation done by the Spectrum Access System (SAS)."
		::={whispApsCbrsStatusEntry 8}

	cbsdEirpRequested	OBJECT-TYPE
		SYNTAX		INTEGER
		UNITS		"dBm"
		MAX-ACCESS	read-only
		STATUS		current
		DESCRIPTION		
			"EIRP requested by the CBRS device."
		::={whispApsCbrsStatusEntry 9}

	cbsdEirpGranted	OBJECT-TYPE
		SYNTAX		INTEGER
		UNITS		"dBm"
		MAX-ACCESS	read-only
		STATUS		current
		DESCRIPTION		
			"EIRP granted by the Spectrum Access System (SAS)."
		::={whispApsCbrsStatusEntry 10}

	cbsdHeartbeatTotal	OBJECT-TYPE
		SYNTAX		Counter32
		MAX-ACCESS	read-only
		STATUS		current
		DESCRIPTION		
			"Total number of heartbeat requests sent by the CBSD to SAS."
		::={whispApsCbrsStatusEntry 11}

	cbsdHeartbeatMissed	OBJECT-TYPE
		SYNTAX		Counter32
		MAX-ACCESS	read-only
		STATUS		current
		DESCRIPTION		
			"Number of heartbeat requests which didn't receive a response from the SAS."
		::={whispApsCbrsStatusEntry 12}

	cbsdHeartbeatFailed	OBJECT-TYPE
		SYNTAX		Counter32
		MAX-ACCESS	read-only
		STATUS		current
		DESCRIPTION		
			"Number of heartbeat requests which received a failure response from the SAS."
		::={whispApsCbrsStatusEntry 13}

	cbsdHeartbeatRelativeBulk	OBJECT-TYPE
		SYNTAX		Counter32
		MAX-ACCESS	read-only
		STATUS		current
		DESCRIPTION		
			"Total number of bulk heartbeat requests sent by AP since the SM established its first session."
		::={whispApsCbrsStatusEntry 14}

	cbsdHeartbeatSkipped	OBJECT-TYPE
		SYNTAX		Counter32
		MAX-ACCESS	read-only
		STATUS		current
		DESCRIPTION		
			"Number of bulk heartbeat requests sent by AP which didn't include an entry for the SM because it was not connected to the AP."
		::={whispApsCbrsStatusEntry 15}

	cbsdHeartbeatFailedSuspend	OBJECT-TYPE
		SYNTAX		Counter32
		MAX-ACCESS	read-only
		STATUS		current
		DESCRIPTION		
			"Number of heartbeat requests which received a grant suspend failure response from the SAS."
		::={whispApsCbrsStatusEntry 16}

	cbsdHeartbeatFailedTerminate	OBJECT-TYPE
		SYNTAX		Counter32
		MAX-ACCESS	read-only
		STATUS		current
		DESCRIPTION		
			"Number of heartbeat requests which received a grant terminate failure response from the SAS."
		::={whispApsCbrsStatusEntry 17}

	cbsdHeartbeatFailedUnsync	OBJECT-TYPE
		SYNTAX		Counter32
		MAX-ACCESS	read-only
		STATUS		current
		DESCRIPTION		
			"Number of heartbeat requests which received a grant state out-of-sync failure response from the SAS."
		::={whispApsCbrsStatusEntry 18}

	cbsdId	OBJECT-TYPE
		SYNTAX		DisplayString
		MAX-ACCESS	read-only
		STATUS		current
		DESCRIPTION		
			"Unique identifier assigned by the Spectrum Access System (SAS) for Citizens Broadband Radio Service Device(CBSD)."
		::={whispApsCbrsStatusEntry 19}

	cbsdMacAddress	OBJECT-TYPE
		SYNTAX		DisplayString
		MAX-ACCESS	read-only
		STATUS		current
		DESCRIPTION		
			"MAC address of Citizens Broadband Radio Service Device(CBSD)"
		::={whispApsCbrsStatusEntry 20}

	cbsdHeartbeatStandalone	OBJECT-TYPE
		SYNTAX		Counter32
		MAX-ACCESS	read-only
		STATUS		current
		DESCRIPTION		
			"Number of heartbeat requests from the CBSD which were not part of a bulk heartbeat request."
		::={whispApsCbrsStatusEntry 21}

	cbsdSasEirpRequested	OBJECT-TYPE
		SYNTAX		DisplayString
		UNITS		"dBm"
		MAX-ACCESS	read-only
		STATUS		current
		DESCRIPTION		
			"EIRP requested by the CBRS device in decimal."
		::={whispApsCbrsStatusEntry 22}

	cbsdSasEirpGranted	OBJECT-TYPE
		SYNTAX		DisplayString
		UNITS		"dBm"
		MAX-ACCESS	read-only
		STATUS		current
		DESCRIPTION		
			"EIRP granted by the Spectrum Access System (SAS) in decimal."
		::={whispApsCbrsStatusEntry 23}

	cbsdNumGrants	OBJECT-TYPE
		SYNTAX		INTEGER
		MAX-ACCESS	read-only
		STATUS		current
		DESCRIPTION		
			"Number of valid grants in CBSD"
		::={whispApsCbrsStatusEntry 24}

	cbsdMultiGrantMode	OBJECT-TYPE
		SYNTAX		INTEGER {
					false(0),
					true(1)}
		MAX-ACCESS	read-only
		STATUS		current
		DESCRIPTION		
			"Specifies if the CBSD is running in multi grant mode."
		::={whispApsCbrsStatusEntry 25}

	cbsdEirpInUse	OBJECT-TYPE
		SYNTAX		INTEGER
		UNITS		"dBm"
		MAX-ACCESS	read-only
		STATUS		current
		DESCRIPTION		
			"EIRP in use by the CBRS device."
		::={whispApsCbrsStatusEntry 26}

	cbsdSasEirpInUse	OBJECT-TYPE
		SYNTAX		DisplayString
		UNITS		"dBm"
		MAX-ACCESS	read-only
		STATUS		current
		DESCRIPTION		
			"EIRP in use by the CBRS device in decimal."
		::={whispApsCbrsStatusEntry 27}

	whispApsCbrsSMsConfigTable OBJECT-TYPE
		SYNTAX		SEQUENCE OF WhispApsCbrsSMsConfigEntry
		MAX-ACCESS	not-accessible
		STATUS		current
		DESCRIPTION
			"CBSD SMs configuration table"
		::= {whispApsCbrs 4}

	whispApsCbrsSMsConfigEntry OBJECT-TYPE
		SYNTAX		WhispApsCbrsSMsConfigEntry
		MAX-ACCESS	not-accessible
		STATUS		current
		DESCRIPTION
			"SM CBSD specific configuration table entry"
		INDEX		{cbsdLuidIndex}
		::= {whispApsCbrsSMsConfigTable 1}

		WhispApsCbrsSMsConfigEntry ::= SEQUENCE{
			cbsdLuidIndex		INTEGER,
			cbsdSelectRelinquishment		INTEGER,
			cbsdSelectDeregistration	INTEGER
			}

	cbsdLuidIndex	OBJECT-TYPE
		SYNTAX		INTEGER (2..253)
		MAX-ACCESS	read-only
		STATUS		current
		DESCRIPTION		
			"Logical User Identification (LUID) number for the Citizens Broadband Radio Service (CBRS) device."
		::={whispApsCbrsSMsConfigEntry 1}

	cbsdSelectRelinquishment	OBJECT-TYPE
		SYNTAX		INTEGER {
					disable(0),
					enable(1)}
		MAX-ACCESS	read-write
		STATUS		current
		DESCRIPTION		
			"Enable to add CBSD for spectrum relinquishment and disable to remove it from the selection"
		::={whispApsCbrsSMsConfigEntry 2}

	cbsdSelectDeregistration	OBJECT-TYPE
		SYNTAX		INTEGER {
					disable(0),
					enable(1)}
		MAX-ACCESS	read-write
		STATUS		current
		DESCRIPTION		
			"Enable to add CBSD for deregistration and disable to remove it from the selection"
		::={whispApsCbrsSMsConfigEntry 3}

	whispApsCbrsApGrant OBJECT-TYPE
		SYNTAX		SEQUENCE OF WhispApsCbrsApGrantEntry
		MAX-ACCESS	not-accessible
		STATUS		current
		DESCRIPTION
			"Table indicating status of grants in Citizens Broadband Radio Service (CBRS) device."
		::= {whispApsCbrs 5}

	whispApsCbrsApGrantEntry OBJECT-TYPE
		SYNTAX		WhispApsCbrsApGrantEntry
		MAX-ACCESS	not-accessible
		STATUS		current
		DESCRIPTION
			"Citizens Broadband Radio Service (CBRS) device grant entry."
		INDEX		{apGrantLowFreq}
		::= {whispApsCbrsApGrant 1}

		WhispApsCbrsApGrantEntry ::= SEQUENCE{
			apGrantLowFreq		INTEGER,
			apGrantHighFreq		INTEGER,
			apGrantId		DisplayString,
			apGrantState		DisplayString,
			apGrantStateDuration		DisplayString,
			apGrantLastHeartbeatTime		DisplayString,
			apGrantHeartbeatInterval		INTEGER,
			apGrantExpiry		DisplayString,
			apGrantTxExpiry		DisplayString,
			apGrantChannelType		DisplayString,
			apGrantEirp		DisplayString,
			apGrantHeartbeatTotal		Counter32,
			apGrantHeartbeatMissed		Counter32,
			apGrantHeartbeatFailed		Counter32,
			apGrantHeartbeatFailedSuspend		Counter32,
			apGrantHeartbeatFailedTerminate		Counter32,
			apGrantHeartbeatFailedUnsync	Counter32
			}

	apGrantLowFreq	OBJECT-TYPE
		SYNTAX		INTEGER (3550000..3700000)
		MAX-ACCESS	read-only
		STATUS		current
		DESCRIPTION		
			"The lowest frequency of the grant frequency range in kHz."
		::={whispApsCbrsApGrantEntry 1}

	apGrantHighFreq	OBJECT-TYPE
		SYNTAX		INTEGER (3550000..3700000)
		MAX-ACCESS	read-only
		STATUS		current
		DESCRIPTION		
			"The highest frequency of the grant frequency range in kHz."
		::={whispApsCbrsApGrantEntry 2}

	apGrantId	OBJECT-TYPE
		SYNTAX		DisplayString
		MAX-ACCESS	read-only
		STATUS		current
		DESCRIPTION		
			"The unique ID of the grant from the Spectrum Access System (SAS)."
		::={whispApsCbrsApGrantEntry 3}

	apGrantState	OBJECT-TYPE
		SYNTAX		DisplayString
		MAX-ACCESS	read-only
		STATUS		current
		DESCRIPTION		
			"Current state of the grant in Citizens Broadband Radio Service (CBRS) device."
		::={whispApsCbrsApGrantEntry 4}

	apGrantStateDuration	OBJECT-TYPE
		SYNTAX		DisplayString
		MAX-ACCESS	read-only
		STATUS		current
		DESCRIPTION		
			"Time elapsed in the current state of grant."
		::={whispApsCbrsApGrantEntry 5}

	apGrantLastHeartbeatTime	OBJECT-TYPE
		SYNTAX		DisplayString
		MAX-ACCESS	read-only
		STATUS		current
		DESCRIPTION		
			"Time when the last heartbeat request was sent."
		::={whispApsCbrsApGrantEntry 6}

	apGrantHeartbeatInterval	OBJECT-TYPE
		SYNTAX		INTEGER
		UNITS		"seconds"
		MAX-ACCESS	read-only
		STATUS		current
		DESCRIPTION		
			"Heartbeat Interval returned by the Spectrum Access System (SAS)."
		::={whispApsCbrsApGrantEntry 7}

	apGrantExpiry	OBJECT-TYPE
		SYNTAX		DisplayString
		MAX-ACCESS	read-only
		STATUS		current
		DESCRIPTION		
			"Expiry time of the grant acquired from the Spectrum Access System (SAS)."
		::={whispApsCbrsApGrantEntry 8}

	apGrantTxExpiry	OBJECT-TYPE
		SYNTAX		DisplayString
		MAX-ACCESS	read-only
		STATUS		current
		DESCRIPTION		
			"Transmit expiry time specified by the Spectrum Access System (SAS)."
		::={whispApsCbrsApGrantEntry 9}

	apGrantChannelType	OBJECT-TYPE
		SYNTAX		DisplayString
		MAX-ACCESS	read-only
		STATUS		current
		DESCRIPTION		
			"Type of channel allocation done by the Spectrum Access System (SAS) for the grant."
		::={whispApsCbrsApGrantEntry 10}

	apGrantEirp	OBJECT-TYPE
		SYNTAX		DisplayString
		MAX-ACCESS	read-only
		STATUS		current
		DESCRIPTION		
			"EIRP granted by the Spectrum Access System (SAS)."
		::={whispApsCbrsApGrantEntry 11}

	apGrantHeartbeatTotal	OBJECT-TYPE
		SYNTAX		Counter32
		MAX-ACCESS	read-only
		STATUS		current
		DESCRIPTION		
			"Total number of heartbeat requests sent by the AP CBSD for the grant to SAS."
		::={whispApsCbrsApGrantEntry 12}

	apGrantHeartbeatMissed	OBJECT-TYPE
		SYNTAX		Counter32
		MAX-ACCESS	read-only
		STATUS		current
		DESCRIPTION		
			"Number of heartbeat requests for the grant which didn't receive a response from the SAS."
		::={whispApsCbrsApGrantEntry 13}

	apGrantHeartbeatFailed	OBJECT-TYPE
		SYNTAX		Counter32
		MAX-ACCESS	read-only
		STATUS		current
		DESCRIPTION		
			"Number of heartbeat requests for the grant which received a failure response for the AP CBSD from the SAS."
		::={whispApsCbrsApGrantEntry 14}

	apGrantHeartbeatFailedSuspend	OBJECT-TYPE
		SYNTAX		Counter32
		MAX-ACCESS	read-only
		STATUS		current
		DESCRIPTION		
			"Number of heartbeat requests for the grant which received a grant suspend for the AP CBSD from the SAS."
		::={whispApsCbrsApGrantEntry 15}

	apGrantHeartbeatFailedTerminate	OBJECT-TYPE
		SYNTAX		Counter32
		MAX-ACCESS	read-only
		STATUS		current
		DESCRIPTION		
			"Number of heartbeat requests for the grant which received a grant terminate response for the AP CBSD from the SAS."
		::={whispApsCbrsApGrantEntry 16}

	apGrantHeartbeatFailedUnsync	OBJECT-TYPE
		SYNTAX		Counter32
		MAX-ACCESS	read-only
		STATUS		current
		DESCRIPTION		
			"Number of heartbeat requests for the grant which received a grant out-of-sync failure response for the AP CBSD from the SAS."
		::={whispApsCbrsApGrantEntry 17}

	whispApsCbrsSmGrant OBJECT-TYPE
		SYNTAX		SEQUENCE OF WhispApsCbrsSmGrantEntry
		MAX-ACCESS	not-accessible
		STATUS		current
		DESCRIPTION
			"Table indicating status of grants in Citizens Broadband Radio Service (CBRS) device."
		::= {whispApsCbrs 6}

	whispApsCbrsSmGrantEntry OBJECT-TYPE
		SYNTAX		WhispApsCbrsSmGrantEntry
		MAX-ACCESS	not-accessible
		STATUS		current
		DESCRIPTION
			"Citizens Broadband Radio Service (CBRS) device grant entry."
		INDEX		{smGrantLuid,smGrantLowFreq}
		::= {whispApsCbrsSmGrant 1}

		WhispApsCbrsSmGrantEntry ::= SEQUENCE{
			smGrantLuid		INTEGER,
			smGrantLowFreq		INTEGER,
			smGrantHighFreq		INTEGER,
			smGrantMac		DisplayString,
			smGrantId		DisplayString,
			smGrantState		DisplayString,
			smGrantStateDuration		DisplayString,
			smGrantLastHeartbeatTime		DisplayString,
			smGrantHeartbeatInterval		INTEGER,
			smGrantExpiry		DisplayString,
			smGrantTxExpiry		DisplayString,
			smGrantChannelType		DisplayString,
			smGrantEirp		DisplayString,
			smGrantHeartbeatTotal		Counter32,
			smGrantHeartbeatMissed		Counter32,
			smGrantHeartbeatFailed		Counter32,
			smGrantHeartbeatFailedSuspend		Counter32,
			smGrantHeartbeatFailedTerminate		Counter32,
			smGrantHeartbeatFailedUnsync		Counter32,
			smGrantHeartbeatSkipped		Counter32,
			smGrantHeartbeatRelativeBulk		Counter32,
			smGrantHeartbeatStandalone	Counter32
			}

	smGrantLuid	OBJECT-TYPE
		SYNTAX		INTEGER (2..239)
		MAX-ACCESS	read-only
		STATUS		current
		DESCRIPTION		
			"Logical User Identification (LUID) number for the Citizens Broadband Radio Service (CBRS) device holding the grant."
		::={whispApsCbrsSmGrantEntry 1}

	smGrantLowFreq	OBJECT-TYPE
		SYNTAX		INTEGER (3550000..3700000)
		MAX-ACCESS	read-only
		STATUS		current
		DESCRIPTION		
			"The lowest frequency of the grant frequency range in kHz."
		::={whispApsCbrsSmGrantEntry 2}

	smGrantHighFreq	OBJECT-TYPE
		SYNTAX		INTEGER (3550000..3700000)
		MAX-ACCESS	read-only
		STATUS		current
		DESCRIPTION		
			"The highest frequency of the grant frequency range in kHz."
		::={whispApsCbrsSmGrantEntry 3}

	smGrantMac	OBJECT-TYPE
		SYNTAX		DisplayString
		MAX-ACCESS	read-only
		STATUS		current
		DESCRIPTION		
			"MAC address of Citizens Broadband Radio Service Device(CBSD) holding the grant."
		::={whispApsCbrsSmGrantEntry 4}

	smGrantId	OBJECT-TYPE
		SYNTAX		DisplayString
		MAX-ACCESS	read-only
		STATUS		current
		DESCRIPTION		
			"The unique ID of the grant from the Spectrum Access System (SAS)."
		::={whispApsCbrsSmGrantEntry 5}

	smGrantState	OBJECT-TYPE
		SYNTAX		DisplayString
		MAX-ACCESS	read-only
		STATUS		current
		DESCRIPTION		
			"Current state of the grant in Citizens Broadband Radio Service (CBRS) device."
		::={whispApsCbrsSmGrantEntry 6}

	smGrantStateDuration	OBJECT-TYPE
		SYNTAX		DisplayString
		MAX-ACCESS	read-only
		STATUS		current
		DESCRIPTION		
			"Time elapsed in the current state of grant."
		::={whispApsCbrsSmGrantEntry 7}

	smGrantLastHeartbeatTime	OBJECT-TYPE
		SYNTAX		DisplayString
		MAX-ACCESS	read-only
		STATUS		current
		DESCRIPTION		
			"Time when the last heartbeat request was sent."
		::={whispApsCbrsSmGrantEntry 8}

	smGrantHeartbeatInterval	OBJECT-TYPE
		SYNTAX		INTEGER
		UNITS		"seconds"
		MAX-ACCESS	read-only
		STATUS		current
		DESCRIPTION		
			"Heartbeat Interval returned by the Spectrum Access System (SAS)."
		::={whispApsCbrsSmGrantEntry 9}

	smGrantExpiry	OBJECT-TYPE
		SYNTAX		DisplayString
		MAX-ACCESS	read-only
		STATUS		current
		DESCRIPTION		
			"Expiry time of the grant acquired from the Spectrum Access System (SAS)."
		::={whispApsCbrsSmGrantEntry 10}

	smGrantTxExpiry	OBJECT-TYPE
		SYNTAX		DisplayString
		MAX-ACCESS	read-only
		STATUS		current
		DESCRIPTION		
			"Transmit expiry time specified by the Spectrum Access System (SAS)."
		::={whispApsCbrsSmGrantEntry 11}

	smGrantChannelType	OBJECT-TYPE
		SYNTAX		DisplayString
		MAX-ACCESS	read-only
		STATUS		current
		DESCRIPTION		
			"Type of channel allocation done by the Spectrum Access System (SAS) for the grant."
		::={whispApsCbrsSmGrantEntry 12}

	smGrantEirp	OBJECT-TYPE
		SYNTAX		DisplayString
		MAX-ACCESS	read-only
		STATUS		current
		DESCRIPTION		
			"EIRP granted by the Spectrum Access System (SAS)."
		::={whispApsCbrsSmGrantEntry 13}

	smGrantHeartbeatTotal	OBJECT-TYPE
		SYNTAX		Counter32
		MAX-ACCESS	read-only
		STATUS		current
		DESCRIPTION		
			"Total number of heartbeat requests sent by the AP CBSD for the grant to SAS."
		::={whispApsCbrsSmGrantEntry 14}

	smGrantHeartbeatMissed	OBJECT-TYPE
		SYNTAX		Counter32
		MAX-ACCESS	read-only
		STATUS		current
		DESCRIPTION		
			"Number of heartbeat requests for the grant which didn't receive a response from the SAS."
		::={whispApsCbrsSmGrantEntry 15}

	smGrantHeartbeatFailed	OBJECT-TYPE
		SYNTAX		Counter32
		MAX-ACCESS	read-only
		STATUS		current
		DESCRIPTION		
			"Number of heartbeat requests for the grant which received a failure response for the AP CBSD from the SAS."
		::={whispApsCbrsSmGrantEntry 16}

	smGrantHeartbeatFailedSuspend	OBJECT-TYPE
		SYNTAX		Counter32
		MAX-ACCESS	read-only
		STATUS		current
		DESCRIPTION		
			"Number of heartbeat requests for the grant which received a grant suspend for the AP CBSD from the SAS."
		::={whispApsCbrsSmGrantEntry 17}

	smGrantHeartbeatFailedTerminate	OBJECT-TYPE
		SYNTAX		Counter32
		MAX-ACCESS	read-only
		STATUS		current
		DESCRIPTION		
			"Number of heartbeat requests for the grant which received a grant terminate response for the AP CBSD from the SAS."
		::={whispApsCbrsSmGrantEntry 18}

	smGrantHeartbeatFailedUnsync	OBJECT-TYPE
		SYNTAX		Counter32
		MAX-ACCESS	read-only
		STATUS		current
		DESCRIPTION		
			"Number of heartbeat requests for the grant which received a grant out-of-sync failure response for the AP CBSD from the SAS."
		::={whispApsCbrsSmGrantEntry 19}

	smGrantHeartbeatSkipped	OBJECT-TYPE
		SYNTAX		Counter32
		MAX-ACCESS	read-only
		STATUS		current
		DESCRIPTION		
			"Number of bulk heartbeat requests sent by AP which didn't include an entry for the SM because it was not connected to the AP."
		::={whispApsCbrsSmGrantEntry 20}

	smGrantHeartbeatRelativeBulk	OBJECT-TYPE
		SYNTAX		Counter32
		MAX-ACCESS	read-only
		STATUS		current
		DESCRIPTION		
			"Total number of bulk heartbeat requests sent by AP since the SM established its first session."
		::={whispApsCbrsSmGrantEntry 21}

	smGrantHeartbeatStandalone	OBJECT-TYPE
		SYNTAX		Counter32
		MAX-ACCESS	read-only
		STATUS		current
		DESCRIPTION		
			"Number of heartbeat requests from the CBSD which were not part of a bulk heartbeat request."
		::={whispApsCbrsSmGrantEntry 22}

	whispApsRFConfigRadios OBJECT-TYPE
		SYNTAX		SEQUENCE OF WhispApsRFConfigRadioEntry
		MAX-ACCESS	not-accessible
		STATUS		current
		DESCRIPTION
			"Radio configuration table."
		::= {whispApsRFConfig 1}

	whispApsRFConfigRadioEntry OBJECT-TYPE
		SYNTAX		WhispApsRFConfigRadioEntry
		MAX-ACCESS	not-accessible
		STATUS		current
		DESCRIPTION
			"Radio configuration entry."
		AUGMENTS		{whispBoxRFPhysicalRadioEntry}
		::= {whispApsRFConfigRadios 1}

		WhispApsRFConfigRadioEntry ::= SEQUENCE{
			radioFreqCarrier		INTEGER,
			radioDownlinkPercent		INTEGER,
			radioMaxRange		INTEGER,
			radioControlSlots		INTEGER,
			radioTransmitOutputPower		INTEGER,
			radioColorCode		INTEGER,
			radioMaxRangeUnit	INTEGER
			}

	radioFreqCarrier	OBJECT-TYPE
		SYNTAX		INTEGER {
					wired(0)}
		UNITS		"kHz"
		MAX-ACCESS	read-write
		STATUS		current
		DESCRIPTION		
			"RF Frequency.  Please see the whispBoxRFPhysicalRadioFrequencies SNMP table for a list of available
            frequencies.
            0:  wired.
            As of release 16.1, this OID no longer requires reboot to take affect. It will be applied immediately. SMs will be signaled to the configured frequency."
		::={whispApsRFConfigRadioEntry 1}

	radioDownlinkPercent	OBJECT-TYPE
		SYNTAX		INTEGER (1..99)
		UNITS		"%"
		MAX-ACCESS	read-write
		STATUS		current
		DESCRIPTION		
			"This is the percentage of frame data space allocated for downlink.
                       Various radio platforms and regions will have different allowable downlink percentages."
		::={whispApsRFConfigRadioEntry 2}

	radioMaxRange	OBJECT-TYPE
		SYNTAX		INTEGER
		MAX-ACCESS	read-write
		STATUS		current
		DESCRIPTION		
			"Access point max range. This can be in miles or KM based upon the radioMaxRangeUnit setting so set radioMaxRangeUnit first and then radioMaxRange. RadioMaxRangeUnit alone should not be changed so please make sure that radioMaxRange value is also set after setting the unit."
		::={whispApsRFConfigRadioEntry 3}

	radioControlSlots	OBJECT-TYPE
		SYNTAX		INTEGER
		MAX-ACCESS	read-write
		STATUS		current
		DESCRIPTION		
			"Total number of contention slots for HW Scheduling Point-to-Mulitpoint mode (Not applicable for PtoP radios).
                       For PMP 450 the minimum is 1 control slot, others minimum is zero.
                       Maximum contention slots is 15."
		::={whispApsRFConfigRadioEntry 4}

	radioTransmitOutputPower	OBJECT-TYPE
		SYNTAX		INTEGER
		UNITS		"dBm"
		MAX-ACCESS	read-write
		STATUS		current
		DESCRIPTION		
			"Transmitter output power.
                        Deprecated in favor of 'TransmitterOP' in radioConfig.
                        For 450v, see carrierTxPower."
		::={whispApsRFConfigRadioEntry 5}

	radioColorCode	OBJECT-TYPE
		SYNTAX		INTEGER (0..254)
		MAX-ACCESS	read-write
		STATUS		current
		DESCRIPTION		
			"Color code."
		::={whispApsRFConfigRadioEntry 6}

	radioMaxRangeUnit	OBJECT-TYPE
		SYNTAX		INTEGER {
					miles(0),
					km(1)}
		MAX-ACCESS	read-write
		STATUS		current
		DESCRIPTION		
			"Unit of Max range value. Set radioMaxRangeUnit first and then radioMaxRange. RadioMaxRangeUnit alone should not be changed so please make sure that radioMaxRange value is also set after changing the unit."
		::={whispApsRFConfigRadioEntry 7}

	apCarrierInfo OBJECT-TYPE
		SYNTAX		SEQUENCE OF APCarrierInfoEntry
		MAX-ACCESS	not-accessible
		STATUS		current
		DESCRIPTION
			"Canopy V AP Carrier Information table"
		::= {whispApsRFStatus 1}

	apCarrierInfoEntry OBJECT-TYPE
		SYNTAX		APCarrierInfoEntry
		MAX-ACCESS	not-accessible
		STATUS		current
		DESCRIPTION
			"Canopy V AP Carrier Information table entry"
		INDEX		{apCarrierInfoTableIdx}
		::= {apCarrierInfo 1}

		APCarrierInfoEntry ::= SEQUENCE{
			apCarrierInfoTableIdx		INTEGER,
			apCarrierStatus		INTEGER,
			apCarrierBand		INTEGER,
			apCarrierFrequency		INTEGER,
			apCarrierAggregateBw		INTEGER,
			apCarrierTxPwr		INTEGER,
			apCarrierEIRP	INTEGER
			}

	apCarrierInfoTableIdx	OBJECT-TYPE
		SYNTAX		INTEGER (1..2)
		MAX-ACCESS	read-only
		STATUS		current
		DESCRIPTION		
			"Carrier Table Index"
		::={apCarrierInfoEntry 1}

	apCarrierStatus	OBJECT-TYPE
		SYNTAX		INTEGER {
					inactive(0),
					active(1)}
		MAX-ACCESS	read-only
		STATUS		current
		DESCRIPTION		
			"Carrier Status 1-Active 0-Inactive"
		::={apCarrierInfoEntry 2}

	apCarrierBand	OBJECT-TYPE
		SYNTAX		INTEGER {
					band700(0),
					band900(1),
					band2400(2),
					band3500(3),
					band3700(4),
					band4900(5),
					band5100(6),
					band5200(7),
					band5400(8),
					band5700(9),
					band5800(10),
					band5900(11),
					band6050(12),
					band3600(13),
					band4959(14),
					band3(15),
					band5170(16),
					band65(17),
					band67(18),
					band5763(19),
					band66(20)}
		MAX-ACCESS	read-only
		STATUS		current
		DESCRIPTION		
			"Carrier Band"
		::={apCarrierInfoEntry 3}

	apCarrierFrequency	OBJECT-TYPE
		SYNTAX		INTEGER
		UNITS		"kHz"
		MAX-ACCESS	read-only
		STATUS		current
		DESCRIPTION		
			"Carrier Frequency in kHz"
		::={apCarrierInfoEntry 4}

	apCarrierAggregateBw	OBJECT-TYPE
		SYNTAX		INTEGER
		UNITS		"MHz"
		MAX-ACCESS	read-only
		STATUS		current
		DESCRIPTION		
			"Carrier Aggregate Bandwidth in MHz"
		::={apCarrierInfoEntry 5}

	apCarrierTxPwr	OBJECT-TYPE
		SYNTAX		INTEGER
		UNITS		"dBm"
		MAX-ACCESS	read-only
		STATUS		current
		DESCRIPTION		
			"Carrier Transmit Power in dBm"
		::={apCarrierInfoEntry 6}

	apCarrierEIRP	OBJECT-TYPE
		SYNTAX		INTEGER
		UNITS		"dBm"
		MAX-ACCESS	read-only
		STATUS		current
		DESCRIPTION		
			"Carrier EIRP in dBm"
		::={apCarrierInfoEntry 7}

	apComponentCarrierInfo OBJECT-TYPE
		SYNTAX		SEQUENCE OF APComponentCarrierInfoEntry
		MAX-ACCESS	not-accessible
		STATUS		current
		DESCRIPTION
			"Canopy V AP Component Carrier Information table"
		::= {whispApsRFStatus 2}

	apComponentCarrierInfoEntry OBJECT-TYPE
		SYNTAX		APComponentCarrierInfoEntry
		MAX-ACCESS	not-accessible
		STATUS		current
		DESCRIPTION
			"Canopy V AP Component Carrier Information table entry"
		INDEX		{apCCTableIdx}
		::= {apComponentCarrierInfo 1}

		APComponentCarrierInfoEntry ::= SEQUENCE{
			apCCTableIdx		INTEGER,
			apCCStatus		INTEGER,
			apCCCarrierAssignment		INTEGER,
			apCCChannelFreq		INTEGER,
			apCCChannelBW		INTEGER,
			apCCTxPwr		INTEGER,
			apCCFrameutilizationDL		INTEGER,
			apCCFrameutilizationUL		INTEGER,
			apCCSpecEffExtrapDL		INTEGER,
			apCCSpecEffExtrapUL	INTEGER
			}

	apCCTableIdx	OBJECT-TYPE
		SYNTAX		INTEGER (1..4)
		MAX-ACCESS	read-only
		STATUS		current
		DESCRIPTION		
			"Index to the Canopy V Component Carrier Information Table"
		::={apComponentCarrierInfoEntry 1}

	apCCStatus	OBJECT-TYPE
		SYNTAX		INTEGER {
					inactive(0),
					active(1)}
		MAX-ACCESS	read-only
		STATUS		current
		DESCRIPTION		
			"The Component Carrier Status 1-Active 0-Inactive"
		::={apComponentCarrierInfoEntry 2}

	apCCCarrierAssignment	OBJECT-TYPE
		SYNTAX		INTEGER
		MAX-ACCESS	read-only
		STATUS		current
		DESCRIPTION		
			"Carrier Assignment for the Component Carrier"
		::={apComponentCarrierInfoEntry 3}

	apCCChannelFreq	OBJECT-TYPE
		SYNTAX		INTEGER
		UNITS		"kHz"
		MAX-ACCESS	read-only
		STATUS		current
		DESCRIPTION		
			"Component Carrier Specific Channel Frequency Value in kHz"
		::={apComponentCarrierInfoEntry 4}

	apCCChannelBW	OBJECT-TYPE
		SYNTAX		INTEGER
		UNITS		"MHz"
		MAX-ACCESS	read-only
		STATUS		current
		DESCRIPTION		
			"The Component Carrier Channel Bandwidth in MHz"
		::={apComponentCarrierInfoEntry 5}

	apCCTxPwr	OBJECT-TYPE
		SYNTAX		INTEGER
		UNITS		"dBm"
		MAX-ACCESS	read-only
		STATUS		current
		DESCRIPTION		
			"The Component Carrier Transmit Power in dBm"
		::={apComponentCarrierInfoEntry 7}

	apCCFrameutilizationDL	OBJECT-TYPE
		SYNTAX		INTEGER
		MAX-ACCESS	read-only
		STATUS		current
		DESCRIPTION		
			"Percentage of the Component Carrier's Total Downlink Frame Utilization for 5 minutes."
		::={apComponentCarrierInfoEntry 8}

	apCCFrameutilizationUL	OBJECT-TYPE
		SYNTAX		INTEGER
		MAX-ACCESS	read-only
		STATUS		current
		DESCRIPTION		
			"Percentage of the Component Carrier's Total Uplink Frame Utilization for 5 minutes."
		::={apComponentCarrierInfoEntry 9}

	apCCSpecEffExtrapDL	OBJECT-TYPE
		SYNTAX		INTEGER
		MAX-ACCESS	read-only
		STATUS		current
		DESCRIPTION		
			"Extrapolated Downlink Spectral Efficiency of the Component carrier in the last 5 minute (Multiplied by 1000). Measured in units of user data bits per second per hertz.
                            Divide by 1000 for actual number."
		::={apComponentCarrierInfoEntry 10}

	apCCSpecEffExtrapUL	OBJECT-TYPE
		SYNTAX		INTEGER
		MAX-ACCESS	read-only
		STATUS		current
		DESCRIPTION		
			"Extrapolated Uplink Spectral Efficiency of the Component carrier in the last 5 minute (Multiplied by 1000). Measured in units of user data bits per second per hertz.
                            Divide by 1000 for actual number."
		::={apComponentCarrierInfoEntry 11}

	apSmComponentCarrierInfo OBJECT-TYPE
		SYNTAX		SEQUENCE OF APSmComponentCarrierInfoEntry
		MAX-ACCESS	not-accessible
		STATUS		current
		DESCRIPTION
			"Component Carrier Information table for each SM on the AP"
		::= {whispApsRFStatus 3}

	apSmComponentCarrierInfoEntry OBJECT-TYPE
		SYNTAX		APSmComponentCarrierInfoEntry
		MAX-ACCESS	not-accessible
		STATUS		current
		DESCRIPTION
			"Component Carrier Information table entry for each SM on the AP"
		INDEX		{apSmLUID,apSmCCInfoIdx}
		::= {apSmComponentCarrierInfo 1}

		APSmComponentCarrierInfoEntry ::= SEQUENCE{
			apSmLUID		INTEGER,
			apSmCCInfoIdx		INTEGER,
			apSmCCRssiHorizontal		DisplayString,
			apSmCCRssiVertical	DisplayString
			}

	apSmLUID	OBJECT-TYPE
		SYNTAX		INTEGER (1..4)
		MAX-ACCESS	read-only
		STATUS		current
		DESCRIPTION		
			"SM Logical User Identification (LUID) number for the Canopy V Component Carrier Information Table"
		::={apSmComponentCarrierInfoEntry 1}

	apSmCCInfoIdx	OBJECT-TYPE
		SYNTAX		INTEGER (1..4)
		MAX-ACCESS	read-only
		STATUS		current
		DESCRIPTION		
			"Component Carrier index to the Canopy V Component Carrier Information Table"
		::={apSmComponentCarrierInfoEntry 2}

	apSmCCRssiHorizontal	OBJECT-TYPE
		SYNTAX		DisplayString
		MAX-ACCESS	read-only
		STATUS		current
		DESCRIPTION		
			"Component Carrier receive power level of the horizontal antenna in dBm."
		::={apSmComponentCarrierInfoEntry 3}

	apSmCCRssiVertical	OBJECT-TYPE
		SYNTAX		DisplayString
		MAX-ACCESS	read-only
		STATUS		current
		DESCRIPTION		
			"Component Carrier receive power level of the vertical antenna in dBm."
		::={apSmComponentCarrierInfoEntry 4}

	whispLinkTable OBJECT-TYPE
		SYNTAX		SEQUENCE OF WhispLinkEntry
		MAX-ACCESS	not-accessible
		STATUS		current
		DESCRIPTION
			"Link Status Table"
		::= {whispAps 4}

	whispLinkEntry OBJECT-TYPE
		SYNTAX		WhispLinkEntry
		MAX-ACCESS	not-accessible
		STATUS		current
		DESCRIPTION
			"Link Status"
		INDEX		{linkLUID}
		::= {whispLinkTable 1}

		WhispLinkEntry ::= SEQUENCE{
			linkLUID		INTEGER,
			linkDescr		DisplayString,
			linkPhysAddress		PhysAddress,
			linkMtu		INTEGER,
			linkSpeed		Gauge32,
			linkOperStatus		INTEGER,
			linkInOctets		Counter32,
			linkInUcastPkts		Counter32,
			linkInNUcastPkts		Counter32,
			linkInDiscards		Counter32,
			linkInError		Counter32,
			linkInUnknownProtos		Counter32,
			linkOutOctets		Counter32,
			linkOutUcastPkts		Counter32,
			linkOutNUcastPkts		Counter32,
			linkOutDiscards		Counter32,
			linkOutError		Counter32,
			linkInOctets64		Counter64,
			linkInUcastPkts64		Counter64,
			linkInNUcastPkts64		Counter64,
			linkInDiscards64		Counter64,
			linkInError64		Counter64,
			linkOutOctets64		Counter64,
			linkOutUcastPkts64		Counter64,
			linkOutNUcastPkts64		Counter64,
			linkOutDiscards64		Counter64,
			linkOutError64		Counter64,
			linkOutQLen		Gauge32,
			linkSessState		INTEGER,
			linkESN		PhysAddress,
			linkRSSI		INTEGER,
			linkAveJitter		Gauge32,
			linkLastJitter		Gauge32,
			linkAirDelay		INTEGER,
			linkRegCount		INTEGER,
			linkReRegCount		INTEGER,
			linkTimeOut		INTEGER,
			linkLastRSSI		INTEGER,
			sessionCount		INTEGER,
			softwareVersion		DisplayString,
			softwareBootVersion		DisplayString,
			fpgaVersion		DisplayString,
			linkSiteName		DisplayString,
			avgPowerLevel		DisplayString,
			lastPowerLevel		DisplayString,
			sesDownLinkRate		INTEGER,
			sesDownLinkLimit		INTEGER,
			sesUpLinkRate		INTEGER,
			sesUpLinkLimit		INTEGER,
			adaptRate		DisplayString,
			sesLoUpCIR		INTEGER,
			sesLoDownCIR		INTEGER,
			sesMedUpCIR		INTEGER,
			sesMedDownCIR		INTEGER,
			sesHiUpCIR		INTEGER,
			sesHiDownCIR		INTEGER,
			sesUHiUpCIR		INTEGER,
			sesUHiDownCIR		INTEGER,
			linkPlatformVer		INTEGER,
			smSessionTmr		TimeTicks,
			smSessionSeqNumMismatch		Counter32,
			dataVCNum		INTEGER,
			mediumPriQEn		INTEGER,
			dataVCNumMediumQ		INTEGER,
			linkInOctetsMediumQ		Counter64,
			linkInUcastPktsMediumQ		Counter64,
			linkInNUcastPktsMediumQ		Counter64,
			linkInDiscardsMediumQ		Counter64,
			linkInErrorMediumQ		Counter64,
			linkInUnknownProtosMediumQ		Counter32,
			linkOutOctetsMediumQ		Counter64,
			linkOutUcastPktsMediumQ		Counter64,
			linkOutNUcastPktsMediumQ		Counter64,
			linkOutDiscardsMediumQ		Counter64,
			linkOutErrorMediumQ		Counter64,
			vcQOverflowMediumQ		Counter32,
			hiPriQEn		INTEGER,
			dataVCNumHiQ		INTEGER,
			linkInOctetsHiQ		Counter32,
			linkInUcastPktsHiQ		Counter32,
			linkInNUcastPktsHiQ		Counter32,
			linkInDiscardsHiQ		Counter32,
			linkInErrorHiQ		Counter32,
			linkInUnknownProtosHiQ		Counter32,
			linkOutOctetsHiQ		Counter32,
			linkOutUcastPktsHiQ		Counter32,
			linkOutNUcastPktsHiQ		Counter32,
			linkOutDiscardsHiQ		Counter32,
			linkOutErrorHiQ		Counter32,
			linkInOctetsHiQ64		Counter64,
			linkInUcastPktsHiQ64		Counter64,
			linkInNUcastPktsHiQ64		Counter64,
			linkInDiscardsHiQ64		Counter64,
			linkInErrorHiQ64		Counter64,
			linkOutOctetsHiQ64		Counter64,
			linkOutUcastPktsHiQ64		Counter64,
			linkOutNUcastPktsHiQ64		Counter64,
			linkOutDiscardsHiQ64		Counter64,
			linkOutErrorHiQ64		Counter64,
			vcQOverflow		Counter32,
			vcQOverflowHiQ		Counter32,
			p7p8HiPriQEn		INTEGER,
			p7p8HiPriQ		Counter32,
			ultraHighPriQEn		INTEGER,
			dataVCNumUltraHighQ		INTEGER,
			linkInOctetsUltraHighQ		Counter64,
			linkInUcastPktsUltraHighQ		Counter64,
			linkInNUcastPktsUltraHighQ		Counter64,
			linkInDiscardsUltraHighQ		Counter64,
			linkInErrorUltraHighQ		Counter64,
			linkInUnknownProtosUltraHighQ		Counter32,
			linkOutOctetsUltraHighQ		Counter64,
			linkOutUcastPktsUltraHighQ		Counter64,
			linkOutNUcastPktsUltraHighQ		Counter64,
			linkOutDiscardsUltraHighQ		Counter64,
			linkOutErrorUltraHighQ		Counter64,
			vcQOverflowUltraHighQ		Counter32,
			linkAirDelayns		INTEGER,
			linkQualityAPData		DisplayString,
			linkManagementIP		IpAddress,
			linkFragmentsReceived1XVertical		Counter32,
			linkFragmentsReceived2XVertical		Counter32,
			linkFragmentsReceived3XVertical		Counter32,
			linkFragmentsReceived4XVertical		Counter32,
			signalToNoiseRatioVertical		INTEGER,
			radiusReplyMsg		DisplayString,
			autoUpdateStatus		INTEGER,
			radiusFramedIPAddress		IpAddress,
			radiusFramedIPNetmask		IpAddress,
			radiusDefaultGateway		IpAddress,
			linkFragmentsReceived1XHorizontal		Counter32,
			linkFragmentsReceived2XHorizontal		Counter32,
			linkFragmentsReceived3XHorizontal		Counter32,
			linkFragmentsReceived4XHorizontal		Counter32,
			signalToNoiseRatioHorizontal		INTEGER,
			linkSignalStrengthRatio		DisplayString,
			linkRadioDbmHorizontal		DisplayString,
			linkRadioDbmVertical		DisplayString,
			maxSMTxPwr		INTEGER,
			productType		INTEGER,
			linkAdaptRateLowPri		INTEGER,
			linkAdaptRateHighPri		INTEGER,
			avgPowerLevelInt		INTEGER,
			mimoPowerLevelVertical		INTEGER,
			mimoPowerLevelHorizontal		INTEGER,
			linkSwVersion		DisplayString,
			linkSpatialFrequency		INTEGER,
			retransmittedFragmentsCount		DisplayString,
			soundingState		INTEGER,
			downlinkSoundingState		INTEGER,
			uplinkSoundingState		INTEGER,
			downlinkMumimoRateAdapt		INTEGER,
			uplinkMumimoRateAdapt		INTEGER,
			averageEvmDownlinkPathA		INTEGER,
			averageEvmDownlinkPathB		INTEGER,
			combinedEvmDownlink		INTEGER,
			averageEvmUplinkPathA		INTEGER,
			averageEvmUplinkPathB		INTEGER,
			combinedEvmUplink		INTEGER,
			fastRateAdaptActive		INTEGER,
			bestEvmDownlinkPathA		INTEGER,
			bestEvmDownlinkPathB		INTEGER,
			bestEvmUplinkPathA		INTEGER,
			bestEvmUplinkPathB		INTEGER,
			worstEvmDownlinkPathA		INTEGER,
			worstEvmDownlinkPathB		INTEGER,
			worstEvmUplinkPathA		INTEGER,
			worstEvmUplinkPathB		INTEGER,
			linkColorCodePriority		INTEGER,
			modRateDL		DisplayString,
			linkVcDepth	INTEGER
			}

	linkLUID	OBJECT-TYPE
		SYNTAX		INTEGER (2..239)
		MAX-ACCESS	read-only
		STATUS		current
		DESCRIPTION		
			"LUID number."
		::={whispLinkEntry 1}

	linkDescr	OBJECT-TYPE
		SYNTAX		DisplayString
		MAX-ACCESS	read-only
		STATUS		current
		DESCRIPTION		
			"A textual string containing information about the
            unit.  This string should include the name of
            the manufacturer, the product name and the version
            of the hardware interface."
		::={whispLinkEntry 2}

	linkPhysAddress	OBJECT-TYPE
		SYNTAX		PhysAddress
		MAX-ACCESS	read-only
		STATUS		current
		DESCRIPTION		
			"Physical Address of the unit."
		::={whispLinkEntry 3}

	linkMtu	OBJECT-TYPE
		SYNTAX		INTEGER
		MAX-ACCESS	read-only
		STATUS		current
		DESCRIPTION		
			"The size of the largest datagram which can be
            sent/received on the interface, specified in
            octets.  For interfaces that are used for
            transmitting network datagrams, this is the size
            of the largest network datagram that can be sent
            on the interface."
		::={whispLinkEntry 4}

	linkSpeed	OBJECT-TYPE
		SYNTAX		Gauge32
		MAX-ACCESS	read-only
		STATUS		current
		DESCRIPTION		
			"An estimate of the interface's current bandwidth
            in bits per second.  For interfaces which do not
            vary in bandwidth or for those where no accurate
            estimation can be made, this object should contain
            the nominal bandwidth."
		::={whispLinkEntry 5}

	linkOperStatus	OBJECT-TYPE
		SYNTAX		INTEGER {
					up(1),
					down(2),
					testing(3)}
		MAX-ACCESS	read-only
		STATUS		obsolete
		DESCRIPTION		
			"This variable is not used."
		::={whispLinkEntry 6}

	linkInOctets	OBJECT-TYPE
		SYNTAX		Counter32
		MAX-ACCESS	read-only
		STATUS		deprecated
		DESCRIPTION		
			"The total number of octets received on the interface, including framing characters.
                             Use linkInOctets64 instead."
		::={whispLinkEntry 7}

	linkInUcastPkts	OBJECT-TYPE
		SYNTAX		Counter32
		MAX-ACCESS	read-only
		STATUS		deprecated
		DESCRIPTION		
			"The number of subnetwork-unicast packets  delivered to a higher-layer protocol.
                            Use linkInUcastPkts64 instead."
		::={whispLinkEntry 8}

	linkInNUcastPkts	OBJECT-TYPE
		SYNTAX		Counter32
		MAX-ACCESS	read-only
		STATUS		deprecated
		DESCRIPTION		
			"The number of non-unicast (i.e., subnetwork-broadcast or subnetwork-multicast) packets
                            delivered to a higher-layer protocol.
                            Use linkInNUcastPkts64 instead."
		::={whispLinkEntry 9}

	linkInDiscards	OBJECT-TYPE
		SYNTAX		Counter32
		MAX-ACCESS	read-only
		STATUS		deprecated
		DESCRIPTION		
			"The number of inbound packets which were chosen to be discarded even though no errors had been
                            detected to prevent their being deliverable to a higher-layer protocol. One possible reason for
                            discarding such a packet could be to free up buffer space. Use linkInDiscards64 instead."
		::={whispLinkEntry 10}

	linkInError	OBJECT-TYPE
		SYNTAX		Counter32
		MAX-ACCESS	read-only
		STATUS		deprecated
		DESCRIPTION		
			"The number of inbound packets that contained errors preventing them from being deliverable to a
                             higher-layer protocol. Use linkInError64 instead."
		::={whispLinkEntry 11}

	linkInUnknownProtos	OBJECT-TYPE
		SYNTAX		Counter32
		MAX-ACCESS	read-only
		STATUS		current
		DESCRIPTION		
			"The number of packets received via the interface which were discarded because of an unknown or
                            unsupported protocol."
		::={whispLinkEntry 12}

	linkOutOctets	OBJECT-TYPE
		SYNTAX		Counter32
		MAX-ACCESS	read-only
		STATUS		deprecated
		DESCRIPTION		
			"The total number of octets transmitted out of the interface, including framing characters.
                            Use linkOutOctets64 instead."
		::={whispLinkEntry 13}

	linkOutUcastPkts	OBJECT-TYPE
		SYNTAX		Counter32
		MAX-ACCESS	read-only
		STATUS		deprecated
		DESCRIPTION		
			"The total number of packets that higher-level protocols requested be transmitted to a
                            subnetwork-unicast address, including those that were discarded or not sent.
                            Use linkOutUcastPkts64 instead."
		::={whispLinkEntry 14}

	linkOutNUcastPkts	OBJECT-TYPE
		SYNTAX		Counter32
		MAX-ACCESS	read-only
		STATUS		deprecated
		DESCRIPTION		
			"The total number of packets that higher-level protocols requested be transmitted to a non-unicast  
                            (i.e., a subnetwork-broadcast or subnetwork-multicast) address, including those that were discarded or not sent.
                            Use linkOutNUcastPkts64 instead."
		::={whispLinkEntry 15}

	linkOutDiscards	OBJECT-TYPE
		SYNTAX		Counter32
		MAX-ACCESS	read-only
		STATUS		deprecated
		DESCRIPTION		
			"The number of outbound packets which were chosen to be discarded even though no errors had been
                            detected to prevent their being transmitted. One possible reason for discarding such a packet could
                            be to free up buffer space. Use linkOutDiscards64 instead"
		::={whispLinkEntry 16}

	linkOutError	OBJECT-TYPE
		SYNTAX		Counter32
		MAX-ACCESS	read-only
		STATUS		deprecated
		DESCRIPTION		
			"The number of outbound packets that could not be transmitted because of errors.
                            Use linkOutError64 instead."
		::={whispLinkEntry 17}

	linkOutQLen	OBJECT-TYPE
		SYNTAX		Gauge32
		MAX-ACCESS	read-only
		STATUS		current
		DESCRIPTION		
			"Number of packets in output packet queue."
		::={whispLinkEntry 18}

	linkSessState	OBJECT-TYPE
		SYNTAX		INTEGER {
					idle(0),
					inSession(1),
					clearing(2),
					reRegDnRst(3),
					authChal(4),
					registering(5),
					notInUse(6)}
		MAX-ACCESS	read-only
		STATUS		current
		DESCRIPTION		
			"Current operational state of an interface.
            0 = Idle
            1 = In Session
            2 = Clearing
            3 = Reregistration downlink reset
            4 = Authentication Challenge
            5 = Registering
            6 = Not in use"
		::={whispLinkEntry 19}

	linkESN	OBJECT-TYPE
		SYNTAX		PhysAddress
		MAX-ACCESS	read-only
		STATUS		current
		DESCRIPTION		
			"Link Electronic serial number. It is MAC address."
		::={whispLinkEntry 20}

	linkRSSI	OBJECT-TYPE
		SYNTAX		INTEGER
		MAX-ACCESS	read-only
		STATUS		current
		DESCRIPTION		
			"The average RSSI reading of all packets received from an SM. Applicable to FSK radios only."
		::={whispLinkEntry 21}

	linkAveJitter	OBJECT-TYPE
		SYNTAX		Gauge32 (0..15)
		MAX-ACCESS	read-only
		STATUS		current
		DESCRIPTION		
			"The average Jitter reading of all packets received from an SM.  Applicable to FSK radios only."
		::={whispLinkEntry 22}

	linkLastJitter	OBJECT-TYPE
		SYNTAX		Gauge32 (0..15)
		MAX-ACCESS	read-only
		STATUS		current
		DESCRIPTION		
			"Last jitter value. Applicable to FSK radios only."
		::={whispLinkEntry 23}

	linkAirDelay	OBJECT-TYPE
		SYNTAX		INTEGER
		MAX-ACCESS	read-only
		STATUS		current
		DESCRIPTION		
			"The current round trip air delay in bits measured between the AP and SM."
		::={whispLinkEntry 24}

	linkRegCount	OBJECT-TYPE
		SYNTAX		INTEGER
		MAX-ACCESS	read-only
		STATUS		current
		DESCRIPTION		
			"The number of times an SM has registered to an AP."
		::={whispLinkEntry 25}

	linkReRegCount	OBJECT-TYPE
		SYNTAX		INTEGER
		MAX-ACCESS	read-only
		STATUS		current
		DESCRIPTION		
			"The number of times an SM has tried to register with the AP while it still has
            an active session with the AP."
		::={whispLinkEntry 26}

	linkTimeOut	OBJECT-TYPE
		SYNTAX		INTEGER
		MAX-ACCESS	read-only
		STATUS		current
		DESCRIPTION		
			"Link time out."
		::={whispLinkEntry 27}

	linkLastRSSI	OBJECT-TYPE
		SYNTAX		INTEGER
		MAX-ACCESS	read-only
		STATUS		current
		DESCRIPTION		
			"The last RSSI reading of all packets received from an SM. Applicable to FSK radios only."
		::={whispLinkEntry 28}

	sessionCount	OBJECT-TYPE
		SYNTAX		INTEGER
		MAX-ACCESS	read-only
		STATUS		current
		DESCRIPTION		
			"How many times has this mac been in/out of session."
		::={whispLinkEntry 29}

	softwareVersion	OBJECT-TYPE
		SYNTAX		DisplayString
		MAX-ACCESS	read-only
		STATUS		current
		DESCRIPTION		
			"The software version of registered SM."
		::={whispLinkEntry 30}

	softwareBootVersion	OBJECT-TYPE
		SYNTAX		DisplayString
		MAX-ACCESS	read-only
		STATUS		current
		DESCRIPTION		
			"The software boot version of registered SM."
		::={whispLinkEntry 31}

	fpgaVersion	OBJECT-TYPE
		SYNTAX		DisplayString
		MAX-ACCESS	read-only
		STATUS		current
		DESCRIPTION		
			"The FPGA version of registered SM."
		::={whispLinkEntry 32}

	linkSiteName	OBJECT-TYPE
		SYNTAX		DisplayString
		MAX-ACCESS	read-only
		STATUS		current
		DESCRIPTION		
			"The site name of the registered SM."
		::={whispLinkEntry 33}

	avgPowerLevel	OBJECT-TYPE
		SYNTAX		DisplayString
		MAX-ACCESS	read-only
		STATUS		current
		DESCRIPTION		
			"The average power level of registered SM.
                            For systems that support power control, this value can read 'NA' when the AP adjusts the transmit power of a SM
                            until new packets are received from the SM with it transmitting at its new power level.
                            For MIMO this is the combined receive power."
		::={whispLinkEntry 34}

	lastPowerLevel	OBJECT-TYPE
		SYNTAX		DisplayString
		MAX-ACCESS	read-only
		STATUS		current
		DESCRIPTION		
			"The last power level of registered SM.
                            For MIMO radios this is the combined receive power."
		::={whispLinkEntry 35}

	sesDownLinkRate	OBJECT-TYPE
		SYNTAX		INTEGER
		MAX-ACCESS	read-only
		STATUS		current
		DESCRIPTION		
			"Downlink rate."
		::={whispLinkEntry 36}

	sesDownLinkLimit	OBJECT-TYPE
		SYNTAX		INTEGER
		MAX-ACCESS	read-only
		STATUS		current
		DESCRIPTION		
			"Downlink limit."
		::={whispLinkEntry 37}

	sesUpLinkRate	OBJECT-TYPE
		SYNTAX		INTEGER
		MAX-ACCESS	read-only
		STATUS		current
		DESCRIPTION		
			"Uplink rate."
		::={whispLinkEntry 38}

	sesUpLinkLimit	OBJECT-TYPE
		SYNTAX		INTEGER
		MAX-ACCESS	read-only
		STATUS		current
		DESCRIPTION		
			"Uplink limit."
		::={whispLinkEntry 39}

	adaptRate	OBJECT-TYPE
		SYNTAX		DisplayString
		MAX-ACCESS	read-only
		STATUS		current
		DESCRIPTION		
			"Downlink adapt rate to registered SM."
		::={whispLinkEntry 40}

	sesLoUpCIR	OBJECT-TYPE
		SYNTAX		INTEGER
		MAX-ACCESS	read-only
		STATUS		current
		DESCRIPTION		
			"Low priority uplink CIR."
		::={whispLinkEntry 41}

	sesLoDownCIR	OBJECT-TYPE
		SYNTAX		INTEGER
		MAX-ACCESS	read-only
		STATUS		current
		DESCRIPTION		
			"Low priority downlink CIR."
		::={whispLinkEntry 42}

	sesHiUpCIR	OBJECT-TYPE
		SYNTAX		INTEGER
		MAX-ACCESS	read-only
		STATUS		current
		DESCRIPTION		
			"High priority uplink CIR."
		::={whispLinkEntry 43}

	sesHiDownCIR	OBJECT-TYPE
		SYNTAX		INTEGER
		MAX-ACCESS	read-only
		STATUS		current
		DESCRIPTION		
			"High priority downlink CIR."
		::={whispLinkEntry 44}

	linkPlatformVer	OBJECT-TYPE
		SYNTAX		INTEGER
		MAX-ACCESS	read-only
		STATUS		current
		DESCRIPTION		
			"Platform Version."
		::={whispLinkEntry 45}

	smSessionTmr	OBJECT-TYPE
		SYNTAX		TimeTicks
		MAX-ACCESS	read-only
		STATUS		current
		DESCRIPTION		
			"SM session uptime"
		::={whispLinkEntry 46}

	smSessionSeqNumMismatch	OBJECT-TYPE
		SYNTAX		Counter32
		MAX-ACCESS	read-only
		STATUS		current
		DESCRIPTION		
			"The count of how many sequence number mismatch between the AP/BHM and the SM/BHS during the authentication
                            challenge and authentication response messages.  This status is only valid in a system where encryption is
                            enabled and no authentication server is configured."
		::={whispLinkEntry 47}

	dataVCNum	OBJECT-TYPE
		SYNTAX		INTEGER (18..255)
		MAX-ACCESS	read-only
		STATUS		current
		DESCRIPTION		
			"The Low Priority Data VC number in use for this link."
		::={whispLinkEntry 48}

	hiPriQEn	OBJECT-TYPE
		SYNTAX		INTEGER {
					disabled(0),
					enabled(1)}
		MAX-ACCESS	read-only
		STATUS		current
		DESCRIPTION		
			"Returns whether High Priority channel is enabled.  On P7/P8 devices will return 0 always.  Use p7p8HiPriQEn OID for P7/P8 radios."
		::={whispLinkEntry 49}

	dataVCNumHiQ	OBJECT-TYPE
		SYNTAX		INTEGER (18..255)
		MAX-ACCESS	read-only
		STATUS		current
		DESCRIPTION		
			"The high priority Data VC number in use for this link, if any.  If 0, no High Priority channel is in place."
		::={whispLinkEntry 50}

	linkInOctetsHiQ	OBJECT-TYPE
		SYNTAX		Counter32
		MAX-ACCESS	read-only
		STATUS		current
		DESCRIPTION		
			"The total number of octets received on High Priority Queue, including framing characters."
		::={whispLinkEntry 51}

	linkInUcastPktsHiQ	OBJECT-TYPE
		SYNTAX		Counter32
		MAX-ACCESS	read-only
		STATUS		current
		DESCRIPTION		
			"The number of subnetwork-unicast packets on High Priority Queue delivered to a higher-layer protocol."
		::={whispLinkEntry 52}

	linkInNUcastPktsHiQ	OBJECT-TYPE
		SYNTAX		Counter32
		MAX-ACCESS	read-only
		STATUS		current
		DESCRIPTION		
			"The number of non-unicast (i.e., subnetwork-broadcast or subnetwork-multicast) packets on High Priority Queue
                            delivered to a higher-layer protocol."
		::={whispLinkEntry 53}

	linkInDiscardsHiQ	OBJECT-TYPE
		SYNTAX		Counter32
		MAX-ACCESS	read-only
		STATUS		current
		DESCRIPTION		
			"The number of inbound packets on High Priority Queue which were chosen to be discarded even though no errors had been
                            detected to prevent their being deliverable to a higher-layer protocol.One possible reason for discarding such a packet 
                            could be to free up buffer space."
		::={whispLinkEntry 54}

	linkInErrorHiQ	OBJECT-TYPE
		SYNTAX		Counter32
		MAX-ACCESS	read-only
		STATUS		current
		DESCRIPTION		
			"The number of inbound packets on High Priority Queue that contained
                            errors preventing them from being deliverable to a higher-layer protocol."
		::={whispLinkEntry 55}

	linkInUnknownProtosHiQ	OBJECT-TYPE
		SYNTAX		Counter32
		MAX-ACCESS	read-only
		STATUS		current
		DESCRIPTION		
			"The number of packets received on High Priority Queue via the interface
                            which were discarded because of an unknown or unsupported protocol."
		::={whispLinkEntry 56}

	linkOutOctetsHiQ	OBJECT-TYPE
		SYNTAX		Counter32
		MAX-ACCESS	read-only
		STATUS		current
		DESCRIPTION		
			"The total number of octets on High Priority Queue transmitted out of the
                            interface, including framing characters."
		::={whispLinkEntry 57}

	linkOutUcastPktsHiQ	OBJECT-TYPE
		SYNTAX		Counter32
		MAX-ACCESS	read-only
		STATUS		current
		DESCRIPTION		
			"The total number of packets on High Priority Queue that higher-level  protocols requested be 
                             transmitted to a subnetwork-unicast address, including those that  were discarded or not sent."
		::={whispLinkEntry 58}

	linkOutNUcastPktsHiQ	OBJECT-TYPE
		SYNTAX		Counter32
		MAX-ACCESS	read-only
		STATUS		current
		DESCRIPTION		
			"The total number of packets on High Priority Queue that higher-level  protocols requested be transmitted to a non-
                            unicast (i.e., a subnetwork-broadcast or subnetwork-multicast) address, including those
                            that were discarded or not sent."
		::={whispLinkEntry 59}

	linkOutDiscardsHiQ	OBJECT-TYPE
		SYNTAX		Counter32
		MAX-ACCESS	read-only
		STATUS		current
		DESCRIPTION		
			"The number of outbound packets on High Priority Queue which were chosen  to be discarded even though no errors had been
                            detected to prevent their being transmitted.One possible reason for discarding such a packet could
                            be to free up buffer space."
		::={whispLinkEntry 60}

	linkOutErrorHiQ	OBJECT-TYPE
		SYNTAX		Counter32
		MAX-ACCESS	read-only
		STATUS		current
		DESCRIPTION		
			"The number of outbound packets on High Priority Queue that could not be
                            transmitted because of errors."
		::={whispLinkEntry 61}

	vcQOverflow	OBJECT-TYPE
		SYNTAX		Counter32
		MAX-ACCESS	read-only
		STATUS		current
		DESCRIPTION		
			"The number of packets dropped due to Queue overflow on VC."
		::={whispLinkEntry 62}

	vcQOverflowHiQ	OBJECT-TYPE
		SYNTAX		Counter32
		MAX-ACCESS	read-only
		STATUS		current
		DESCRIPTION		
			"The number of packets dropped due to Queue overflow on High Priority VC, if enabled."
		::={whispLinkEntry 63}

	p7p8HiPriQEn	OBJECT-TYPE
		SYNTAX		INTEGER {
					disabled-or-NA(0),
					enabled(1)}
		MAX-ACCESS	read-only
		STATUS		current
		DESCRIPTION		
			"Returns whether P7/P8 hi priority channel is enabled.  On non-P7/P8 devices will return 0 always."
		::={whispLinkEntry 64}

	p7p8HiPriQ	OBJECT-TYPE
		SYNTAX		Counter32
		MAX-ACCESS	read-only
		STATUS		current
		DESCRIPTION		
			"Hi Priority Queue statistics for P7 or P8 radios, if enabled.  If not enabled, or not a P7 or P8, will return 0."
		::={whispLinkEntry 65}

	linkAirDelayns	OBJECT-TYPE
		SYNTAX		INTEGER
		MAX-ACCESS	read-only
		STATUS		current
		DESCRIPTION		
			"The current round trip air delay in nanoseconds measured between the AP and SM."
		::={whispLinkEntry 66}

	linkQualityAPData	OBJECT-TYPE
		SYNTAX		DisplayString
		MAX-ACCESS	read-only
		STATUS		current
		DESCRIPTION		
			"Engineering use only.
                                The current link quality of the SM's data from the AP.
                                This is relative to the current modulation rate (1X, 2X, 3X, etc)."
		::={whispLinkEntry 67}

	linkManagementIP	OBJECT-TYPE
		SYNTAX		IpAddress
		MAX-ACCESS	read-only
		STATUS		current
		DESCRIPTION		
			"Management IP Address of the unit.  0 indicates SM is not publically addressable."
		::={whispLinkEntry 69}

	linkFragmentsReceived1XVertical	OBJECT-TYPE
		SYNTAX		Counter32
		MAX-ACCESS	read-only
		STATUS		current
		DESCRIPTION		
			"Engineering use only.
                            Number of fragments received in 1x (QPSK) modulation.
                            For GenII OFDM and forward.
                            For MIMO this is the vertical path."
		::={whispLinkEntry 70}

	linkFragmentsReceived2XVertical	OBJECT-TYPE
		SYNTAX		Counter32
		MAX-ACCESS	read-only
		STATUS		current
		DESCRIPTION		
			"Engineering use only.
                            Number of fragments received in 2x (16-QAM) modulation.
                            For GenII OFDM and forward.
                            For MIMO this is the vertical path."
		::={whispLinkEntry 71}

	linkFragmentsReceived3XVertical	OBJECT-TYPE
		SYNTAX		Counter32
		MAX-ACCESS	read-only
		STATUS		current
		DESCRIPTION		
			"Engineering use only.
                            Number of fragments received in 3x (64-QAM) modulation.
                            For GenII OFDM and forward.
                            For MIMO this is the vertical path."
		::={whispLinkEntry 72}

	linkFragmentsReceived4XVertical	OBJECT-TYPE
		SYNTAX		Counter32
		MAX-ACCESS	read-only
		STATUS		current
		DESCRIPTION		
			"Engineering use only.
                            Number of fragments received in 4x (256-QAM) modulation.
                            For GenII OFDM and forward.
                            For MIMO this is the vertical path."
		::={whispLinkEntry 73}

	signalToNoiseRatioVertical	OBJECT-TYPE
		SYNTAX		INTEGER
		MAX-ACCESS	read-only
		STATUS		current
		DESCRIPTION		
			"Estimate of the receive signal to noise ratio in dB.
                            For GenII OFDM and forward.
                            For MIMO this is the vertical path."
		::={whispLinkEntry 74}

	radiusReplyMsg	OBJECT-TYPE
		SYNTAX		DisplayString
		MAX-ACCESS	read-only
		STATUS		current
		DESCRIPTION		
			"The RADIUS Reply-Msg populated for the SM.
                            This is only valid when using a backen AAA server."
		::={whispLinkEntry 75}

	autoUpdateStatus	OBJECT-TYPE
		SYNTAX		INTEGER
		MAX-ACCESS	read-only
		STATUS		current
		DESCRIPTION		
			"status of the auto update process"
		::={whispLinkEntry 76}

	radiusFramedIPAddress	OBJECT-TYPE
		SYNTAX		IpAddress
		MAX-ACCESS	read-only
		STATUS		current
		DESCRIPTION		
			"This Attribute indicates the IP address to be configured for the SM management interface."
		::={whispLinkEntry 77}

	radiusFramedIPNetmask	OBJECT-TYPE
		SYNTAX		IpAddress
		MAX-ACCESS	read-only
		STATUS		current
		DESCRIPTION		
			"This Attribute indicates the netmask to be configured for the SM management interface."
		::={whispLinkEntry 78}

	radiusDefaultGateway	OBJECT-TYPE
		SYNTAX		IpAddress
		MAX-ACCESS	read-only
		STATUS		current
		DESCRIPTION		
			"This Attribute indicates the default gateway to be configured for the SM management interface."
		::={whispLinkEntry 79}

	linkFragmentsReceived1XHorizontal	OBJECT-TYPE
		SYNTAX		Counter32
		MAX-ACCESS	read-only
		STATUS		current
		DESCRIPTION		
			"Engineering use only.
                            Number of fragments received in 1x (QPSK) modulation.
                            For MIMO only.
                            For MIMO this is the horizontal path.
                            If operating in MIMO-A this will return 0."
		::={whispLinkEntry 80}

	linkFragmentsReceived2XHorizontal	OBJECT-TYPE
		SYNTAX		Counter32
		MAX-ACCESS	read-only
		STATUS		current
		DESCRIPTION		
			"Engineering use only.
                            Number of fragments received in 2x (16-QAM) modulation.
                            For MIMO only.
                            For MIMO this is the horizontal path.
                            If operating in MIMO-A this will return 0."
		::={whispLinkEntry 81}

	linkFragmentsReceived3XHorizontal	OBJECT-TYPE
		SYNTAX		Counter32
		MAX-ACCESS	read-only
		STATUS		current
		DESCRIPTION		
			"Engineering use only.
                            Number of fragments received in 3x (64-QAM) modulation.
                            For MIMO only.
                            For MIMO this is the horizontal path.
                            If operating in MIMO-A this will return 0."
		::={whispLinkEntry 82}

	linkFragmentsReceived4XHorizontal	OBJECT-TYPE
		SYNTAX		Counter32
		MAX-ACCESS	read-only
		STATUS		current
		DESCRIPTION		
			"Engineering use only.
                            Number of fragments received in 4x (256-QAM) modulation.
                            For MIMO only.
                            For MIMO this is the horizontal path.
                            If operating in MIMO-A this will return 0."
		::={whispLinkEntry 83}

	signalToNoiseRatioHorizontal	OBJECT-TYPE
		SYNTAX		INTEGER
		MAX-ACCESS	read-only
		STATUS		current
		DESCRIPTION		
			"Estimate of the receive signal to noise ratio in dB.
                            MIMO radios only.
                            For MIMO this is the horizontal path.
                            If operating in MIMO-A this will return 0."
		::={whispLinkEntry 84}

	linkSignalStrengthRatio	OBJECT-TYPE
		SYNTAX		DisplayString
		MAX-ACCESS	read-only
		STATUS		current
		DESCRIPTION		
			"Signal Strength Ratio in dB is the power received by the vertical antenna input (dB) -
                            power received by the horizontal antenna input (dB).
                            MIMO radios only."
		::={whispLinkEntry 86}

	linkRadioDbmHorizontal	OBJECT-TYPE
		SYNTAX		DisplayString
		MAX-ACCESS	read-only
		STATUS		current
		DESCRIPTION		
			"Receive power level of the horizontal antenna in dBm.
                            MIMO radios only."
		::={whispLinkEntry 87}

	linkRadioDbmVertical	OBJECT-TYPE
		SYNTAX		DisplayString
		MAX-ACCESS	read-only
		STATUS		current
		DESCRIPTION		
			"Receive power level of the vertical antenna in dBm.
                            MIMO radios only."
		::={whispLinkEntry 88}

	maxSMTxPwr	OBJECT-TYPE
		SYNTAX		INTEGER
		MAX-ACCESS	read-only
		STATUS		current
		DESCRIPTION		
			"Returns whether SM is transmitting at its configured max power level.
                            Engineering use only."
		::={whispLinkEntry 89}

	productType	OBJECT-TYPE
		SYNTAX		INTEGER {
					unknown(0),
					pmp450MIMOOFDM(1),
					pmp430SISOOFDM(2),
					pmp450SISOOFDM(3),
					ptp450(4),
					pmp450i(5),
					ptp450i(6),
					pmp450b(7),
					ptp450b(8)}
		MAX-ACCESS	read-only
		STATUS		current
		DESCRIPTION		
			"Returns which type of product the SM/BHS is.
                            450 platform only."
		::={whispLinkEntry 90}

	linkAdaptRateLowPri	OBJECT-TYPE
		SYNTAX		INTEGER {
					noSession(0),
					rate1X(1),
					rate2X(2),
					rate3X(3),
					rate4X(4),
					rate5X(5),
					rate6X(6),
					rate7X(7),
					rate8X(8)}
		MAX-ACCESS	read-only
		STATUS		current
		DESCRIPTION		
			"The current transmitting rate of the Low Priority Data Channel.
                            0 : SM is not in session
                            1 : 1X QPSK MIMO-A/SISO
                            2 : 2X 16-QAM MIMO-A/SISO or QPSK MIMO-B
                            3 : 3X 64-QAM MIMO-A/SISO or 8-QAM MIMO-B
                            4 : 4X 256-QAM MIMO-A/SISO or 16-QAM MIMO-B
                            5 : 5X 32-QAM MIMO-B
                            6 : 6X 64-QAM MIMO-B
                            7 : 7X 128-QAM MIMO-B
                            8 : 8X 256-QAM MIMO-B
                            
                            NOTE: As of 15.2 for 450 platform, the adapt rates are the same per LUID. This OID will provide this common per LUID rate."
		::={whispLinkEntry 91}

	linkAdaptRateHighPri	OBJECT-TYPE
		SYNTAX		INTEGER {
					noHighPriorityChannel(-1),
					noSession(0),
					rate1X(1),
					rate2X(2),
					rate3X(3),
					rate4X(4),
					rate5X(5),
					rate6X(6),
					rate7X(7),
					rate8X(8)}
		MAX-ACCESS	read-only
		STATUS		deprecated
		DESCRIPTION		
			"The current transmitting rate of the High Priority Data Channel.
                            -1 : High Priority Channel not configured
                            0 : SM is not in session
                            1 : 1X QPSK MIMO-A/SISO
                            2 : 2X 16-QAM MIMO-A/SISO or QPSK MIMO-B
                            3 : 3X 64-QAM MIMO-A/SISO or 8-QAM MIMO-B
                            4 : 4X 256-QAM MIMO-A/SISO or 16-QAM MIMO-B
                            5 : 5X 32-QAM MIMO-B
                            6 : 6X 64-QAM MIMO-B
                            7 : 7X 128-QAM MIMO-B
                            8 : 8X 256-QAM MIMO-B
                            
                            NOTE: As of 15.2 for 450 platform, the adapt rates are the same per LUID. OID linkAdaptRateLowPri will provide this common per LUID rate."
		::={whispLinkEntry 92}

	avgPowerLevelInt	OBJECT-TYPE
		SYNTAX		INTEGER
		MAX-ACCESS	read-only
		STATUS		current
		DESCRIPTION		
			"The average power level of registered SM as Integer.
                            For systems that support power control, this value can read '0' when the AP adjusts the transmit power of a SM
                            until new packets are received from the SM with it transmitting at its new power level.
                            For MIMO this is the combined receive power."
		::={whispLinkEntry 93}

	mimoPowerLevelVertical	OBJECT-TYPE
		SYNTAX		INTEGER
		MAX-ACCESS	read-only
		STATUS		current
		DESCRIPTION		
			"For MIMO radios, the Vertical power level of registered SM as Integer.
                            The Vertical Power (+45) level in case of 2.4GHz Dual slant MIMO"
		::={whispLinkEntry 94}

	mimoPowerLevelHorizontal	OBJECT-TYPE
		SYNTAX		INTEGER
		MAX-ACCESS	read-only
		STATUS		current
		DESCRIPTION		
			"For MIMO radios, the Horizontal power level of registered SM as Integer.
                            The Horizontal Power(-45) level in case of 2.4GHz Dual slant MIMO"
		::={whispLinkEntry 95}

	linkSwVersion	OBJECT-TYPE
		SYNTAX		DisplayString
		MAX-ACCESS	read-only
		STATUS		current
		DESCRIPTION		
			"The swversion of registered SM, to be used internally."
		::={whispLinkEntry 96}

	linkSpatialFrequency	OBJECT-TYPE
		SYNTAX		INTEGER {
					noSession(-1),
					invalid(2048)}
		MAX-ACCESS	read-only
		STATUS		current
		DESCRIPTION		
			"The spatial frequency of registered SM.
                            Spatial Frequency is the phase advance of the wavefront from one antenna column
                            to the next caused by the angle at which the wavefront impinges on the array.
                            It is represented in integer units, with 1024 equating to 360 degrees per column.
                            A value of 2048 is used to signify a spatial frequency that is not yet known or otherwise invalid.
                            A value of -1 is used to indicate that SM is not in session. 
                            PMP 450m only."
		::={whispLinkEntry 97}

	sesMedUpCIR	OBJECT-TYPE
		SYNTAX		INTEGER
		MAX-ACCESS	read-only
		STATUS		current
		DESCRIPTION		
			"Medium priority uplink CIR."
		::={whispLinkEntry 98}

	sesMedDownCIR	OBJECT-TYPE
		SYNTAX		INTEGER
		MAX-ACCESS	read-only
		STATUS		current
		DESCRIPTION		
			"Medium priority downlink CIR."
		::={whispLinkEntry 99}

	sesUHiUpCIR	OBJECT-TYPE
		SYNTAX		INTEGER
		MAX-ACCESS	read-only
		STATUS		current
		DESCRIPTION		
			"Ultra High priority uplink CIR."
		::={whispLinkEntry 100}

	sesUHiDownCIR	OBJECT-TYPE
		SYNTAX		INTEGER
		MAX-ACCESS	read-only
		STATUS		current
		DESCRIPTION		
			"Ultra High priority downlink CIR."
		::={whispLinkEntry 101}

	mediumPriQEn	OBJECT-TYPE
		SYNTAX		INTEGER {
					disabled(0),
					enabled(1)}
		MAX-ACCESS	read-only
		STATUS		current
		DESCRIPTION		
			"Returns whether Medium Priority channel is enabled."
		::={whispLinkEntry 102}

	dataVCNumMediumQ	OBJECT-TYPE
		SYNTAX		INTEGER (18..255)
		MAX-ACCESS	read-only
		STATUS		current
		DESCRIPTION		
			"The Medium priority Data VC number in use for this link, if any.  If 0, no Medium Priority channel is in place."
		::={whispLinkEntry 103}

	linkInOctetsMediumQ	OBJECT-TYPE
		SYNTAX		Counter64
		MAX-ACCESS	read-only
		STATUS		current
		DESCRIPTION		
			"The total number of octets received on Medium Priority Queue, including framing characters."
		::={whispLinkEntry 104}

	linkInUcastPktsMediumQ	OBJECT-TYPE
		SYNTAX		Counter64
		MAX-ACCESS	read-only
		STATUS		current
		DESCRIPTION		
			"The number of subnetwork-unicast packets on Medium Priority Queue
                            delivered to a higher-layer protocol."
		::={whispLinkEntry 105}

	linkInNUcastPktsMediumQ	OBJECT-TYPE
		SYNTAX		Counter64
		MAX-ACCESS	read-only
		STATUS		current
		DESCRIPTION		
			"The number of non-unicast (i.e., subnetwork-broadcast or subnetwork-multicast) packets on Medium Priority Queue
                            delivered to a higher-layer protocol."
		::={whispLinkEntry 106}

	linkInDiscardsMediumQ	OBJECT-TYPE
		SYNTAX		Counter64
		MAX-ACCESS	read-only
		STATUS		current
		DESCRIPTION		
			"The number of inbound packets on Medium Priority Queue which were chosen to be discarded even though no errors had been
                            detected to prevent their being deliverable to a higher-layer protocol.One possible reason for
                            discarding such a packet could be to free up  buffer space."
		::={whispLinkEntry 107}

	linkInErrorMediumQ	OBJECT-TYPE
		SYNTAX		Counter64
		MAX-ACCESS	read-only
		STATUS		current
		DESCRIPTION		
			"The number of inbound packets on Medium Priority Queue that contained
                            errors preventing them from being deliverable to a higher-layer protocol."
		::={whispLinkEntry 108}

	linkInUnknownProtosMediumQ	OBJECT-TYPE
		SYNTAX		Counter32
		MAX-ACCESS	read-only
		STATUS		current
		DESCRIPTION		
			"The number of packets received on Medium Priority Queue via the interface
                            which were discarded because of an unknown or
                            unsupported protocol."
		::={whispLinkEntry 109}

	linkOutOctetsMediumQ	OBJECT-TYPE
		SYNTAX		Counter64
		MAX-ACCESS	read-only
		STATUS		current
		DESCRIPTION		
			"The total number of octets on Medium Priority Queue transmitted out of the
                            interface, including framing characters."
		::={whispLinkEntry 110}

	linkOutUcastPktsMediumQ	OBJECT-TYPE
		SYNTAX		Counter64
		MAX-ACCESS	read-only
		STATUS		current
		DESCRIPTION		
			"The total number of packets on Medium Priority Queue that higher-levelprotocols requested be transmitted
                            to a subnetwork-unicast address,including those that were discarded or not sent."
		::={whispLinkEntry 111}

	linkOutNUcastPktsMediumQ	OBJECT-TYPE
		SYNTAX		Counter64
		MAX-ACCESS	read-only
		STATUS		current
		DESCRIPTION		
			"The total number of packets on Medium Priority Queue that higher-levelprotocols requested be transmitted
                            to a subnetwork-unicast address, including those that were discarded or not sent."
		::={whispLinkEntry 112}

	linkOutDiscardsMediumQ	OBJECT-TYPE
		SYNTAX		Counter64
		MAX-ACCESS	read-only
		STATUS		current
		DESCRIPTION		
			"The number of outbound packets on Medium Priority Queue which were chosen to be discarded even though no errors 
                             had been detected to prevent their being transmitted.One possible reason for discarding such a packet could
                             be to free up buffer space."
		::={whispLinkEntry 113}

	linkOutErrorMediumQ	OBJECT-TYPE
		SYNTAX		Counter64
		MAX-ACCESS	read-only
		STATUS		current
		DESCRIPTION		
			"The number of outbound packets on Medium Priority Queue that could not be transmitted because of errors."
		::={whispLinkEntry 114}

	ultraHighPriQEn	OBJECT-TYPE
		SYNTAX		INTEGER {
					disabled(0),
					enabled(1)}
		MAX-ACCESS	read-only
		STATUS		current
		DESCRIPTION		
			"Returns whether Ultra High Priority channel is enabled."
		::={whispLinkEntry 115}

	dataVCNumUltraHighQ	OBJECT-TYPE
		SYNTAX		INTEGER (18..255)
		MAX-ACCESS	read-only
		STATUS		current
		DESCRIPTION		
			"The Ultra High priority Data VC number in use for this link, if any. If 0, no Ultra High Priority channel is in place."
		::={whispLinkEntry 116}

	linkInOctetsUltraHighQ	OBJECT-TYPE
		SYNTAX		Counter64
		MAX-ACCESS	read-only
		STATUS		current
		DESCRIPTION		
			"The total number of octets received on Ultra High Priority Queue, including framing characters."
		::={whispLinkEntry 117}

	linkInUcastPktsUltraHighQ	OBJECT-TYPE
		SYNTAX		Counter64
		MAX-ACCESS	read-only
		STATUS		current
		DESCRIPTION		
			"The number of subnetwork-unicast packets on Ultra High Priority Queue delivered to a higher-layer protocol."
		::={whispLinkEntry 118}

	linkInNUcastPktsUltraHighQ	OBJECT-TYPE
		SYNTAX		Counter64
		MAX-ACCESS	read-only
		STATUS		current
		DESCRIPTION		
			"The number of non-unicast (i.e., subnetwork-broadcast or subnetwork-multicast) packets on Ultra High Priority Queue
                            delivered to a higher-layer protocol."
		::={whispLinkEntry 119}

	linkInDiscardsUltraHighQ	OBJECT-TYPE
		SYNTAX		Counter64
		MAX-ACCESS	read-only
		STATUS		current
		DESCRIPTION		
			"The number of inbound packets on Ultra High Priority Queue which were chosen to be discarded even though no errors had been
                            detected to prevent their being deliverable to a higher-layer protocol.One possible reason for  discarding such a packet could 
                            be to free up buffer space."
		::={whispLinkEntry 120}

	linkInErrorUltraHighQ	OBJECT-TYPE
		SYNTAX		Counter64
		MAX-ACCESS	read-only
		STATUS		current
		DESCRIPTION		
			"The number of inbound packets on Ultra High Priority Queue that contained errors preventing them 
                            from being deliverable to a higher-layer protocol."
		::={whispLinkEntry 121}

	linkInUnknownProtosUltraHighQ	OBJECT-TYPE
		SYNTAX		Counter32
		MAX-ACCESS	read-only
		STATUS		current
		DESCRIPTION		
			"The number of packets received on Ultra High Priority Queue via the interface which were discarded because 
                            of an unknown or unsupported protocol."
		::={whispLinkEntry 122}

	linkOutOctetsUltraHighQ	OBJECT-TYPE
		SYNTAX		Counter64
		MAX-ACCESS	read-only
		STATUS		current
		DESCRIPTION		
			"The total number of octets on Ultra High Priority Queue transmitted out of the
                            interface, including framing characters."
		::={whispLinkEntry 123}

	linkOutUcastPktsUltraHighQ	OBJECT-TYPE
		SYNTAX		Counter64
		MAX-ACCESS	read-only
		STATUS		current
		DESCRIPTION		
			"The total number of packets on Ultra High Priority Queue that higher-level protocols requested be transmitted to a
                            subnetwork-unicast address, including those that were discarded or not sent."
		::={whispLinkEntry 124}

	linkOutNUcastPktsUltraHighQ	OBJECT-TYPE
		SYNTAX		Counter64
		MAX-ACCESS	read-only
		STATUS		current
		DESCRIPTION		
			"The total number of packets on Ultra High Priority Queue that higher-level protocols requested be transmitted to a non-
                            unicast (i.e., a subnetwork-broadcast or subnetwork-multicast) address, including those that were discarded or not sent."
		::={whispLinkEntry 125}

	linkOutDiscardsUltraHighQ	OBJECT-TYPE
		SYNTAX		Counter64
		MAX-ACCESS	read-only
		STATUS		current
		DESCRIPTION		
			"The number of outbound packets on Ultra High Priority Queue which were chosen to be discarded even though no errors 
                            had been detected to prevent their being transmitted.One possible reason for discarding such a packet could Be to 
                            free up buffer space."
		::={whispLinkEntry 126}

	linkOutErrorUltraHighQ	OBJECT-TYPE
		SYNTAX		Counter64
		MAX-ACCESS	read-only
		STATUS		current
		DESCRIPTION		
			"The number of outbound packets on Ultra High Priority Queue that could not be transmitted because of errors."
		::={whispLinkEntry 127}

	vcQOverflowMediumQ	OBJECT-TYPE
		SYNTAX		Counter32
		MAX-ACCESS	read-only
		STATUS		current
		DESCRIPTION		
			"The number of packets dropped due to Queue overflow on Medium Priority VC, if enabled."
		::={whispLinkEntry 128}

	vcQOverflowUltraHighQ	OBJECT-TYPE
		SYNTAX		Counter32
		MAX-ACCESS	read-only
		STATUS		current
		DESCRIPTION		
			"The number of packets dropped due to Queue overflow on Ultra High Priority VC, if enabled."
		::={whispLinkEntry 129}

	linkInOctets64	OBJECT-TYPE
		SYNTAX		Counter64
		MAX-ACCESS	read-only
		STATUS		current
		DESCRIPTION		
			"The total number of octets received on the interface, including framing characters."
		::={whispLinkEntry 130}

	linkInUcastPkts64	OBJECT-TYPE
		SYNTAX		Counter64
		MAX-ACCESS	read-only
		STATUS		current
		DESCRIPTION		
			"The number of subnetwork-unicast packets delivered to a higher-layer protocol."
		::={whispLinkEntry 131}

	linkInNUcastPkts64	OBJECT-TYPE
		SYNTAX		Counter64
		MAX-ACCESS	read-only
		STATUS		current
		DESCRIPTION		
			"The number of non-unicast (i.e., subnetwork-broadcast or subnetwork-multicast) packets
                            delivered to a higher-layer protocol."
		::={whispLinkEntry 132}

	linkInDiscards64	OBJECT-TYPE
		SYNTAX		Counter64
		MAX-ACCESS	read-only
		STATUS		current
		DESCRIPTION		
			"The number of inbound packets which were chosen to be discarded even though no errors had been
                            detected to prevent their being deliverable to a higher-layer protocol. One possible reason for
                            discarding such a packet could be to free up buffer space."
		::={whispLinkEntry 133}

	linkInError64	OBJECT-TYPE
		SYNTAX		Counter64
		MAX-ACCESS	read-only
		STATUS		current
		DESCRIPTION		
			"The number of inbound packets that contained errors preventing them from being deliverable to a
                            higher-layer protocol."
		::={whispLinkEntry 134}

	linkOutOctets64	OBJECT-TYPE
		SYNTAX		Counter64
		MAX-ACCESS	read-only
		STATUS		current
		DESCRIPTION		
			"The total number of octets transmitted out of the interface, including framing characters."
		::={whispLinkEntry 135}

	linkOutUcastPkts64	OBJECT-TYPE
		SYNTAX		Counter64
		MAX-ACCESS	read-only
		STATUS		current
		DESCRIPTION		
			"The total number of packets that higher-level  protocols requested be transmitted to a
                            subnetwork-unicast address, including those that  were discarded or not sent."
		::={whispLinkEntry 136}

	linkOutNUcastPkts64	OBJECT-TYPE
		SYNTAX		Counter64
		MAX-ACCESS	read-only
		STATUS		current
		DESCRIPTION		
			"The total number of packets that higher-level protocols requested be transmitted to a non-
                            unicast (i.e., a subnetwork-broadcast or subnetwork-multicast) address, including those that were
                            discarded or not sent."
		::={whispLinkEntry 137}

	linkOutDiscards64	OBJECT-TYPE
		SYNTAX		Counter64
		MAX-ACCESS	read-only
		STATUS		current
		DESCRIPTION		
			"The number of outbound packets which were chosen to be discarded even though no errors had been
                            detected to prevent their being transmitted.One possible reason for discarding such a packet could
                            be to free up buffer space."
		::={whispLinkEntry 138}

	linkOutError64	OBJECT-TYPE
		SYNTAX		Counter64
		MAX-ACCESS	read-only
		STATUS		current
		DESCRIPTION		
			"The number of outbound packets that could not be transmitted because of errors."
		::={whispLinkEntry 139}

	linkInOctetsHiQ64	OBJECT-TYPE
		SYNTAX		Counter64
		MAX-ACCESS	read-only
		STATUS		current
		DESCRIPTION		
			"The total number of octets received on High Priority Queue, including framing characters."
		::={whispLinkEntry 140}

	linkInUcastPktsHiQ64	OBJECT-TYPE
		SYNTAX		Counter64
		MAX-ACCESS	read-only
		STATUS		current
		DESCRIPTION		
			"The number of subnetwork-unicast packets on High Priority Queue delivered to a higher-layer protocol."
		::={whispLinkEntry 141}

	linkInNUcastPktsHiQ64	OBJECT-TYPE
		SYNTAX		Counter64
		MAX-ACCESS	read-only
		STATUS		current
		DESCRIPTION		
			"The number of non-unicast (i.e., subnetwork-broadcast or subnetwork-multicast) packets on High Priority Queue
                            delivered to a higher-layer protocol."
		::={whispLinkEntry 142}

	linkInDiscardsHiQ64	OBJECT-TYPE
		SYNTAX		Counter64
		MAX-ACCESS	read-only
		STATUS		current
		DESCRIPTION		
			"The number of inbound packets on High Priority Queue which were chosen to be discarded even though no errors had been
                            detected to prevent their being deliverable to a higher-layer protocol.One possible reason for discarding such a packet 
                            could be to free up buffer space."
		::={whispLinkEntry 143}

	linkInErrorHiQ64	OBJECT-TYPE
		SYNTAX		Counter64
		MAX-ACCESS	read-only
		STATUS		current
		DESCRIPTION		
			"The number of inbound packets on High Priority Queue that contained
                            errors preventing them from being deliverable to a higher-layer protocol."
		::={whispLinkEntry 144}

	linkOutOctetsHiQ64	OBJECT-TYPE
		SYNTAX		Counter64
		MAX-ACCESS	read-only
		STATUS		current
		DESCRIPTION		
			"The total number of octets on High Priority Queue transmitted out of the
                            interface, including framing characters."
		::={whispLinkEntry 145}

	linkOutUcastPktsHiQ64	OBJECT-TYPE
		SYNTAX		Counter64
		MAX-ACCESS	read-only
		STATUS		current
		DESCRIPTION		
			"The total number of packets on High Priority Queue that higher-level  protocols requested be 
                             transmitted to a subnetwork-unicast address, including those that  were discarded or not sent."
		::={whispLinkEntry 146}

	linkOutNUcastPktsHiQ64	OBJECT-TYPE
		SYNTAX		Counter64
		MAX-ACCESS	read-only
		STATUS		current
		DESCRIPTION		
			"The total number of packets on High Priority Queue that higher-level  protocols requested be transmitted to a non-
                            unicast (i.e., a subnetwork-broadcast or subnetwork-multicast) address, including those
                            that were discarded or not sent."
		::={whispLinkEntry 147}

	linkOutDiscardsHiQ64	OBJECT-TYPE
		SYNTAX		Counter64
		MAX-ACCESS	read-only
		STATUS		current
		DESCRIPTION		
			"The number of outbound packets on High Priority Queue which were chosen  to be discarded even though no errors had been
                            detected to prevent their being transmitted.One possible reason for discarding such a packet could
                            be to free up buffer space."
		::={whispLinkEntry 148}

	linkOutErrorHiQ64	OBJECT-TYPE
		SYNTAX		Counter64
		MAX-ACCESS	read-only
		STATUS		current
		DESCRIPTION		
			"The number of outbound packets on High Priority Queue that could not be
                            transmitted because of errors."
		::={whispLinkEntry 149}

	retransmittedFragmentsCount	OBJECT-TYPE
		SYNTAX		DisplayString
		MAX-ACCESS	read-only
		STATUS		current
		DESCRIPTION		
			"Retransmitted fragments are a normal part of operation, and are not considered errors.
                            Higher modulation rate are periodically tested in the system and will result in retransmissions.
                            For example, a link operating at 8X may have more retransmissions than a link at 6X but still be able to higher throughput at 8X.
                            Therefore this statistic can be misleading, analyze with caution."
		::={whispLinkEntry 150}

	soundingState	OBJECT-TYPE
		SYNTAX		INTEGER {
					unknown(0),
					new(1),
					assessing(2),
					tracking(3),
					untrusted(4)}
		MAX-ACCESS	read-only
		STATUS		current
		DESCRIPTION		
			"Current operational state of an interface.
                            0 = Unknown
                            1 = New
                            2 = Assessing
                            3 = Tracking
                            4 = Untrusted"
		::={whispLinkEntry 151}

	downlinkSoundingState	OBJECT-TYPE
		SYNTAX		INTEGER {
					unknown(0),
					new(1),
					assessing(2),
					tracking(3),
					untrusted(4)}
		MAX-ACCESS	read-only
		STATUS		current
		DESCRIPTION		
			"Current operational state of an interface.
                            0 = Unknown
                            1 = New
                            2 = Assessing
                            3 = Tracking
                            4 = Untrusted"
		::={whispLinkEntry 152}

	uplinkSoundingState	OBJECT-TYPE
		SYNTAX		INTEGER {
					unknown(0),
					new(1),
					assessing(2),
					tracking(3),
					untrusted(4)}
		MAX-ACCESS	read-only
		STATUS		current
		DESCRIPTION		
			"Current operational state of an interface.
                            0 = Unknown
                            1 = New
                            2 = Assessing
                            3 = Tracking
                            4 = Untrusted"
		::={whispLinkEntry 153}

	downlinkMumimoRateAdapt	OBJECT-TYPE
		SYNTAX		INTEGER {
					noSession(0),
					rate1X(1),
					rate2X(2),
					rate3X(3),
					rate4X(4),
					rate5X(5),
					rate6X(6),
					rate7X(7),
					rate8X(8),
					ineligibleForMumimo(9)}
		MAX-ACCESS	read-only
		STATUS		current
		DESCRIPTION		
			"Downlink MU-MIMO Rate Adapt
                            0 : SM is not in session
                            1 : 1X QPSK MIMO-A
                            2 : 2X 16-QAM MIMO-A or QPSK MIMO-B
                            3 : 3X 64-QAM MIMO-A or 8-QAM MIMO-B
                            4 : 4X 256-QAM MIMO-A or 16-QAM MIMO-B
                            5 : 5X 32-QAM MIMO-B
                            6 : 6X 64-QAM MIMO-B
                            7 : 7X 128-QAM MIMO-B
                            8 : 8X 256-QAM MIMO-B
                            9 : Ineligible for MU-MIMO Operation"
		::={whispLinkEntry 154}

	uplinkMumimoRateAdapt	OBJECT-TYPE
		SYNTAX		INTEGER {
					noSession(0),
					rate1X(1),
					rate2X(2),
					rate3X(3),
					rate4X(4),
					rate5X(5),
					rate6X(6),
					rate7X(7),
					rate8X(8),
					ineligibleForMumimo(9)}
		MAX-ACCESS	read-only
		STATUS		current
		DESCRIPTION		
			"Uplink MU-MIMO Rate Adapt
                            0 : SM is not in session
                            1 : 1X QPSK MIMO-A
                            2 : 2X 16-QAM MIMO-A or QPSK MIMO-B
                            3 : 3X 64-QAM MIMO-A or 8-QAM MIMO-B
                            4 : 4X 256-QAM MIMO-A or 16-QAM MIMO-B
                            5 : 5X 32-QAM MIMO-B
                            6 : 6X 64-QAM MIMO-B
                            7 : 7X 128-QAM MIMO-B
                            8 : 8X 256-QAM MIMO-B
                            9 : Ineligible for MU-MIMO Operation"
		::={whispLinkEntry 155}

	averageEvmDownlinkPathA	OBJECT-TYPE
		SYNTAX		INTEGER {
					na(0)}
		MAX-ACCESS	read-only
		STATUS		current
		DESCRIPTION		
			"The average downlink EVM expressed in dB for Path A."
		::={whispLinkEntry 156}

	averageEvmDownlinkPathB	OBJECT-TYPE
		SYNTAX		INTEGER {
					na(0)}
		MAX-ACCESS	read-only
		STATUS		current
		DESCRIPTION		
			"The average downlink EVM expressed in dB for Path B."
		::={whispLinkEntry 157}

	combinedEvmDownlink	OBJECT-TYPE
		SYNTAX		INTEGER {
					na(0)}
		MAX-ACCESS	read-only
		STATUS		current
		DESCRIPTION		
			"The combined downlink EVM expressed in dB for both paths.
                            This value is scaled up by 10 (ie. -269 is equivalent to -26.9 dB)."
		::={whispLinkEntry 158}

	averageEvmUplinkPathA	OBJECT-TYPE
		SYNTAX		INTEGER {
					na(0)}
		MAX-ACCESS	read-only
		STATUS		current
		DESCRIPTION		
			"The average uplink EVM expressed in dB for Path A."
		::={whispLinkEntry 159}

	averageEvmUplinkPathB	OBJECT-TYPE
		SYNTAX		INTEGER {
					na(0)}
		MAX-ACCESS	read-only
		STATUS		current
		DESCRIPTION		
			"The average uplink EVM expressed in dB for Path B."
		::={whispLinkEntry 160}

	combinedEvmUplink	OBJECT-TYPE
		SYNTAX		INTEGER {
					na(0)}
		MAX-ACCESS	read-only
		STATUS		current
		DESCRIPTION		
			"The combined uplink EVM expressed in dB for both paths.
                            This value is scaled up by 10 (ie. -269 is equivalent to -26.9 dB)."
		::={whispLinkEntry 161}

	fastRateAdaptActive	OBJECT-TYPE
		SYNTAX		INTEGER {
					false(0),
					true(1)}
		MAX-ACCESS	read-only
		STATUS		current
		DESCRIPTION		
			"Returns TRUE if Fast Rate Adapt is active on this link.
                            Engineering Key only."
		::={whispLinkEntry 162}

	bestEvmDownlinkPathA	OBJECT-TYPE
		SYNTAX		INTEGER {
					na(0)}
		MAX-ACCESS	read-only
		STATUS		current
		DESCRIPTION		
			"The best downlink EVM for 1 minute expressed in dB for Path A."
		::={whispLinkEntry 163}

	bestEvmDownlinkPathB	OBJECT-TYPE
		SYNTAX		INTEGER {
					na(0)}
		MAX-ACCESS	read-only
		STATUS		current
		DESCRIPTION		
			"The best downlink EVM for 1 minute expressed in dB for Path B."
		::={whispLinkEntry 164}

	bestEvmUplinkPathA	OBJECT-TYPE
		SYNTAX		INTEGER {
					na(0)}
		MAX-ACCESS	read-only
		STATUS		current
		DESCRIPTION		
			"The best uplink EVM for 1 minute expressed in dB for Path A."
		::={whispLinkEntry 165}

	bestEvmUplinkPathB	OBJECT-TYPE
		SYNTAX		INTEGER {
					na(0)}
		MAX-ACCESS	read-only
		STATUS		current
		DESCRIPTION		
			"The best uplink EVM for 1 minute expressed in dB for Path B."
		::={whispLinkEntry 166}

	worstEvmDownlinkPathA	OBJECT-TYPE
		SYNTAX		INTEGER {
					na(0)}
		MAX-ACCESS	read-only
		STATUS		current
		DESCRIPTION		
			"The worst downlink EVM for 1 minute expressed in dB for Path A."
		::={whispLinkEntry 167}

	worstEvmDownlinkPathB	OBJECT-TYPE
		SYNTAX		INTEGER {
					na(0)}
		MAX-ACCESS	read-only
		STATUS		current
		DESCRIPTION		
			"The worst downlink EVM for 1 minute expressed in dB for Path B."
		::={whispLinkEntry 168}

	worstEvmUplinkPathA	OBJECT-TYPE
		SYNTAX		INTEGER {
					na(0)}
		MAX-ACCESS	read-only
		STATUS		current
		DESCRIPTION		
			"The worst uplink EVM for 1 minute expressed in dB for Path A."
		::={whispLinkEntry 169}

	worstEvmUplinkPathB	OBJECT-TYPE
		SYNTAX		INTEGER {
					na(0)}
		MAX-ACCESS	read-only
		STATUS		current
		DESCRIPTION		
			"The worst uplink EVM for 1 minute expressed in dB for Path B."
		::={whispLinkEntry 170}

	linkColorCodePriority	OBJECT-TYPE
		SYNTAX		INTEGER {
					noSession(-1),
					installationColorCode(0),
					primary(1),
					secondary(2),
					tertiary(3)}
		MAX-ACCESS	read-only
		STATUS		current
		DESCRIPTION		
			"Color Code Priority"
		::={whispLinkEntry 171}

	modRateDL	OBJECT-TYPE
		SYNTAX		DisplayString
		MAX-ACCESS	read-only
		STATUS		current
		DESCRIPTION		
			"Downlink modulation rate of registered CanopyV SMs."
		::={whispLinkEntry 172}

	linkVcDepth	OBJECT-TYPE
		SYNTAX		INTEGER {
					na(0)}
		MAX-ACCESS	read-only
		STATUS		current
		DESCRIPTION		
			"VC Depth for the given LUID."
		::={whispLinkEntry 173}

	whispFailedRegTable OBJECT-TYPE
		SYNTAX		SEQUENCE OF WhispFailedRegEntry
		MAX-ACCESS	not-accessible
		STATUS		current
		DESCRIPTION
			"List of link test results"
		::= {whispAps 8}

	whispFailedRegEntry OBJECT-TYPE
		SYNTAX		WhispFailedRegEntry
		MAX-ACCESS	not-accessible
		STATUS		current
		DESCRIPTION
			"List of Failed ESNs"
		INDEX		{regFailSeqNum}
		::= {whispFailedRegTable 1}

		WhispFailedRegEntry ::= SEQUENCE{
			regFailSeqNum		Counter32,
			regFailESN		PhysAddress,
			regGrantReason		INTEGER,
			regFailTime		TimeTicks,
			regFailReasonText	DisplayString
			}

	regGrantReason	OBJECT-TYPE
		SYNTAX		INTEGER {
					reggnt-valid(0),
					reggnt-outofrange(1),
					reggnt-nolUIDS(2),
					reggnt-rerange(3),
					reggnt-authfail(4),
					reggnt-encryptfail(5),
					reggnt-poweradjust(6),
					reggnt-novcs(7),
					reggnt-failvcreserve(8),
					reggnt-failvcactive(9),
					reggnt-failhivcdata(10),
					reggnt-failsmlimit(11),
					reggnt-fail95orabove(12)}
		MAX-ACCESS	read-only
		STATUS		current
		DESCRIPTION		
			"The registration failure reason"
		::={whispFailedRegEntry 1}

	regFailESN	OBJECT-TYPE
		SYNTAX		PhysAddress
		MAX-ACCESS	read-only
		STATUS		current
		DESCRIPTION		
			"The ESN that failed to register"
		::={whispFailedRegEntry 2}

	regFailTime	OBJECT-TYPE
		SYNTAX		TimeTicks
		MAX-ACCESS	read-only
		STATUS		current
		DESCRIPTION		
			"The number of ticks that occurred when the ESN failed to register"
		::={whispFailedRegEntry 3}

	regFailSeqNum	OBJECT-TYPE
		SYNTAX		Counter32
		MAX-ACCESS	read-only
		STATUS		current
		DESCRIPTION		
			"The sequence when the register failure was given."
		::={whispFailedRegEntry 4}

	regFailReasonText	OBJECT-TYPE
		SYNTAX		DisplayString
		MAX-ACCESS	read-only
		STATUS		current
		DESCRIPTION		
			"The text description of the failure."
		::={whispFailedRegEntry 5}


END
