CAMBIUM-PTP650-MIB DEFINITIONS ::= BEGIN

   IMPORTS
      MODULE-IDENTITY, OBJECT-TYPE, NOTIFICATION-TYPE,
      Integer32, IpAddress,
      enterprises
         FROM SNMPv2-SMI
      MODULE-COMPLIANCE, OBJECT-GROUP, NOTIFICATION-GROUP
         FROM SNMPv2-CONF
      DisplayString
         FROM SNMPv2-TC
      InetAddress, InetAddressType
         FROM INET-ADDRESS-MIB;

   cambium MODULE-IDENTITY
      LAST-UPDATED "201502060443Z"
      ORGANIZATION "Cambium Networks Ltd."
      CONTACT-INFO
         "Post:  Simon Whitaker
                 Cambium Networks Ltd.
                 Unit B2,
                 Linhay Business Park,
                 Eastern Road,
                 Ashburton,
                 Devon.
                 TQ13 7UP
                 United Kingdom
         Phone:  +44 (0) 1364 655 500
         Email:  simon.whitaker@cambiumnetworks.com"
      DESCRIPTION
         "MIB for non-line-of-sight (NLOS) wireless ethernet bridge."
      REVISION "201502060443Z"
      DESCRIPTION
         "PTP650-01-40:
         Added Second Data Service attributes to support a second data path over
         wireless link.
         Added support for Cable Diagnostics.
         Added IEEE 1588 Transparent Clock source port and Transparent Clock source
         alarm attributes."
      REVISION "201406181412Z"
      DESCRIPTION
         "PTP650-01-20:
         Added TDM group and NIDU attributes to support the telecomms interfaces.
         Added Router Protocols group to support Microwave Adaptive Bandwidth (MAB).
         Added support for Out-Of-Band Remote Management, and for mute and enable
         transmission. Renamed 'ethernet bridging' attributes to 'data bridging'.
         Made more SyncE attributes writable."
      REVISION "201402211503Z"
      DESCRIPTION
         "PTP650-01-10:
         Added Synchronous Ethernet (SyncE) and IEEE 1588 Transparent Clock.
         Support PTP650s. Clarified localPacketFiltering, regulatoryBand,
         TDD Sync status & alarm. TX power max increased to 30dBm.
         Modified the bit assignments of enabledDiagnosticAlarms to combine
         the various status & warning bits for the main PSU, Aux & SFP ports
         into a single portState bit."
      REVISION "201308021028Z"
      DESCRIPTION "PTP650-01-00: Initial revision."
      ::= { enterprises 17713 }

   -- Groups in cambium
   ptp                OBJECT IDENTIFIER ::= { cambium 1 }
   ptmp               OBJECT IDENTIFIER ::= { cambium 2 }
   ptp650             OBJECT IDENTIFIER ::= { cambium 7 }

   -- Groups in ptp650
   dfs                 OBJECT IDENTIFIER ::= { ptp650 3 }
   bridge              OBJECT IDENTIFIER ::= { ptp650 4 }
   configuration       OBJECT IDENTIFIER ::= { ptp650 5 }
   ethernet            OBJECT IDENTIFIER ::= { ptp650 6 }
   tDM                 OBJECT IDENTIFIER ::= { ptp650 7 }
   license             OBJECT IDENTIFIER ::= { ptp650 8 }
   management          OBJECT IDENTIFIER ::= { ptp650 9 }
   phyControl          OBJECT IDENTIFIER ::= { ptp650 10 }
   phyStatus           OBJECT IDENTIFIER ::= { ptp650 12 }
   alarms              OBJECT IDENTIFIER ::= { ptp650 13 }
   smtp                OBJECT IDENTIFIER ::= { ptp650 15 }
   snmpControl         OBJECT IDENTIFIER ::= { ptp650 16 }
   sntp                OBJECT IDENTIFIER ::= { ptp650 17 }
   reset               OBJECT IDENTIFIER ::= { ptp650 18 }
   versions            OBJECT IDENTIFIER ::= { ptp650 19 }
   pubStats            OBJECT IDENTIFIER ::= { ptp650 20 }
   encryption          OBJECT IDENTIFIER ::= { ptp650 22 }
   tDDControl          OBJECT IDENTIFIER ::= { ptp650 23 }
   aAAControl          OBJECT IDENTIFIER ::= { ptp650 25 }
   syslogControl       OBJECT IDENTIFIER ::= { ptp650 24 }
   routerProtocols     OBJECT IDENTIFIER ::= { ptp650 26 }
   cableDiagnostics    OBJECT IDENTIFIER ::= { ptp650 27 }
   supplementary       OBJECT IDENTIFIER ::= { ptp650 96 }
   ptpGroups          OBJECT IDENTIFIER ::= { ptp650 98 }
   ptpTraps           OBJECT IDENTIFIER ::= { ptp650 99 }
   ptpTrapPrefix      OBJECT IDENTIFIER ::= { ptpTraps 0 }

   -- Compliance information
   --
   ptpCompliance MODULE-COMPLIANCE
      STATUS current
      DESCRIPTION
         "The compliance statement for the Cambium PTP MIB"
      MODULE -- this module
         MANDATORY-GROUPS { dfsGroup
                          , bridgeGroup
                          , configurationGroup
                          , ethernetGroup
                          , tDMGroup
                          , licenseGroup
                          , managementGroup
                          , phyControlGroup
                          , phyStatusGroup
                          , alarmsGroup
                          , smtpGroup
                          , snmpControlGroup
                          , sntpGroup
                          , resetGroup
                          , versionsGroup
                          , pubStatsGroup
                          , encryptionGroup
                          , tDDControlGroup
                          , aAAControlGroup
                          , syslogControlGroup
                          , routerProtocolsGroup
                          , cableDiagnosticsGroup
                          , supplementaryGroup
                          , notificationsGroup
                          } 
         ::= { ptp650 97 }

   dfsGroup OBJECT-GROUP
      OBJECTS { dfsTableNumber
              , extendedSpectrumScanning
              , dfsMeans
              , dfsNineNinePointNinePercentiles
              , dfsPeaks
              }
      STATUS  current
      DESCRIPTION "The dfs object group."
      ::= { ptpGroups 3 }

   bridgeGroup OBJECT-GROUP
      OBJECTS { localPacketFiltering
              }
      STATUS  current
      DESCRIPTION "The bridge object group."
      ::= { ptpGroups 4 }

   configurationGroup OBJECT-GROUP
      OBJECTS { iPv4Address
              , subnetMask
              , gatewayIPAddress
              , targetMACAddress
              , masterSlaveMode
              , maximumTransmitPower
              , antennaGain
              , cableLoss
              , eIRP
              , channelBandwidth
              , linkName
              , siteName
              , accessMethod
              , groupID
              , iPv6Address
              , iPVersion
              , iPv6AutoConfiguredLinkLocalAddress
              , iPv6PrefixLength
              , iPv6GatewayAddress
              , remoteInternetAddressType
              , remoteInternetAddress
              , subbandLowestFrequency
              , subbandHighestFrequency
              , enableTransmission
              }
      STATUS  current
      DESCRIPTION "The configuration object group."
      ::= { ptpGroups 5 }

   ethernetGroup OBJECT-GROUP
      OBJECTS { mainPSUPortAutoNegotiation
              , mainPSUPortAutoNegAdvertisement
              , mainPSUPortAutoMdix
              , mainPSUPortStatus
              , mainPSUPortSpeedAndDuplex
              , dataPortWirelessDownAlert
              , useVLANForManagementInterfaces
              , vLANManagementPriority
              , vLANManagementVID
              , auxPortStatus
              , auxPortSpeedAndDuplex
              , ethernetPriorityTableNumber
              , l2CPPriorityTableNumber
              , iPDSCPPriorityTableNumber
              , mPLSTCPriorityTableNumber
              , managementPortWirelessDownAlert
              , qOSPriorityScheme
              , unknownNetworkPriorityQueueMapping
              , dSCPManagementPriority
              , dataBridgingStatus
              , mainPSUPortAllocation
              , auxPortAllocation
              , sFPPortAllocation
              , dataPortPauseFrames
              , sFPPortAutoNegotiation
              , sFPPortAutoNegAdvertisement
              , sFPPortAutoMdix
              , sFPPortStatus
              , sFPPortSpeedAndDuplex
              , auxPortPowerOverEthernetOutput
              , auxPortPowerOverEthernetOutputStatus
              , syncETracking
              , syncEEquipmentClock
              , mainPSUPortQLRxOverwrite
              , mainPSUPortSSMTx
              , sFPPortSSMTx
              , auxPortSSMTx
              , syncETrackingState
              , mainPSUPortQLRx
              , auxPortQLRx
              , sFPPortQLRx
              , mainPSUPortQLTx
              , auxPortQLTx
              , sFPPortQLTx
              , mainPSUPortSyncEMasterSlaveStatus
              , auxPortSyncEMasterSlaveStatus
              , sFPPortSyncEMasterSlaveStatus
              , mainPSUPortGigabitMasterSlaveStatus
              , auxPortGigabitMasterSlaveStatus
              , sFPPortGigabitMasterSlaveStatus
              , transparentClock
              , transparentClockVLAN
              , transparentClockVID
              , mainPSUPortAcceptedQLRx
              , auxPortAcceptedQLRx
              , sFPPortAcceptedQLRx
              , mainPSUPortSyncERxStatus
              , auxPortSyncERxStatus
              , sFPPortSyncERxStatus
              , nIDULanPortStatus
              , nIDULanPortSpeedAndDuplex
              , oOBPriorityQueueMapping
              , nIDULanPortAutoNegotiation
              , nIDULanPortAutoNegAdvertisement
              , nIDULanPortAutoMdix
              , nIDULanPortGigabitMasterSlaveStatus
              , txMABFrames
              , managementNetworkAccessEnabled
              , secondDataPortPauseFrames
              , secondDataBridgingStatus
              , transparentClockPort
              , ethernetPriorityQueueMapping
              , l2CPPriorityQueueMapping
              , iPDSCPPriorityQueueMapping
              , mPLSTCPriorityQueueMapping
              }
      STATUS  current
      DESCRIPTION "The ethernet object group."
      ::= { ptpGroups 6 }

   tDMGroup OBJECT-GROUP
      OBJECTS { tDMInterfaceControl
              , tDMInterfaceStatus
              , tDMEnabledChannels
              , tdmTableNumber
              , tDMConfigurationMismatch
              , lowestTDMModulationMode
              , tDMChannelStatus
              , tDMChannelLineCode
              , tDMChannelCableLength
              , tDMChannelLoopback
              }
      STATUS  current
      DESCRIPTION "The tDM object group."
      ::= { ptpGroups 7 }

   licenseGroup OBJECT-GROUP
      OBJECTS { regulatoryBand
              , productVariant
              , productName
              , frequencyVariant
              , sNMPv3Enable
              , licenseVersion
              , licenseUnitSerialNumber
              , licenseIssueNumber
              , licenseCountry
              , licenseNumberOfRegulatoryBands
              , licenseBandwidthCap
              , licenseEncryption
              , licenseSecurityLevel
              , licenseGroupAccess
              , licenseOOBManagementSupport
              , licenseSFPPortSupport
              , licenseAuxiliaryPortSupport
              , licenseCapacity
              , licenseMaxNumberOfTDMChannels
              , licenseIEEE1588Support
              , licenseSyncESupport
              , licenseIPv6Support
              , licenseMinimumFirmwareVersion
              , licenseFullCapabilityTrialStatus
              , licenseRemainingTrialPeriod
              , licenseRemainingTrialPeriodAlarm
              , capacityVariantMismatch
              , licenseTDDSyncSupport
              , licenseMaxLinkRange
              , licenseTrialPeriod
              , licenseRARSupport
              , licenseRegulatoryBandsList
              }
      STATUS  current
      DESCRIPTION "The license object group."
      ::= { ptpGroups 8 }

   managementGroup OBJECT-GROUP
      OBJECTS { targetRange
              , rangingMode
              , installStatus
              , installArmState
              , tFTPServerPortNumber
              , tFTPSoftwareUpgradeFileName
              , tFTPStartSoftwareUpgrade
              , tFTPSoftwareUpgradeStatus
              , tFTPSoftwareUpgradeStatusText
              , tFTPSoftwareUpgradeStatusAdditionalText
              , hTTPAccessEnabled
              , telnetAccessEnabled
              , hTTPPortNumber
              , hTTPSPortNumber
              , telnetPortNumber
              , hTTPSAccessEnabled
              , tFTPServerInternetAddressType
              , tFTPServerInternetAddress
              , lowestDataModulationMode
              , lowestSecondDataModulationMode
              }
      STATUS  current
      DESCRIPTION "The management object group."
      ::= { ptpGroups 9 }

   phyControlGroup OBJECT-GROUP
      OBJECTS { linkSymmetry
              , userConfiguredMaxModulationMode
              , linkModeOptimization
              , txColorCode
              , rxColorCode
              , remoteMaximumTransmitPower
              }
      STATUS  current
      DESCRIPTION "The phyControl object group."
      ::= { ptpGroups 10 }

   phyStatusGroup OBJECT-GROUP
      OBJECTS { linkLoss
              , receivePower
              , vectorError
              , transmitPower
              , receiveChannel
              , transmitChannel
              , receiveFreqMHz
              , transmitFreqMHz
              , signalStrengthRatio
              , receiveFreqKHz
              , transmitFreqKHz
              , rawReceivePower
              , range
              , receiveModulationMode
              , transmitModulationMode
              , searchState
              }
      STATUS  current
      DESCRIPTION "The phyStatus object group."
      ::= { ptpGroups 12 }

   alarmsGroup OBJECT-GROUP
      OBJECTS { unitOutOfCalibration
              , incompatibleRegulatoryBands
              , noWirelessChannelAvailable
              , wirelessLinkDisabledWarning
              , mainPSUPortDisabledWarning
              , sFPError
              , mainPSUPortConfigurationMismatch
              , incompatibleMasterAndSlave
              , tDDSynchronizationStatus
              , auxPortDisabledWarning
              , tDDSynchronizationAlarm
              , linkModeOptimizationMismatch
              , auxPortConfigurationMismatch
              , secureModeAlarm
              , dataBridgingStatusAlarm
              , sFPPortDisabledWarning
              , sFPPortConfigurationMismatch
              , maxLinkRangeExceeded
              , nIDULanPortDisabledWarning
              , nIDULanPortConfigurationMismatch
              , portAllocationMismatch
              , secondDataBridgingStatusAlarm
              , transparentClockSourcePortAlarm
              }
      STATUS  current
      DESCRIPTION "The alarms object group."
      ::= { ptpGroups 13 }

   smtpGroup OBJECT-GROUP
      OBJECTS { sMTPEmailAlert
              , sMTPServerPortNumber
              , sMTPSourceEmailAddress
              , sMTPDestinationEmailAddress
              , sMTPEnabledMessages
              , sMTPServerInternetAddressType
              , sMTPServerInternetAddress
              }
      STATUS  current
      DESCRIPTION "The smtp object group."
      ::= { ptpGroups 15 }

   snmpControlGroup OBJECT-GROUP
      OBJECTS { sNMPPortNumber
              , sNMPCommunityString
              , sNMPTrapTableNumber
              , sNMPTrapVersion
              , sNMPEnabledTraps
              , enabledDiagnosticAlarms
              , sNMPSendAllTrapsAtStartup
              , sNMPTrapPortNumber
              , sNMPTrapInternetAddressType
              , sNMPTrapInternetAddress
              , sNMPTrapReceiverEnabled
              }
      STATUS  current
      DESCRIPTION "The snmpControl object group."
      ::= { ptpGroups 16 }

   sntpGroup OBJECT-GROUP
      OBJECTS { sNTPState
              , sNTPPollInterval
              , sNTPSync
              , sNTPLastSync
              , systemClock
              , timeZone
              , daylightSaving
              , sNTPPrimaryServer
              , sNTPPrimaryServerDeadTime
              , sNTPServerRetries
              , sNTPServerTimeout
              , sNTPServerTableNumber
              , sNTPServerPortNumber
              , sNTPServerStatus
              , sNTPServerInternetAddressType
              , sNTPServerInternetAddress
              }
      STATUS  current
      DESCRIPTION "The sntp object group."
      ::= { ptpGroups 17 }

   resetGroup OBJECT-GROUP
      OBJECTS { systemReset
              }
      STATUS  current
      DESCRIPTION "The reset object group."
      ::= { ptpGroups 18 }

   versionsGroup OBJECT-GROUP
      OBJECTS { softwareVersion
              , hardwareVersion
              , secondarySoftwareVersion
              , bootVersion
              }
      STATUS  current
      DESCRIPTION "The versions object group."
      ::= { ptpGroups 19 }

   pubStatsGroup OBJECT-GROUP
      OBJECTS { receiveDataRate
              , transmitDataRate
              , aggregateDataRate
              , wirelessLinkAvailability
              , wirelessLinkStatus
              , byteErrorRatio
              , receiveModulationModeDetail
              , dataBridgingAvailability
              }
      STATUS  current
      DESCRIPTION "The pubStats object group."
      ::= { ptpGroups 20 }

   encryptionGroup OBJECT-GROUP
      OBJECTS { encryptionAlgorithm
              }
      STATUS  current
      DESCRIPTION "The encryption object group."
      ::= { ptpGroups 22 }

   tDDControlGroup OBJECT-GROUP
      OBJECTS { tDDSynchronizationMode
              }
      STATUS  current
      DESCRIPTION "The tDDControl object group."
      ::= { ptpGroups 23 }

   aAAControlGroup OBJECT-GROUP
      OBJECTS { userTableNumber
              , userName
              , userRole
              , userEnabled
              , userPassword
              }
      STATUS  current
      DESCRIPTION "The aAAControl object group."
      ::= { ptpGroups 25 }

   syslogControlGroup OBJECT-GROUP
      OBJECTS { syslogClient
              , syslogState
              }
      STATUS  current
      DESCRIPTION "The syslogControl object group."
      ::= { ptpGroups 24 }

   routerProtocolsGroup OBJECT-GROUP
      OBJECTS { microwaveAdaptiveBandwidth
              , mABNominalModulationMode
              , mABTransmissionInterval
              , mABHoldoffPeriod
              , mABMaintenanceLevel
              , useVLANForMABProtocol
              , mABProtocolVID
              , mABProtocolVLANPriority
              , mABState
              , mABNominalTransmitCapacity
              , mABCurrentTransmitCapacity
              }
      STATUS  current
      DESCRIPTION "The routerProtocols object group."
      ::= { ptpGroups 26 }

   cableDiagnosticsGroup OBJECT-GROUP
      OBJECTS { cableDiagnosticsPorts
              , cableDiagnosticsControl
              , cableDiagnosticsWarning
              , cableDiagnosticsResultTableNumber
              , cableDiagnosticsResultsDateTime
              , cableDiagPair1Results
              , cableDiagPair1Distance
              , cableDiagPair2Results
              , cableDiagPair2Distance
              , cableDiagPair3Results
              , cableDiagPair3Distance
              , cableDiagPair4Results
              , cableDiagPair4Distance
              }
      STATUS  current
      DESCRIPTION "The cableDiagnostics object group."
      ::= { ptpGroups 27 }

   supplementaryGroup OBJECT-GROUP
      OBJECTS { longitude
              , latitude
              , altitude
              }
      STATUS  current
      DESCRIPTION "The supplementary object group."
      ::= { ptpGroups 96 }

   notificationsGroup NOTIFICATION-GROUP
      NOTIFICATIONS { channelChangeTrap
                    , dfsImpulsiveInterferenceTrap
                    , mainPSUPortStatusTrap
                    , mainPSUPortDisabledWarningTrap
                    , mainPSUPortConfigurationMismatchTrap
                    , auxPortStatusTrap
                    , auxPortDisabledWarningTrap
                    , regulatoryBandTrap
                    , installStatusTrap
                    , installArmStateTrap
                    , unitOutOfCalibrationTrap
                    , auxPortPowerOverEthernetOutputStatusTrap
                    , incompatibleRegulatoryBandsTrap
                    , noWirelessChannelAvailableTrap
                    , wirelessLinkDisabledWarningTrap
                    , auxPortConfigurationMismatchTrap
                    , sFPErrorTrap
                    , sFPPortStatusTrap
                    , incompatibleMasterAndSlaveTrap
                    , sNTPSyncTrap
                    , tDDSynchronizationAlarmTrap
                    , sFPPortDisabledWarningTrap
                    , sFPPortConfigurationMismatchTrap
                    , linkModeOptimizationMismatchTrap
                    , tDMInterfaceStatusTrap
                    , tDMChannelStatusTrap
                    , tDMChannelLoopbackTrap
                    , nIDULanPortStatusTrap
                    , syslogStateTrap
                    , syslogLocalNearlyFullTrap
                    , syslogLocalWrappedTrap
                    , syslogClientTrap
                    , secureModeAlarmTrap
                    , dataBridgingStatusAlarmTrap
                    , licenseRemainingTrialPeriodAlarmTrap
                    , capacityVariantMismatchTrap
                    , maxLinkRangeExceededTrap
                    , tDMConfigurationMismatchTrap
                    , nIDULanPortDisabledWarningTrap
                    , nIDULanPortConfigurationMismatchTrap
                    , secondDataBridgingStatusAlarmTrap
                    , transparentClockSourcePortAlarmTrap
                    , portAllocationMismatchTrap
                    }
      STATUS current
      DESCRIPTION "The notifications group."
      ::= { ptpGroups 99 }

 
   DfsTableEntry ::=
      SEQUENCE { dfsTableIndex INTEGER
               , dfsMeans Integer32
               , dfsNineNinePointNinePercentiles Integer32
               , dfsPeaks Integer32
      }
 
   dfsTable OBJECT-TYPE
      SYNTAX SEQUENCE OF DfsTableEntry
      MAX-ACCESS not-accessible
      STATUS current
      DESCRIPTION 
        " A table storing a snapshot of various DFS measurements for each channel"
      ::= { dfs 2 }
 
   dfsTableEntry OBJECT-TYPE
      SYNTAX DfsTableEntry
      MAX-ACCESS not-accessible
      STATUS current
      DESCRIPTION 
        "Table DfsTable"
      INDEX { dfsTableIndex }
      ::= { dfsTable 1 }
 
   EthernetPriorityTableEntry ::=
      SEQUENCE { ethernetPriorityTableIndex INTEGER
               , ethernetPriorityQueueMapping INTEGER
      }
 
   ethernetPriorityTable OBJECT-TYPE
      SYNTAX SEQUENCE OF EthernetPriorityTableEntry
      MAX-ACCESS not-accessible
      STATUS current
      DESCRIPTION 
        " A priority queue mapping table. This is a list of packet queues indexed by Ethernet priority."
      ::= { ethernet 15 }
 
   ethernetPriorityTableEntry OBJECT-TYPE
      SYNTAX EthernetPriorityTableEntry
      MAX-ACCESS not-accessible
      STATUS current
      DESCRIPTION 
        "Table EthernetPriorityTable"
      INDEX { ethernetPriorityTableIndex }
      ::= { ethernetPriorityTable 1 }
 
   L2CPPriorityTableEntry ::=
      SEQUENCE { l2CPPriorityTableIndex INTEGER
               , l2CPPriorityQueueMapping INTEGER
      }
 
   l2CPPriorityTable OBJECT-TYPE
      SYNTAX SEQUENCE OF L2CPPriorityTableEntry
      MAX-ACCESS not-accessible
      STATUS current
      DESCRIPTION 
        " A priority queue mapping table. This is a list of packet queues indexed by L2CP priority."
      ::= { ethernet 17 }
 
   l2CPPriorityTableEntry OBJECT-TYPE
      SYNTAX L2CPPriorityTableEntry
      MAX-ACCESS not-accessible
      STATUS current
      DESCRIPTION 
        "Table L2CPPriorityTable"
      INDEX { l2CPPriorityTableIndex }
      ::= { l2CPPriorityTable 1 }
 
   IPDSCPPriorityTableEntry ::=
      SEQUENCE { iPDSCPPriorityTableIndex INTEGER
               , iPDSCPPriorityQueueMapping INTEGER
      }
 
   iPDSCPPriorityTable OBJECT-TYPE
      SYNTAX SEQUENCE OF IPDSCPPriorityTableEntry
      MAX-ACCESS not-accessible
      STATUS current
      DESCRIPTION 
        " A priority queue mapping table. This is a list of packet queues indexed by L3 IP DSCP priority."
      ::= { ethernet 19 }
 
   iPDSCPPriorityTableEntry OBJECT-TYPE
      SYNTAX IPDSCPPriorityTableEntry
      MAX-ACCESS not-accessible
      STATUS current
      DESCRIPTION 
        "Table IPDSCPPriorityTable"
      INDEX { iPDSCPPriorityTableIndex }
      ::= { iPDSCPPriorityTable 1 }
 
   MPLSTCPriorityTableEntry ::=
      SEQUENCE { mPLSTCPriorityTableIndex INTEGER
               , mPLSTCPriorityQueueMapping INTEGER
      }
 
   mPLSTCPriorityTable OBJECT-TYPE
      SYNTAX SEQUENCE OF MPLSTCPriorityTableEntry
      MAX-ACCESS not-accessible
      STATUS current
      DESCRIPTION 
        " A priority queue mapping table. This is a list of priority queues indexed by MPLS TC priority."
      ::= { ethernet 21 }
 
   mPLSTCPriorityTableEntry OBJECT-TYPE
      SYNTAX MPLSTCPriorityTableEntry
      MAX-ACCESS not-accessible
      STATUS current
      DESCRIPTION 
        "Table MPLSTCPriorityTable"
      INDEX { mPLSTCPriorityTableIndex }
      ::= { mPLSTCPriorityTable 1 }
 
   TdmTableEntry ::=
      SEQUENCE { tdmTableIndex INTEGER
               , tDMChannelStatus INTEGER
               , tDMChannelLineCode INTEGER
               , tDMChannelCableLength INTEGER
               , tDMChannelLoopback INTEGER
      }
 
   tdmTable OBJECT-TYPE
      SYNTAX SEQUENCE OF TdmTableEntry
      MAX-ACCESS not-accessible
      STATUS current
      DESCRIPTION 
        " A table storing a configuration and status for each TDM channel"
      ::= { tDM 5 }
 
   tdmTableEntry OBJECT-TYPE
      SYNTAX TdmTableEntry
      MAX-ACCESS not-accessible
      STATUS current
      DESCRIPTION 
        "Table TdmTable"
      INDEX { tdmTableIndex }
      ::= { tdmTable 1 }
 
   LicenseRegulatoryBandsTableEntry ::=
      SEQUENCE { licenseRegulatoryBandsTableIndex INTEGER
               , licenseRegulatoryBandsList INTEGER
      }
 
   licenseRegulatoryBandsTable OBJECT-TYPE
      SYNTAX SEQUENCE OF LicenseRegulatoryBandsTableEntry
      MAX-ACCESS not-accessible
      STATUS current
      DESCRIPTION 
        ""
      ::= { license 18 }
 
   licenseRegulatoryBandsTableEntry OBJECT-TYPE
      SYNTAX LicenseRegulatoryBandsTableEntry
      MAX-ACCESS not-accessible
      STATUS current
      DESCRIPTION 
        "Table LicenseRegulatoryBandsTable"
      INDEX { licenseRegulatoryBandsTableIndex }
      ::= { licenseRegulatoryBandsTable 1 }
 
   SNMPTrapTableEntry ::=
      SEQUENCE { sNMPTrapTableIndex INTEGER
               , sNMPTrapPortNumber INTEGER
               , sNMPTrapInternetAddressType INTEGER
               , sNMPTrapInternetAddress InetAddress
               , sNMPTrapReceiverEnabled INTEGER
      }
 
   sNMPTrapTable OBJECT-TYPE
      SYNTAX SEQUENCE OF SNMPTrapTableEntry
      MAX-ACCESS not-accessible
      STATUS current
      DESCRIPTION 
        " SNMP trap configuration table."
      ::= { snmpControl 4 }
 
   sNMPTrapTableEntry OBJECT-TYPE
      SYNTAX SNMPTrapTableEntry
      MAX-ACCESS not-accessible
      STATUS current
      DESCRIPTION 
        "Table SNMPTrapTable"
      INDEX { sNMPTrapTableIndex }
      ::= { sNMPTrapTable 1 }
 
   SNTPServerTableEntry ::=
      SEQUENCE { sNTPServerTableIndex INTEGER
               , sNTPServerPortNumber INTEGER
               , sNTPServerStatus DisplayString
               , sNTPServerInternetAddressType INTEGER
               , sNTPServerInternetAddress InetAddress
      }
 
   sNTPServerTable OBJECT-TYPE
      SYNTAX SEQUENCE OF SNTPServerTableEntry
      MAX-ACCESS not-accessible
      STATUS current
      DESCRIPTION 
        ""
      ::= { sntp 15 }
 
   sNTPServerTableEntry OBJECT-TYPE
      SYNTAX SNTPServerTableEntry
      MAX-ACCESS not-accessible
      STATUS current
      DESCRIPTION 
        "Table SNTPServerTable"
      INDEX { sNTPServerTableIndex }
      ::= { sNTPServerTable 1 }
 
   UserTableEntry ::=
      SEQUENCE { userTableIndex INTEGER
               , userName DisplayString
               , userRole INTEGER
               , userEnabled INTEGER
               , userPassword DisplayString
      }
 
   userTable OBJECT-TYPE
      SYNTAX SEQUENCE OF UserTableEntry
      MAX-ACCESS not-accessible
      STATUS current
      DESCRIPTION 
        " The User Table Control group contains objects specifically for user account management."
      ::= { aAAControl 2 }
 
   userTableEntry OBJECT-TYPE
      SYNTAX UserTableEntry
      MAX-ACCESS not-accessible
      STATUS current
      DESCRIPTION 
        "Table UserTable"
      INDEX { userTableIndex }
      ::= { userTable 1 }
 
   CableDiagnosticsResultTableEntry ::=
      SEQUENCE { cableDiagnosticsResultTableIndex INTEGER
               , cableDiagnosticsResultsDateTime Integer32
               , cableDiagPair1Results INTEGER
               , cableDiagPair1Distance Integer32
               , cableDiagPair2Results INTEGER
               , cableDiagPair2Distance Integer32
               , cableDiagPair3Results INTEGER
               , cableDiagPair3Distance Integer32
               , cableDiagPair4Results INTEGER
               , cableDiagPair4Distance Integer32
      }
 
   cableDiagnosticsResultTable OBJECT-TYPE
      SYNTAX SEQUENCE OF CableDiagnosticsResultTableEntry
      MAX-ACCESS not-accessible
      STATUS current
      DESCRIPTION 
        ""
      ::= { cableDiagnostics 5 }
 
   cableDiagnosticsResultTableEntry OBJECT-TYPE
      SYNTAX CableDiagnosticsResultTableEntry
      MAX-ACCESS not-accessible
      STATUS current
      DESCRIPTION 
        "Table CableDiagnosticsResultTable"
      INDEX { cableDiagnosticsResultTableIndex }
      ::= { cableDiagnosticsResultTable 1 }
 
   -- Dfs group attribute definitions 
   --
   dfsTableNumber OBJECT-TYPE
      SYNTAX INTEGER (1..63)
      MAX-ACCESS read-only
      STATUS current
      DESCRIPTION
             "Number of entries in the dfsTable"  
      ::= { dfs 1 } 
 
   extendedSpectrumScanning OBJECT-TYPE
      SYNTAX INTEGER {
                       disabled(0),
                       enabled(1)
                     }
      MAX-ACCESS read-only
      STATUS current
      DESCRIPTION
             "Enables Extended Spectrum Scanning"  
      ::= { dfs 3 } 
 
   -- DfsTable group attribute definitions 
   --
   dfsTableIndex OBJECT-TYPE
      SYNTAX INTEGER (1..63)
      MAX-ACCESS not-accessible
      STATUS current
      DESCRIPTION
             "used to index values in the dfsTable."  
      ::= { dfsTableEntry 1 } 
 
   dfsMeans OBJECT-TYPE
      SYNTAX Integer32
      MAX-ACCESS read-only
      STATUS current
      DESCRIPTION
             "Snapshot of DFS means"  
      ::= { dfsTableEntry 2 } 
 
   dfsNineNinePointNinePercentiles OBJECT-TYPE
      SYNTAX Integer32
      MAX-ACCESS read-only
      STATUS current
      DESCRIPTION
             "Snapshot of DFS 99.9 percentiles"  
      ::= { dfsTableEntry 3 } 
 
   dfsPeaks OBJECT-TYPE
      SYNTAX Integer32
      MAX-ACCESS read-only
      STATUS current
      DESCRIPTION
             "Snapshot of DFS peaks"  
      ::= { dfsTableEntry 4 } 
 
   -- Bridge group attribute definitions 
   --
   localPacketFiltering OBJECT-TYPE
      SYNTAX INTEGER {
                       disabled(0),
                       enabled(1)
                     }
      MAX-ACCESS read-write
      STATUS current
      DESCRIPTION
             "When Local Packet Filtering is Enabled, the unit keeps 
             track of the port (Main, SFP, Aux or Wireless) on which a 
             packet with a given MAC source address destined to the 
             management agent has been received. This MAC address to 
             port mapping is then used in order to route any response 
             from the management agent to the right port. When Local 
             Packet Filtering is Disabled, any Ethernet packet from 
             the management agent is sent to all ports."  
      ::= { bridge 1 } 
 
   -- Configuration group attribute definitions 
   --
   iPv4Address OBJECT-TYPE
      SYNTAX IpAddress
      MAX-ACCESS read-write
      STATUS current
      DESCRIPTION
             "Internet protocol (IPv4) address. This address is used 
             by the family of Internet protocols to uniquely identify 
             the unit on a network."  
      ::= { configuration 1 } 
 
   subnetMask OBJECT-TYPE
      SYNTAX IpAddress
      MAX-ACCESS read-write
      STATUS current
      DESCRIPTION
             "A subnet allows the flow of network traffic between 
             hosts to be segregated based on a network configuration. 
             By organizing hosts into logical groups, subnetting can 
             improve network security and performance."  
      ::= { configuration 2 } 
 
   gatewayIPAddress OBJECT-TYPE
      SYNTAX IpAddress
      MAX-ACCESS read-write
      STATUS current
      DESCRIPTION
             "The IPv4 address of a device on the current network that 
             acts as an IPv4 network gateway. A gateway acts as an 
             entrance / exit to packets from / to other networks"  
      ::= { configuration 3 } 
 
   targetMACAddress OBJECT-TYPE
      SYNTAX OCTET STRING (SIZE(6))
      MAX-ACCESS read-only
      STATUS current
      DESCRIPTION
             "MAC address of the PTP wireless unit forming the other 
             end of the PTP link"  
      ::= { configuration 4 } 
 
   masterSlaveMode OBJECT-TYPE
      SYNTAX INTEGER {
                       master(0),
                       slave(1)
                     }
      MAX-ACCESS read-write
      STATUS current
      DESCRIPTION
             "The PTP wireless link operates using a master and slave 
             relationship"  
      ::= { configuration 5 } 
 
   maximumTransmitPower OBJECT-TYPE
      SYNTAX INTEGER (-15..30)
      MAX-ACCESS read-only
      STATUS current
      DESCRIPTION
             "Maximum transmit power the wireless unit is permitted to 
             use when establishing and maintaining the wireless link. 
             This may be reduced during installation"  
      ::= { configuration 6 } 
 
   antennaGain OBJECT-TYPE
      SYNTAX INTEGER (130..610)
      MAX-ACCESS read-write
      STATUS current
      DESCRIPTION
             "Antenna Gain. Expressed in 10ths of dBi."  
      ::= { configuration 7 } 
 
   cableLoss OBJECT-TYPE
      SYNTAX INTEGER (0..255)
      MAX-ACCESS read-write
      STATUS current
      DESCRIPTION
             "Loss in the cable between the ODU and the antenna. 
             Expressed in 10ths of dB. NB: This attribute is ignored 
             for variants with an integral antenna."  
      ::= { configuration 8 } 
 
   eIRP OBJECT-TYPE
      SYNTAX Integer32
      MAX-ACCESS read-only
      STATUS current
      DESCRIPTION
             "Effective Isotropic Radiated Power (EIRP) describes the 
             strength of the radio signal leaving the wireless unit. 
             Expressed in 10ths of dBm"  
      ::= { configuration 9 } 
 
   channelBandwidth OBJECT-TYPE
      SYNTAX INTEGER {
                       bw30MHz(0),
                       bw15MHz(1),
                       bw10MHz(2),
                       bw5MHz(3),
                       bw20MHz(4),
                       bw56MHz(5),
                       bw50MHz(6),
                       bw40MHz(7),
                       bw45MHz(8)
                     }
      MAX-ACCESS read-only
      STATUS current
      DESCRIPTION
             "This control sets the bandwidth of the transmit and 
             receive radio channels"  
      ::= { configuration 11 } 
 
   linkName OBJECT-TYPE
      SYNTAX DisplayString (SIZE(0..63))
      MAX-ACCESS read-write
      STATUS current
      DESCRIPTION
             "Name of the PTP link allocated by the System 
             Administrator. Used to establish a connection with the 
             correct PTP wireless unit at the other end of the link. 
             NOTE: The link name MUST be the same at both ends of the 
             PTP link."  
      ::= { configuration 14 } 
 
   siteName OBJECT-TYPE
      SYNTAX DisplayString (SIZE(0..63))
      MAX-ACCESS read-write
      STATUS current
      DESCRIPTION
             "This field contains a user-provided description of the 
             site name together with any additional notes"  
      ::= { configuration 15 } 
 
   accessMethod OBJECT-TYPE
      SYNTAX INTEGER {
                       linkAccess(0),
                       linkNameAccess(1),
                       groupAccess(2)
                     }
      MAX-ACCESS read-only
      STATUS current
      DESCRIPTION
             "ODUs must be configured in pairs before a link can be 
             established. The Access Method attribute determines how 
             the paired ODUs will recognise each other. For the Link 
             Access method, each ODU must be configured with Target 
             MAC Address equal to the MAC Address of the other unit. 
             For the Link Name Access method, both units must be 
             configured with the same Link Name. For the Group Access 
             method, both units must be configured with the same Group 
             ID."  
      ::= { configuration 16 } 
 
   groupID OBJECT-TYPE
      SYNTAX INTEGER (0..255)
      MAX-ACCESS read-write
      STATUS current
      DESCRIPTION
             "When Access Method is set to Group Access, the Group ID 
             identifies all the units belonging to the same group"  
      ::= { configuration 17 } 
 
   iPv6Address OBJECT-TYPE
      SYNTAX DisplayString (SIZE(0..39))
      MAX-ACCESS read-write
      STATUS current
      DESCRIPTION
             "Internet protocol (IPv6) address. This address is used 
             by the family of Internet protocols to uniquely identify 
             the unit on a network."  
      ::= { configuration 18 } 
 
   iPVersion OBJECT-TYPE
      SYNTAX INTEGER {
                       iPv4(0),
                       iPv6(1),
                       dualIPv4andIPv6(2)
                     }
      MAX-ACCESS read-write
      STATUS current
      DESCRIPTION
             "IP protocol selection. Choice of IPv4, IPv6 or Dual."  
      ::= { configuration 20 } 
 
   iPv6AutoConfiguredLinkLocalAddress OBJECT-TYPE
      SYNTAX DisplayString (SIZE(0..39))
      MAX-ACCESS read-only
      STATUS current
      DESCRIPTION
             "The auto configured link local IPv6 address"  
      ::= { configuration 21 } 
 
   iPv6PrefixLength OBJECT-TYPE
      SYNTAX INTEGER (0..128)
      MAX-ACCESS read-write
      STATUS current
      DESCRIPTION
             "IPv6 prefix length"  
      ::= { configuration 22 } 
 
   iPv6GatewayAddress OBJECT-TYPE
      SYNTAX DisplayString (SIZE(0..39))
      MAX-ACCESS read-write
      STATUS current
      DESCRIPTION
             "The IPv6 address of a device on the current network that 
             is currently acting as an IPv6 network gateway. A gateway 
             acts as an entrance / exit to packets from / to other 
             networks."  
      ::= { configuration 23 } 
 
   remoteInternetAddressType OBJECT-TYPE
      SYNTAX INTEGER {
                       unknown(0),
                       ipv4(1),
                       ipv6(2),
                       ipv4z(3),
                       ipv6z(4),
                       unknown6(5),
                       unknown7(6),
                       unknown8(7),
                       unknown9(8),
                       unknown10(9),
                       unknown11(10),
                       unknown12(11),
                       unknown13(12),
                       unknown14(13),
                       unknown15(14),
                       unknown16(15),
                       dns(16)
                     }
      MAX-ACCESS read-only
      STATUS current
      DESCRIPTION
             "The type of Internet address specified by the associated 
             remoteInternetAddressType."  
      ::= { configuration 24 } 
 
   remoteInternetAddress OBJECT-TYPE
      SYNTAX InetAddress
      MAX-ACCESS read-only
      STATUS current
      DESCRIPTION
             "INET address used to identify the peer wireless unit"  
      ::= { configuration 25 } 
 
   subbandLowestFrequency OBJECT-TYPE
      SYNTAX Integer32
      MAX-ACCESS read-only
      STATUS current
      DESCRIPTION
             "Lowest center frequency of the subset of channels."  
      ::= { configuration 26 } 
 
   subbandHighestFrequency OBJECT-TYPE
      SYNTAX Integer32
      MAX-ACCESS read-only
      STATUS current
      DESCRIPTION
             "Highest center frequency of the subset of channels."  
      ::= { configuration 27 } 
 
   enableTransmission OBJECT-TYPE
      SYNTAX INTEGER {
                       enabled(0),
                       muted(1)
                     }
      MAX-ACCESS read-write
      STATUS current
      DESCRIPTION
             "Control for enabling/disabling the radio transmitter of 
             the Master. Note: Use Web Properties to control this 
             feature."  
      ::= { configuration 28 } 
 
   -- Ethernet group attribute definitions 
   --
   mainPSUPortAutoNegotiation OBJECT-TYPE
      SYNTAX INTEGER {
                       disabled(0),
                       enabled(1)
                     }
      MAX-ACCESS read-only
      STATUS current
      DESCRIPTION
             "This controls whether the local Ethernet interface 
             configuration is automatically negotiated or forced. Do 
             not use a forced setting together with auto negotiation 
             at the Ethernet link partner. If you want to run your 
             Ethernet link at a fixed speed and duplex then you would 
             normally leave auto negotiation enabled and only enable 
             the single Auto Neg Advertisement option that you want 
             the link to run in - FORCING ETHERNET CONFIGURATION IS A 
             LAST RESORT WHICH SHOULD ONLY BE PERFORMED IF YOU ARE 
             HAVING PROBLEMS WITH AUTO NEGOTIATION - AND YOU MUST 
             ENSURE THAT YOU CONFIGURE BOTH THIS UNIT AND THE ETHERNET 
             LINK PARTNER TO WHICH IT IS CONNECTED IDENTICALLY (THE 
             LINK PARTNER MUST NOT HAVE AUTO NEGOTIATION ENABLED 
             EITHER, OTHERWISE A DUPLEX MISMATCH WILL OCCUR). NB: The 
             new setting will only take effect after a system reboot."  
      ::= { ethernet 1 } 
 
   mainPSUPortAutoNegAdvertisement OBJECT-TYPE
      SYNTAX BITS {
                    negInvalid(2),
                    neg10MbpsHalfDuplex(3),
                    neg10MbpsFullDuplex(4),
                    neg100MbpsHalfDuplex(5),
                    neg100MbpsFullDuplex(6),
                    neg1000MbpsFullDuplex(7)
                  }
      MAX-ACCESS read-only
      STATUS current
      DESCRIPTION
             "This sets the different Ethernet configurations that 
             will be advertised during auto negotiation. Note the new 
             setting will only take effect after a system reboot. 
             WARNING: Duplex mismatch may result if both ends of the 
             Ethernet link do not have the same settings. Do not auto 
             negotiation together with a fixed setting at the Ethernet 
             link partner. WARNING: Make sure that you select 
             option(s) that you know your connected equipment can 
             cater for!"  
      ::= { ethernet 2 } 
 
   mainPSUPortAutoMdix OBJECT-TYPE
      SYNTAX INTEGER {
                       disabled(0),
                       enabled(1)
                     }
      MAX-ACCESS read-only
      STATUS current
      DESCRIPTION
             "This enables/disables the Auto MDI/MDIX capability. NB: 
             The new setting will only take effect after a system 
             reboot"  
      ::= { ethernet 3 } 
 
   mainPSUPortStatus OBJECT-TYPE
      SYNTAX INTEGER {
                       down(0),
                       copperLinkUp(1),
                       fiberLinkUp(2)
                     }
      MAX-ACCESS read-only
      STATUS current
      DESCRIPTION
             "Current status of the Main PSU Ethernet link. NB: a 
             change of state may generate an SNMP trap and/or SMTP 
             email alert"  
      ::= { ethernet 4 } 
 
   mainPSUPortSpeedAndDuplex OBJECT-TYPE
      SYNTAX INTEGER {
                       speed1000MbpsFullDuplex(0),
                       speed100MbpsFullDuplex(1),
                       speed100MbpsHalfDuplex(2),
                       speed10MbpsFullDuplex(3),
                       speed10MbpsHalfDuplex(4),
                       speedUnknown6(5)
                     }
      MAX-ACCESS read-only
      STATUS current
      DESCRIPTION
             "The current speed and duplex of the Main PSU Ethernet 
             link"  
      ::= { ethernet 5 } 
 
   dataPortWirelessDownAlert OBJECT-TYPE
      SYNTAX INTEGER {
                       disabled(0),
                       enabled(1)
                     }
      MAX-ACCESS read-write
      STATUS current
      DESCRIPTION
             "When enabled, this causes the Ethernet link to be 
             dropped briefly when the wireless link drops. This is so 
             that spanning tree algorithms can quickly detect that 
             there is a problem."  
      ::= { ethernet 6 } 
 
   useVLANForManagementInterfaces OBJECT-TYPE
      SYNTAX INTEGER {
                       noVLANTagging(0),
                       iEEE8021QTaggedCTagType8100(1),
                       iEEE8021adTaggedSTagorBTagType88a8(2)
                     }
      MAX-ACCESS read-write
      STATUS current
      DESCRIPTION
             "This controls whether the management interfaces 
             (WWW/SNMP/SMTP/SNTP) use VLAN tags or not. NB: The new 
             setting will only take effect after a system reboot"  
      ::= { ethernet 7 } 
 
   vLANManagementPriority OBJECT-TYPE
      SYNTAX INTEGER {
                       p0(0),
                       p1(1),
                       p2(2),
                       p3(3),
                       p4(4),
                       p5(5),
                       p6(6),
                       p7(7)
                     }
      MAX-ACCESS read-write
      STATUS current
      DESCRIPTION
             "This VLAN Priority (0-7) will be included in packets 
             generated by the management interfaces"  
      ::= { ethernet 8 } 
 
   vLANManagementVID OBJECT-TYPE
      SYNTAX INTEGER (0..4094)
      MAX-ACCESS read-write
      STATUS current
      DESCRIPTION
             "This VLAN VID (0-4094) will be included in packets 
             generated by the management interfaces. Note the new 
             setting will only take effect after a system reboot"  
      ::= { ethernet 11 } 
 
   auxPortStatus OBJECT-TYPE
      SYNTAX INTEGER {
                       down(0),
                       copperLinkUp(1)
                     }
      MAX-ACCESS read-only
      STATUS current
      DESCRIPTION
             "Current status of the Aux Ethernet link. NB: a change of 
             state may generate an SNMP trap and/or SMTP email alert"  
      ::= { ethernet 12 } 
 
   auxPortSpeedAndDuplex OBJECT-TYPE
      SYNTAX INTEGER {
                       speed1000MbpsFullDuplex(0),
                       speed100MbpsFullDuplex(1),
                       speed100MbpsHalfDuplex(2),
                       speed10MbpsFullDuplex(3),
                       speed10MbpsHalfDuplex(4),
                       speedUnknown6(5)
                     }
      MAX-ACCESS read-only
      STATUS current
      DESCRIPTION
             "The current speed and duplex of the Aux Ethernet link"  
      ::= { ethernet 13 } 
 
   ethernetPriorityTableNumber OBJECT-TYPE
      SYNTAX INTEGER (9)
      MAX-ACCESS read-only
      STATUS current
      DESCRIPTION
             "Number of entries in the vLANPriorityTable."  
      ::= { ethernet 14 } 
 
   l2CPPriorityTableNumber OBJECT-TYPE
      SYNTAX INTEGER (5)
      MAX-ACCESS read-only
      STATUS current
      DESCRIPTION
             "Number of entries in the l2CPPriorityTable."  
      ::= { ethernet 16 } 
 
   iPDSCPPriorityTableNumber OBJECT-TYPE
      SYNTAX INTEGER (64)
      MAX-ACCESS read-only
      STATUS current
      DESCRIPTION
             "Number of entries in the iPDSCPPriorityTable."  
      ::= { ethernet 18 } 
 
   mPLSTCPriorityTableNumber OBJECT-TYPE
      SYNTAX INTEGER (8)
      MAX-ACCESS read-only
      STATUS current
      DESCRIPTION
             "Number of entries in the mPLSTCPriorityTable."  
      ::= { ethernet 20 } 
 
   managementPortWirelessDownAlert OBJECT-TYPE
      SYNTAX INTEGER {
                       disabled(0),
                       enabled(1)
                     }
      MAX-ACCESS read-write
      STATUS current
      DESCRIPTION
             "When enabled, this causes the management link to be 
             dropped briefly when the wireless link drops. This is so 
             that spanning tree algorithms can quickly detect that 
             there is a problem."  
      ::= { ethernet 23 } 
 
   qOSPriorityScheme OBJECT-TYPE
      SYNTAX INTEGER {
                       ethernet(0),
                       iPMPLS(1)
                     }
      MAX-ACCESS read-write
      STATUS current
      DESCRIPTION
             "Selects classification based on fields in the Ethernet 
             header (Layer 2) or in the Network header (Layer 3). The 
             unit recognises two network layer protocols: IP and MPLS"  
      ::= { ethernet 24 } 
 
   unknownNetworkPriorityQueueMapping OBJECT-TYPE
      SYNTAX INTEGER {
                       q0(0),
                       q1(1),
                       q2(2),
                       q3(3),
                       q4(4),
                       q5(5),
                       q6(6),
                       q7(7)
                     }
      MAX-ACCESS read-write
      STATUS current
      DESCRIPTION
             "Configures the classification of unknown network 
             protocols to an egress queue at the wireless port. 
             Unknown means something other than IP and MPLS"  
      ::= { ethernet 25 } 
 
   dSCPManagementPriority OBJECT-TYPE
      SYNTAX INTEGER (0..63)
      MAX-ACCESS read-only
      STATUS current
      DESCRIPTION
             "This Differentiated Services Code Point value will be 
             inserted in the IP Header of all IP Datagrams transmitted 
             by the management interfaces"  
      ::= { ethernet 26 } 
 
   dataBridgingStatus OBJECT-TYPE
      SYNTAX INTEGER {
                       disabled(0),
                       enabled(1)
                     }
      MAX-ACCESS read-only
      STATUS current
      DESCRIPTION
             "Current status of Ethernet Data traffic bridging over 
             the wireless link"  
      ::= { ethernet 27 } 
 
   mainPSUPortAllocation OBJECT-TYPE
      SYNTAX INTEGER {
                       disabled(0),
                       dataOnly(1),
                       dataandInBandManagement(2),
                       outofBandLocalManagement(3),
                       outofBandRemoteManagement(4),
                       secondDataOnly(5),
                       secondDataandInBandManagement(6)
                     }
      MAX-ACCESS read-only
      STATUS current
      DESCRIPTION
             "Indicates the service or services supported by the Main 
             PSU Ethernet port"  
      ::= { ethernet 28 } 
 
   auxPortAllocation OBJECT-TYPE
      SYNTAX INTEGER {
                       disabled(0),
                       dataOnly(1),
                       dataandInBandManagement(2),
                       outofBandLocalManagement(3),
                       outofBandRemoteManagement(4),
                       secondDataOnly(5),
                       secondDataandInBandManagement(6)
                     }
      MAX-ACCESS read-only
      STATUS current
      DESCRIPTION
             "Indicates the service or services supported by the Aux 
             Ethernet port"  
      ::= { ethernet 29 } 
 
   sFPPortAllocation OBJECT-TYPE
      SYNTAX INTEGER {
                       disabled(0),
                       dataOnly(1),
                       dataandInBandManagement(2),
                       outofBandLocalManagement(3),
                       outofBandRemoteManagement(4),
                       secondDataOnly(5),
                       secondDataandInBandManagement(6)
                     }
      MAX-ACCESS read-only
      STATUS current
      DESCRIPTION
             "Indicates the service or services supported by the SFP 
             Ethernet port"  
      ::= { ethernet 30 } 
 
   dataPortPauseFrames OBJECT-TYPE
      SYNTAX INTEGER {
                       tunnel(0),
                       discard(1)
                     }
      MAX-ACCESS read-only
      STATUS current
      DESCRIPTION
             "Controls whether the bridge tunnels or discards Layer 2 
             PAUSE frames arriving at the Data Port. Such frames are 
             identified by the destination MAC Address being equal to 
             01-80-C2-00-00-01"  
      ::= { ethernet 31 } 
 
   sFPPortAutoNegotiation OBJECT-TYPE
      SYNTAX INTEGER {
                       disabled(0),
                       enabled(1)
                     }
      MAX-ACCESS read-only
      STATUS current
      DESCRIPTION
             "This controls whether the local SFP Ethernet interface 
             configuration is automatically negotiated or forced. Do 
             not use a forced setting together with auto negotiation 
             at the Ethernet link partner. If you want to run your 
             Ethernet link at a fixed speed and duplex then you would 
             normally leave auto negotiation enabled and only enable 
             the single Auto Neg Advertisement option that you want 
             the link to run in - FORCING ETHERNET CONFIGURATION IS A 
             LAST RESORT WHICH SHOULD ONLY BE PERFORMED IF YOU ARE 
             HAVING PROBLEMS WITH AUTO NEGOTIATION - AND YOU MUST 
             ENSURE THAT YOU CONFIGURE BOTH THIS UNIT AND THE ETHERNET 
             LINK PARTNER TO WHICH IT IS CONNECTED IDENTICALLY (THE 
             LINK PARTNER MUST NOT HAVE AUTO NEGOTIATION ENABLED 
             EITHER, OTHERWISE A DUPLEX MISMATCH WILL OCCUR). NB: The 
             new setting will only take effect after a system reboot."  
      ::= { ethernet 32 } 
 
   sFPPortAutoNegAdvertisement OBJECT-TYPE
      SYNTAX BITS {
                    negInvalid(2),
                    neg10MbpsHalfDuplex(3),
                    neg10MbpsFullDuplex(4),
                    neg100MbpsHalfDuplex(5),
                    neg100MbpsFullDuplex(6),
                    neg1000MbpsFullDuplex(7)
                  }
      MAX-ACCESS read-only
      STATUS current
      DESCRIPTION
             "This sets the different SFP Ethernet configurations that 
             will be advertised during auto negotiation. Note the new 
             setting will only take effect after a system reboot. 
             WARNING: Duplex mismatch may result if both ends of the 
             Ethernet link do not have the same settings. Do not auto 
             negotiation together with a fixed setting at the Ethernet 
             link partner. WARNING: Make sure that you select 
             option(s) that you know your connected equipment can 
             cater for!"  
      ::= { ethernet 33 } 
 
   sFPPortAutoMdix OBJECT-TYPE
      SYNTAX INTEGER {
                       disabled(0),
                       enabled(1)
                     }
      MAX-ACCESS read-only
      STATUS current
      DESCRIPTION
             "This enables/disables the Auto MDI/MDIX capability. NB: 
             The new setting will only take effect after a system 
             reboot"  
      ::= { ethernet 34 } 
 
   sFPPortStatus OBJECT-TYPE
      SYNTAX INTEGER {
                       down(0),
                       copperLinkUp(1),
                       fiberLinkUp(2)
                     }
      MAX-ACCESS read-only
      STATUS current
      DESCRIPTION
             "Current status of the SFP Ethernet link. NB: a change of 
             state may generate an SNMP trap and/or SMTP email alert"  
      ::= { ethernet 35 } 
 
   sFPPortSpeedAndDuplex OBJECT-TYPE
      SYNTAX INTEGER {
                       speed1000MbpsFullDuplex(0),
                       speed100MbpsFullDuplex(1),
                       speed100MbpsHalfDuplex(2),
                       speed10MbpsFullDuplex(3),
                       speed10MbpsHalfDuplex(4),
                       speedUnknown6(5)
                     }
      MAX-ACCESS read-only
      STATUS current
      DESCRIPTION
             "The current speed and duplex of the SFP Ethernet link"  
      ::= { ethernet 36 } 
 
   auxPortPowerOverEthernetOutput OBJECT-TYPE
      SYNTAX INTEGER {
                       disabled(0),
                       enabled(1)
                     }
      MAX-ACCESS read-only
      STATUS current
      DESCRIPTION
             "The state of the Power Over Ethernet (PoE) output of the 
             Aux port. Enabling PoE output may lead to system 
             instability; please refer to the User Guide before 
             enabling this control"  
      ::= { ethernet 37 } 
 
   auxPortPowerOverEthernetOutputStatus OBJECT-TYPE
      SYNTAX INTEGER {
                       poEOutputOn(0),
                       poEOutputDisabled(1),
                       poEOutputEnabledbutNotActiveErrororNoLoadPresent(2),
                       poEOutputOverloadError(3),
                       poEOutputOverTempError(4),
                       poEOutputErrorDetected(5)
                     }
      MAX-ACCESS read-only
      STATUS current
      DESCRIPTION
             "Current status of the Power Over Ethernet (PoE) output 
             of the Aux port"  
      ::= { ethernet 38 } 
 
   syncETracking OBJECT-TYPE
      SYNTAX INTEGER {
                       disabled(0),
                       enabled(1),
                       internalTDMUseOnly(2)
                     }
      MAX-ACCESS read-write
      STATUS current
      DESCRIPTION
             "Controls whether Synchronous Ethernet (SyncE) network 
             synchronization is enabled."  
      ::= { ethernet 39 } 
 
   syncEEquipmentClock OBJECT-TYPE
      SYNTAX INTEGER {
                       eECOption1(0),
                       eECOption2(1)
                     }
      MAX-ACCESS read-write
      STATUS current
      DESCRIPTION
             "EEC-Option 1 applies to synchronous Ethernet equipments 
             that are designed to interwork with networks optimized 
             for the 2048-kbit/s hierarchy. Corresponds to ITU-T G.813 
             Option 1; EEC-Option 2 applies to synchronous Ethernet 
             equipments that are designed to interwork with networks 
             optimized for the 1544-kbit/s hierarchy. Corresponds to 
             Type IV clock from ITU-T G.812."  
      ::= { ethernet 40 } 
 
   mainPSUPortQLRxOverwrite OBJECT-TYPE
      SYNTAX INTEGER {
                       disabled(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12)
                     }
      MAX-ACCESS read-write
      STATUS current
      DESCRIPTION
             "Override for the Synchronous Ethernet (SyncE) received 
             Quality Level (QL) on the main PSU port."  
      ::= { ethernet 41 } 
 
   mainPSUPortSSMTx OBJECT-TYPE
      SYNTAX INTEGER {
                       disabled(0),
                       enabled(1)
                     }
      MAX-ACCESS read-write
      STATUS current
      DESCRIPTION
             "Controls whether the Synchronous Ethernet (SyncE) 
             Quality Level (QL) is transmitted on the Main PSU port"  
      ::= { ethernet 42 } 
 
   sFPPortSSMTx OBJECT-TYPE
      SYNTAX INTEGER {
                       disabled(0),
                       enabled(1)
                     }
      MAX-ACCESS read-write
      STATUS current
      DESCRIPTION
             "Controls whether the Synchronous Ethernet (SyncE) 
             Quality Level (QL) is transmitted on the SFP port"  
      ::= { ethernet 43 } 
 
   auxPortSSMTx OBJECT-TYPE
      SYNTAX INTEGER {
                       disabled(0),
                       enabled(1)
                     }
      MAX-ACCESS read-write
      STATUS current
      DESCRIPTION
             "Controls whether the Synchronous Ethernet (SyncE) 
             Quality Level (QL) is transmitted on the Aux port"  
      ::= { ethernet 44 } 
 
   syncETrackingState OBJECT-TYPE
      SYNTAX INTEGER {
                       disabled(0),
                       acquiringWirelessLock(1),
                       freeRunning(2),
                       lockedLocalAcquiringHoldover(3),
                       lockedLocalHoldoverAcquired(4),
                       holdover(5),
                       lockedRemoteAcquiringHoldover(6),
                       lockedRemoteHoldoverAcquired(7)
                     }
      MAX-ACCESS read-only
      STATUS current
      DESCRIPTION
             "The current state of Synchronous Ethernet (SyncE) 
             network synchronization."  
      ::= { ethernet 45 } 
 
   mainPSUPortQLRx OBJECT-TYPE
      SYNTAX INTEGER {
                       none(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12),
                       qLFAILED(13)
                     }
      MAX-ACCESS read-only
      STATUS current
      DESCRIPTION
             "The Synchronous Ethernet (SyncE) Quality Level (QL) 
             currently being received on the main PSU port."  
      ::= { ethernet 46 } 
 
   auxPortQLRx OBJECT-TYPE
      SYNTAX INTEGER {
                       none(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12),
                       qLFAILED(13)
                     }
      MAX-ACCESS read-only
      STATUS current
      DESCRIPTION
             "The Synchronous Ethernet (SyncE) Quality Level (QL) 
             currently being received on the auxiliary port."  
      ::= { ethernet 47 } 
 
   sFPPortQLRx OBJECT-TYPE
      SYNTAX INTEGER {
                       none(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12),
                       qLFAILED(13)
                     }
      MAX-ACCESS read-only
      STATUS current
      DESCRIPTION
             "The Synchronous Ethernet (SyncE) Quality Level (QL) 
             currently being received on the SFP port."  
      ::= { ethernet 48 } 
 
   mainPSUPortQLTx OBJECT-TYPE
      SYNTAX INTEGER {
                       none(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12)
                     }
      MAX-ACCESS read-only
      STATUS current
      DESCRIPTION
             "The Synchronous Ethernet (SyncE) transmit Quality Level 
             (QL) of the main PSU port."  
      ::= { ethernet 49 } 
 
   auxPortQLTx OBJECT-TYPE
      SYNTAX INTEGER {
                       none(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12)
                     }
      MAX-ACCESS read-only
      STATUS current
      DESCRIPTION
             "The Synchronous Ethernet (SyncE) transmit Quality Level 
             (QL) of the auxiliary port."  
      ::= { ethernet 50 } 
 
   sFPPortQLTx OBJECT-TYPE
      SYNTAX INTEGER {
                       none(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12)
                     }
      MAX-ACCESS read-only
      STATUS current
      DESCRIPTION
             "The Synchronous Ethernet (SyncE) transmit Quality Level 
             (QL) of the SFP port."  
      ::= { ethernet 51 } 
 
   mainPSUPortSyncEMasterSlaveStatus OBJECT-TYPE
      SYNTAX INTEGER {
                       master(0),
                       slave(1)
                     }
      MAX-ACCESS read-only
      STATUS current
      DESCRIPTION
             "The main PSU port Synchronous Ethernet (SyncE) 
             Master/Slave status"  
      ::= { ethernet 52 } 
 
   auxPortSyncEMasterSlaveStatus OBJECT-TYPE
      SYNTAX INTEGER {
                       master(0),
                       slave(1)
                     }
      MAX-ACCESS read-only
      STATUS current
      DESCRIPTION
             "The auxiliary port Synchronous Ethernet (SyncE) 
             Master/Slave status"  
      ::= { ethernet 53 } 
 
   sFPPortSyncEMasterSlaveStatus OBJECT-TYPE
      SYNTAX INTEGER {
                       master(0),
                       slave(1)
                     }
      MAX-ACCESS read-only
      STATUS current
      DESCRIPTION
             "The SFP port Synchronous Ethernet (SyncE) Master/Slave 
             status"  
      ::= { ethernet 54 } 
 
   mainPSUPortGigabitMasterSlaveStatus OBJECT-TYPE
      SYNTAX INTEGER {
                       master(0),
                       slave(1),
                       notApplicable(2)
                     }
      MAX-ACCESS read-only
      STATUS current
      DESCRIPTION
             "The main PSU port Gigabit Ethernet Master/Slave status"  
      ::= { ethernet 55 } 
 
   auxPortGigabitMasterSlaveStatus OBJECT-TYPE
      SYNTAX INTEGER {
                       master(0),
                       slave(1),
                       notApplicable(2)
                     }
      MAX-ACCESS read-only
      STATUS current
      DESCRIPTION
             "The auxiliary port Gigabit Ethernet Master/Slave status"  
      ::= { ethernet 56 } 
 
   sFPPortGigabitMasterSlaveStatus OBJECT-TYPE
      SYNTAX INTEGER {
                       master(0),
                       slave(1),
                       notApplicable(2)
                     }
      MAX-ACCESS read-only
      STATUS current
      DESCRIPTION
             "The SFP port Gigabit Ethernet Master/Slave status"  
      ::= { ethernet 57 } 
 
   transparentClock OBJECT-TYPE
      SYNTAX INTEGER {
                       disabled(0),
                       enabled(1)
                     }
      MAX-ACCESS read-write
      STATUS current
      DESCRIPTION
             "This control enables the Precision Time Protocol 
             (IEEE-1588) Transparent Clock. Once enabled the unit will 
             modify the correction field in PTP event messages to take 
             account of the time these frames have been resident in 
             this system. This will happen for all PTP frames at Layer 
             2 & Layer 3 (IPv4 & IPv6) unless a transparent clock VLAN 
             is enabled."  
      ::= { ethernet 58 } 
 
   transparentClockVLAN OBJECT-TYPE
      SYNTAX INTEGER {
                       all(0),
                       sTagged(1),
                       cTagged(2)
                     }
      MAX-ACCESS read-write
      STATUS current
      DESCRIPTION
             "If All is selected then all PTP frames will have their 
             correction fields modified with the residence time. If an 
             S-TAG or C-TAG is selected, only frames with this VLAN 
             tag and matching the VLAN ID in the Transparent Clock VID 
             will have their correction fields modified."  
      ::= { ethernet 59 } 
 
   transparentClockVID OBJECT-TYPE
      SYNTAX INTEGER (0..4094)
      MAX-ACCESS read-write
      STATUS current
      DESCRIPTION
             "The VLAN ID which frames must match if they are to be 
             corrected. Only valid when an S-TAG or C-TAG has been 
             selected."  
      ::= { ethernet 60 } 
 
   mainPSUPortAcceptedQLRx OBJECT-TYPE
      SYNTAX INTEGER {
                       none(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12),
                       qLFAILED(13)
                     }
      MAX-ACCESS read-only
      STATUS current
      DESCRIPTION
             "The Synchronous Ethernet (SyncE) Quality Level (QL) 
             currently accepted (validated) on the main PSU port."  
      ::= { ethernet 61 } 
 
   auxPortAcceptedQLRx OBJECT-TYPE
      SYNTAX INTEGER {
                       none(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12),
                       qLFAILED(13)
                     }
      MAX-ACCESS read-only
      STATUS current
      DESCRIPTION
             "The Synchronous Ethernet (SyncE) Quality Level (QL) 
             currently accepted (validated) on the auxiliary port."  
      ::= { ethernet 62 } 
 
   sFPPortAcceptedQLRx OBJECT-TYPE
      SYNTAX INTEGER {
                       none(0),
                       qLPRS(1),
                       qLSTU(2),
                       qLPRC(3),
                       qLST2(4),
                       qLSSUAQLTNC(5),
                       qLSSUB(6),
                       qLST3E(7),
                       qLEEC2QLST3(8),
                       qLEEC1QLSEC(9),
                       qLSMC(10),
                       qLPROV(11),
                       qLDNUQLDUS(12),
                       qLFAILED(13)
                     }
      MAX-ACCESS read-only
      STATUS current
      DESCRIPTION
             "The Synchronous Ethernet (SyncE) Quality Level (QL) 
             currently accepted (validated) on the SFP port."  
      ::= { ethernet 63 } 
 
   mainPSUPortSyncERxStatus OBJECT-TYPE
      SYNTAX INTEGER {
                       good(0),
                       waittoRestore(1),
                       failed(2)
                     }
      MAX-ACCESS read-only
      STATUS current
      DESCRIPTION
             "The Synchronous Ethernet (SyncE) Receive Status of the 
             main PSU port"  
      ::= { ethernet 64 } 
 
   auxPortSyncERxStatus OBJECT-TYPE
      SYNTAX INTEGER {
                       good(0),
                       waittoRestore(1),
                       failed(2)
                     }
      MAX-ACCESS read-only
      STATUS current
      DESCRIPTION
             "The Synchronous Ethernet (SyncE) Receive Status of the 
             auxiliary port"  
      ::= { ethernet 65 } 
 
   sFPPortSyncERxStatus OBJECT-TYPE
      SYNTAX INTEGER {
                       good(0),
                       waittoRestore(1),
                       failed(2)
                     }
      MAX-ACCESS read-only
      STATUS current
      DESCRIPTION
             "The Synchronous Ethernet (SyncE) Receive Status of the 
             SFP port"  
      ::= { ethernet 66 } 
 
   nIDULanPortStatus OBJECT-TYPE
      SYNTAX INTEGER {
                       down(0),
                       copperLinkUp(1),
                       fiberLinkUp(2)
                     }
      MAX-ACCESS read-only
      STATUS current
      DESCRIPTION
             "Current status of the NIDU LAN Ethernet link. NB: a 
             change of state may generate an SNMP trap and/or SMTP 
             email alert"  
      ::= { ethernet 67 } 
 
   nIDULanPortSpeedAndDuplex OBJECT-TYPE
      SYNTAX INTEGER {
                       speed1000MbpsFullDuplex(0),
                       speed100MbpsFullDuplex(1),
                       speed100MbpsHalfDuplex(2),
                       speed10MbpsFullDuplex(3),
                       speed10MbpsHalfDuplex(4),
                       speedUnknown6(5)
                     }
      MAX-ACCESS read-only
      STATUS current
      DESCRIPTION
             "The current speed and duplex of the Ethernet link to the 
             NIDU LAN Port"  
      ::= { ethernet 68 } 
 
   oOBPriorityQueueMapping OBJECT-TYPE
      SYNTAX INTEGER {
                       q0(0),
                       q1(1),
                       q2(2),
                       q3(3),
                       q4(4),
                       q5(5),
                       q6(6),
                       q7(7)
                     }
      MAX-ACCESS read-write
      STATUS current
      DESCRIPTION
             "Configures the classification of traffic to an egress 
             queue at the wireless port"  
      ::= { ethernet 69 } 
 
   nIDULanPortAutoNegotiation OBJECT-TYPE
      SYNTAX INTEGER {
                       disabled(0),
                       enabled(1)
                     }
      MAX-ACCESS read-only
      STATUS current
      DESCRIPTION
             "This controls whether the local Ethernet interface 
             configuration is automatically negotiated or forced. Do 
             not use a forced setting together with auto negotiation 
             at the Ethernet link partner. If you want to run your 
             Ethernet link at a fixed speed and duplex then you would 
             normally leave auto negotiation enabled and only enable 
             the single Auto Neg Advertisement option that you want 
             the link to run in - FORCING ETHERNET CONFIGURATION IS A 
             LAST RESORT WHICH SHOULD ONLY BE PERFORMED IF YOU ARE 
             HAVING PROBLEMS WITH AUTO NEGOTIATION - AND YOU MUST 
             ENSURE THAT YOU CONFIGURE BOTH THIS UNIT AND THE ETHERNET 
             LINK PARTNER TO WHICH IT IS CONNECTED IDENTICALLY (THE 
             LINK PARTNER MUST NOT HAVE AUTO NEGOTIATION ENABLED 
             EITHER, OTHERWISE A DUPLEX MISMATCH WILL OCCUR). NB: The 
             new setting will only take effect after a system reboot."  
      ::= { ethernet 70 } 
 
   nIDULanPortAutoNegAdvertisement OBJECT-TYPE
      SYNTAX BITS {
                    negInvalid(2),
                    neg10MbpsHalfDuplex(3),
                    neg10MbpsFullDuplex(4),
                    neg100MbpsHalfDuplex(5),
                    neg100MbpsFullDuplex(6),
                    neg1000MbpsFullDuplex(7)
                  }
      MAX-ACCESS read-only
      STATUS current
      DESCRIPTION
             "This sets the different Ethernet configurations that 
             will be advertised during auto negotiation. Note the new 
             setting will only take effect after a system reboot. 
             WARNING: Duplex mismatch may result if both ends of the 
             Ethernet link do not have the same settings. Do not auto 
             negotiation together with a fixed setting at the Ethernet 
             link partner. WARNING: Make sure that you select 
             option(s) that you know your connected equipment can 
             cater for!"  
      ::= { ethernet 71 } 
 
   nIDULanPortAutoMdix OBJECT-TYPE
      SYNTAX INTEGER {
                       disabled(0),
                       enabled(1)
                     }
      MAX-ACCESS read-only
      STATUS current
      DESCRIPTION
             "This enables/disables the Auto MDI/MDIX capability. NB: 
             The new setting will only take effect after a system 
             reboot"  
      ::= { ethernet 72 } 
 
   nIDULanPortGigabitMasterSlaveStatus OBJECT-TYPE
      SYNTAX INTEGER {
                       master(0),
                       slave(1),
                       notApplicable(2)
                     }
      MAX-ACCESS read-only
      STATUS current
      DESCRIPTION
             "The NIDU LAN port Gigabit Ethernet Master/Slave status"  
      ::= { ethernet 73 } 
 
   txMABFrames OBJECT-TYPE
      SYNTAX Integer32
      MAX-ACCESS read-only
      STATUS current
      DESCRIPTION
             "Number of MAB frames transmitted"  
      ::= { ethernet 74 } 
 
   managementNetworkAccessEnabled OBJECT-TYPE
      SYNTAX INTEGER {
                       no(0),
                       yes(1)
                     }
      MAX-ACCESS read-write
      STATUS current
      DESCRIPTION
             "When enabled the local Out-of-Band interface can be used 
             to access the remote management network. If not enabled 
             the local management agent can still be accessed from the 
             remote management network and the local Out-of-Band 
             interface"  
      ::= { ethernet 75 } 
 
   secondDataPortPauseFrames OBJECT-TYPE
      SYNTAX INTEGER {
                       tunnel(0),
                       discard(1)
                     }
      MAX-ACCESS read-only
      STATUS current
      DESCRIPTION
             "Controls whether the bridge tunnels or discards Layer 2 
             PAUSE frames arriving at the Second Data Service Port. 
             Such frames are identified by the destination MAC Address 
             being equal to 01-80-C2-00-00-01"  
      ::= { ethernet 76 } 
 
   secondDataBridgingStatus OBJECT-TYPE
      SYNTAX INTEGER {
                       disabled(0),
                       enabled(1)
                     }
      MAX-ACCESS read-only
      STATUS current
      DESCRIPTION
             "Current status of bridging Second Data Service Ethernet 
             traffic over the wireless link"  
      ::= { ethernet 80 } 
 
   transparentClockPort OBJECT-TYPE
      SYNTAX INTEGER {
                       mainPSU(0),
                       aux(1),
                       sFP(2)
                     }
      MAX-ACCESS read-write
      STATUS current
      DESCRIPTION
             "IEEE 1588 Transparent Clock source"  
      ::= { ethernet 81 } 
 
   -- EthernetPriorityTable group attribute definitions 
   --
   ethernetPriorityTableIndex OBJECT-TYPE
      SYNTAX INTEGER {
                       p0(1),
                       p1(2),
                       p2(3),
                       p3(4),
                       p4(5),
                       p5(6),
                       p6(7),
                       p7(8),
                       untagged(9)
                     }
      MAX-ACCESS not-accessible
      STATUS current
      DESCRIPTION
             "Ethernet priority flag, used to index values in the 
             ethernetPriorityTable"  
      ::= { ethernetPriorityTableEntry 1 } 
 
   ethernetPriorityQueueMapping OBJECT-TYPE
      SYNTAX INTEGER {
                       q0(0),
                       q1(1),
                       q2(2),
                       q3(3),
                       q4(4),
                       q5(5),
                       q6(6),
                       q7(7)
                     }
      MAX-ACCESS read-write
      STATUS current
      DESCRIPTION
             "Configures the classification of this Ethernet priority 
             (also known as IEEE 802.1p value) to an egress queue at 
             the wireless port"  
      ::= { ethernetPriorityTableEntry 2 } 
 
   -- L2CPPriorityTable group attribute definitions 
   --
   l2CPPriorityTableIndex OBJECT-TYPE
      SYNTAX INTEGER {
                       bridge(1),
                       mRP(2),
                       cFM(3),
                       rAPS(4),
                       eAPS(5)
                     }
      MAX-ACCESS not-accessible
      STATUS current
      DESCRIPTION
             "L2CP priority flag, used to index values in the 
             l2CPPriorityTable"  
      ::= { l2CPPriorityTableEntry 1 } 
 
   l2CPPriorityQueueMapping OBJECT-TYPE
      SYNTAX INTEGER {
                       q0(0),
                       q1(1),
                       q2(2),
                       q3(3),
                       q4(4),
                       q5(5),
                       q6(6),
                       q7(7)
                     }
      MAX-ACCESS read-write
      STATUS current
      DESCRIPTION
             "Configures the classification of this layer two control 
             protocol (L2CP) to an egress queue at the wireless port"  
      ::= { l2CPPriorityTableEntry 2 } 
 
   -- IPDSCPPriorityTable group attribute definitions 
   --
   iPDSCPPriorityTableIndex OBJECT-TYPE
      SYNTAX INTEGER (1..64)
      MAX-ACCESS not-accessible
      STATUS current
      DESCRIPTION
             "IP DSCP priority flag, used to index values in the 
             iPDSCPPriorityTable"  
      ::= { iPDSCPPriorityTableEntry 1 } 
 
   iPDSCPPriorityQueueMapping OBJECT-TYPE
      SYNTAX INTEGER {
                       q0(0),
                       q1(1),
                       q2(2),
                       q3(3),
                       q4(4),
                       q5(5),
                       q6(6),
                       q7(7)
                     }
      MAX-ACCESS read-write
      STATUS current
      DESCRIPTION
             "Configures the classification of this IP differentiated 
             services code point (DSCP) value to an egress queue at 
             the wireless port"  
      ::= { iPDSCPPriorityTableEntry 2 } 
 
   -- MPLSTCPriorityTable group attribute definitions 
   --
   mPLSTCPriorityTableIndex OBJECT-TYPE
      SYNTAX INTEGER (1..8)
      MAX-ACCESS not-accessible
      STATUS current
      DESCRIPTION
             "MPLS TC priority flag, used to index values in the 
             mPLSTCPriorityTable"  
      ::= { mPLSTCPriorityTableEntry 1 } 
 
   mPLSTCPriorityQueueMapping OBJECT-TYPE
      SYNTAX INTEGER {
                       q0(0),
                       q1(1),
                       q2(2),
                       q3(3),
                       q4(4),
                       q5(5),
                       q6(6),
                       q7(7)
                     }
      MAX-ACCESS read-write
      STATUS current
      DESCRIPTION
             "Configures the classification of this MPLS traffic class 
             (the field formerly known as EXP) to an egress queue at 
             the wireless port"  
      ::= { mPLSTCPriorityTableEntry 2 } 
 
   -- TDM group attribute definitions 
   --
   tDMInterfaceControl OBJECT-TYPE
      SYNTAX INTEGER {
                       none(0),
                       e1(1),
                       t1(2)
                     }
      MAX-ACCESS read-only
      STATUS current
      DESCRIPTION
             "The line interface type. If this is set to 'None' then 
             the TDM interfaces are disabled, and the TDM settings 
             will be ignored."  
      ::= { tDM 1 } 
 
   tDMInterfaceStatus OBJECT-TYPE
      SYNTAX INTEGER {
                       ok(0),
                       connectedNotConfigured(1),
                       notConnected(2),
                       nIDUdetectedonAUXport(3),
                       error(4),
                       codeDownloadInProgress(5)
                     }
      MAX-ACCESS read-only
      STATUS current
      DESCRIPTION
             "@Current status of the connection to the TDM Box. A 
             state of 'Up' on a green background indicates that the 
             TDM Box is connected OK. When connecting a TDM Box only 
             the Main Ethernet port should be used"  
      ::= { tDM 2 } 
 
   tDMEnabledChannels OBJECT-TYPE
      SYNTAX INTEGER (0..8)
      MAX-ACCESS read-only
      STATUS current
      DESCRIPTION
             "The number of TDM channels enabled in the system"  
      ::= { tDM 3 } 
 
   tdmTableNumber OBJECT-TYPE
      SYNTAX INTEGER (1..8)
      MAX-ACCESS read-only
      STATUS current
      DESCRIPTION
             "Number of entries in the TdmTable"  
      ::= { tDM 4 } 
 
   tDMConfigurationMismatch OBJECT-TYPE
      SYNTAX INTEGER {
                       ok(0),
                       linetypemismatch(1),
                       enabledchannelsmismatch(2),
                       linetypeandenabledchannelsmismatch(3)
                     }
      MAX-ACCESS read-only
      STATUS current
      DESCRIPTION
             "Current status of the configuration of the TDM Box. A 
             state of 'Ok' on a green background indicates that the 
             TDM Box configuration is matched OK with the remote end."  
      ::= { tDM 6 } 
 
   lowestTDMModulationMode OBJECT-TYPE
      SYNTAX INTEGER {
                       modAcquisition(0),
                       modBpsk63percent(1),
                       modQpsk63percentSingle(2),
                       modTransient1(3),
                       modQpsk87percentSingle(4),
                       modTransient2(5),
                       mod16qam63percentSingleA(6),
                       modTransient3(7),
                       mod16qam87percentSingle(8),
                       modTransient4(9),
                       mod64qam75percentSingle(10),
                       modTransient5(11),
                       mod64qam92percentSingle(12),
                       modTransient6(13),
                       mod256qam81percentSingle(14),
                       mod16qam63percentSingleB(15),
                       mod16qam63percentDual(16),
                       modTransient7(17),
                       mod16qam87percentDual(18),
                       modTransient8(19),
                       mod64qam75percentDual(20),
                       modTransient9(21),
                       mod64qam92percentDual(22),
                       modTransient10(23),
                       mod256qam81percentDual(24)
                     }
      MAX-ACCESS read-only
      STATUS current
      DESCRIPTION
             "The lowest modulation mode at which tdm data will be 
             sent. The effective lowest modulation mode is displayed 
             in the TDM Configuration page"  
      ::= { tDM 7 } 
 
   -- TdmTable group attribute definitions 
   --
   tdmTableIndex OBJECT-TYPE
      SYNTAX INTEGER (1..8)
      MAX-ACCESS not-accessible
      STATUS current
      DESCRIPTION
             "TDM Channel flag, used to index channels in the 
             TdmTable"  
      ::= { tdmTableEntry 1 } 
 
   tDMChannelStatus OBJECT-TYPE
      SYNTAX INTEGER {
                       up(0),
                       noSignalLocal(1),
                       noSignalRemote(2),
                       noSignalLocalandRemote(3),
                       remoteTiming(4),
                       noSignalLocalandRemoteTiming(5),
                       disabled(6)
                     }
      MAX-ACCESS read-only
      STATUS current
      DESCRIPTION
             "Current status of the TDM channels. A value of 0 
             indicates that a TDM channel is established"  
      ::= { tdmTableEntry 2 } 
 
   tDMChannelLineCode OBJECT-TYPE
      SYNTAX INTEGER {
                       aMI(0),
                       b8ZSorHDB3(1)
                     }
      MAX-ACCESS read-only
      STATUS current
      DESCRIPTION
             "The line code setting of the TDM interfaces. This must 
             match the setting of the device connected to an 
             interface"  
      ::= { tdmTableEntry 3 } 
 
   tDMChannelCableLength OBJECT-TYPE
      SYNTAX INTEGER {
                       feet133(0),
                       feet266(1),
                       feet399(2),
                       feet533(3),
                       feet655(4)
                     }
      MAX-ACCESS read-only
      STATUS current
      DESCRIPTION
             "The lengths of the cables connected to the TDM 
             interfaces, measured in feet"  
      ::= { tdmTableEntry 4 } 
 
   tDMChannelLoopback OBJECT-TYPE
      SYNTAX INTEGER {
                       none(0),
                       copper(1),
                       wireless(2)
                     }
      MAX-ACCESS read-only
      STATUS current
      DESCRIPTION
             "The loopback status of TDM channels. This is intended 
             for installation testing and should be set to 'None' for 
             normal operation. The wire connections to a unit can be 
             tested by applying a 'Copper' loopback to the local unit. 
             The wireless connection to the remote unit can be tested 
             by applying a 'Wireless' loopback to the remote unit with 
             no loopback on the local unit. NB: a change of state may 
             generate an SNMP trap and/or SMTP email alert"  
      ::= { tdmTableEntry 5 } 
 
   -- License group attribute definitions 
   --
   regulatoryBand OBJECT-TYPE
      SYNTAX INTEGER {
                       regInvalid(0),
                       reg158GHz(1),
                       reg258GHz(2),
                       reg358GHz(3),
                       reg458GHz(4),
                       reg558GHz(5),
                       reg658GHz(6),
                       reg754GHzUnrestrictedEIRPwithDFS(7),
                       reg854GHzUnrestrictedEIRP(8),
                       reg9(9),
                       reg1058GHz(10),
                       reg1158GHz(11),
                       reg1254GHzFCCUNII2C(12),
                       reg1354GHz(13),
                       reg1449GHzPublicSafety(14),
                       reg15(15),
                       reg1659GHz(16),
                       reg1759GHz(17),
                       reg1849GHzPublicSafety(18),
                       reg1958GHz(19),
                       reg2054GHz(20),
                       reg2154GHz(21),
                       reg2258GHz(22),
                       reg23(23),
                       reg2458GHz(24),
                       reg2558GHzETSI(25),
                       reg2654GHzETSI(26),
                       reg2758GHz(27),
                       reg2858GHz(28),
                       reg2958GHzUnrestrictedEIRPwithDFSandRTTT(29),
                       reg3054GHz(30),
                       reg3158GHz(31),
                       reg3249GHzLicensed(32),
                       reg3349GHzETSIBroadbandDisasterRelief(33),
                       reg3458GHz(34),
                       reg3558GHzUnrestrictedEIRP(35),
                       reg3654GHz(36),
                       reg3758GHz(37),
                       reg3852GHzFCCUNII2A(38),
                       reg3951GHzETSIBroadbandDisasterRelief(39),
                       reg4054GHz(40),
                       reg4154GHz(41),
                       reg4254GHz(42),
                       reg4354GHz(43),
                       reg4458GHz(44),
                       reg4558GHz(45),
                       reg4658GHz(46),
                       reg4758GHz(47),
                       reg4858GHz(48),
                       reg4958GHz(49),
                       reg5058GHz(50),
                       reg5158GHz(51),
                       reg5258GHz(52),
                       reg5358GHz(53),
                       reg5458GHz(54),
                       reg5558GHz(55),
                       reg5654GHz(56),
                       reg5754GHz(57),
                       reg5858GHz(58),
                       reg5958GHz(59),
                       reg6058GHz(60),
                       reg6149GHz(61),
                       reg6252GHz(62),
                       reg6352GHz(63),
                       reg6451GHz(64),
                       reg6551GHz(65),
                       reg6651GHz(66),
                       reg6752GHz(67),
                       reg6852GHz(68),
                       reg6952GHz(69),
                       reg7052GHz(70),
                       reg7152GHz(71),
                       reg7252GHz(72),
                       reg7352GHz(73),
                       reg7452GHz(74),
                       reg7552GHz(75),
                       reg7652GHz(76),
                       reg7752GHz(77),
                       reg7849GHz(78),
                       reg7954GHz(79),
                       reg8049GHz(80),
                       reg8147GHz(81),
                       reg8247GHz(82),
                       reg8352GHz(83),
                       reg8451GHzFCCUNII1(84),
                       reg8552GHzFCCUNII12A(85),
                       reg8654GHzFCCUNII2A2C(86),
                       reg8758GHz(87),
                       reg8849GHz(88),
                       reg8949GHz(89),
                       reg9054GHzFCCUNII2CParabolicantenna(90),
                       reg9152GHzFCCUNII2AParabolicantenna(91),
                       reg9251GHzFCCUNII1Parabolicantenna(92),
                       reg9349GHz(93),
                       reg94(94),
                       reg95(95),
                       reg96(96),
                       reg97(97),
                       reg98(98),
                       reg99(99),
                       reg100(100),
                       reg101(101),
                       reg102(102),
                       reg103(103),
                       reg104(104),
                       reg105(105),
                       reg106(106),
                       reg107(107),
                       reg108(108),
                       reg109(109),
                       reg110(110),
                       reg111(111),
                       reg112(112),
                       reg113(113),
                       reg114(114),
                       reg115(115),
                       reg116(116),
                       reg117(117),
                       reg118(118),
                       reg119(119),
                       reg120(120),
                       reg121(121),
                       reg122(122),
                       reg123(123),
                       reg124(124),
                       reg125(125),
                       reg126(126),
                       reg127(127),
                       reg128(128),
                       reg129(129),
                       reg130(130),
                       reg131(131),
                       reg132(132),
                       reg133(133),
                       reg134(134),
                       reg135(135),
                       reg136(136),
                       reg137(137),
                       reg138(138),
                       reg139(139),
                       reg140(140),
                       reg141(141),
                       reg142(142),
                       reg143(143),
                       reg144(144),
                       reg145(145),
                       reg146(146),
                       reg147(147),
                       reg148(148),
                       reg149(149),
                       reg150(150),
                       reg151(151),
                       reg152(152),
                       reg153(153),
                       reg154(154),
                       reg155(155),
                       reg156(156),
                       reg157(157),
                       reg158(158),
                       reg159(159),
                       reg160(160),
                       reg161(161),
                       reg162(162),
                       reg163(163),
                       reg164(164),
                       reg165(165),
                       reg166(166),
                       reg167(167),
                       reg168(168),
                       reg169(169),
                       reg170(170),
                       reg171(171),
                       reg172(172),
                       reg173(173),
                       reg174(174),
                       reg175(175),
                       reg176(176),
                       reg177(177),
                       reg178(178),
                       reg179(179),
                       reg180(180),
                       reg181(181),
                       reg182(182),
                       reg183(183),
                       reg184(184),
                       reg185(185),
                       reg186(186),
                       reg187(187),
                       reg188(188),
                       reg189(189),
                       reg190(190),
                       reg191(191),
                       reg192(192),
                       reg193(193),
                       reg194(194),
                       reg195(195),
                       reg196(196),
                       reg197(197),
                       reg198(198),
                       reg199(199),
                       reg200(200),
                       reg201(201),
                       reg202(202),
                       reg203(203),
                       reg204(204),
                       reg205(205),
                       reg206(206),
                       reg207(207),
                       reg208(208),
                       reg209(209),
                       reg210(210),
                       reg211(211),
                       reg212(212),
                       reg213(213),
                       reg214(214),
                       reg215(215),
                       reg216(216),
                       reg217(217),
                       reg218(218),
                       reg219(219),
                       reg220(220),
                       reg221(221),
                       reg222(222),
                       reg223(223),
                       reg224(224),
                       reg225(225),
                       reg226(226),
                       reg227(227),
                       reg228(228),
                       reg229(229),
                       reg230(230),
                       reg231(231),
                       reg232(232),
                       reg233(233),
                       reg234(234),
                       reg235(235),
                       reg236(236),
                       reg237(237),
                       reg238(238),
                       reg239(239),
                       reg240(240),
                       reg241(241),
                       reg242(242),
                       reg243(243),
                       reg244(244),
                       reg245(245),
                       reg246(246),
                       reg247(247),
                       reg248(248),
                       reg249(249),
                       reg250(250),
                       reg251(251),
                       reg252(252),
                       reg253(253),
                       reg254(254),
                       reg255(255)
                     }
      MAX-ACCESS read-only
      STATUS current
      DESCRIPTION
             "The Regulatory Band prohibits the wireless unit from 
             operating outside the regulated limits. An invalid 
             Regulatory Band may be caused by a missing or incorrect 
             License Key, a corrupt MAC Address or an attempt to 
             configure a Regulatory Band not allowed by the License 
             Key. NB: a change of state may generate an SNMP trap 
             and/or SMTP email alert."  
      ::= { license 1 } 
 
   productVariant OBJECT-TYPE
      SYNTAX INTEGER {
                       pTPxx400Full(0),
                       pTPxx400Deprecated1(1),
                       pTPxx400Deprecated2(2),
                       pTPxx400Lite(3),
                       spare1(4),
                       pTPxx300(5),
                       spare2(6),
                       spare3(7),
                       pTPxx500FullDeprecated(8),
                       pTPxx500LiteDeprecated(9),
                       pTPxx500(10),
                       pTPxx600Lite(11),
                       pTPxx600Full(12),
                       pTPxx650(13),
                       spare6(14),
                       pTP800(15)
                     }
      MAX-ACCESS read-only
      STATUS current
      DESCRIPTION
             "The product variant"  
      ::= { license 2 } 
 
   productName OBJECT-TYPE
      SYNTAX DisplayString (SIZE(0..63))
      MAX-ACCESS read-only
      STATUS current
      DESCRIPTION
             "Name of the product variant"  
      ::= { license 3 } 
 
   frequencyVariant OBJECT-TYPE
      SYNTAX INTEGER {
                       freq5GHz(0),
                       freq4GHz(1)
                     }
      MAX-ACCESS read-only
      STATUS current
      DESCRIPTION
             "The hardware frequency variant"  
      ::= { license 5 } 
 
   sNMPv3Enable OBJECT-TYPE
      SYNTAX INTEGER {
                       disabled(0),
                       enabled(1)
                     }
      MAX-ACCESS read-only
      STATUS current
      DESCRIPTION
             "SNMPv3 availability control"  
      ::= { license 9 } 
 
   licenseVersion OBJECT-TYPE
      SYNTAX INTEGER (1)
      MAX-ACCESS read-only
      STATUS current
      DESCRIPTION
             "The license key version."  
      ::= { license 12 } 
 
   licenseUnitSerialNumber OBJECT-TYPE
      SYNTAX DisplayString (SIZE(0..11))
      MAX-ACCESS read-only
      STATUS current
      DESCRIPTION
             "The unit serial number."  
      ::= { license 13 } 
 
   licenseIssueNumber OBJECT-TYPE
      SYNTAX INTEGER (0..2147483647)
      MAX-ACCESS read-only
      STATUS current
      DESCRIPTION
             "The license key issue number for this unit."  
      ::= { license 15 } 
 
   licenseCountry OBJECT-TYPE
      SYNTAX DisplayString (SIZE(0..103))
      MAX-ACCESS read-only
      STATUS current
      DESCRIPTION
             "The country in which this unit is licensed to operate."  
      ::= { license 16 } 
 
   licenseNumberOfRegulatoryBands OBJECT-TYPE
      SYNTAX INTEGER (0..32)
      MAX-ACCESS read-only
      STATUS current
      DESCRIPTION
             "The number of regulatory bands for which the unit is 
             licensed to operate."  
      ::= { license 17 } 
 
   licenseBandwidthCap OBJECT-TYPE
      SYNTAX INTEGER (0..2147483647)
      MAX-ACCESS read-only
      STATUS current
      DESCRIPTION
             "The wireless link bandwidth cap in MHz. Zero indicates 
             no bandwidth cap."  
      ::= { license 20 } 
 
   licenseEncryption OBJECT-TYPE
      SYNTAX INTEGER {
                       none(0),
                       aESRijndael(1),
                       aES192bitRijndael(2),
                       aES256bitRijndael(3)
                     }
      MAX-ACCESS read-only
      STATUS current
      DESCRIPTION
             "The license key encryption algorithms available."  
      ::= { license 21 } 
 
   licenseSecurityLevel OBJECT-TYPE
      SYNTAX INTEGER {
                       normal(0),
                       fIPS(1),
                       uCAPL(2)
                     }
      MAX-ACCESS read-only
      STATUS current
      DESCRIPTION
             "The license key security level."  
      ::= { license 22 } 
 
   licenseGroupAccess OBJECT-TYPE
      SYNTAX INTEGER {
                       disabled(0),
                       enabled(1)
                     }
      MAX-ACCESS read-only
      STATUS current
      DESCRIPTION
             "The license key group access setting."  
      ::= { license 23 } 
 
   licenseOOBManagementSupport OBJECT-TYPE
      SYNTAX INTEGER {
                       disabled(0),
                       enabled(1)
                     }
      MAX-ACCESS read-only
      STATUS current
      DESCRIPTION
             "The license key Out-Of-Band (OOB) support setting."  
      ::= { license 24 } 
 
   licenseSFPPortSupport OBJECT-TYPE
      SYNTAX INTEGER {
                       disabled(0),
                       enabled(1)
                     }
      MAX-ACCESS read-only
      STATUS current
      DESCRIPTION
             "The license key Ethernet SFP Port support setting."  
      ::= { license 25 } 
 
   licenseAuxiliaryPortSupport OBJECT-TYPE
      SYNTAX INTEGER {
                       disabled(0),
                       enabled(1)
                     }
      MAX-ACCESS read-only
      STATUS current
      DESCRIPTION
             "The license key Ethernet Auxiliary Port support 
             setting."  
      ::= { license 26 } 
 
   licenseCapacity OBJECT-TYPE
      SYNTAX INTEGER {
                       full(0),
                       mid(1),
                       lite(2)
                     }
      MAX-ACCESS read-only
      STATUS current
      DESCRIPTION
             "The license key capacity"  
      ::= { license 27 } 
 
   licenseMaxNumberOfTDMChannels OBJECT-TYPE
      SYNTAX INTEGER (0..8)
      MAX-ACCESS read-only
      STATUS current
      DESCRIPTION
             "The license key maximum TDM channels setting. Zero 
             indicates TDM not available."  
      ::= { license 28 } 
 
   licenseIEEE1588Support OBJECT-TYPE
      SYNTAX INTEGER {
                       disabled(0),
                       enabled(1)
                     }
      MAX-ACCESS read-only
      STATUS current
      DESCRIPTION
             "The license key IEEE-1588 support setting."  
      ::= { license 29 } 
 
   licenseSyncESupport OBJECT-TYPE
      SYNTAX INTEGER {
                       disabled(0),
                       enabled(1)
                     }
      MAX-ACCESS read-only
      STATUS current
      DESCRIPTION
             "The license key SyncE support setting."  
      ::= { license 30 } 
 
   licenseIPv6Support OBJECT-TYPE
      SYNTAX INTEGER {
                       disabled(0),
                       enabled(1)
                     }
      MAX-ACCESS read-only
      STATUS current
      DESCRIPTION
             "The license key IPv6 support setting."  
      ::= { license 31 } 
 
   licenseMinimumFirmwareVersion OBJECT-TYPE
      SYNTAX DisplayString (SIZE(0..23))
      MAX-ACCESS read-only
      STATUS current
      DESCRIPTION
             "The minimum firmware version required to support this 
             license key."  
      ::= { license 32 } 
 
   licenseFullCapabilityTrialStatus OBJECT-TYPE
      SYNTAX INTEGER {
                       available(0),
                       active(1),
                       inactive(2),
                       expired(3),
                       unavailable(4)
                     }
      MAX-ACCESS read-only
      STATUS current
      DESCRIPTION
             "The license key full capability trial period status."  
      ::= { license 33 } 
 
   licenseRemainingTrialPeriod OBJECT-TYPE
      SYNTAX INTEGER (0..31536000)
      MAX-ACCESS read-only
      STATUS current
      DESCRIPTION
             "The remaining time for the license key full capability 
             trial period."  
      ::= { license 34 } 
 
   licenseRemainingTrialPeriodAlarm OBJECT-TYPE
      SYNTAX INTEGER {
                       fullCapabilityTrialNotActiveOrMoreThan7DaysRemaining(0),
                       fullCapabilityTrialExpiringInLessThan7Days(1),
                       fullCapabilityTrialExpiringInLessThan6Days(2),
                       fullCapabilityTrialExpiringInLessThan5Days(3),
                       fullCapabilityTrialExpiringInLessThan4Days(4),
                       fullCapabilityTrialExpiringInLessThan3Days(5),
                       fullCapabilityTrialExpiringInLessThan2Days(6),
                       fullCapabilityTrialExpiringInLessThan1Day(7),
                       fullCapabilityTrialHasExpired(8)
                     }
      MAX-ACCESS read-only
      STATUS current
      DESCRIPTION
             "If the full capability trial license period is about to 
             expire then purchase a license upgrade from your 
             reseller."  
      ::= { license 35 } 
 
   capacityVariantMismatch OBJECT-TYPE
      SYNTAX INTEGER {
                       noError(0),
                       mismatchDetected(1)
                     }
      MAX-ACCESS read-only
      STATUS current
      DESCRIPTION
             "The remote node of this link has a lower link capacity. 
             Operating with a reduced effective link capacity."  
      ::= { license 36 } 
 
   licenseTDDSyncSupport OBJECT-TYPE
      SYNTAX INTEGER {
                       disabled(0),
                       enabled(1)
                     }
      MAX-ACCESS read-only
      STATUS current
      DESCRIPTION
             "The license key TDD Synchronization support setting."  
      ::= { license 37 } 
 
   licenseMaxLinkRange OBJECT-TYPE
      SYNTAX INTEGER (0..1999)
      MAX-ACCESS read-only
      STATUS current
      DESCRIPTION
             "Maximum licensed range for the wireless link in tenths 
             of km. A value of zero indicates that the maximum link 
             range is not limited by the license."  
      ::= { license 38 } 
 
   licenseTrialPeriod OBJECT-TYPE
      SYNTAX INTEGER (0..365)
      MAX-ACCESS read-only
      STATUS current
      DESCRIPTION
             "The license key maximum trial period, in days."  
      ::= { license 39 } 
 
   licenseRARSupport OBJECT-TYPE
      SYNTAX INTEGER {
                       disabled(0),
                       mAB(1),
                       dLEP(2),
                       mABandDLEP(3)
                     }
      MAX-ACCESS read-only
      STATUS current
      DESCRIPTION
             "The license key Radio Aware Routing support setting."  
      ::= { license 40 } 
 
   -- LicenseRegulatoryBandsTable group attribute definitions 
   --
   licenseRegulatoryBandsTableIndex OBJECT-TYPE
      SYNTAX INTEGER (1..32)
      MAX-ACCESS not-accessible
      STATUS current
      DESCRIPTION
             "License regulatory bands, used to index the 
             LicenseRegulatoryBandsTable."  
      ::= { licenseRegulatoryBandsTableEntry 1 } 
 
   licenseRegulatoryBandsList OBJECT-TYPE
      SYNTAX INTEGER {
                       regInvalid(0),
                       reg158GHz(1),
                       reg258GHz(2),
                       reg358GHz(3),
                       reg458GHz(4),
                       reg558GHz(5),
                       reg658GHz(6),
                       reg754GHzUnrestrictedEIRPwithDFS(7),
                       reg854GHzUnrestrictedEIRP(8),
                       reg9(9),
                       reg1058GHz(10),
                       reg1158GHz(11),
                       reg1254GHzFCCUNII2C(12),
                       reg1354GHz(13),
                       reg1449GHzPublicSafety(14),
                       reg15(15),
                       reg1659GHz(16),
                       reg1759GHz(17),
                       reg1849GHzPublicSafety(18),
                       reg1958GHz(19),
                       reg2054GHz(20),
                       reg2154GHz(21),
                       reg2258GHz(22),
                       reg23(23),
                       reg2458GHz(24),
                       reg2558GHzETSI(25),
                       reg2654GHzETSI(26),
                       reg2758GHz(27),
                       reg2858GHz(28),
                       reg2958GHzUnrestrictedEIRPwithDFSandRTTT(29),
                       reg3054GHz(30),
                       reg3158GHz(31),
                       reg3249GHzLicensed(32),
                       reg3349GHzETSIBroadbandDisasterRelief(33),
                       reg3458GHz(34),
                       reg3558GHzUnrestrictedEIRP(35),
                       reg3654GHz(36),
                       reg3758GHz(37),
                       reg3852GHzFCCUNII2A(38),
                       reg3951GHzETSIBroadbandDisasterRelief(39),
                       reg4054GHz(40),
                       reg4154GHz(41),
                       reg4254GHz(42),
                       reg4354GHz(43),
                       reg4458GHz(44),
                       reg4558GHz(45),
                       reg4658GHz(46),
                       reg4758GHz(47),
                       reg4858GHz(48),
                       reg4958GHz(49),
                       reg5058GHz(50),
                       reg5158GHz(51),
                       reg5258GHz(52),
                       reg5358GHz(53),
                       reg5458GHz(54),
                       reg5558GHz(55),
                       reg5654GHz(56),
                       reg5754GHz(57),
                       reg5858GHz(58),
                       reg5958GHz(59),
                       reg6058GHz(60),
                       reg6149GHz(61),
                       reg6252GHz(62),
                       reg6352GHz(63),
                       reg6451GHz(64),
                       reg6551GHz(65),
                       reg6651GHz(66),
                       reg6752GHz(67),
                       reg6852GHz(68),
                       reg6952GHz(69),
                       reg7052GHz(70),
                       reg7152GHz(71),
                       reg7252GHz(72),
                       reg7352GHz(73),
                       reg7452GHz(74),
                       reg7552GHz(75),
                       reg7652GHz(76),
                       reg7752GHz(77),
                       reg7849GHz(78),
                       reg7954GHz(79),
                       reg8049GHz(80),
                       reg8147GHz(81),
                       reg8247GHz(82),
                       reg8352GHz(83),
                       reg8451GHzFCCUNII1(84),
                       reg8552GHzFCCUNII12A(85),
                       reg8654GHzFCCUNII2A2C(86),
                       reg8758GHz(87),
                       reg8849GHz(88),
                       reg8949GHz(89),
                       reg9054GHzFCCUNII2CParabolicantenna(90),
                       reg9152GHzFCCUNII2AParabolicantenna(91),
                       reg9251GHzFCCUNII1Parabolicantenna(92),
                       reg9349GHz(93),
                       reg94(94),
                       reg95(95),
                       reg96(96),
                       reg97(97),
                       reg98(98),
                       reg99(99),
                       reg100(100),
                       reg101(101),
                       reg102(102),
                       reg103(103),
                       reg104(104),
                       reg105(105),
                       reg106(106),
                       reg107(107),
                       reg108(108),
                       reg109(109),
                       reg110(110),
                       reg111(111),
                       reg112(112),
                       reg113(113),
                       reg114(114),
                       reg115(115),
                       reg116(116),
                       reg117(117),
                       reg118(118),
                       reg119(119),
                       reg120(120),
                       reg121(121),
                       reg122(122),
                       reg123(123),
                       reg124(124),
                       reg125(125),
                       reg126(126),
                       reg127(127),
                       reg128(128),
                       reg129(129),
                       reg130(130),
                       reg131(131),
                       reg132(132),
                       reg133(133),
                       reg134(134),
                       reg135(135),
                       reg136(136),
                       reg137(137),
                       reg138(138),
                       reg139(139),
                       reg140(140),
                       reg141(141),
                       reg142(142),
                       reg143(143),
                       reg144(144),
                       reg145(145),
                       reg146(146),
                       reg147(147),
                       reg148(148),
                       reg149(149),
                       reg150(150),
                       reg151(151),
                       reg152(152),
                       reg153(153),
                       reg154(154),
                       reg155(155),
                       reg156(156),
                       reg157(157),
                       reg158(158),
                       reg159(159),
                       reg160(160),
                       reg161(161),
                       reg162(162),
                       reg163(163),
                       reg164(164),
                       reg165(165),
                       reg166(166),
                       reg167(167),
                       reg168(168),
                       reg169(169),
                       reg170(170),
                       reg171(171),
                       reg172(172),
                       reg173(173),
                       reg174(174),
                       reg175(175),
                       reg176(176),
                       reg177(177),
                       reg178(178),
                       reg179(179),
                       reg180(180),
                       reg181(181),
                       reg182(182),
                       reg183(183),
                       reg184(184),
                       reg185(185),
                       reg186(186),
                       reg187(187),
                       reg188(188),
                       reg189(189),
                       reg190(190),
                       reg191(191),
                       reg192(192),
                       reg193(193),
                       reg194(194),
                       reg195(195),
                       reg196(196),
                       reg197(197),
                       reg198(198),
                       reg199(199),
                       reg200(200),
                       reg201(201),
                       reg202(202),
                       reg203(203),
                       reg204(204),
                       reg205(205),
                       reg206(206),
                       reg207(207),
                       reg208(208),
                       reg209(209),
                       reg210(210),
                       reg211(211),
                       reg212(212),
                       reg213(213),
                       reg214(214),
                       reg215(215),
                       reg216(216),
                       reg217(217),
                       reg218(218),
                       reg219(219),
                       reg220(220),
                       reg221(221),
                       reg222(222),
                       reg223(223),
                       reg224(224),
                       reg225(225),
                       reg226(226),
                       reg227(227),
                       reg228(228),
                       reg229(229),
                       reg230(230),
                       reg231(231),
                       reg232(232),
                       reg233(233),
                       reg234(234),
                       reg235(235),
                       reg236(236),
                       reg237(237),
                       reg238(238),
                       reg239(239),
                       reg240(240),
                       reg241(241),
                       reg242(242),
                       reg243(243),
                       reg244(244),
                       reg245(245),
                       reg246(246),
                       reg247(247),
                       reg248(248),
                       reg249(249),
                       reg250(250),
                       reg251(251),
                       reg252(252),
                       reg253(253),
                       reg254(254),
                       reg255(255)
                     }
      MAX-ACCESS read-only
      STATUS current
      DESCRIPTION
             "The list of regulatory bands for which the unit is 
             licensed to operate. A regulatory band prohibits the 
             wireless unit from operating outside the regulated 
             limits. An invalid regulatory band indicates a corrupted 
             license key. NB: a change of state may generate an SNMP 
             trap and/or SMTP email alert."  
      ::= { licenseRegulatoryBandsTableEntry 2 } 
 
   -- Management group attribute definitions 
   --
   targetRange OBJECT-TYPE
      SYNTAX INTEGER (0..2000)
      MAX-ACCESS read-only
      STATUS current
      DESCRIPTION
             "Initial target range used in installation +/-1, 
             expressed in tenths of a kilometer. When Auto-Ranging 
             this must be set to 0"  
      ::= { management 1 } 
 
   rangingMode OBJECT-TYPE
      SYNTAX INTEGER {
                       auto0to40km(0),
                       auto0to100km(1),
                       auto0to200km(2),
                       targetRange(3)
                     }
      MAX-ACCESS read-only
      STATUS current
      DESCRIPTION
             "Type of ranging to use during installation, either 
             Auto-Ranging or use a selectable Target Range"  
      ::= { management 2 } 
 
   installStatus OBJECT-TYPE
      SYNTAX INTEGER {
                       ok(0),
                       wrongPeer(1)
                     }
      MAX-ACCESS read-only
      STATUS current
      DESCRIPTION
             "A non-zero value indicates that signalling was received 
             with the wrong MAC address or a mismatched link name. NB: 
             It is very unusual to detect this, because units with 
             mis-configured Target MAC Address will normally fail to 
             establish a wireless link. However, rare circumstances 
             may establish a partial wireless link and detect this 
             situation. NB: A non-zero value on start-up, or a change 
             of value during operation, may generate an SNMP trap 
             and/or SMTP email alert"  
      ::= { management 3 } 
 
   installArmState OBJECT-TYPE
      SYNTAX INTEGER {
                       disarmed(0),
                       armed(1)
                     }
      MAX-ACCESS read-only
      STATUS current
      DESCRIPTION
             "Indicates if the unit is being installed. NB: a change 
             of state may generate an SNMP trap and/or SMTP email 
             alert"  
      ::= { management 4 } 
 
   tFTPServerPortNumber OBJECT-TYPE
      SYNTAX INTEGER (0..65535)
      MAX-ACCESS read-write
      STATUS current
      DESCRIPTION
             "The port number of the TFTP Server from which the TFTP 
             Software Upgrade File Name will be retrieved"  
      ::= { management 6 } 
 
   tFTPSoftwareUpgradeFileName OBJECT-TYPE
      SYNTAX DisplayString (SIZE(0..127))
      MAX-ACCESS read-write
      STATUS current
      DESCRIPTION
             "Filename of the Software Upgrade to be loaded from the 
             TFTP Server"  
      ::= { management 7 } 
 
   tFTPStartSoftwareUpgrade OBJECT-TYPE
      SYNTAX Integer32
      MAX-ACCESS read-write
      STATUS current
      DESCRIPTION
             "Write '1' to this attribute to start the TFTP software 
             upgrade process. The attribute will be reset to 0 when 
             the upgrade process has finished. Continuing with the 
             software upgrade will cause spectrum management (DSO) 
             channel metrics collection to stop. The wireless unit 
             will no longer search for the optimal operational radio 
             channel. The performance of this wireless link may 
             deterioate over time. If operating in a regulatory band 
             where RADAR detection is mandatory you must complete the 
             software upgrade and reboot the unit. Channel metrics 
             collection will only be restarted after the wireless unit 
             has been rebooted"  
      ::= { management 8 } 
 
   tFTPSoftwareUpgradeStatus OBJECT-TYPE
      SYNTAX INTEGER {
                       idle(0),
                       uploadinprogress(1),
                       uploadsuccessfulprogrammingFLASH(2),
                       upgradesuccessfulreboottorunthenewsoftwareimage(3),
                       upgradefailed(4),
                       upgradewarning(5)
                     }
      MAX-ACCESS read-only
      STATUS current
      DESCRIPTION
             "The current status of the TFTP Software upgrade process"  
      ::= { management 9 } 
 
   tFTPSoftwareUpgradeStatusText OBJECT-TYPE
      SYNTAX DisplayString (SIZE(0..127))
      MAX-ACCESS read-only
      STATUS current
      DESCRIPTION
             "Descriptive text describing the status of the TFTP 
             Software upgrade process, including any error details"  
      ::= { management 10 } 
 
   tFTPSoftwareUpgradeStatusAdditionalText OBJECT-TYPE
      SYNTAX DisplayString (SIZE(0..127))
      MAX-ACCESS read-only
      STATUS current
      DESCRIPTION
             "Any additional text describing the status of the TFTP 
             Software upgrade process, including any error details"  
      ::= { management 11 } 
 
   hTTPAccessEnabled OBJECT-TYPE
      SYNTAX INTEGER {
                       no(0),
                       yes(1)
                     }
      MAX-ACCESS read-write
      STATUS current
      DESCRIPTION
             "This controls whether or not HTTP access is enabled, 
             i.e. if this is disabled (0) then the unit will not 
             respond to any requests on the HTTP port. Remote 
             management via HTTPS is not affected by this setting. Any 
             change in this setting will not take effect until the 
             unit has been rebooted. (Factory default = Enabled)"  
      ::= { management 12 } 
 
   telnetAccessEnabled OBJECT-TYPE
      SYNTAX INTEGER {
                       no(0),
                       yes(1)
                     }
      MAX-ACCESS read-write
      STATUS current
      DESCRIPTION
             "This controls whether or not Telnet access is enabled, 
             i.e. if this is disabled (0) then the unit will not 
             respond to any requests on the TELNET port. Any change in 
             this setting will not take effect until the unit has been 
             rebooted. (Factory default = Disabled)"  
      ::= { management 13 } 
 
   hTTPPortNumber OBJECT-TYPE
      SYNTAX INTEGER (0..65535)
      MAX-ACCESS read-write
      STATUS current
      DESCRIPTION
             "This controls the port number for HTTP access. A value 
             of zero will use the default port number. Any change in 
             this setting will not take effect until the unit has been 
             rebooted. (Factory default = 80)"  
      ::= { management 14 } 
 
   hTTPSPortNumber OBJECT-TYPE
      SYNTAX INTEGER (0..65535)
      MAX-ACCESS read-write
      STATUS current
      DESCRIPTION
             "This controls the port number for HTTPS access. A value 
             of zero will use the default port number. Availability of 
             HTTPS is controlled via the License Key. Any change in 
             this setting will not take effect until the unit has been 
             rebooted. (Factory default = 443)"  
      ::= { management 15 } 
 
   telnetPortNumber OBJECT-TYPE
      SYNTAX INTEGER (0..65535)
      MAX-ACCESS read-write
      STATUS current
      DESCRIPTION
             "This controls the port number for TELNET access. A value 
             of zero will use the default port number. Any change in 
             this setting will not take effect until the unit has been 
             rebooted. (Factory default = 23)"  
      ::= { management 16 } 
 
   hTTPSAccessEnabled OBJECT-TYPE
      SYNTAX INTEGER {
                       no(0),
                       yes(1)
                     }
      MAX-ACCESS read-write
      STATUS current
      DESCRIPTION
             "This controls whether or not HTTPS access is enabled, 
             i.e. if this is disabled (0) then the unit will not 
             respond to any requests on the HTTPS port. Remote 
             management via HTTP is not affected by this setting. Any 
             change in this setting will not take effect until the 
             unit has been rebooted. (Factory default = Enabled)"  
      ::= { management 17 } 
 
   tFTPServerInternetAddressType OBJECT-TYPE
      SYNTAX INTEGER {
                       unknown(0),
                       ipv4(1),
                       ipv6(2),
                       ipv4z(3),
                       ipv6z(4),
                       unknown6(5),
                       unknown7(6),
                       unknown8(7),
                       unknown9(8),
                       unknown10(9),
                       unknown11(10),
                       unknown12(11),
                       unknown13(12),
                       unknown14(13),
                       unknown15(14),
                       unknown16(15),
                       dns(16)
                     }
      MAX-ACCESS read-only
      STATUS current
      DESCRIPTION
             "The type of Internet address specified by the associated 
             tFTPServerInternetAddress."  
      ::= { management 18 } 
 
   tFTPServerInternetAddress OBJECT-TYPE
      SYNTAX InetAddress
      MAX-ACCESS read-write
      STATUS current
      DESCRIPTION
             "INET address of the TFTP Server from which the TFTP 
             Software Upgrade File Name will be retrieved"  
      ::= { management 19 } 
 
   lowestDataModulationMode OBJECT-TYPE
      SYNTAX INTEGER {
                       modAcquisition(0),
                       modBpsk63percent(1),
                       modQpsk63percentSingle(2),
                       modTransient1(3),
                       modQpsk87percentSingle(4),
                       modTransient2(5),
                       mod16qam63percentSingleA(6),
                       modTransient3(7),
                       mod16qam87percentSingle(8),
                       modTransient4(9),
                       mod64qam75percentSingle(10),
                       modTransient5(11),
                       mod64qam92percentSingle(12),
                       modTransient6(13),
                       mod256qam81percentSingle(14),
                       mod16qam63percentSingleB(15),
                       mod16qam63percentDual(16),
                       modTransient7(17),
                       mod16qam87percentDual(18),
                       modTransient8(19),
                       mod64qam75percentDual(20),
                       modTransient9(21),
                       mod64qam92percentDual(22),
                       modTransient10(23),
                       mod256qam81percentDual(24)
                     }
      MAX-ACCESS read-only
      STATUS current
      DESCRIPTION
             "The lowest modulation mode at which Ethernet Data 
             traffic will be bridged over the wireless link"  
      ::= { management 20 } 
 
   lowestSecondDataModulationMode OBJECT-TYPE
      SYNTAX INTEGER {
                       modAcquisition(0),
                       modBpsk63percent(1),
                       modQpsk63percentSingle(2),
                       modTransient1(3),
                       modQpsk87percentSingle(4),
                       modTransient2(5),
                       mod16qam63percentSingleA(6),
                       modTransient3(7),
                       mod16qam87percentSingle(8),
                       modTransient4(9),
                       mod64qam75percentSingle(10),
                       modTransient5(11),
                       mod64qam92percentSingle(12),
                       modTransient6(13),
                       mod256qam81percentSingle(14),
                       mod16qam63percentSingleB(15),
                       mod16qam63percentDual(16),
                       modTransient7(17),
                       mod16qam87percentDual(18),
                       modTransient8(19),
                       mod64qam75percentDual(20),
                       modTransient9(21),
                       mod64qam92percentDual(22),
                       modTransient10(23),
                       mod256qam81percentDual(24)
                     }
      MAX-ACCESS read-only
      STATUS current
      DESCRIPTION
             "The lowest modulation mode at which Second Data Service 
             Ethernet traffic will be bridged over the wireless link"  
      ::= { management 21 } 
 
   -- PhyControl group attribute definitions 
   --
   linkSymmetry OBJECT-TYPE
      SYNTAX INTEGER {
                       symmetryAdaptive(0),
                       symmetry2to1(1),
                       symmetry1to1(2),
                       symmetry1to2(3),
                       symmetry3to1(4),
                       symmetry1to3(5),
                       symmetry5to1(6),
                       symmetry1to5(7)
                     }
      MAX-ACCESS read-only
      STATUS current
      DESCRIPTION
             "Provides configuration options for sharing the available 
             wireless capacity between the transmit and receive 
             directions. Fixed link symmetry is defined by a ratio of 
             the burst duration for the transmit direction to the 
             burst duration for the receive direction. Permitted 
             settings are 5:1, 3:1, 2:1, 1:1, 1:2, 1:3, 1:5. The 1:1 
             option provides fixed symmetric operation. The adaptive 
             option selects transmit and receive burst durations 
             automatically in response to the offered Ethernet traffic 
             in each link direction. This attribute is valid only for 
             a unit configured as a TDD Master"  
      ::= { phyControl 1 } 
 
   userConfiguredMaxModulationMode OBJECT-TYPE
      SYNTAX INTEGER {
                       modBpsk63percent(0),
                       modQpsk63percent(1),
                       modQpsk87percent(2),
                       mod16qam63percent(3),
                       mod16qam87percent(4),
                       mod64qam75percent(5),
                       mod64qam92percent(6),
                       mod256qam81percent(7)
                     }
      MAX-ACCESS read-write
      STATUS current
      DESCRIPTION
             "The maximum receive modulation mode controls the MAX 
             mode used for adaptive modulation. NOTE: This attribute 
             is automatically disabled when the installation agent is 
             armed. To disarm the installation agent use the 
             installation wizard"  
      ::= { phyControl 2 } 
 
   linkModeOptimization OBJECT-TYPE
      SYNTAX INTEGER {
                       iPTraffic(0),
                       tDMTraffic(1)
                     }
      MAX-ACCESS read-only
      STATUS current
      DESCRIPTION
             "Optimizes the wireless link behavior for the type of 
             traffic to be carried. In 'IP Traffic' mode, the wireless 
             link will minimize transmission errors by automatically 
             adapting the modulation mode. In 'TDM Traffic' mode, the 
             wireless link will minimize transmission latency and 
             preserve throughput by maintaining a higher modulation 
             mode in the presence of a limited number of errors. The 
             'TDM Traffic' mode is recommended for E1/T1 applications 
             and connectionless protocols."  
      ::= { phyControl 3 } 
 
   txColorCode OBJECT-TYPE
      SYNTAX INTEGER {
                       a(0),
                       b(1),
                       c(2),
                       d(3),
                       e(4)
                     }
      MAX-ACCESS read-only
      STATUS current
      DESCRIPTION
             "Transmit Color Code. This attribute need only be 
             considered when the unit is installed in a network of PTP 
             units and where some of the units are operating on the 
             same frequency. In this case, the value would normally be 
             derived by a network planner. In all other cases, it is 
             recommended that this attribute is left at the default 
             value. NOTE: For the link to operate, the value of this 
             parameter must in all cases match the value of the Rx 
             Color Code parameter at the far end of the link."  
      ::= { phyControl 4 } 
 
   rxColorCode OBJECT-TYPE
      SYNTAX INTEGER {
                       a(0),
                       b(1),
                       c(2),
                       d(3),
                       e(4)
                     }
      MAX-ACCESS read-only
      STATUS current
      DESCRIPTION
             "Receive Color Code. This attribute need only be 
             considered when the unit is installed in a network of PTP 
             units and where some of the units are operating on the 
             same frequency. In this case, the value would normally be 
             derived by a network planner. In all other cases, it is 
             recommended that this attribute is left at the default 
             value. NOTE: For the link to operate, the value of this 
             parameter must in all cases match the value of the Tx 
             Color Code parameter at the far end of the link."  
      ::= { phyControl 5 } 
 
   remoteMaximumTransmitPower OBJECT-TYPE
      SYNTAX INTEGER (-15..30)
      MAX-ACCESS read-only
      STATUS current
      DESCRIPTION
             "Maximum transmit power the remote wireless unit is 
             permitted to use when establishing and maintaining the 
             wireless link"  
      ::= { phyControl 6 } 
 
   -- PhyStatus group attribute definitions 
   --
   linkLoss OBJECT-TYPE
      SYNTAX INTEGER (-500..500)
      MAX-ACCESS read-only
      STATUS current
      DESCRIPTION
             "The wireless link loss expressed in tenths of a dB"  
      ::= { phyStatus 1 } 
 
   receivePower OBJECT-TYPE
      SYNTAX Integer32
      MAX-ACCESS read-only
      STATUS current
      DESCRIPTION
             "Receive power expressed in tenths of a dBm"  
      ::= { phyStatus 2 } 
 
   vectorError OBJECT-TYPE
      SYNTAX Integer32
      MAX-ACCESS read-only
      STATUS current
      DESCRIPTION
             "The vector error measurement compares the received 
             signal's IQ modulation characteristics to an ideal signal 
             to determine the composite error vector magnitude. The 
             value represented by this attribute is the average vector 
             error over the previous second expressed in tenths of a 
             dB"  
      ::= { phyStatus 3 } 
 
   transmitPower OBJECT-TYPE
      SYNTAX Integer32
      MAX-ACCESS read-only
      STATUS current
      DESCRIPTION
             "Transmit power expressed in tenths of a dBm"  
      ::= { phyStatus 4 } 
 
   receiveChannel OBJECT-TYPE
      SYNTAX INTEGER (0..63)
      MAX-ACCESS read-only
      STATUS current
      DESCRIPTION
             "Current active receive channel"  
      ::= { phyStatus 5 } 
 
   transmitChannel OBJECT-TYPE
      SYNTAX INTEGER (0..63)
      MAX-ACCESS read-only
      STATUS current
      DESCRIPTION
             "Current active transmit channel"  
      ::= { phyStatus 6 } 
 
   receiveFreqMHz OBJECT-TYPE
      SYNTAX INTEGER (0..6050)
      MAX-ACCESS read-only
      STATUS current
      DESCRIPTION
             "Current receive frequency expressed in integer MHz"  
      ::= { phyStatus 7 } 
 
   transmitFreqMHz OBJECT-TYPE
      SYNTAX INTEGER (0..6050)
      MAX-ACCESS read-only
      STATUS current
      DESCRIPTION
             "Current transmit frequency expressed in integer MHz"  
      ::= { phyStatus 8 } 
 
   signalStrengthRatio OBJECT-TYPE
      SYNTAX Integer32
      MAX-ACCESS read-only
      STATUS current
      DESCRIPTION
             "Signal strength ratio (Vertical / Horizontal) : the 
             number of dB larger the Vertical antenna input is than 
             the Horizontal antenna input expressed in tenths of a dB"  
      ::= { phyStatus 9 } 
 
   receiveFreqKHz OBJECT-TYPE
      SYNTAX INTEGER (0..6050000)
      MAX-ACCESS read-only
      STATUS current
      DESCRIPTION
             "Current receive frequency expressed as KHz"  
      ::= { phyStatus 10 } 
 
   transmitFreqKHz OBJECT-TYPE
      SYNTAX INTEGER (0..6050000)
      MAX-ACCESS read-only
      STATUS current
      DESCRIPTION
             "Current transmit frequency expressed as KHz"  
      ::= { phyStatus 11 } 
 
   rawReceivePower OBJECT-TYPE
      SYNTAX Integer32
      MAX-ACCESS read-only
      STATUS current
      DESCRIPTION
             "Raw receive power expressed in tenths of a dBm"  
      ::= { phyStatus 12 } 
 
   range OBJECT-TYPE
      SYNTAX Integer32
      MAX-ACCESS read-only
      STATUS current
      DESCRIPTION
             "Distance between the two peer wireless units expressed 
             in tenths of a kilometer"  
      ::= { phyStatus 13 } 
 
   receiveModulationMode OBJECT-TYPE
      SYNTAX INTEGER {
                       modAcquisition(0),
                       modBpsk63percent(1),
                       modQpsk63percentSingle(2),
                       modTransient1(3),
                       modQpsk87percentSingle(4),
                       modTransient2(5),
                       mod16qam63percentSingleA(6),
                       modTransient3(7),
                       mod16qam87percentSingle(8),
                       modTransient4(9),
                       mod64qam75percentSingle(10),
                       modTransient5(11),
                       mod64qam92percentSingle(12),
                       modTransient6(13),
                       mod256qam81percentSingle(14),
                       mod16qam63percentSingleB(15),
                       mod16qam63percentDual(16),
                       modTransient7(17),
                       mod16qam87percentDual(18),
                       modTransient8(19),
                       mod64qam75percentDual(20),
                       modTransient9(21),
                       mod64qam92percentDual(22),
                       modTransient10(23),
                       mod256qam81percentDual(24)
                     }
      MAX-ACCESS read-only
      STATUS current
      DESCRIPTION
             "Current active receive modulation mode"  
      ::= { phyStatus 14 } 
 
   transmitModulationMode OBJECT-TYPE
      SYNTAX INTEGER {
                       modAcquisition(0),
                       modBpsk63percent(1),
                       modQpsk63percentSingle(2),
                       modTransient1(3),
                       modQpsk87percentSingle(4),
                       modTransient2(5),
                       mod16qam63percentSingleA(6),
                       modTransient3(7),
                       mod16qam87percentSingle(8),
                       modTransient4(9),
                       mod64qam75percentSingle(10),
                       modTransient5(11),
                       mod64qam92percentSingle(12),
                       modTransient6(13),
                       mod256qam81percentSingle(14),
                       mod16qam63percentSingleB(15),
                       mod16qam63percentDual(16),
                       modTransient7(17),
                       mod16qam87percentDual(18),
                       modTransient8(19),
                       mod64qam75percentDual(20),
                       modTransient9(21),
                       mod64qam92percentDual(22),
                       modTransient10(23),
                       mod256qam81percentDual(24)
                     }
      MAX-ACCESS read-only
      STATUS current
      DESCRIPTION
             "Current active transmit modulation mode"  
      ::= { phyStatus 15 } 
 
   searchState OBJECT-TYPE
      SYNTAX INTEGER {
                       registering(0),
                       searching(1),
                       acquiring(2)
                     }
      MAX-ACCESS read-only
      STATUS current
      DESCRIPTION
             "Search status of the wireless modem. 'Registering' means 
             that the modem has locked to an OFDM signal, and the 
             wireless link is up. 'Searching' means that no wireless 
             signal has been detected. 'Acquiring' means that a 
             wireless signal has been detected, but the modem has not 
             locked to an OFDM signal."  
      ::= { phyStatus 16 } 
 
   -- Alarms group attribute definitions 
   --
   unitOutOfCalibration OBJECT-TYPE
      SYNTAX INTEGER {
                       calibrated(0),
                       partialCalibration(1),
                       invalidCalibration(2),
                       bandwidthvariantunsupportedPAsShutdown(3),
                       outOfCalibrationPAsShutdown(4)
                     }
      MAX-ACCESS read-only
      STATUS current
      DESCRIPTION
             "The unit is out of calibration"  
      ::= { alarms 1 } 
 
   incompatibleRegulatoryBands OBJECT-TYPE
      SYNTAX INTEGER {
                       regOK(0),
                       regIncompatibleLicenseKeys(1)
                     }
      MAX-ACCESS read-only
      STATUS current
      DESCRIPTION
             "The master and slave units have incompatible regulatory 
             bands. NB: Both units must have compatible license keys"  
      ::= { alarms 4 } 
 
   noWirelessChannelAvailable OBJECT-TYPE
      SYNTAX INTEGER {
                       ok(0),
                       noWirelessChannelAvailable(1)
                     }
      MAX-ACCESS read-only
      STATUS current
      DESCRIPTION
             "Spectrum Management was unable to locate a suitable 
             wireless channel to operate on"  
      ::= { alarms 5 } 
 
   wirelessLinkDisabledWarning OBJECT-TYPE
      SYNTAX INTEGER {
                       ok(0),
                       disabledBySNMPifAdminStatus(1)
                     }
      MAX-ACCESS read-only
      STATUS current
      DESCRIPTION
             "The SNMP ifAdminStatus of the wireless interface has 
             disabled wireless traffic"  
      ::= { alarms 6 } 
 
   mainPSUPortDisabledWarning OBJECT-TYPE
      SYNTAX INTEGER {
                       ok(0),
                       disabledBySNMPifAdminStatus(1)
                     }
      MAX-ACCESS read-only
      STATUS current
      DESCRIPTION
             "The SNMP ifAdminStatus of the interface has disabled 
             Ethernet traffic"  
      ::= { alarms 7 } 
 
   sFPError OBJECT-TYPE
      SYNTAX INTEGER {
                       ok(0),
                       installedSFPNotLicensed(1),
                       fiberLinkNotEstablishedButLOSNotDetected(2),
                       fiberLinkNotEstablishedAndLOSDetected(3),
                       installedSFPNotSupported(4),
                       sFPInitializationFailed(5)
                     }
      MAX-ACCESS read-only
      STATUS current
      DESCRIPTION
             "If the SFP link is not OK, there are five possible 
             causes: Either a SFP has been installed but the license 
             key does not include SFP fiber support, a fiber link 
             could not be established even though no LOS was detected 
             (i.e. an optical carrier was detected, which could be due 
             to a broken TX fiber, or because the link is disabled at 
             the fiber link partner), a fiber link could not be 
             established and LOS is detected (i.e. no optical carrier 
             is detected), the installed SFP is not supported or the 
             installed SFP failed to initialize correctly. NB: a 
             change of status may generate an SNMP trap and/or SMTP 
             email alert"  
      ::= { alarms 8 } 
 
   mainPSUPortConfigurationMismatch OBJECT-TYPE
      SYNTAX INTEGER {
                       noError(0),
                       mismatchDetected(1)
                     }
      MAX-ACCESS read-only
      STATUS current
      DESCRIPTION
             "The detection of Ethernet fragments (runt packets) when 
             the link is in full duplex is an indication of an 
             auto-negotiation or forced configuration mismatch"  
      ::= { alarms 9 } 
 
   incompatibleMasterAndSlave OBJECT-TYPE
      SYNTAX INTEGER {
                       ok(0),
                       incompatibleProductVariants(1),
                       differentSoftwareVersionsRunning(2)
                     }
      MAX-ACCESS read-only
      STATUS current
      DESCRIPTION
             "A non-zero value indicates that the master and slave 
             ends of a link are different hardware products, or have 
             different software versions. NB: It is very unusual to 
             detect this, because incompatible units will normally 
             fail to establish a wireless link. However, some 
             combinations may establish a partial wireless link and 
             detect this situation. NB: A non-zero value may generate 
             an SNMP trap and/or SMTP email alert"  
      ::= { alarms 10 } 
 
   tDDSynchronizationStatus OBJECT-TYPE
      SYNTAX INTEGER {
                       locked(0),
                       holdover(1),
                       holdoverNoGPSSyncIn(2),
                       notSynchronized(3),
                       notSynchronizedNoGPSSyncIn(4),
                       pTPSYNCNotConnected(5),
                       initialising(6),
                       clusterTimingMaster(7),
                       acquiringLock(8),
                       inactive(9)
                     }
      MAX-ACCESS read-only
      STATUS current
      DESCRIPTION
             "An alarm value (displayed in red) indicates that one of 
             the following conditions has not been met (i) An external 
             timing system is connected or internal timing has been 
             configured. (ii) The timing system is providing a useable 
             reference. (iii) The ODU is locked to this reference."  
      ::= { alarms 11 } 
 
   auxPortDisabledWarning OBJECT-TYPE
      SYNTAX INTEGER {
                       ok(0),
                       disabledBySNMPifAdminStatus(1)
                     }
      MAX-ACCESS read-only
      STATUS current
      DESCRIPTION
             "The SNMP ifAdminStatus of the interface has disabled 
             Ethernet traffic"  
      ::= { alarms 12 } 
 
   tDDSynchronizationAlarm OBJECT-TYPE
      SYNTAX INTEGER {
                       ok(0),
                       synchronizationLost(1),
                       referenceSignalLost(2)
                     }
      MAX-ACCESS read-only
      STATUS current
      DESCRIPTION
             "Not Synchronized indicates failure of the external 
             timing system for a period greater than the holdover 
             timer. TDD frame timing will have drifted, and this link 
             may cause interference with other links in a synchronized 
             network. Timing System Failure is an early warning, 
             indicating that 80% of the holdover period has expired."  
      ::= { alarms 13 } 
 
   linkModeOptimizationMismatch OBJECT-TYPE
      SYNTAX INTEGER {
                       ok(0),
                       linkModeOptimizationMismatch(1)
                     }
      MAX-ACCESS read-only
      STATUS current
      DESCRIPTION
             "The remote node of this link has been configured with a 
             different link mode optimization"  
      ::= { alarms 14 } 
 
   auxPortConfigurationMismatch OBJECT-TYPE
      SYNTAX INTEGER {
                       noError(0),
                       mismatchDetected(1)
                     }
      MAX-ACCESS read-only
      STATUS current
      DESCRIPTION
             "The detection of Ethernet fragments (runt packets) when 
             the link is in full duplex is an indication of an 
             auto-negotiation or forced configuration mismatch. This 
             alarm is only raised if an Out-of-Band Management Mode 
             has been configured."  
      ::= { alarms 15 } 
 
   secureModeAlarm OBJECT-TYPE
      SYNTAX INTEGER {
                       secureModeIsActive(0),
                       secureModeIsNotConfigured(1),
                       secureModeIsConfiguredButNotActive(2),
                       secureModeIsNotSupported(3)
                     }
      MAX-ACCESS read-only
      STATUS current
      DESCRIPTION
             "The secure mode (e.g. FIPS, UC-APL) state of the unit. 
             The secure mode is not configured(1) state indicates that 
             the unit is capable of secure mode operation, and one or 
             more of the following security materials has not been 
             configured: Key Of Keys, Private Key, Public Certificate, 
             DRNG Entropy Status, Wireless Encryption Key. The secure 
             mode mode is configured but not active(2) state indicates 
             that the unit is capable of secure mode operation, and 
             the security material has been configured, but the 
             configuration of interfaces is not consistent with secure 
             mode operation. The secure mode is not supported(3) state 
             indicates that the unit is not capable of secure mode 
             operation. The secure mode capability requires 
             appropriate hardware compatibility, license key and 
             software image."  
      ::= { alarms 16 } 
 
   dataBridgingStatusAlarm OBJECT-TYPE
      SYNTAX INTEGER {
                       bridgingEnabled(0),
                       bridgingDisabled(1)
                     }
      MAX-ACCESS read-only
      STATUS current
      DESCRIPTION
             "Ethernet Data traffic bridging is disabled because the 
             wireless link is not operating at the configured Lowest 
             Data Modulation Mode"  
      ::= { alarms 17 } 
 
   sFPPortDisabledWarning OBJECT-TYPE
      SYNTAX INTEGER {
                       ok(0),
                       disabledBySNMPifAdminStatus(1)
                     }
      MAX-ACCESS read-only
      STATUS current
      DESCRIPTION
             "The SNMP ifAdminStatus of the interface has disabled 
             Ethernet traffic"  
      ::= { alarms 18 } 
 
   sFPPortConfigurationMismatch OBJECT-TYPE
      SYNTAX INTEGER {
                       noError(0),
                       mismatchDetected(1)
                     }
      MAX-ACCESS read-only
      STATUS current
      DESCRIPTION
             "The detection of Ethernet fragments (runt packets) when 
             the link is in full duplex is an indication of an 
             auto-negotiation or forced configuration mismatch. This 
             alarm is only raised if an Out-of-Band Management Mode 
             has been configured."  
      ::= { alarms 19 } 
 
   maxLinkRangeExceeded OBJECT-TYPE
      SYNTAX INTEGER {
                       maxLinkRangeOK(0),
                       maxLinkRangeExceeded(1)
                     }
      MAX-ACCESS read-only
      STATUS current
      DESCRIPTION
             "The measured link range is greater than the maximum 
             allowed by the license key. The link will operate at a 
             reduced capacity while this condition applies. This alarm 
             is only raised if the license specifies a maximum link 
             range and the trial license is not active."  
      ::= { alarms 20 } 
 
   nIDULanPortDisabledWarning OBJECT-TYPE
      SYNTAX INTEGER {
                       ok(0),
                       disabledBySNMPifAdminStatus(1)
                     }
      MAX-ACCESS read-only
      STATUS current
      DESCRIPTION
             "The SNMP ifAdminStatus of the interface has disabled 
             Ethernet traffic"  
      ::= { alarms 21 } 
 
   nIDULanPortConfigurationMismatch OBJECT-TYPE
      SYNTAX INTEGER {
                       noError(0),
                       mismatchDetected(1)
                     }
      MAX-ACCESS read-only
      STATUS current
      DESCRIPTION
             "The detection of Ethernet fragments (runt packets) when 
             the link is in full duplex is an indication of an 
             auto-negotiation or forced configuration mismatch."  
      ::= { alarms 22 } 
 
   portAllocationMismatch OBJECT-TYPE
      SYNTAX INTEGER {
                       portAllocationOK(0),
                       mismatchinSecondDataService(1),
                       mismatchinOutofBandRemoteManagementService(2)
                     }
      MAX-ACCESS read-only
      STATUS current
      DESCRIPTION
             "The local and remote ODUs have different services 
             configured."  
      ::= { alarms 23 } 
 
   secondDataBridgingStatusAlarm OBJECT-TYPE
      SYNTAX INTEGER {
                       bridgingEnabled(0),
                       bridgingDisabled(1)
                     }
      MAX-ACCESS read-only
      STATUS current
      DESCRIPTION
             "Bridging of Ethernet traffic from Second Data Service 
             has been disabled because the wireless link is not 
             operating at the configured Lowest Second Data Modulation 
             Mode"  
      ::= { alarms 24 } 
 
   transparentClockSourcePortAlarm OBJECT-TYPE
      SYNTAX INTEGER {
                       ok(0),
                       invalidTransparentClockSourcePort(1)
                     }
      MAX-ACCESS read-only
      STATUS current
      DESCRIPTION
             "Transparent Clock will not function properly because 
             SFP, the selected clock source port is not FIBER"  
      ::= { alarms 25 } 
 
   -- Smtp group attribute definitions 
   --
   sMTPEmailAlert OBJECT-TYPE
      SYNTAX INTEGER {
                       disabled(0),
                       enabled(1)
                     }
      MAX-ACCESS read-write
      STATUS current
      DESCRIPTION
             "Simple Mail Transfer Protocol is used to send equipment 
             alerts via email to a specified email address"  
      ::= { smtp 1 } 
 
   sMTPServerPortNumber OBJECT-TYPE
      SYNTAX INTEGER (0..65535)
      MAX-ACCESS read-write
      STATUS current
      DESCRIPTION
             "Port number of the SMTP server"  
      ::= { smtp 3 } 
 
   sMTPSourceEmailAddress OBJECT-TYPE
      SYNTAX DisplayString (SIZE(0..63))
      MAX-ACCESS read-write
      STATUS current
      DESCRIPTION
             "The 'from' email address used when constructing the 
             automatically generated e-mail message"  
      ::= { smtp 4 } 
 
   sMTPDestinationEmailAddress OBJECT-TYPE
      SYNTAX DisplayString (SIZE(0..63))
      MAX-ACCESS read-write
      STATUS current
      DESCRIPTION
             "The 'to' email address used when constructing the 
             automatically generated e-mail message"  
      ::= { smtp 5 } 
 
   sMTPEnabledMessages OBJECT-TYPE
      SYNTAX BITS {
                    nIDULanPortUpDown(0),
                    sFPPortUpDown(1),
                    auxPortUpDown(2),
                    mainPSUPortUpDown(3),
                    enabledDiagnosticAlarms(4),
                    dFSImpulseInterference(5),
                    channelChange(6),
                    wirelessLinkUpDown(7)
                  }
      MAX-ACCESS read-write
      STATUS current
      DESCRIPTION
             "This controls which SMTP messages the unit will send"  
      ::= { smtp 6 } 
 
   sMTPServerInternetAddressType OBJECT-TYPE
      SYNTAX INTEGER {
                       unknown(0),
                       ipv4(1),
                       ipv6(2),
                       ipv4z(3),
                       ipv6z(4),
                       unknown6(5),
                       unknown7(6),
                       unknown8(7),
                       unknown9(8),
                       unknown10(9),
                       unknown11(10),
                       unknown12(11),
                       unknown13(12),
                       unknown14(13),
                       unknown15(14),
                       unknown16(15),
                       dns(16)
                     }
      MAX-ACCESS read-only
      STATUS current
      DESCRIPTION
             "The type of Internet address specified by the associated 
             sMTPServerInternetAddress."  
      ::= { smtp 7 } 
 
   sMTPServerInternetAddress OBJECT-TYPE
      SYNTAX InetAddress
      MAX-ACCESS read-write
      STATUS current
      DESCRIPTION
             "Internet address of the SMTP server"  
      ::= { smtp 8 } 
 
   -- SnmpControl group attribute definitions 
   --
   sNMPPortNumber OBJECT-TYPE
      SYNTAX INTEGER (0..65535)
      MAX-ACCESS read-write
      STATUS current
      DESCRIPTION
             "The IP port number used to access the SNMP MIB (i.e. 
             Gets and Sets) (default = 161). NB: A system reboot is 
             required to activate changes to this attribute"  
      ::= { snmpControl 1 } 
 
   sNMPCommunityString OBJECT-TYPE
      SYNTAX DisplayString (SIZE(0..63))
      MAX-ACCESS read-write
      STATUS current
      DESCRIPTION
             "The SNMP community string. NB: A system reboot is 
             required to activate changes to this attribute"  
      ::= { snmpControl 2 } 
 
   sNMPTrapTableNumber OBJECT-TYPE
      SYNTAX INTEGER (2)
      MAX-ACCESS read-only
      STATUS current
      DESCRIPTION
             "Number of entries in the sNMPTrapTable."  
      ::= { snmpControl 3 } 
 
   sNMPTrapVersion OBJECT-TYPE
      SYNTAX INTEGER {
                       v1(0),
                       v2c(1)
                     }
      MAX-ACCESS read-write
      STATUS current
      DESCRIPTION
             "The SNMP protocol version to use for SNMP Traps. NB: A 
             system reboot is required to activate changes to this 
             attribute"  
      ::= { snmpControl 5 } 
 
   sNMPEnabledTraps OBJECT-TYPE
      SYNTAX BITS {
                    auxPortUpDown(0),
                    mainPSUPortUpDown(1),
                    authenticationFailure(2),
                    enabledDiagnosticAlarms(3),
                    dFSImpulseInterference(4),
                    channelChange(5),
                    wirelessLinkUpDown(6),
                    coldStart(7),
                    nIDULanPortUpDown(14),
                    sFPPortUpDown(15)
                  }
      MAX-ACCESS read-write
      STATUS current
      DESCRIPTION
             "This controls which SNMP Traps the unit will send"  
      ::= { snmpControl 6 } 
 
   enabledDiagnosticAlarms OBJECT-TYPE
      SYNTAX BITS {
                    portState(0),
                    incompatibleMasterAndSlave(1),
                    incompatibleRegulatoryBands(2),
                    maximumLinkRangeExceeded(3),
                    unitOutOfCalibration(4),
                    installArmState(5),
                    installStatus(6),
                    regulatoryBand(7),
                    syslogLocalWrapped(8),
                    syslogLocalNearlyFull(9),
                    syslogDisabledWarning(10),
                    linkModeOptimizationMismatch(11),
                    tDDSynchronizationAlarm(12),
                    wirelessLinkDisabledWarning(13),
                    sNTPSynchronizationFailed(14),
                    noWirelessChannelAvailable(15),
                    tDMAlarms(18),
                    capacityVariantMismatch(19),
                    remainingFullCapacityTrialTime(20),
                    dataBridgingStatus(21),
                    unknown18(22),
                    syslogClientDisabledWarning(23)
                  }
      MAX-ACCESS read-write
      STATUS current
      DESCRIPTION
             "Controls which individual diagnostic alarms are enabled. 
             The unit may be configured to generate SNMP traps and/or 
             SMTP email alerts for these enabled alarms by selecting 
             'Enabled Diagnostic Alarms' on the 'SNMP Enabled Traps' 
             and/or 'SMTP Enabled Messages' attributes"  
      ::= { snmpControl 7 } 
 
   sNMPSendAllTrapsAtStartup OBJECT-TYPE
      SYNTAX INTEGER {
                       disabled(0),
                       enabled(1)
                     }
      MAX-ACCESS read-write
      STATUS current
      DESCRIPTION
             "Controls whether cleared traps are reported at start-up 
             as well as raised traps. Only enabled traps will be 
             reported. NB: Traps corresponding to transient events 
             (i.e. not associated with an alarm or status value) are 
             only sent when required and not at start-up."  
      ::= { snmpControl 8 } 
 
   -- SNMPTrapTable group attribute definitions 
   --
   sNMPTrapTableIndex OBJECT-TYPE
      SYNTAX INTEGER (1..2)
      MAX-ACCESS not-accessible
      STATUS current
      DESCRIPTION
             "SNMP trap value, used to index the SNMPTrapTable."  
      ::= { sNMPTrapTableEntry 1 } 
 
   sNMPTrapPortNumber OBJECT-TYPE
      SYNTAX INTEGER (0..65535)
      MAX-ACCESS read-write
      STATUS current
      DESCRIPTION
             "Destination port for SNMP Traps (default=162). NB: A 
             system reboot is required to activate changes to this 
             attribute."  
      ::= { sNMPTrapTableEntry 3 } 
 
   sNMPTrapInternetAddressType OBJECT-TYPE
      SYNTAX INTEGER {
                       unknown(0),
                       ipv4(1),
                       ipv6(2),
                       ipv4z(3),
                       ipv6z(4),
                       unknown6(5),
                       unknown7(6),
                       unknown8(7),
                       unknown9(8),
                       unknown10(9),
                       unknown11(10),
                       unknown12(11),
                       unknown13(12),
                       unknown14(13),
                       unknown15(14),
                       unknown16(15),
                       dns(16)
                     }
      MAX-ACCESS read-only
      STATUS current
      DESCRIPTION
             "The type of Internet address specified by the associated 
             sNMPTrapInternetAddress."  
      ::= { sNMPTrapTableEntry 4 } 
 
   sNMPTrapInternetAddress OBJECT-TYPE
      SYNTAX InetAddress
      MAX-ACCESS read-write
      STATUS current
      DESCRIPTION
             "The Internet address to which all SNMP Traps are sent."  
      ::= { sNMPTrapTableEntry 5 } 
 
   sNMPTrapReceiverEnabled OBJECT-TYPE
      SYNTAX INTEGER {
                       disabled(0),
                       enabled(1)
                     }
      MAX-ACCESS read-write
      STATUS current
      DESCRIPTION
             "A value of 0 disables the sending of SNMP trap to 
             corresponding receiver. A value of 1 enables the sending 
             of SNMP trap to corresponding receiver."  
      ::= { sNMPTrapTableEntry 6 } 
 
   -- Sntp group attribute definitions 
   --
   sNTPState OBJECT-TYPE
      SYNTAX INTEGER {
                       disabled(0),
                       enabled(1)
                     }
      MAX-ACCESS read-write
      STATUS current
      DESCRIPTION
             "SNTP control state"  
      ::= { sntp 1 } 
 
   sNTPPollInterval OBJECT-TYPE
      SYNTAX INTEGER (60..43200)
      MAX-ACCESS read-write
      STATUS current
      DESCRIPTION
             "The SNTP server polling interval"  
      ::= { sntp 4 } 
 
   sNTPSync OBJECT-TYPE
      SYNTAX INTEGER {
                       noSync(0),
                       inSync(1)
                     }
      MAX-ACCESS read-only
      STATUS current
      DESCRIPTION
             "If SNTP Sync fails then check the server settings in the 
             Remote Management page, or disable SNTP"  
      ::= { sntp 5 } 
 
   sNTPLastSync OBJECT-TYPE
      SYNTAX Integer32
      MAX-ACCESS read-only
      STATUS current
      DESCRIPTION
             "Last SNTP sync time"  
      ::= { sntp 6 } 
 
   systemClock OBJECT-TYPE
      SYNTAX Integer32
      MAX-ACCESS read-only
      STATUS current
      DESCRIPTION
             "System clock presented as local time"  
      ::= { sntp 7 } 
 
   timeZone OBJECT-TYPE
      SYNTAX INTEGER {
                       gmtMinus1200(0),
                       gmtMinus1130(1),
                       gmtMinus1100(2),
                       gmtMinus1030(3),
                       gmtMinus1000(4),
                       gmtMinus0930(5),
                       gmtMinus0900(6),
                       gmtMinus0830(7),
                       gmtMinus0800(8),
                       gmtMinus0730(9),
                       gmtMinus0700(10),
                       gmtMinus0630(11),
                       gmtMinus0600(12),
                       gmtMinus0530(13),
                       gmtMinus0500(14),
                       gmtMinus0430(15),
                       gmtMinus0400(16),
                       gmtMinus0330(17),
                       gmtMinus0300(18),
                       gmtMinus0230(19),
                       gmtMinus0200(20),
                       gmtMinus0130(21),
                       gmtMinus0100(22),
                       gmtMinus0030(23),
                       gmtZero(24),
                       gmtPlus0030(25),
                       gmtPlus0100(26),
                       gmtPlus0130(27),
                       gmtPlus0200(28),
                       gmtPlus0230(29),
                       gmtPlus0300(30),
                       gmtPlus0330(31),
                       gmtPlus0400(32),
                       gmtPlus0430(33),
                       gmtPlus0500(34),
                       gmtPlus0530(35),
                       gmtPlus0600(36),
                       gmtPlus0630(37),
                       gmtPlus0700(38),
                       gmtPlus0730(39),
                       gmtPlus0800(40),
                       gmtPlus0830(41),
                       gmtPlus0900(42),
                       gmtPlus0930(43),
                       gmtPlus1000(44),
                       gmtPlus1030(45),
                       gmtPlus1100(46),
                       gmtPlus1130(47),
                       gmtPlus1200(48),
                       gmtPlus1230(49),
                       gmtPlus1300(50)
                     }
      MAX-ACCESS read-write
      STATUS current
      DESCRIPTION
             "Time zone offsets from Greenwich Mean Time (GMT)"  
      ::= { sntp 8 } 
 
   daylightSaving OBJECT-TYPE
      SYNTAX INTEGER {
                       disabled(0),
                       enabled(1)
                     }
      MAX-ACCESS read-write
      STATUS current
      DESCRIPTION
             "Daylight Saving Time"  
      ::= { sntp 9 } 
 
   sNTPPrimaryServer OBJECT-TYPE
      SYNTAX INTEGER {
                       server1(0),
                       server2(1)
                     }
      MAX-ACCESS read-write
      STATUS current
      DESCRIPTION
             "Specifies the primary SNTP server, determining the order 
             in which the servers are tried."  
      ::= { sntp 10 } 
 
   sNTPPrimaryServerDeadTime OBJECT-TYPE
      SYNTAX INTEGER (0..86400)
      MAX-ACCESS read-write
      STATUS current
      DESCRIPTION
             "Time (in seconds) to wait before retrying communications 
             with an unresponsive primary SNTP server. Setting the 
             value to 0 disables the timer."  
      ::= { sntp 11 } 
 
   sNTPServerRetries OBJECT-TYPE
      SYNTAX INTEGER (0..10)
      MAX-ACCESS read-write
      STATUS current
      DESCRIPTION
             "Number of times the PTP will retry after an SNTP server 
             fails to respond."  
      ::= { sntp 12 } 
 
   sNTPServerTimeout OBJECT-TYPE
      SYNTAX INTEGER (1..15)
      MAX-ACCESS read-write
      STATUS current
      DESCRIPTION
             "Time (in seconds) the PTP will wait for a response from 
             an SNTP server."  
      ::= { sntp 13 } 
 
   sNTPServerTableNumber OBJECT-TYPE
      SYNTAX INTEGER (2)
      MAX-ACCESS read-only
      STATUS current
      DESCRIPTION
             "Number of entries in the SNTPServerTable."  
      ::= { sntp 14 } 
 
   -- SNTPServerTable group attribute definitions 
   --
   sNTPServerTableIndex OBJECT-TYPE
      SYNTAX INTEGER (1..2)
      MAX-ACCESS not-accessible
      STATUS current
      DESCRIPTION
             "Index range for the SNTPServerTable."  
      ::= { sNTPServerTableEntry 1 } 
 
   sNTPServerPortNumber OBJECT-TYPE
      SYNTAX INTEGER (0..65535)
      MAX-ACCESS read-write
      STATUS current
      DESCRIPTION
             "The IP port number of the SNTP server. Defaults to port 
             123."  
      ::= { sNTPServerTableEntry 3 } 
 
   sNTPServerStatus OBJECT-TYPE
      SYNTAX DisplayString (SIZE(0..127))
      MAX-ACCESS read-only
      STATUS current
      DESCRIPTION
             "Status message reflecting the result of communications 
             with the SNTP server when last polled"  
      ::= { sNTPServerTableEntry 4 } 
 
   sNTPServerInternetAddressType OBJECT-TYPE
      SYNTAX INTEGER {
                       unknown(0),
                       ipv4(1),
                       ipv6(2),
                       ipv4z(3),
                       ipv6z(4),
                       unknown6(5),
                       unknown7(6),
                       unknown8(7),
                       unknown9(8),
                       unknown10(9),
                       unknown11(10),
                       unknown12(11),
                       unknown13(12),
                       unknown14(13),
                       unknown15(14),
                       unknown16(15),
                       dns(16)
                     }
      MAX-ACCESS read-only
      STATUS current
      DESCRIPTION
             "The type of Internet address specified by the associated 
             sNTPServerInternetAddress."  
      ::= { sNTPServerTableEntry 5 } 
 
   sNTPServerInternetAddress OBJECT-TYPE
      SYNTAX InetAddress
      MAX-ACCESS read-write
      STATUS current
      DESCRIPTION
             "The Internet address of a valid SNTP server"  
      ::= { sNTPServerTableEntry 6 } 
 
   -- Reset group attribute definitions 
   --
   systemReset OBJECT-TYPE
      SYNTAX INTEGER {
                       running(0),
                       consoleReboot(1)
                     }
      MAX-ACCESS read-write
      STATUS current
      DESCRIPTION
             "Setting this attribute to '1' will cause a system 
             reboot. NB: a system reboot will apply any pending new 
             settings held in memory"  
      ::= { reset 1 } 
 
   -- Versions group attribute definitions 
   --
   softwareVersion OBJECT-TYPE
      SYNTAX DisplayString (SIZE(0..63))
      MAX-ACCESS read-only
      STATUS current
      DESCRIPTION
             "Current software version"  
      ::= { versions 1 } 
 
   hardwareVersion OBJECT-TYPE
      SYNTAX DisplayString (SIZE(0..63))
      MAX-ACCESS read-only
      STATUS current
      DESCRIPTION
             "Hardware platform version"  
      ::= { versions 2 } 
 
   secondarySoftwareVersion OBJECT-TYPE
      SYNTAX DisplayString (SIZE(0..63))
      MAX-ACCESS read-only
      STATUS current
      DESCRIPTION
             "Secondary software version, used when the primary 
             software image is invalid or erased"  
      ::= { versions 3 } 
 
   bootVersion OBJECT-TYPE
      SYNTAX DisplayString (SIZE(0..63))
      MAX-ACCESS read-only
      STATUS current
      DESCRIPTION
             "Boot code software version"  
      ::= { versions 4 } 
 
   -- PubStats group attribute definitions 
   --
   receiveDataRate OBJECT-TYPE
      SYNTAX Integer32
      MAX-ACCESS read-only
      STATUS current
      DESCRIPTION
             "Average data rate over the last one second interval 
             (kbps)"  
      ::= { pubStats 1 } 
 
   transmitDataRate OBJECT-TYPE
      SYNTAX Integer32
      MAX-ACCESS read-only
      STATUS current
      DESCRIPTION
             "Average data rate over the last one second interval 
             (kbps)"  
      ::= { pubStats 2 } 
 
   aggregateDataRate OBJECT-TYPE
      SYNTAX Integer32
      MAX-ACCESS read-only
      STATUS current
      DESCRIPTION
             "Average data rate over the last one second interval 
             (kbps)"  
      ::= { pubStats 3 } 
 
   wirelessLinkAvailability OBJECT-TYPE
      SYNTAX INTEGER (0..1000000)
      MAX-ACCESS read-only
      STATUS current
      DESCRIPTION
             "Link availability calculated since the last reset of the 
             system counters, as a percentage multiplied by 10000 to 
             give four decimal places of precision"  
      ::= { pubStats 4 } 
 
   wirelessLinkStatus OBJECT-TYPE
      SYNTAX INTEGER {
                       up(0),
                       registering(1),
                       searching(2),
                       acquiring(3),
                       radarCAC(4),
                       initialising(5)
                     }
      MAX-ACCESS read-only
      STATUS current
      DESCRIPTION
             "Current status of the wireless link"  
      ::= { pubStats 5 } 
 
   byteErrorRatio OBJECT-TYPE
      SYNTAX Integer32
      MAX-ACCESS read-only
      STATUS current
      DESCRIPTION
             "Reciprocal of the byte error ratio calculated since the 
             last reset of the system counters"  
      ::= { pubStats 6 } 
 
   receiveModulationModeDetail OBJECT-TYPE
      SYNTAX INTEGER {
                       runningAtMaximumReceiveMode(0),
                       runningAtUserConfiguredMaxModulationMode(1),
                       restrictedBecauseInstallationIsArmed(2),
                       restrictedBecauseOfByteErrorsOnTheWirelessLink(3),
                       restrictedBecauseTheLinkParametersAreUpdating(4),
                       restrictedBecauseChannelChangeIsInProgress(5),
                       restrictedDueToTheLowEthernetLinkSpeed(6),
                       runningAtMaximumReceiveModeForChannelBandwidth(7),
                       limitedByTheWirelessConditions(8),
                       restrictedBecauseFullCapabilityTrialLicenseExpired(9)
                     }
      MAX-ACCESS read-only
      STATUS current
      DESCRIPTION
             "The reason for the current receive modulation mode"  
      ::= { pubStats 7 } 
 
   dataBridgingAvailability OBJECT-TYPE
      SYNTAX INTEGER (0..1000000)
      MAX-ACCESS read-only
      STATUS current
      DESCRIPTION
             "Link availability bridging Ethernet Data traffic 
             calculated since the last reset of the system counters, 
             as a percentage multiplied by 10000 to give four decimal 
             places of precision"  
      ::= { pubStats 8 } 
 
   -- Encryption group attribute definitions 
   --
   encryptionAlgorithm OBJECT-TYPE
      SYNTAX INTEGER {
                       none(0),
                       aESRijndael(1),
                       aES192bitRijndael(2),
                       aES256bitRijndael(3)
                     }
      MAX-ACCESS read-only
      STATUS current
      DESCRIPTION
             "The Encryption Algorithm used by the wireless link. NB: 
             A system reboot is required to activate changes to this 
             attribute. NB: The same Encryption Algorithm must be 
             configured at BOTH ends of the link for it to function 
             correctly"  
      ::= { encryption 1 } 
 
   -- TDDControl group attribute definitions 
   --
   tDDSynchronizationMode OBJECT-TYPE
      SYNTAX INTEGER {
                       disabled(0),
                       enabled(1)
                     }
      MAX-ACCESS read-only
      STATUS current
      DESCRIPTION
             "TDD Synchronization Mode selection"  
      ::= { tDDControl 1 } 
 
   -- AAAControl group attribute definitions 
   --
   userTableNumber OBJECT-TYPE
      SYNTAX INTEGER (1..10)
      MAX-ACCESS read-only
      STATUS current
      DESCRIPTION
             "Number of entries in the userTable"  
      ::= { aAAControl 1 } 
 
   -- UserTable group attribute definitions 
   --
   userTableIndex OBJECT-TYPE
      SYNTAX INTEGER (1..10)
      MAX-ACCESS not-accessible
      STATUS current
      DESCRIPTION
             "used to index values in the userTable."  
      ::= { userTableEntry 1 } 
 
   userName OBJECT-TYPE
      SYNTAX DisplayString (SIZE(0..67))
      MAX-ACCESS read-only
      STATUS current
      DESCRIPTION
             "User name which must be entered, along with the 
             appropriate password, in order to gain access to the 
             system."  
      ::= { userTableEntry 2 } 
 
   userRole OBJECT-TYPE
      SYNTAX INTEGER {
                       readOnly(0),
                       systemAdministrator(1),
                       securityOfficer(2)
                     }
      MAX-ACCESS read-only
      STATUS current
      DESCRIPTION
             "Role of the selected user. A Security Officer has access 
             to and can modify all settings. A System Administrator 
             has access to and can modify all non-security settings. A 
             Read Only user can view settings, but cannot make any 
             changes."  
      ::= { userTableEntry 3 } 
 
   userEnabled OBJECT-TYPE
      SYNTAX INTEGER {
                       disabled(0),
                       enabled(1)
                     }
      MAX-ACCESS read-only
      STATUS current
      DESCRIPTION
             "Enable / Disable the selected user"  
      ::= { userTableEntry 4 } 
 
   userPassword OBJECT-TYPE
      SYNTAX DisplayString (SIZE(0..67))
      MAX-ACCESS read-write
      STATUS current
      DESCRIPTION
             "User password, which must be entered in order to gain 
             access to the system."  
      ::= { userTableEntry 5 } 
 
   -- SyslogControl group attribute definitions 
   --
   syslogClient OBJECT-TYPE
      SYNTAX INTEGER {
                       disabled(0),
                       enabled(1)
                     }
      MAX-ACCESS read-only
      STATUS current
      DESCRIPTION
             "Enable or disable the syslog client"  
      ::= { syslogControl 1 } 
 
   syslogState OBJECT-TYPE
      SYNTAX INTEGER {
                       disabled(0),
                       enabled(1)
                     }
      MAX-ACCESS read-only
      STATUS current
      DESCRIPTION
             "The syslog service has been enabled or disabled"  
      ::= { syslogControl 2 } 
 
   -- RouterProtocols group attribute definitions 
   --
   microwaveAdaptiveBandwidth OBJECT-TYPE
      SYNTAX INTEGER {
                       disabled(0),
                       enabled(1)
                     }
      MAX-ACCESS read-only
      STATUS current
      DESCRIPTION
             "Enable support of Microwave Adaptive Bandwidth Protocol. 
             MAB is disabled if link symmetry is configured as 
             Adaptive"  
      ::= { routerProtocols 1 } 
 
   mABNominalModulationMode OBJECT-TYPE
      SYNTAX INTEGER {
                       modAcquisition(0),
                       modBpsk63percent(1),
                       modQpsk63percentSingle(2),
                       modTransient1(3),
                       modQpsk87percentSingle(4),
                       modTransient2(5),
                       mod16qam63percentSingleA(6),
                       modTransient3(7),
                       mod16qam87percentSingle(8),
                       modTransient4(9),
                       mod64qam75percentSingle(10),
                       modTransient5(11),
                       mod64qam92percentSingle(12),
                       modTransient6(13),
                       mod256qam81percentSingle(14),
                       mod16qam63percentSingleB(15),
                       mod16qam63percentDual(16),
                       modTransient7(17),
                       mod16qam87percentDual(18),
                       modTransient8(19),
                       mod64qam75percentDual(20),
                       modTransient9(21),
                       mod64qam92percentDual(22),
                       modTransient10(23),
                       mod256qam81percentDual(24)
                     }
      MAX-ACCESS read-only
      STATUS current
      DESCRIPTION
             "The Nominal modulation mode is the desired modulation 
             mode. MAB VSM packets are generated when the current 
             modulation mode falls below the nominal modulation."  
      ::= { routerProtocols 2 } 
 
   mABTransmissionInterval OBJECT-TYPE
      SYNTAX INTEGER {
                       transmissionInterval1s(0),
                       transmissionInterval10s(1),
                       transmissionInterval60s(2)
                     }
      MAX-ACCESS read-only
      STATUS current
      DESCRIPTION
             "The minimum interval (in seconds) between successive MAB 
             vendor specific messages (VSM). These VSM are sent when 
             the current transmit capacity falls below the configured 
             MAB Nominal Modulation Mode."  
      ::= { routerProtocols 3 } 
 
   mABHoldoffPeriod OBJECT-TYPE
      SYNTAX INTEGER (10..60)
      MAX-ACCESS read-only
      STATUS current
      DESCRIPTION
             "The period (in seconds) over which transmit capacity is 
             averaged over to determine when the wireless link has 
             degraded"  
      ::= { routerProtocols 4 } 
 
   mABMaintenanceLevel OBJECT-TYPE
      SYNTAX INTEGER (0..7)
      MAX-ACCESS read-only
      STATUS current
      DESCRIPTION
             "Maintenance Levels (0-7) determines the destination MAC 
             address of MAB vendor specific messages."  
      ::= { routerProtocols 5 } 
 
   useVLANForMABProtocol OBJECT-TYPE
      SYNTAX INTEGER {
                       noVLANTagging(0),
                       iEEE8021QTaggedCTagType8100(1)
                     }
      MAX-ACCESS read-only
      STATUS current
      DESCRIPTION
             "This controls whether MAB vendor specific messages (VSM) 
             packets use VLAN tags or not."  
      ::= { routerProtocols 6 } 
 
   mABProtocolVID OBJECT-TYPE
      SYNTAX INTEGER (0..4094)
      MAX-ACCESS read-only
      STATUS current
      DESCRIPTION
             "This VLAN VID (0-4094) will be included in MAB vendor 
             specific messages (VSM) packets."  
      ::= { routerProtocols 7 } 
 
   mABProtocolVLANPriority OBJECT-TYPE
      SYNTAX INTEGER (0..7)
      MAX-ACCESS read-only
      STATUS current
      DESCRIPTION
             "This VLAN Priority (0-7) will be included in MAB vendor 
             specific messages (VSM) packets."  
      ::= { routerProtocols 8 } 
 
   mABState OBJECT-TYPE
      SYNTAX INTEGER {
                       normal(0),
                       degraded(1)
                     }
      MAX-ACCESS read-only
      STATUS current
      DESCRIPTION
             "Current state of MAB Protocol. A state of 'Normal' on a 
             green background indicates that a PTP link is operating 
             at nominal capacity"  
      ::= { routerProtocols 9 } 
 
   mABNominalTransmitCapacity OBJECT-TYPE
      SYNTAX INTEGER (0..1000)
      MAX-ACCESS read-only
      STATUS current
      DESCRIPTION
             "The nominal Tx capacity used in MAB Vendor Specific 
             Messages for the selected nominal modulation mode "  
      ::= { routerProtocols 10 } 
 
   mABCurrentTransmitCapacity OBJECT-TYPE
      SYNTAX INTEGER (0..1000)
      MAX-ACCESS read-only
      STATUS current
      DESCRIPTION
             "The current Tx capacity of the wireless link used in the 
             last MAB Vendor Specific Message transmitted."  
      ::= { routerProtocols 11 } 
 
   -- CableDiagnostics group attribute definitions 
   --
   cableDiagnosticsPorts OBJECT-TYPE
      SYNTAX BITS {
                    auxPort(6),
                    mainPSUPort(7)
                  }
      MAX-ACCESS read-write
      STATUS current
      DESCRIPTION
             "Select ports on which Cable Diagnostics must be 
             executed"  
      ::= { cableDiagnostics 1 } 
 
   cableDiagnosticsControl OBJECT-TYPE
      SYNTAX INTEGER {
                       startTest(0),
                       testInProgress(1)
                     }
      MAX-ACCESS read-write
      STATUS current
      DESCRIPTION
             "Set this attribute to 'Test in Progress' to start a 
             Cable Diagnostics test"  
      ::= { cableDiagnostics 2 } 
 
   cableDiagnosticsWarning OBJECT-TYPE
      SYNTAX INTEGER {
                       idle(0),
                       testInProgress(1)
                     }
      MAX-ACCESS read-only
      STATUS current
      DESCRIPTION
             "Normal Ethernet operation is disrupted when a Cable 
             Diagnostics test is in progress"  
      ::= { cableDiagnostics 3 } 
 
   cableDiagnosticsResultTableNumber OBJECT-TYPE
      SYNTAX INTEGER (1..2)
      MAX-ACCESS read-only
      STATUS current
      DESCRIPTION
             "Number of rows in the Cable Diagnostics Result Table."  
      ::= { cableDiagnostics 4 } 
 
   -- CableDiagnosticsResultTable group attribute definitions 
   --
   cableDiagnosticsResultTableIndex OBJECT-TYPE
      SYNTAX INTEGER (1..2)
      MAX-ACCESS not-accessible
      STATUS current
      DESCRIPTION
             "Cable Diagnostics Port value used to index into the 
             result table."  
      ::= { cableDiagnosticsResultTableEntry 1 } 
 
   cableDiagnosticsResultsDateTime OBJECT-TYPE
      SYNTAX Integer32
      MAX-ACCESS read-only
      STATUS current
      DESCRIPTION
             "The Date and Time when a Cable Diagnostics test was last 
             executed"  
      ::= { cableDiagnosticsResultTableEntry 2 } 
 
   cableDiagPair1Results OBJECT-TYPE
      SYNTAX INTEGER {
                       ok(0),
                       unknown(1),
                       inProgress(2),
                       notTested(3),
                       openCircuit(4),
                       shortCircuit(5)
                     }
      MAX-ACCESS read-only
      STATUS current
      DESCRIPTION
             "The result of the most recent execution of Cable 
             Diagnostics on cable pair 1. According to the T658B 
             wiring scheme, pair 1 is pins 4 & 5 on the RJ45 socket on 
             the ODU. Open Circuit is reported when the impedance is 
             greater than 330 ohms. Short Circuit is reported when the 
             impedance is less than 33 ohms. Unknown is reported when 
             a continuous signal is received from the link partner for 
             125 ms, preventing start of the test."  
      ::= { cableDiagnosticsResultTableEntry 3 } 
 
   cableDiagPair1Distance OBJECT-TYPE
      SYNTAX Integer32
      MAX-ACCESS read-only
      STATUS current
      DESCRIPTION
             "The distance in meters from the ODU to the fault 
             detected on the cable pair during the most recent 
             execution of Cable Diagnostics. Faults in cables longer 
             than 160 meters (525 feet) may not be detected. The error 
             margin is +/-2 meters (6.5 feet)."  
      ::= { cableDiagnosticsResultTableEntry 4 } 
 
   cableDiagPair2Results OBJECT-TYPE
      SYNTAX INTEGER {
                       ok(0),
                       unknown(1),
                       inProgress(2),
                       notTested(3),
                       openCircuit(4),
                       shortCircuit(5)
                     }
      MAX-ACCESS read-only
      STATUS current
      DESCRIPTION
             "The result of the most recent execution of Cable 
             Diagnostics on cable pair 2. According to the T658B 
             wiring scheme, pair 2 is pins 1 & 2 on the RJ45 socket on 
             the ODU. Open Circuit is reported when the impedance is 
             greater than 330 ohms. Short Circuit is reported when the 
             impedance is less than 33 ohms. Unknown is reported when 
             a continuous signal is received from the link partner for 
             125 ms, preventing start of the test."  
      ::= { cableDiagnosticsResultTableEntry 5 } 
 
   cableDiagPair2Distance OBJECT-TYPE
      SYNTAX Integer32
      MAX-ACCESS read-only
      STATUS current
      DESCRIPTION
             "The distance in meters from the ODU to the fault 
             detected on the cable pair during the most recent 
             execution of Cable Diagnostics. Faults in cables longer 
             than 160 meters (525 feet) may not be detected. The error 
             margin is +/-2 meters (6.5 feet)."  
      ::= { cableDiagnosticsResultTableEntry 6 } 
 
   cableDiagPair3Results OBJECT-TYPE
      SYNTAX INTEGER {
                       ok(0),
                       unknown(1),
                       inProgress(2),
                       notTested(3),
                       openCircuit(4),
                       shortCircuit(5)
                     }
      MAX-ACCESS read-only
      STATUS current
      DESCRIPTION
             "The result of the most recent execution of Cable 
             Diagnostics on cable pair 3. According to the T658B 
             wiring scheme, pair 3 is pins 3 & 6 on the RJ45 socket on 
             the ODU. Open Circuit is reported when the impedance is 
             greater than 330 ohms. Short Circuit is reported when the 
             impedance is less than 33 ohms. Unknown is reported when 
             a continuous signal is received from the link partner for 
             125 ms, preventing start of the test."  
      ::= { cableDiagnosticsResultTableEntry 7 } 
 
   cableDiagPair3Distance OBJECT-TYPE
      SYNTAX Integer32
      MAX-ACCESS read-only
      STATUS current
      DESCRIPTION
             "The distance in meters from the ODU to the fault 
             detected on the cable pair during the most recent 
             execution of Cable Diagnostics. Faults in cables longer 
             than 160 meters (525 feet) may not be detected. The error 
             margin is +/-2 meters (6.5 feet)."  
      ::= { cableDiagnosticsResultTableEntry 8 } 
 
   cableDiagPair4Results OBJECT-TYPE
      SYNTAX INTEGER {
                       ok(0),
                       unknown(1),
                       inProgress(2),
                       notTested(3),
                       openCircuit(4),
                       shortCircuit(5)
                     }
      MAX-ACCESS read-only
      STATUS current
      DESCRIPTION
             "The result of the most recent execution of Cable 
             Diagnostics on cable pair 4. According to the T658B 
             wiring scheme, pair 4 is pins 7 & 8 on the RJ45 socket on 
             the ODU. Open Circuit is reported when the impedance is 
             greater than 330 ohms. Short Circuit is reported when the 
             impedance is less than 33 ohms. Unknown is reported when 
             a continuous signal is received from the link partner for 
             125 ms, preventing start of the test."  
      ::= { cableDiagnosticsResultTableEntry 9 } 
 
   cableDiagPair4Distance OBJECT-TYPE
      SYNTAX Integer32
      MAX-ACCESS read-only
      STATUS current
      DESCRIPTION
             "The distance in meters from the ODU to the fault 
             detected on the cable pair during the most recent 
             execution of Cable Diagnostics. Faults in cables longer 
             than 160 meters (525 feet) may not be detected. The error 
             margin is +/-2 meters (6.5 feet)."  
      ::= { cableDiagnosticsResultTableEntry 10 } 
 
   -- Supplementary group attribute definitions 
   --
   longitude OBJECT-TYPE
      SYNTAX DisplayString (SIZE(0..19))
      MAX-ACCESS read-write
      STATUS current
      DESCRIPTION
             "The longitude of the unit, measured in decimal degrees. 
             This object is set by the SNMP manager and has no 
             internal function."  
      ::= { supplementary 1 } 
 
   latitude OBJECT-TYPE
      SYNTAX DisplayString (SIZE(0..19))
      MAX-ACCESS read-write
      STATUS current
      DESCRIPTION
             "The latitude of the unit, measured in decimal degrees. 
             This object is set by the SNMP manager and has no 
             internal function."  
      ::= { supplementary 2 } 
 
   altitude OBJECT-TYPE
      SYNTAX Integer32
      MAX-ACCESS read-write
      STATUS current
      DESCRIPTION
             "The altitude of the unit, measured in meters. This 
             object is set by the SNMP manager and has no internal 
             function."  
      ::= { supplementary 3 } 
 
   -- Enterprise NOTIFICATION definitions
   --

   channelChangeTrap NOTIFICATION-TYPE
      OBJECTS { receiveChannel }
      STATUS current
      DESCRIPTION "The PTP radio has changed wireless channel.
                 This has been caused by either
                 i) mandatory radar avoidance,
                    a DFS impulsive interference event will also be
                    detected,
                 or
                 ii) Dynamic Spectrum Optimization, (DSO)
                     DSO improves link performance by selecting the
                     most appropriate transmit and receive channels
                     with the lowest level of interference."
      ::= { ptpTrapPrefix 1 }

   dfsImpulsiveInterferenceTrap NOTIFICATION-TYPE
      OBJECTS { receiveChannel }
      STATUS current
      DESCRIPTION "DFS impulsive interference detected event"
      ::= { ptpTrapPrefix 2 }

   mainPSUPortStatusTrap NOTIFICATION-TYPE
      OBJECTS { mainPSUPortStatus }
      STATUS current
      DESCRIPTION
             "Current status of the Main PSU Ethernet link. NB: a 
             change of state may generate an SNMP trap and/or SMTP 
             email alert"  
      ::= { ptpTrapPrefix 3 }

   mainPSUPortDisabledWarningTrap NOTIFICATION-TYPE
      OBJECTS { mainPSUPortDisabledWarning }
      STATUS current
      DESCRIPTION
             "The SNMP ifAdminStatus of the interface has disabled 
             Ethernet traffic"  
      ::= { ptpTrapPrefix 4 }

   mainPSUPortConfigurationMismatchTrap NOTIFICATION-TYPE
      OBJECTS { mainPSUPortConfigurationMismatch }
      STATUS current
      DESCRIPTION
             "The detection of Ethernet fragments (runt packets) when 
             the link is in full duplex is an indication of an 
             auto-negotiation or forced configuration mismatch"  
      ::= { ptpTrapPrefix 5 }

   auxPortStatusTrap NOTIFICATION-TYPE
      OBJECTS { auxPortStatus }
      STATUS current
      DESCRIPTION
             "Current status of the Aux Ethernet link. NB: a change of 
             state may generate an SNMP trap and/or SMTP email alert"  
      ::= { ptpTrapPrefix 6 }

   auxPortDisabledWarningTrap NOTIFICATION-TYPE
      OBJECTS { auxPortDisabledWarning }
      STATUS current
      DESCRIPTION
             "The SNMP ifAdminStatus of the interface has disabled 
             Ethernet traffic"  
      ::= { ptpTrapPrefix 7 }

   regulatoryBandTrap NOTIFICATION-TYPE
      OBJECTS { regulatoryBand }
      STATUS current
      DESCRIPTION
             "The Regulatory Band prohibits the wireless unit from 
             operating outside the regulated limits. An invalid 
             Regulatory Band may be caused by a missing or incorrect 
             License Key, a corrupt MAC Address or an attempt to 
             configure a Regulatory Band not allowed by the License 
             Key. NB: a change of state may generate an SNMP trap 
             and/or SMTP email alert."  
      ::= { ptpTrapPrefix 8 }

   installStatusTrap NOTIFICATION-TYPE
      OBJECTS { installStatus }
      STATUS current
      DESCRIPTION
             "A non-zero value indicates that signalling was received 
             with the wrong MAC address or a mismatched link name. NB: 
             It is very unusual to detect this, because units with 
             mis-configured Target MAC Address will normally fail to 
             establish a wireless link. However, rare circumstances 
             may establish a partial wireless link and detect this 
             situation. NB: A non-zero value on start-up, or a change 
             of value during operation, may generate an SNMP trap 
             and/or SMTP email alert"  
      ::= { ptpTrapPrefix 9 }

   installArmStateTrap NOTIFICATION-TYPE
      OBJECTS { installArmState }
      STATUS current
      DESCRIPTION
             "Indicates if the unit is being installed. NB: a change 
             of state may generate an SNMP trap and/or SMTP email 
             alert"  
      ::= { ptpTrapPrefix 10 }

   unitOutOfCalibrationTrap NOTIFICATION-TYPE
      OBJECTS { unitOutOfCalibration }
      STATUS current
      DESCRIPTION
             "The unit is out of calibration"  
      ::= { ptpTrapPrefix 11 }

   auxPortPowerOverEthernetOutputStatusTrap NOTIFICATION-TYPE
      OBJECTS { auxPortPowerOverEthernetOutputStatus }
      STATUS current
      DESCRIPTION
             "Current status of the Power Over Ethernet (PoE) output 
             of the Aux port"  
      ::= { ptpTrapPrefix 12 }

   incompatibleRegulatoryBandsTrap NOTIFICATION-TYPE
      OBJECTS { incompatibleRegulatoryBands }
      STATUS current
      DESCRIPTION
             "The master and slave units have incompatible regulatory 
             bands. NB: Both units must have compatible license keys"  
      ::= { ptpTrapPrefix 14 }

   noWirelessChannelAvailableTrap NOTIFICATION-TYPE
      OBJECTS { noWirelessChannelAvailable }
      STATUS current
      DESCRIPTION
             "Spectrum Management was unable to locate a suitable 
             wireless channel to operate on"  
      ::= { ptpTrapPrefix 15 }

   wirelessLinkDisabledWarningTrap NOTIFICATION-TYPE
      OBJECTS { wirelessLinkDisabledWarning }
      STATUS current
      DESCRIPTION
             "The SNMP ifAdminStatus of the wireless interface has 
             disabled wireless traffic"  
      ::= { ptpTrapPrefix 16 }

   auxPortConfigurationMismatchTrap NOTIFICATION-TYPE
      OBJECTS { auxPortConfigurationMismatch }
      STATUS current
      DESCRIPTION
             "The detection of Ethernet fragments (runt packets) when 
             the link is in full duplex is an indication of an 
             auto-negotiation or forced configuration mismatch. This 
             alarm is only raised if an Out-of-Band Management Mode 
             has been configured."  
      ::= { ptpTrapPrefix 17 }

   sFPErrorTrap NOTIFICATION-TYPE
      OBJECTS { sFPError }
      STATUS current
      DESCRIPTION
             "If the SFP link is not OK, there are five possible 
             causes: Either a SFP has been installed but the license 
             key does not include SFP fiber support, a fiber link 
             could not be established even though no LOS was detected 
             (i.e. an optical carrier was detected, which could be due 
             to a broken TX fiber, or because the link is disabled at 
             the fiber link partner), a fiber link could not be 
             established and LOS is detected (i.e. no optical carrier 
             is detected), the installed SFP is not supported or the 
             installed SFP failed to initialize correctly. NB: a 
             change of status may generate an SNMP trap and/or SMTP 
             email alert"  
      ::= { ptpTrapPrefix 18 }

   sFPPortStatusTrap NOTIFICATION-TYPE
      OBJECTS { sFPPortStatus }
      STATUS current
      DESCRIPTION
             "Current status of the SFP Ethernet link. NB: a change of 
             state may generate an SNMP trap and/or SMTP email alert"  
      ::= { ptpTrapPrefix 19 }

   incompatibleMasterAndSlaveTrap NOTIFICATION-TYPE
      OBJECTS { incompatibleMasterAndSlave }
      STATUS current
      DESCRIPTION
             "A non-zero value indicates that the master and slave 
             ends of a link are different hardware products, or have 
             different software versions. NB: It is very unusual to 
             detect this, because incompatible units will normally 
             fail to establish a wireless link. However, some 
             combinations may establish a partial wireless link and 
             detect this situation. NB: A non-zero value may generate 
             an SNMP trap and/or SMTP email alert"  
      ::= { ptpTrapPrefix 20 }

   sNTPSyncTrap NOTIFICATION-TYPE
      OBJECTS { sNTPSync }
      STATUS current
      DESCRIPTION
             "If SNTP Sync fails then check the server settings in the 
             Remote Management page, or disable SNTP"  
      ::= { ptpTrapPrefix 21 }

   tDDSynchronizationAlarmTrap NOTIFICATION-TYPE
      OBJECTS { tDDSynchronizationAlarm }
      STATUS current
      DESCRIPTION
             "Not Synchronized indicates failure of the external 
             timing system for a period greater than the holdover 
             timer. TDD frame timing will have drifted, and this link 
             may cause interference with other links in a synchronized 
             network. Timing System Failure is an early warning, 
             indicating that 80% of the holdover period has expired."  
      ::= { ptpTrapPrefix 22 }

   sFPPortDisabledWarningTrap NOTIFICATION-TYPE
      OBJECTS { sFPPortDisabledWarning }
      STATUS current
      DESCRIPTION
             "The SNMP ifAdminStatus of the interface has disabled 
             Ethernet traffic"  
      ::= { ptpTrapPrefix 23 }

   sFPPortConfigurationMismatchTrap NOTIFICATION-TYPE
      OBJECTS { sFPPortConfigurationMismatch }
      STATUS current
      DESCRIPTION
             "The detection of Ethernet fragments (runt packets) when 
             the link is in full duplex is an indication of an 
             auto-negotiation or forced configuration mismatch. This 
             alarm is only raised if an Out-of-Band Management Mode 
             has been configured."  
      ::= { ptpTrapPrefix 24 }

   linkModeOptimizationMismatchTrap NOTIFICATION-TYPE
      OBJECTS { linkModeOptimizationMismatch }
      STATUS current
      DESCRIPTION
             "The remote node of this link has been configured with a 
             different link mode optimization"  
      ::= { ptpTrapPrefix 25 }

   tDMInterfaceStatusTrap NOTIFICATION-TYPE
      OBJECTS { tDMInterfaceStatus }
      STATUS current
      DESCRIPTION
             "@Current status of the connection to the TDM Box. A 
             state of 'Up' on a green background indicates that the 
             TDM Box is connected OK. When connecting a TDM Box only 
             the Main Ethernet port should be used"  
      ::= { ptpTrapPrefix 26 }

   tDMChannelStatusTrap NOTIFICATION-TYPE
      OBJECTS { tDMChannelStatus }
      STATUS current
      DESCRIPTION
             "Current status of the TDM channels. A value of 0 
             indicates that a TDM channel is established"  
      ::= { ptpTrapPrefix 27 }

   tDMChannelLoopbackTrap NOTIFICATION-TYPE
      OBJECTS { tDMChannelLoopback }
      STATUS current
      DESCRIPTION
             "The loopback status of TDM channels. This is intended 
             for installation testing and should be set to 'None' for 
             normal operation. The wire connections to a unit can be 
             tested by applying a 'Copper' loopback to the local unit. 
             The wireless connection to the remote unit can be tested 
             by applying a 'Wireless' loopback to the remote unit with 
             no loopback on the local unit. NB: a change of state may 
             generate an SNMP trap and/or SMTP email alert"  
      ::= { ptpTrapPrefix 28 }

   nIDULanPortStatusTrap NOTIFICATION-TYPE
      OBJECTS { nIDULanPortStatus }
      STATUS current
      DESCRIPTION
             "Current status of the NIDU LAN Ethernet link. NB: a 
             change of state may generate an SNMP trap and/or SMTP 
             email alert"  
      ::= { ptpTrapPrefix 29 }

   syslogStateTrap NOTIFICATION-TYPE
      OBJECTS { syslogState }
      STATUS current
      DESCRIPTION
             "The syslog service has been enabled or disabled"  
      ::= { ptpTrapPrefix 30 }

   syslogLocalNearlyFullTrap NOTIFICATION-TYPE
      STATUS current
      DESCRIPTION "The syslog local log is nearly full (90%)"
      ::= { ptpTrapPrefix 31 }

   syslogLocalWrappedTrap NOTIFICATION-TYPE
      STATUS current
      DESCRIPTION "The syslog local log has wrapped"
      ::= { ptpTrapPrefix 32 }

   syslogClientTrap NOTIFICATION-TYPE
      OBJECTS { syslogClient }
      STATUS current
      DESCRIPTION
             "Enable or disable the syslog client"  
      ::= { ptpTrapPrefix 33 }

   secureModeAlarmTrap NOTIFICATION-TYPE
      OBJECTS { secureModeAlarm }
      STATUS current
      DESCRIPTION
             "The secure mode (e.g. FIPS, UC-APL) state of the unit. 
             The secure mode is not configured(1) state indicates that 
             the unit is capable of secure mode operation, and one or 
             more of the following security materials has not been 
             configured: Key Of Keys, Private Key, Public Certificate, 
             DRNG Entropy Status, Wireless Encryption Key. The secure 
             mode mode is configured but not active(2) state indicates 
             that the unit is capable of secure mode operation, and 
             the security material has been configured, but the 
             configuration of interfaces is not consistent with secure 
             mode operation. The secure mode is not supported(3) state 
             indicates that the unit is not capable of secure mode 
             operation. The secure mode capability requires 
             appropriate hardware compatibility, license key and 
             software image."  
      ::= { ptpTrapPrefix 34 }

   dataBridgingStatusAlarmTrap NOTIFICATION-TYPE
      OBJECTS { dataBridgingStatusAlarm }
      STATUS current
      DESCRIPTION
             "Ethernet Data traffic bridging is disabled because the 
             wireless link is not operating at the configured Lowest 
             Data Modulation Mode"  
      ::= { ptpTrapPrefix 35 }

   licenseRemainingTrialPeriodAlarmTrap NOTIFICATION-TYPE
      OBJECTS { licenseRemainingTrialPeriodAlarm }
      STATUS current
      DESCRIPTION
             "If the full capability trial license period is about to 
             expire then purchase a license upgrade from your 
             reseller."  
      ::= { ptpTrapPrefix 36 }

   capacityVariantMismatchTrap NOTIFICATION-TYPE
      OBJECTS { capacityVariantMismatch }
      STATUS current
      DESCRIPTION
             "The remote node of this link has a lower link capacity. 
             Operating with a reduced effective link capacity."  
      ::= { ptpTrapPrefix 37 }

   maxLinkRangeExceededTrap NOTIFICATION-TYPE
      OBJECTS { maxLinkRangeExceeded }
      STATUS current
      DESCRIPTION
             "The measured link range is greater than the maximum 
             allowed by the license key. The link will operate at a 
             reduced capacity while this condition applies. This alarm 
             is only raised if the license specifies a maximum link 
             range and the trial license is not active."  
      ::= { ptpTrapPrefix 38 }

   tDMConfigurationMismatchTrap NOTIFICATION-TYPE
      OBJECTS { tDMConfigurationMismatch }
      STATUS current
      DESCRIPTION
             "Current status of the configuration of the TDM Box. A 
             state of 'Ok' on a green background indicates that the 
             TDM Box configuration is matched OK with the remote end."  
      ::= { ptpTrapPrefix 39 }

   nIDULanPortDisabledWarningTrap NOTIFICATION-TYPE
      OBJECTS { nIDULanPortDisabledWarning }
      STATUS current
      DESCRIPTION
             "The SNMP ifAdminStatus of the interface has disabled 
             Ethernet traffic"  
      ::= { ptpTrapPrefix 40 }

   nIDULanPortConfigurationMismatchTrap NOTIFICATION-TYPE
      OBJECTS { nIDULanPortConfigurationMismatch }
      STATUS current
      DESCRIPTION
             "The detection of Ethernet fragments (runt packets) when 
             the link is in full duplex is an indication of an 
             auto-negotiation or forced configuration mismatch."  
      ::= { ptpTrapPrefix 41 }

   secondDataBridgingStatusAlarmTrap NOTIFICATION-TYPE
      OBJECTS { secondDataBridgingStatusAlarm }
      STATUS current
      DESCRIPTION
             "Bridging of Ethernet traffic from Second Data Service 
             has been disabled because the wireless link is not 
             operating at the configured Lowest Second Data Modulation 
             Mode"  
      ::= { ptpTrapPrefix 42 }

   transparentClockSourcePortAlarmTrap NOTIFICATION-TYPE
      OBJECTS { transparentClockSourcePortAlarm }
      STATUS current
      DESCRIPTION
             "Transparent Clock will not function properly because 
             SFP, the selected clock source port is not FIBER"  
      ::= { ptpTrapPrefix 43 }

   portAllocationMismatchTrap NOTIFICATION-TYPE
      OBJECTS { portAllocationMismatch }
      STATUS current
      DESCRIPTION
             "The local and remote ODUs have different services 
             configured."  
      ::= { ptpTrapPrefix 44 }

   END
